module fgc-nc-1.0 {
  yang-version 1.1;
  namespace "http://tail-f.com/ns/ned-id/fgc-nc-1.0";
  prefix fgc-nc-1.0;

  import fgc-nc {
    prefix family;
  }

  identity fgc-nc-1.0 {
    base family:fgc-nc;
  }
}
