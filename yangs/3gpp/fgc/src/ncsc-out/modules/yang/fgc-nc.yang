module fgc-nc {
  yang-version 1.1;
  namespace "http://tail-f.com/ns/ned-id/fgc-nc";
  prefix fgc-nc;

  import tailf-common {
    prefix tailf;
  }

  import tailf-ncs-ned {
    prefix ned;
  }

  identity fgc-nc {
    tailf:abstract;
    base ned:netconf-ned-id;
  }
}
