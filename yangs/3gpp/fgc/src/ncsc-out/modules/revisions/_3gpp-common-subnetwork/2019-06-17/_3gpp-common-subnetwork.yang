module _3gpp-common-subnetwork {
  // Generated by yanger -t ncs
  tailf:mount-id fgc-nc-1.0:fgc-nc-1.0;
  tailf:ncs-device-type "netconf";

  yang-version 1.1;
  namespace "urn:3gpp:sa5:_3gpp-common-subnetwork";
  prefix subnet3gpp;

  import _3gpp-common-yang-types {
    prefix types3gpp;
  }
  import _3gpp-common-top {
    prefix top3gpp;
  }
  import _3gpp-common-measurements {
    prefix meas3gpp;
  }
  import ietf-yang-schema-mount {
    prefix yangmnt;
  }
  import "fgc-nc-1.0" {
    prefix "fgc-nc-1.0";
  }
  import tailf-ncs {
    prefix ncs;
  }
  import tailf-common {
    prefix tailf;
  }

  organization
    "3GPP SA5";
  description
    "Defines basic SubNetwork which will be augmented by other IOCs";
  reference
    "3GPP TS 28.622
     Generic Network Resource Model (NRM)
     Integration Reference Point (IRP);
     Information Service (IS)
     
     3GPP TS 28.620
     Umbrella Information Model (UIM)";

  revision 2019-06-17 {
    description
      "Initial revision";
  }

  grouping ncs_template_Domain_Grp {
    description
      "A domain is a partition of instances of managed entities
       such that :
       -  the group represents a topological structure which describes the
       potential for connectivity
       -  Subject to common administration
       -  With common characteristics";
    leaf dnPrefix {
      type string;
      reference "Annex C of 32.300 ";
    }
    leaf userLabel {
      type string;
      description
        "A user-friendly (and user assignable) name of this object.";
    }
    leaf userDefinedNetworkType {
      type string;
      description
        "Textual information indicating network type, e.g. 'UTRAN'.";
    }
  }

  grouping ncs_template_SubNetworkGrp {
    uses ncs_template_Domain_Grp;
    uses meas3gpp:ncs_template_Measurements;
    leaf-list setOfMcc {
      // NCS patched for predictable order
      ordered-by user;
      description
        "Set of Mobile Country Code (MCC).
         The MCC uniquely identifies the country of domicile
         of the mobile subscriber. MCC is part of the IMSI (3GPP TS 23.003)
         
         This list contains all the MCC values in subordinate object
         instances to this SubNetwork instance.
         
         See clause 2.3 of 3GPP TS 23.003 for MCC allocation principles.
         
         It shall be supported if there is more than one value in setOfMcc
         of the SubNetwork. Otherwise the support is optional.";
      type string;
    }
    leaf priorityLabel {
      // NCS drop mandatory statement
      type string;
    }
  }

  grouping ncs_rpc_notif_Domain_Grp {
    description
      "A domain is a partition of instances of managed entities
       such that :
       -  the group represents a topological structure which describes the
       potential for connectivity
       -  Subject to common administration
       -  With common characteristics";
    leaf dnPrefix {
      type types3gpp:DistinguishedName;
      reference "Annex C of 32.300 ";
    }
    leaf userLabel {
      type string;
      description
        "A user-friendly (and user assignable) name of this object.";
    }
    leaf userDefinedNetworkType {
      type string;
      description
        "Textual information indicating network type, e.g. 'UTRAN'.";
    }
  }

  grouping ncs_rpc_notif_SubNetworkGrp {
    uses ncs_rpc_notif_Domain_Grp;
    uses meas3gpp:ncs_rpc_notif_Measurements;
    leaf-list setOfMcc {
      description
        "Set of Mobile Country Code (MCC).
         The MCC uniquely identifies the country of domicile
         of the mobile subscriber. MCC is part of the IMSI (3GPP TS 23.003)
         
         This list contains all the MCC values in subordinate object
         instances to this SubNetwork instance.
         
         See clause 2.3 of 3GPP TS 23.003 for MCC allocation principles.
         
         It shall be supported if there is more than one value in setOfMcc
         of the SubNetwork. Otherwise the support is optional.";
      type types3gpp:Mcc;
    }
    leaf priorityLabel {
      mandatory true;
      type uint32;
    }
  }

  grouping live_ncs_Domain_Grp {
    description
      "A domain is a partition of instances of managed entities
       such that :
       -  the group represents a topological structure which describes the
       potential for connectivity
       -  Subject to common administration
       -  With common characteristics";
    leaf dnPrefix {
      type types3gpp:DistinguishedName;
      reference "Annex C of 32.300 ";
    }
    leaf userLabel {
      type string;
      description
        "A user-friendly (and user assignable) name of this object.";
    }
    leaf userDefinedNetworkType {
      type string;
      description
        "Textual information indicating network type, e.g. 'UTRAN'.";
    }
  }

  grouping live_ncs_SubNetworkGrp {
    uses live_ncs_Domain_Grp;
    uses meas3gpp:live_ncs_Measurements;
    leaf-list setOfMcc {
      description
        "Set of Mobile Country Code (MCC).
         The MCC uniquely identifies the country of domicile
         of the mobile subscriber. MCC is part of the IMSI (3GPP TS 23.003)
         
         This list contains all the MCC values in subordinate object
         instances to this SubNetwork instance.
         
         See clause 2.3 of 3GPP TS 23.003 for MCC allocation principles.
         
         It shall be supported if there is more than one value in setOfMcc
         of the SubNetwork. Otherwise the support is optional.";
      type types3gpp:Mcc;
    }
    leaf priorityLabel {
      // NCS drop mandatory statement
      type uint32;
    }
  }

  grouping Domain_Grp {
    description
      "A domain is a partition of instances of managed entities
       such that :
       -  the group represents a topological structure which describes the
       potential for connectivity
       -  Subject to common administration
       -  With common characteristics";
    leaf dnPrefix {
      type types3gpp:DistinguishedName;
      reference "Annex C of 32.300 ";
    }
    leaf userLabel {
      type string;
      description
        "A user-friendly (and user assignable) name of this object.";
    }
    leaf userDefinedNetworkType {
      type string;
      description
        "Textual information indicating network type, e.g. 'UTRAN'.";
    }
  }

  grouping SubNetworkGrp {
    uses Domain_Grp;
    uses meas3gpp:Measurements;
    leaf-list setOfMcc {
      description
        "Set of Mobile Country Code (MCC).
         The MCC uniquely identifies the country of domicile
         of the mobile subscriber. MCC is part of the IMSI (3GPP TS 23.003)
         
         This list contains all the MCC values in subordinate object
         instances to this SubNetwork instance.
         
         See clause 2.3 of 3GPP TS 23.003 for MCC allocation principles.
         
         It shall be supported if there is more than one value in setOfMcc
         of the SubNetwork. Otherwise the support is optional.";
      type types3gpp:Mcc;
    }
    leaf priorityLabel {
      mandatory true;
      type uint32;
    }
  }

  augment "/ncs:devices/ncs:device/ncs:config" {
    list SubNetwork {
      tailf:ncs-device-type "netconf";
      tailf:display-when "not(../ncs:module) or ../ncs:module[ncs:name='_3gpp-common-subnetwork']";
      key "id";
      description
        "Represents a set of managed entities";
      uses top3gpp:Top_Grp;
      container attributes {
        uses SubNetworkGrp;
        leaf-list parents {
          description
            "Reference to all containg SubNetwork instances
             in strict order from the root subnetwork down to the immediate
             parent subnetwork.
             If subnetworks form a containment hierarchy this is
             modeled using references between the child SubNetwork and the parent
             SubNetworks.
             This reference MUST NOT be present for the top level SubNetwork and
             MUST be present for other SubNetworks.";
          type leafref {
            path "../../../SubNetwork/id";
          }
        }
        leaf-list containedChildren {
          description
            "Reference to all directly contained SubNetwork instances.
             If subnetworks form a containment hierarchy this is
             modeled using references between the child SubNetwork and the parent
             SubNetwork.";
          type leafref {
            path "../../../SubNetwork/id";
          }
        }
      }
      uses meas3gpp:MeasurementSubtree {
        // NCS drop if-feature statement
      }
      uses types3gpp:ManagedNFProfile;
    }
  }
  augment "/ncs:devices/ncs:device/ncs:live-status" {
    list SubNetwork {
      tailf:ncs-device-type "netconf";
      tailf:display-when "not(../ncs:module) or ../ncs:module[ncs:name='_3gpp-common-subnetwork'] or (../ncs:live-status-protocol[not(ncs:capability)]) or (../ncs:live-status-protocol/ncs:capability/ncs:module[.='_3gpp-common-subnetwork'])";
      key "id";
      description
        "Represents a set of managed entities";
      uses top3gpp:live_ncs_Top_Grp;
      container attributes {
        uses live_ncs_SubNetworkGrp;
        leaf-list parents {
          description
            "Reference to all containg SubNetwork instances
             in strict order from the root subnetwork down to the immediate
             parent subnetwork.
             If subnetworks form a containment hierarchy this is
             modeled using references between the child SubNetwork and the parent
             SubNetworks.
             This reference MUST NOT be present for the top level SubNetwork and
             MUST be present for other SubNetworks.";
          type leafref {
            path "../../../SubNetwork/id";
          }
        }
        leaf-list containedChildren {
          description
            "Reference to all directly contained SubNetwork instances.
             If subnetworks form a containment hierarchy this is
             modeled using references between the child SubNetwork and the parent
             SubNetwork.";
          type leafref {
            path "../../../SubNetwork/id";
          }
        }
      }
      uses meas3gpp:live_ncs_MeasurementSubtree {
        // NCS drop if-feature statement
      }
      uses types3gpp:live_ncs_ManagedNFProfile;
    }
  }
  augment "/ncs:devices/ncs:template/ncs:ned-id/ncs:config" {
    list SubNetwork {
      // NCS patched for predictable order
      ordered-by user;
      key "id";
      description
        "Represents a set of managed entities";
      uses top3gpp:ncs_template_Top_Grp;
      container attributes {
        uses ncs_template_SubNetworkGrp;
        leaf-list parents {
          // NCS patched for predictable order
          ordered-by user;
          description
            "Reference to all containg SubNetwork instances
             in strict order from the root subnetwork down to the immediate
             parent subnetwork.
             If subnetworks form a containment hierarchy this is
             modeled using references between the child SubNetwork and the parent
             SubNetworks.
             This reference MUST NOT be present for the top level SubNetwork and
             MUST be present for other SubNetworks.";
          type string;
        }
        leaf-list containedChildren {
          // NCS patched for predictable order
          ordered-by user;
          description
            "Reference to all directly contained SubNetwork instances.
             If subnetworks form a containment hierarchy this is
             modeled using references between the child SubNetwork and the parent
             SubNetwork.";
          type string;
        }
      }
      uses meas3gpp:ncs_template_MeasurementSubtree {
        // NCS drop if-feature statement
      }
      uses types3gpp:ncs_template_ManagedNFProfile;
    }
  }

  feature MeasurementsUnderSubNetwork {
    description
      "The MeasurementSubtree shall be contained under SubNetwork";
  }

  feature ExternalsUnderSubNetwork {
    description
      "Classes representing external entities like EUtranFrequency,
       ExternalGNBCUCPFunction, ExternalENBFunction
       are contained under a Subnetwork list/class.";
  }
}
