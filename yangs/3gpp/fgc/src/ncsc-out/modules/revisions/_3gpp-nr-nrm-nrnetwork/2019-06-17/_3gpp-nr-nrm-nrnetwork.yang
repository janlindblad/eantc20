module _3gpp-nr-nrm-nrnetwork {
  // Generated by yanger -t ncs
  tailf:mount-id fgc-nc-1.0:fgc-nc-1.0;
  tailf:ncs-device-type "netconf";

  yang-version 1.1;
  namespace "urn:3gpp:sa5:_3gpp-nr-nrm-nrnetwork";
  prefix nrnet3gpp;

  import _3gpp-common-subnetwork {
    prefix subnet3gpp;
  }
  import _3gpp-common-top {
    prefix top3gpp;
  }
  import "fgc-nc-1.0" {
    prefix "fgc-nc-1.0";
  }
  import tailf-ncs {
    prefix ncs;
  }
  import tailf-common {
    prefix tailf;
  }

  organization
    "3GPP SA5";
  description
    "Defines the YANG mapping of the NRNetwork Information Object
     Class (IOC) that is part of the NR Network Resource Model (NRM).";
  reference "3GPP TS 28.541 5G Network Resource Model (NRM)";

  revision 2019-06-17 {
    description
      "Initial revision";
  }

  grouping ncs_template_NRNetworkGrp {
    description
      "Represents the NRNetwork IOC.";
    reference "3GPP TS 28.541";
    uses subnet3gpp:ncs_template_SubNetworkGrp;
  }

  grouping ncs_rpc_notif_NRNetworkGrp {
    description
      "Represents the NRNetwork IOC.";
    reference "3GPP TS 28.541";
    uses subnet3gpp:ncs_rpc_notif_SubNetworkGrp;
  }

  grouping live_ncs_NRNetworkGrp {
    description
      "Represents the NRNetwork IOC.";
    reference "3GPP TS 28.541";
    uses subnet3gpp:live_ncs_SubNetworkGrp;
  }

  grouping NRNetworkGrp {
    description
      "Represents the NRNetwork IOC.";
    reference "3GPP TS 28.541";
    uses subnet3gpp:SubNetworkGrp;
  }

  augment "/ncs:devices/ncs:device/ncs:config" {
    list NRNetwork {
      tailf:ncs-device-type "netconf";
      tailf:display-when "not(../ncs:module) or ../ncs:module[ncs:name='_3gpp-nr-nrm-nrnetwork']";
      description
        "A subnetwork containing gNB external NR entities.";
      reference "3GPP TS 28.541";
      key "id";
      uses top3gpp:Top_Grp;
      container attributes {
        uses NRNetworkGrp;
      }
    }
  }
  augment "/ncs:devices/ncs:device/ncs:live-status" {
    list NRNetwork {
      tailf:ncs-device-type "netconf";
      tailf:display-when "not(../ncs:module) or ../ncs:module[ncs:name='_3gpp-nr-nrm-nrnetwork'] or (../ncs:live-status-protocol[not(ncs:capability)]) or (../ncs:live-status-protocol/ncs:capability/ncs:module[.='_3gpp-nr-nrm-nrnetwork'])";
      description
        "A subnetwork containing gNB external NR entities.";
      reference "3GPP TS 28.541";
      key "id";
      uses top3gpp:live_ncs_Top_Grp;
      container attributes {
        uses live_ncs_NRNetworkGrp;
      }
    }
  }
  augment "/ncs:devices/ncs:template/ncs:ned-id/ncs:config" {
    list NRNetwork {
      // NCS patched for predictable order
      ordered-by user;
      description
        "A subnetwork containing gNB external NR entities.";
      reference "3GPP TS 28.541";
      key "id";
      uses top3gpp:ncs_template_Top_Grp;
      container attributes {
        uses ncs_template_NRNetworkGrp;
      }
    }
  }

  feature ExternalsUnderNRNetwork {
    description
      "Classes representing external entities like NRFrequency,
       ExternalGNBCUCPFunction, ExternalGNBDUFunction
       are contained under a NRNetwork list/class.";
  }
}
