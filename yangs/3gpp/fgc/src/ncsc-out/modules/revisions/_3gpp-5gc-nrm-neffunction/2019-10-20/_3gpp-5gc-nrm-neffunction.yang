module _3gpp-5gc-nrm-neffunction {
  // Generated by yanger -t ncs
  tailf:mount-id fgc-nc-1.0:fgc-nc-1.0;
  tailf:ncs-device-type "netconf";

  yang-version 1.1;
  namespace "urn:3gpp:sa5:_3gpp-5gc-nrm-neffunction";
  prefix nef3gpp;

  import _3gpp-common-managed-function {
    prefix mf3gpp;
  }
  import _3gpp-common-managed-element {
    prefix me3gpp;
  }
  import ietf-inet-types {
    prefix inet;
  }
  import _3gpp-common-yang-types {
    prefix types3gpp;
  }
  import _3gpp-5g-common-yang-types {
    prefix types5g3gpp;
  }
  import _3gpp-common-top {
    prefix top3gpp;
  }
  import "fgc-nc-1.0" {
    prefix "fgc-nc-1.0";
  }
  import tailf-ncs {
    prefix ncs;
  }
  import tailf-common {
    prefix tailf;
  }

  organization
    "3gpp SA5";
  description
    "This IOC represents the NEF function in 5GC. For more information about the NEF, see 3GPP TS 23.501.";
  reference "3GPP TS 28.541";

  revision 2019-10-20 {
    description
      "initial revision";
    reference
      "Based on
       3GPP TS 28.541 V16.X.XX";
  }

  grouping ncs_template_NEFFunctionGrp {
    uses mf3gpp:ncs_template_ManagedFunctionGrp;
    leaf sBIFQDN {
      description
        "The FQDN of the registered NF instance in the service-based interface.";
      type string;
    }
    leaf-list sNSSAIList {
      // NCS patched for predictable order
      ordered-by user;
      description
        "List of S-NSSAIs the managed object is capable of supporting.
         (Single Network Slice Selection Assistance Information)
         An S-NSSAI has an SST (Slice/Service type) and an optional SD
         (Slice Differentiator) field.";
      type string;
    }
    leaf-list capabilityList {
      // NCS patched for predictable order
      ordered-by user;
      description
        "List of supported capabilities of the NEF.";
      reference "3GPP TS 23.003";
      type string;
    }
    leaf isINEF {
      type string;
    }
    leaf isCAPIFSup {
      type string;
    }
  }

  grouping ncs_rpc_notif_NEFFunctionGrp {
    uses mf3gpp:ncs_rpc_notif_ManagedFunctionGrp;
    leaf sBIFQDN {
      description
        "The FQDN of the registered NF instance in the service-based interface.";
      type inet:domain-name;
    }
    leaf-list sNSSAIList {
      description
        "List of S-NSSAIs the managed object is capable of supporting.
         (Single Network Slice Selection Assistance Information)
         An S-NSSAI has an SST (Slice/Service type) and an optional SD
         (Slice Differentiator) field.";
      type types3gpp:SNssai;
    }
    leaf-list capabilityList {
      description
        "List of supported capabilities of the NEF.";
      reference "3GPP TS 23.003";
      type string;
    }
    leaf isINEF {
      type boolean;
    }
    leaf isCAPIFSup {
      type boolean;
    }
  }

  grouping live_ncs_NEFFunctionGrp {
    uses mf3gpp:live_ncs_ManagedFunctionGrp;
    leaf sBIFQDN {
      description
        "The FQDN of the registered NF instance in the service-based interface.";
      type inet:domain-name;
    }
    leaf-list sNSSAIList {
      description
        "List of S-NSSAIs the managed object is capable of supporting.
         (Single Network Slice Selection Assistance Information)
         An S-NSSAI has an SST (Slice/Service type) and an optional SD
         (Slice Differentiator) field.";
      type types3gpp:SNssai;
    }
    leaf-list capabilityList {
      description
        "List of supported capabilities of the NEF.";
      reference "3GPP TS 23.003";
      type string;
    }
    leaf isINEF {
      type boolean;
    }
    leaf isCAPIFSup {
      type boolean;
    }
  }

  grouping NEFFunctionGrp {
    uses mf3gpp:ManagedFunctionGrp;
    leaf sBIFQDN {
      description
        "The FQDN of the registered NF instance in the service-based interface.";
      type inet:domain-name;
    }
    leaf-list sNSSAIList {
      description
        "List of S-NSSAIs the managed object is capable of supporting.
         (Single Network Slice Selection Assistance Information)
         An S-NSSAI has an SST (Slice/Service type) and an optional SD
         (Slice Differentiator) field.";
      type types3gpp:SNssai;
    }
    leaf-list capabilityList {
      description
        "List of supported capabilities of the NEF.";
      reference "3GPP TS 23.003";
      type string;
    }
    leaf isINEF {
      type boolean;
    }
    leaf isCAPIFSup {
      type boolean;
    }
  }

  augment "/ncs:devices/ncs:template/ncs:ned-id/ncs:config/me3gpp:ManagedElement" {
    list NEFFunction {
      // NCS patched for predictable order
      ordered-by user;
      description
        "5G Core NEF Function";
      reference "3GPP TS 28.541";
      key "id";
      uses top3gpp:ncs_template_Top_Grp;
      container attributes {
        uses ncs_template_NEFFunctionGrp;
      }
    }
  }
  augment "/ncs:devices/ncs:device/ncs:live-status/me3gpp:ManagedElement" {
    list NEFFunction {
      tailf:ncs-device-type "netconf";
      tailf:display-when "not(../../ncs:module) or ../../ncs:module[ncs:name='_3gpp-5gc-nrm-neffunction'] or (../../ncs:live-status-protocol[not(ncs:capability)]) or (../../ncs:live-status-protocol/ncs:capability/ncs:module[.='_3gpp-5gc-nrm-neffunction'])";
      description
        "5G Core NEF Function";
      reference "3GPP TS 28.541";
      key "id";
      uses top3gpp:live_ncs_Top_Grp;
      container attributes {
        uses live_ncs_NEFFunctionGrp;
      }
    }
  }
  augment "/ncs:devices/ncs:device/ncs:config/me3gpp:ManagedElement" {
    list NEFFunction {
      tailf:ncs-device-type "netconf";
      tailf:display-when "not(../../ncs:module) or ../../ncs:module[ncs:name='_3gpp-5gc-nrm-neffunction']";
      description
        "5G Core NEF Function";
      reference "3GPP TS 28.541";
      key "id";
      uses top3gpp:Top_Grp;
      container attributes {
        uses NEFFunctionGrp;
      }
    }
  }
}
