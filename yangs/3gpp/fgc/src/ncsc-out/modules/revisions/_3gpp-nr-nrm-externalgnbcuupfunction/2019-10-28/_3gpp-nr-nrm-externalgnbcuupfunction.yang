module _3gpp-nr-nrm-externalgnbcuupfunction {
  // Generated by yanger -t ncs
  tailf:mount-id fgc-nc-1.0:fgc-nc-1.0;
  tailf:ncs-device-type "netconf";

  yang-version 1.1;
  namespace "urn:3gpp:sa5:_3gpp-nr-nrm-externalgnbcuupfunction";
  prefix extgnbcuup3gpp;

  import _3gpp-common-managed-function {
    prefix mf3gpp;
  }
  import _3gpp-nr-nrm-nrnetwork {
    prefix nrnet3gpp;
  }
  import _3gpp-common-subnetwork {
    prefix subnet3gpp;
  }
  import _3gpp-common-top {
    prefix top3gpp;
  }
  import "fgc-nc-1.0" {
    prefix "fgc-nc-1.0";
  }
  import tailf-ncs {
    prefix ncs;
  }
  import tailf-common {
    prefix tailf;
  }

  organization
    "3GPP SA5";
  description
    "Defines the YANG mapping of the ExternalGNBCUUPFunction
     Information Object Class (IOC), that is part of the NR Network
     Resource Model (NRM).";
  reference "3GPP TS 28.541 5G Network Resource Model (NRM)";

  revision 2019-10-28 {
    reference "S5-193518";
  }
  revision 2019-06-17 {
    description
      "Initial revision";
  }

  grouping ncs_template_ExternalGNBCUUPFunctionGrp {
    description
      "Represets the ExternalGNBCUUPFunction IOC.";
    reference "3GPP TS 28.541";
    uses mf3gpp:ncs_template_ManagedFunctionGrp;
    leaf gNBId {
      description
        "Identifies a gNB within a PLMN.";
      reference
        "gNB Identifier (gNB ID) in 3GPP TS 38.300, Global gNB ID
         in 3GPP TS 38.413";
      // NCS drop mandatory statement
      type string;
    }
    leaf gNBIdLength {
      description
        "Indicates the number of bits for encoding the gNB ID.";
      reference "gNB ID in 3GPP TS 38.300, Global gNB ID in 3GPP TS 38.413";
      // NCS drop mandatory statement
      type string;
    }
  }

  grouping ncs_template_ExternalGNBCUUPFunctionWrapper {
    list ExternalGNBCUUPFunction {
      // NCS patched for predictable order
      ordered-by user;
      description
        "Represents the properties, known by the management function,
         of a GNBCUUPFunction managed by another management function.";
      reference "3GPP TS 28.541";
      key "id";
      uses top3gpp:ncs_template_Top_Grp;
      container attributes {
        uses ncs_template_ExternalGNBCUUPFunctionGrp;
      }
      uses mf3gpp:ncs_template_ManagedFunctionContainedClasses;
    }
  }

  grouping ncs_rpc_notif_ExternalGNBCUUPFunctionGrp {
    description
      "Represets the ExternalGNBCUUPFunction IOC.";
    reference "3GPP TS 28.541";
    uses mf3gpp:ncs_rpc_notif_ManagedFunctionGrp;
    leaf gNBId {
      description
        "Identifies a gNB within a PLMN.";
      reference
        "gNB Identifier (gNB ID) in 3GPP TS 38.300, Global gNB ID
         in 3GPP TS 38.413";
      mandatory true;
      type int64 {
        range "0..4294967295";
      }
    }
    leaf gNBIdLength {
      description
        "Indicates the number of bits for encoding the gNB ID.";
      reference "gNB ID in 3GPP TS 38.300, Global gNB ID in 3GPP TS 38.413";
      mandatory true;
      type int32 {
        range "22..32";
      }
    }
  }

  grouping ncs_rpc_notif_ExternalGNBCUUPFunctionWrapper {
    list ExternalGNBCUUPFunction {
      description
        "Represents the properties, known by the management function,
         of a GNBCUUPFunction managed by another management function.";
      reference "3GPP TS 28.541";
      key "id";
      uses top3gpp:ncs_rpc_notif_Top_Grp;
      container attributes {
        uses ncs_rpc_notif_ExternalGNBCUUPFunctionGrp;
      }
      uses mf3gpp:ncs_rpc_notif_ManagedFunctionContainedClasses;
    }
  }

  grouping live_ncs_ExternalGNBCUUPFunctionGrp {
    description
      "Represets the ExternalGNBCUUPFunction IOC.";
    reference "3GPP TS 28.541";
    uses mf3gpp:live_ncs_ManagedFunctionGrp;
    leaf gNBId {
      description
        "Identifies a gNB within a PLMN.";
      reference
        "gNB Identifier (gNB ID) in 3GPP TS 38.300, Global gNB ID
         in 3GPP TS 38.413";
      // NCS drop mandatory statement
      type int64 {
        range "0..4294967295";
      }
    }
    leaf gNBIdLength {
      description
        "Indicates the number of bits for encoding the gNB ID.";
      reference "gNB ID in 3GPP TS 38.300, Global gNB ID in 3GPP TS 38.413";
      // NCS drop mandatory statement
      type int32 {
        range "22..32";
      }
    }
  }

  grouping live_ncs_ExternalGNBCUUPFunctionWrapper {
    list ExternalGNBCUUPFunction {
      description
        "Represents the properties, known by the management function,
         of a GNBCUUPFunction managed by another management function.";
      reference "3GPP TS 28.541";
      key "id";
      uses top3gpp:live_ncs_Top_Grp;
      container attributes {
        uses live_ncs_ExternalGNBCUUPFunctionGrp;
      }
      uses mf3gpp:live_ncs_ManagedFunctionContainedClasses;
    }
  }

  grouping ExternalGNBCUUPFunctionGrp {
    description
      "Represets the ExternalGNBCUUPFunction IOC.";
    reference "3GPP TS 28.541";
    uses mf3gpp:ManagedFunctionGrp;
    leaf gNBId {
      description
        "Identifies a gNB within a PLMN.";
      reference
        "gNB Identifier (gNB ID) in 3GPP TS 38.300, Global gNB ID
         in 3GPP TS 38.413";
      mandatory true;
      type int64 {
        range "0..4294967295";
      }
    }
    leaf gNBIdLength {
      description
        "Indicates the number of bits for encoding the gNB ID.";
      reference "gNB ID in 3GPP TS 38.300, Global gNB ID in 3GPP TS 38.413";
      mandatory true;
      type int32 {
        range "22..32";
      }
    }
  }

  grouping ExternalGNBCUUPFunctionWrapper {
    list ExternalGNBCUUPFunction {
      description
        "Represents the properties, known by the management function,
         of a GNBCUUPFunction managed by another management function.";
      reference "3GPP TS 28.541";
      key "id";
      uses top3gpp:Top_Grp;
      container attributes {
        uses ExternalGNBCUUPFunctionGrp;
      }
      uses mf3gpp:ManagedFunctionContainedClasses;
    }
  }

  augment "/ncs:devices/ncs:template/ncs:ned-id/ncs:config/subnet3gpp:SubNetwork" {
    // NCS drop if-feature statement
    uses ncs_template_ExternalGNBCUUPFunctionWrapper;
  }
  augment "/ncs:devices/ncs:device/ncs:live-status/subnet3gpp:SubNetwork" {
    // NCS drop if-feature statement
    uses live_ncs_ExternalGNBCUUPFunctionWrapper {
      refine ExternalGNBCUUPFunction {
        tailf:ncs-device-type "netconf";
        tailf:display-when "not(../../ncs:module) or ../../ncs:module[ncs:name='_3gpp-nr-nrm-externalgnbcuupfunction'] or (../../ncs:live-status-protocol[not(ncs:capability)]) or (../../ncs:live-status-protocol/ncs:capability/ncs:module[.='_3gpp-nr-nrm-externalgnbcuupfunction'])";
      }
    }
  }
  augment "/ncs:devices/ncs:device/ncs:config/subnet3gpp:SubNetwork" {
    // NCS drop if-feature statement
    uses ExternalGNBCUUPFunctionWrapper {
      refine ExternalGNBCUUPFunction {
        tailf:ncs-device-type "netconf";
        tailf:display-when "not(../../ncs:module) or ../../ncs:module[ncs:name='_3gpp-nr-nrm-externalgnbcuupfunction']";
      }
    }
  }
  augment "/ncs:devices/ncs:template/ncs:ned-id/ncs:config/nrnet3gpp:NRNetwork" {
    // NCS drop if-feature statement
    uses ncs_template_ExternalGNBCUUPFunctionWrapper;
  }
  augment "/ncs:devices/ncs:device/ncs:live-status/nrnet3gpp:NRNetwork" {
    // NCS drop if-feature statement
    uses live_ncs_ExternalGNBCUUPFunctionWrapper {
      refine ExternalGNBCUUPFunction {
        tailf:ncs-device-type "netconf";
        tailf:display-when "not(../../ncs:module) or ../../ncs:module[ncs:name='_3gpp-nr-nrm-externalgnbcuupfunction'] or (../../ncs:live-status-protocol[not(ncs:capability)]) or (../../ncs:live-status-protocol/ncs:capability/ncs:module[.='_3gpp-nr-nrm-externalgnbcuupfunction'])";
      }
    }
  }
  augment "/ncs:devices/ncs:device/ncs:config/nrnet3gpp:NRNetwork" {
    // NCS drop if-feature statement
    uses ExternalGNBCUUPFunctionWrapper {
      refine ExternalGNBCUUPFunction {
        tailf:ncs-device-type "netconf";
        tailf:display-when "not(../../ncs:module) or ../../ncs:module[ncs:name='_3gpp-nr-nrm-externalgnbcuupfunction']";
      }
    }
  }
}
