module _3gpp-nr-nrm-externalnrcellcu {
  // Generated by yanger -t ncs
  tailf:mount-id fgc-nc-1.0:fgc-nc-1.0;
  tailf:ncs-device-type "netconf";

  yang-version 1.1;
  namespace "urn:3gpp:sa5:_3gpp-nr-nrm-externalnrcellcu";
  prefix extnrcellcu3gpp;

  import _3gpp-common-yang-types {
    prefix types3gpp;
  }
  import _3gpp-common-managed-function {
    prefix mf3gpp;
  }
  import _3gpp-nr-nrm-nrnetwork {
    prefix nrnet3gpp;
  }
  import _3gpp-common-subnetwork {
    prefix subnet3gpp;
  }
  import _3gpp-nr-nrm-externalgnbcucpfunction {
    prefix extgnbcucp3gpp;
  }
  import _3gpp-common-top {
    prefix top3gpp;
  }
  import "fgc-nc-1.0" {
    prefix "fgc-nc-1.0";
  }
  import tailf-ncs {
    prefix ncs;
  }
  import tailf-common {
    prefix tailf;
  }

  organization
    "3GPP SA5";
  description
    "Defines the YANG mapping of the ExternalNRCellCU Information
     Object Class (IOC), that is part of the NR Network Resource Model (NRM).";
  reference "3GPP TS 28.541 5G Network Resource Model (NRM)";

  revision 2019-10-28 {
    reference "S5-193518";
  }
  revision 2019-06-17 {
    description
      "Initial revision";
  }

  grouping ncs_template_ExternalNRCellCUGrp {
    description
      "Represents the ExternalNRCellCU IOC.";
    reference "3GPP TS 28.541";
    uses mf3gpp:ncs_template_ManagedFunctionGrp;
    leaf cellLocalId {
      description
        "Identifies an NR cell of a gNB. Together with corresponding
         gNB ID it forms the NR Cell Identifier (NCI).";
      reference "NCI in 3GPP TS 38.300";
      // NCS drop mandatory statement
      type string;
    }
    leaf nRPCI {
      description
        "The Physical Cell Identity (PCI) of the NR cell.";
      reference "3GPP TS 36.211";
      // NCS drop mandatory statement
      type string;
    }
    list pLMNIdList {
      // NCS patched for predictable order
      ordered-by user;
      description
        "Defines which PLMNs that are assumed to be served by the
         NR cell in another gNB CU-CP. This list is either updated by the
         managed element itself (e.g. due to ANR, signalling over Xn, etc.) or
         by consumer over the standard interface.";
      key "mcc mnc";
      // NCS drop min-elements statement
      // NCS drop max-elements statement
      uses types3gpp:ncs_template_PLMNId;
    }
    leaf nRFrequencyRef {
      description
        "Reference to corresponding NRFrequency instance.";
      // NCS drop mandatory statement
      type string;
    }
  }

  grouping ncs_template_ExternalNRCellCUWrapper {
    list ExternalNRCellCU {
      // NCS patched for predictable order
      ordered-by user;
      description
        "Represents the properties of an NRCellCU controlled by
         another Management Service Provider.";
      reference "3GPP TS 28.541";
      key "id";
      uses top3gpp:ncs_template_Top_Grp;
      container attributes {
        uses ncs_template_ExternalNRCellCUGrp;
      }
      uses mf3gpp:ncs_template_ManagedFunctionContainedClasses;
    }
  }

  grouping ncs_rpc_notif_ExternalNRCellCUGrp {
    description
      "Represents the ExternalNRCellCU IOC.";
    reference "3GPP TS 28.541";
    uses mf3gpp:ncs_rpc_notif_ManagedFunctionGrp;
    leaf cellLocalId {
      description
        "Identifies an NR cell of a gNB. Together with corresponding
         gNB ID it forms the NR Cell Identifier (NCI).";
      reference "NCI in 3GPP TS 38.300";
      mandatory true;
      type int32 {
        range "0..16383";
      }
    }
    leaf nRPCI {
      description
        "The Physical Cell Identity (PCI) of the NR cell.";
      reference "3GPP TS 36.211";
      mandatory true;
      type int32 {
        range "0..1007";
      }
    }
    list pLMNIdList {
      description
        "Defines which PLMNs that are assumed to be served by the
         NR cell in another gNB CU-CP. This list is either updated by the
         managed element itself (e.g. due to ANR, signalling over Xn, etc.) or
         by consumer over the standard interface.";
      key "mcc mnc";
      min-elements 1;
      max-elements 12;
      uses types3gpp:ncs_rpc_notif_PLMNId;
    }
    leaf nRFrequencyRef {
      description
        "Reference to corresponding NRFrequency instance.";
      mandatory true;
      type types3gpp:DistinguishedName;
    }
  }

  grouping ncs_rpc_notif_ExternalNRCellCUWrapper {
    list ExternalNRCellCU {
      description
        "Represents the properties of an NRCellCU controlled by
         another Management Service Provider.";
      reference "3GPP TS 28.541";
      key "id";
      uses top3gpp:ncs_rpc_notif_Top_Grp;
      container attributes {
        uses ncs_rpc_notif_ExternalNRCellCUGrp;
      }
      uses mf3gpp:ncs_rpc_notif_ManagedFunctionContainedClasses;
    }
  }

  grouping live_ncs_ExternalNRCellCUGrp {
    description
      "Represents the ExternalNRCellCU IOC.";
    reference "3GPP TS 28.541";
    uses mf3gpp:live_ncs_ManagedFunctionGrp;
    leaf cellLocalId {
      description
        "Identifies an NR cell of a gNB. Together with corresponding
         gNB ID it forms the NR Cell Identifier (NCI).";
      reference "NCI in 3GPP TS 38.300";
      // NCS drop mandatory statement
      type int32 {
        range "0..16383";
      }
    }
    leaf nRPCI {
      description
        "The Physical Cell Identity (PCI) of the NR cell.";
      reference "3GPP TS 36.211";
      // NCS drop mandatory statement
      type int32 {
        range "0..1007";
      }
    }
    list pLMNIdList {
      description
        "Defines which PLMNs that are assumed to be served by the
         NR cell in another gNB CU-CP. This list is either updated by the
         managed element itself (e.g. due to ANR, signalling over Xn, etc.) or
         by consumer over the standard interface.";
      key "mcc mnc";
      // NCS drop min-elements statement
      // NCS drop max-elements statement
      uses types3gpp:live_ncs_PLMNId;
    }
    leaf nRFrequencyRef {
      description
        "Reference to corresponding NRFrequency instance.";
      // NCS drop mandatory statement
      type types3gpp:DistinguishedName;
    }
  }

  grouping live_ncs_ExternalNRCellCUWrapper {
    list ExternalNRCellCU {
      description
        "Represents the properties of an NRCellCU controlled by
         another Management Service Provider.";
      reference "3GPP TS 28.541";
      key "id";
      uses top3gpp:live_ncs_Top_Grp;
      container attributes {
        uses live_ncs_ExternalNRCellCUGrp;
      }
      uses mf3gpp:live_ncs_ManagedFunctionContainedClasses;
    }
  }

  grouping ExternalNRCellCUGrp {
    description
      "Represents the ExternalNRCellCU IOC.";
    reference "3GPP TS 28.541";
    uses mf3gpp:ManagedFunctionGrp;
    leaf cellLocalId {
      description
        "Identifies an NR cell of a gNB. Together with corresponding
         gNB ID it forms the NR Cell Identifier (NCI).";
      reference "NCI in 3GPP TS 38.300";
      mandatory true;
      type int32 {
        range "0..16383";
      }
    }
    leaf nRPCI {
      description
        "The Physical Cell Identity (PCI) of the NR cell.";
      reference "3GPP TS 36.211";
      mandatory true;
      type int32 {
        range "0..1007";
      }
    }
    list pLMNIdList {
      description
        "Defines which PLMNs that are assumed to be served by the
         NR cell in another gNB CU-CP. This list is either updated by the
         managed element itself (e.g. due to ANR, signalling over Xn, etc.) or
         by consumer over the standard interface.";
      key "mcc mnc";
      min-elements 1;
      max-elements 12;
      uses types3gpp:PLMNId;
    }
    leaf nRFrequencyRef {
      description
        "Reference to corresponding NRFrequency instance.";
      mandatory true;
      type types3gpp:DistinguishedName;
    }
  }

  grouping ExternalNRCellCUWrapper {
    list ExternalNRCellCU {
      description
        "Represents the properties of an NRCellCU controlled by
         another Management Service Provider.";
      reference "3GPP TS 28.541";
      key "id";
      uses top3gpp:Top_Grp;
      container attributes {
        uses ExternalNRCellCUGrp;
      }
      uses mf3gpp:ManagedFunctionContainedClasses;
    }
  }

  augment "/ncs:devices/ncs:template/ncs:ned-id/ncs:config/subnet3gpp:SubNetwork/extgnbcucp3gpp:ExternalGNBCUCPFunction" {
    // NCS drop if-feature statement
    uses ncs_template_ExternalNRCellCUWrapper;
  }
  augment "/ncs:devices/ncs:device/ncs:live-status/subnet3gpp:SubNetwork/extgnbcucp3gpp:ExternalGNBCUCPFunction" {
    // NCS drop if-feature statement
    uses live_ncs_ExternalNRCellCUWrapper {
      refine ExternalNRCellCU {
        tailf:ncs-device-type "netconf";
        tailf:display-when "not(../../../ncs:module) or ../../../ncs:module[ncs:name='_3gpp-nr-nrm-externalnrcellcu'] or (../../../ncs:live-status-protocol[not(ncs:capability)]) or (../../../ncs:live-status-protocol/ncs:capability/ncs:module[.='_3gpp-nr-nrm-externalnrcellcu'])";
      }
    }
  }
  augment "/ncs:devices/ncs:device/ncs:config/subnet3gpp:SubNetwork/extgnbcucp3gpp:ExternalGNBCUCPFunction" {
    // NCS drop if-feature statement
    uses ExternalNRCellCUWrapper {
      refine ExternalNRCellCU {
        tailf:ncs-device-type "netconf";
        tailf:display-when "not(../../../ncs:module) or ../../../ncs:module[ncs:name='_3gpp-nr-nrm-externalnrcellcu']";
      }
    }
  }
  augment "/ncs:devices/ncs:template/ncs:ned-id/ncs:config/nrnet3gpp:NRNetwork/extgnbcucp3gpp:ExternalGNBCUCPFunction" {
    // NCS drop if-feature statement
    uses ncs_template_ExternalNRCellCUWrapper;
  }
  augment "/ncs:devices/ncs:device/ncs:live-status/nrnet3gpp:NRNetwork/extgnbcucp3gpp:ExternalGNBCUCPFunction" {
    // NCS drop if-feature statement
    uses live_ncs_ExternalNRCellCUWrapper {
      refine ExternalNRCellCU {
        tailf:ncs-device-type "netconf";
        tailf:display-when "not(../../../ncs:module) or ../../../ncs:module[ncs:name='_3gpp-nr-nrm-externalnrcellcu'] or (../../../ncs:live-status-protocol[not(ncs:capability)]) or (../../../ncs:live-status-protocol/ncs:capability/ncs:module[.='_3gpp-nr-nrm-externalnrcellcu'])";
      }
    }
  }
  augment "/ncs:devices/ncs:device/ncs:config/nrnet3gpp:NRNetwork/extgnbcucp3gpp:ExternalGNBCUCPFunction" {
    // NCS drop if-feature statement
    uses ExternalNRCellCUWrapper {
      refine ExternalNRCellCU {
        tailf:ncs-device-type "netconf";
        tailf:display-when "not(../../../ncs:module) or ../../../ncs:module[ncs:name='_3gpp-nr-nrm-externalnrcellcu']";
      }
    }
  }
}
