module _3gpp-5gc-nrm-scpfunction {
  // Generated by yanger -t ncs
  tailf:mount-id fgc-nc-1.0:fgc-nc-1.0;
  tailf:ncs-device-type "netconf";

  yang-version 1.1;
  namespace "urn:3gpp:sa5:_3gpp-5gc-nrm-scpfunction";
  prefix scp3gpp;

  import _3gpp-common-managed-function {
    prefix mf3gpp;
  }
  import _3gpp-common-managed-element {
    prefix me3gpp;
  }
  import ietf-inet-types {
    prefix inet;
  }
  import _3gpp-common-yang-types {
    prefix types3gpp;
  }
  import _3gpp-5g-common-yang-types {
    prefix types5g3gpp;
  }
  import _3gpp-common-top {
    prefix top3gpp;
  }
  import "fgc-nc-1.0" {
    prefix "fgc-nc-1.0";
  }
  import tailf-ncs {
    prefix ncs;
  }
  import tailf-common {
    prefix tailf;
  }

  organization
    "3gpp SA5";
  description
    "This IOC represents the SCP function in 5GC. For more information about the SCP, see 3GPP TS 23.501.";
  reference "3GPP TS 28.541";

  revision 2019-10-20 {
    description
      "initial revision";
    reference
      "Based on
       3GPP TS 28.541 V16.X.XX";
  }

  grouping ncs_template_SCPFunctionGrp {
    uses mf3gpp:ncs_template_ManagedFunctionGrp;
    leaf address {
      description
        "The host address of the SCP.";
      type string;
    }
    list supportedFuncList {
      // NCS patched for predictable order
      ordered-by user;
      // NCS drop min-elements statement
      key "function";
      uses types5g3gpp:ncs_template_SupportedFunc;
    }
  }

  grouping ncs_rpc_notif_SCPFunctionGrp {
    uses mf3gpp:ncs_rpc_notif_ManagedFunctionGrp;
    leaf address {
      description
        "The host address of the SCP.";
      type inet:host;
    }
    list supportedFuncList {
      min-elements 1;
      key "function";
      uses types5g3gpp:ncs_rpc_notif_SupportedFunc;
    }
  }

  grouping live_ncs_SCPFunctionGrp {
    uses mf3gpp:live_ncs_ManagedFunctionGrp;
    leaf address {
      description
        "The host address of the SCP.";
      type inet:host;
    }
    list supportedFuncList {
      // NCS drop min-elements statement
      key "function";
      uses types5g3gpp:live_ncs_SupportedFunc;
    }
  }

  grouping SCPFunctionGrp {
    uses mf3gpp:ManagedFunctionGrp;
    leaf address {
      description
        "The host address of the SCP.";
      type inet:host;
    }
    list supportedFuncList {
      min-elements 1;
      key "function";
      uses types5g3gpp:SupportedFunc;
    }
  }

  augment "/ncs:devices/ncs:template/ncs:ned-id/ncs:config/me3gpp:ManagedElement" {
    list SCPFunction {
      // NCS patched for predictable order
      ordered-by user;
      description
        "5G Core SCP Function";
      reference "3GPP TS 28.541";
      key "id";
      uses top3gpp:ncs_template_Top_Grp;
      container attributes {
        uses ncs_template_SCPFunctionGrp;
      }
    }
  }
  augment "/ncs:devices/ncs:device/ncs:live-status/me3gpp:ManagedElement" {
    list SCPFunction {
      tailf:ncs-device-type "netconf";
      tailf:display-when "not(../../ncs:module) or ../../ncs:module[ncs:name='_3gpp-5gc-nrm-scpfunction'] or (../../ncs:live-status-protocol[not(ncs:capability)]) or (../../ncs:live-status-protocol/ncs:capability/ncs:module[.='_3gpp-5gc-nrm-scpfunction'])";
      description
        "5G Core SCP Function";
      reference "3GPP TS 28.541";
      key "id";
      uses top3gpp:live_ncs_Top_Grp;
      container attributes {
        uses live_ncs_SCPFunctionGrp;
      }
    }
  }
  augment "/ncs:devices/ncs:device/ncs:config/me3gpp:ManagedElement" {
    list SCPFunction {
      tailf:ncs-device-type "netconf";
      tailf:display-when "not(../../ncs:module) or ../../ncs:module[ncs:name='_3gpp-5gc-nrm-scpfunction']";
      description
        "5G Core SCP Function";
      reference "3GPP TS 28.541";
      key "id";
      uses top3gpp:Top_Grp;
      container attributes {
        uses SCPFunctionGrp;
      }
    }
  }
}
