module _3gpp-5gc-nrm-amffunction {
  // Generated by yanger -t ncs
  tailf:mount-id fgc-nc-1.0:fgc-nc-1.0;
  tailf:ncs-device-type "netconf";

  yang-version 1.1;
  namespace "urn:3gpp:sa5:_3gpp-5gc-nrm-amffunction";
  prefix amf3gpp;

  import _3gpp-common-managed-function {
    prefix mf3gpp;
  }
  import _3gpp-common-managed-element {
    prefix me3gpp;
  }
  import _3gpp-common-yang-types {
    prefix types3gpp;
  }
  import _3gpp-5g-common-yang-types {
    prefix types5g3gpp;
  }
  import ietf-inet-types {
    prefix inet;
  }
  import _3gpp-common-top {
    prefix top3gpp;
  }
  import "fgc-nc-1.0" {
    prefix "fgc-nc-1.0";
  }
  import tailf-ncs {
    prefix ncs;
  }
  import tailf-common {
    prefix tailf;
  }

  description
    "AMFFunction derived from basic ManagedFunction.";

  revision 2019-10-25 {
    reference "S5-194457 S5-193518";
  }
  revision 2019-05-31 {
    description
      "Ericsson refactoring.";
  }
  revision 2018-08-07 {
    description
      "Initial revision";
  }

  grouping ncs_template_AMFFunctionGrp {
    uses mf3gpp:ncs_template_ManagedFunctionGrp;
    list pLMNIdList {
      // NCS patched for predictable order
      ordered-by user;
      // NCS drop min-elements statement
      description
        "A list of PLMN identifiers (Mobile Country Code and Mobile Network Code).";
      key "mcc mnc";
      uses types3gpp:ncs_template_PLMNId;
    }
    container aMFIdentifier {
      presence "true";
      description
        "An AMF identifier, comprising an AMF Region ID, an AMF Set ID and an AMF Pointer.";
      uses types3gpp:ncs_template_AmfIdentifier;
    }
    leaf sBIFQDN {
      description
        "The FQDN of the registered NF instance in the service-based interface.";
      type string;
    }
    leaf-list NSSAIList {
      // NCS patched for predictable order
      ordered-by user;
      // NCS drop min-elements statement
      description
        "List of S-NSSAIs the managed object is capable of supporting.
         (Single Network Slice Selection Assistance Information)
         An S-NSSAI has an SST (Slice/Service type) and an optional SD
         (Slice Differentiator) field.";
      reference "3GPP TS 23.003";
      type string;
    }
    list managedNFProfile {
      // NCS patched for predictable order
      ordered-by user;
      key "idx";
      // NCS drop min-elements statement
      uses types3gpp:ncs_template_ManagedNFProfile;
    }
    list commModelList {
      // NCS patched for predictable order
      ordered-by user;
      // NCS drop min-elements statement
      key "groupId";
      uses types5g3gpp:ncs_template_CommModel;
    }
  }

  grouping ncs_rpc_notif_AMFFunctionGrp {
    uses mf3gpp:ncs_rpc_notif_ManagedFunctionGrp;
    list pLMNIdList {
      min-elements 1;
      description
        "A list of PLMN identifiers (Mobile Country Code and Mobile Network Code).";
      key "mcc mnc";
      uses types3gpp:ncs_rpc_notif_PLMNId;
    }
    container aMFIdentifier {
      presence "true";
      description
        "An AMF identifier, comprising an AMF Region ID, an AMF Set ID and an AMF Pointer.";
      uses types3gpp:ncs_rpc_notif_AmfIdentifier;
    }
    leaf sBIFQDN {
      description
        "The FQDN of the registered NF instance in the service-based interface.";
      type inet:domain-name;
    }
    leaf-list NSSAIList {
      min-elements 0;
      description
        "List of S-NSSAIs the managed object is capable of supporting.
         (Single Network Slice Selection Assistance Information)
         An S-NSSAI has an SST (Slice/Service type) and an optional SD
         (Slice Differentiator) field.";
      reference "3GPP TS 23.003";
      type types3gpp:SNssai;
    }
    list managedNFProfile {
      key "idx";
      min-elements 1;
      uses types3gpp:ncs_rpc_notif_ManagedNFProfile;
    }
    list commModelList {
      min-elements 1;
      key "groupId";
      uses types5g3gpp:ncs_rpc_notif_CommModel;
    }
  }

  grouping live_ncs_AMFFunctionGrp {
    uses mf3gpp:live_ncs_ManagedFunctionGrp;
    list pLMNIdList {
      // NCS drop min-elements statement
      description
        "A list of PLMN identifiers (Mobile Country Code and Mobile Network Code).";
      key "mcc mnc";
      uses types3gpp:live_ncs_PLMNId;
    }
    container aMFIdentifier {
      presence "true";
      description
        "An AMF identifier, comprising an AMF Region ID, an AMF Set ID and an AMF Pointer.";
      uses types3gpp:live_ncs_AmfIdentifier;
    }
    leaf sBIFQDN {
      description
        "The FQDN of the registered NF instance in the service-based interface.";
      type inet:domain-name;
    }
    leaf-list NSSAIList {
      // NCS drop min-elements statement
      description
        "List of S-NSSAIs the managed object is capable of supporting.
         (Single Network Slice Selection Assistance Information)
         An S-NSSAI has an SST (Slice/Service type) and an optional SD
         (Slice Differentiator) field.";
      reference "3GPP TS 23.003";
      type types3gpp:SNssai;
    }
    list managedNFProfile {
      key "idx";
      // NCS drop min-elements statement
      uses types3gpp:live_ncs_ManagedNFProfile;
    }
    list commModelList {
      // NCS drop min-elements statement
      key "groupId";
      uses types5g3gpp:live_ncs_CommModel;
    }
  }

  grouping AMFFunctionGrp {
    uses mf3gpp:ManagedFunctionGrp;
    list pLMNIdList {
      min-elements 1;
      description
        "A list of PLMN identifiers (Mobile Country Code and Mobile Network Code).";
      key "mcc mnc";
      uses types3gpp:PLMNId;
    }
    container aMFIdentifier {
      presence "true";
      description
        "An AMF identifier, comprising an AMF Region ID, an AMF Set ID and an AMF Pointer.";
      uses types3gpp:AmfIdentifier;
    }
    leaf sBIFQDN {
      description
        "The FQDN of the registered NF instance in the service-based interface.";
      type inet:domain-name;
    }
    leaf-list NSSAIList {
      min-elements 0;
      description
        "List of S-NSSAIs the managed object is capable of supporting.
         (Single Network Slice Selection Assistance Information)
         An S-NSSAI has an SST (Slice/Service type) and an optional SD
         (Slice Differentiator) field.";
      reference "3GPP TS 23.003";
      type types3gpp:SNssai;
    }
    list managedNFProfile {
      key "idx";
      min-elements 1;
      uses types3gpp:ManagedNFProfile;
    }
    list commModelList {
      min-elements 1;
      key "groupId";
      uses types5g3gpp:CommModel;
    }
  }

  augment "/ncs:devices/ncs:template/ncs:ned-id/ncs:config/me3gpp:ManagedElement" {
    list AMFFunction {
      // NCS patched for predictable order
      ordered-by user;
      description
        "5G Core AMF Function";
      reference "3GPP TS 28.541";
      key "id";
      uses top3gpp:ncs_template_Top_Grp;
      container attributes {
        uses ncs_template_AMFFunctionGrp;
      }
      uses mf3gpp:ncs_template_ManagedFunctionContainedClasses;
    }
  }
  augment "/ncs:devices/ncs:device/ncs:live-status/me3gpp:ManagedElement" {
    list AMFFunction {
      tailf:ncs-device-type "netconf";
      tailf:display-when "not(../../ncs:module) or ../../ncs:module[ncs:name='_3gpp-5gc-nrm-amffunction'] or (../../ncs:live-status-protocol[not(ncs:capability)]) or (../../ncs:live-status-protocol/ncs:capability/ncs:module[.='_3gpp-5gc-nrm-amffunction'])";
      description
        "5G Core AMF Function";
      reference "3GPP TS 28.541";
      key "id";
      uses top3gpp:live_ncs_Top_Grp;
      container attributes {
        uses live_ncs_AMFFunctionGrp;
      }
      uses mf3gpp:live_ncs_ManagedFunctionContainedClasses;
    }
  }
  augment "/ncs:devices/ncs:device/ncs:config/me3gpp:ManagedElement" {
    list AMFFunction {
      tailf:ncs-device-type "netconf";
      tailf:display-when "not(../../ncs:module) or ../../ncs:module[ncs:name='_3gpp-5gc-nrm-amffunction']";
      description
        "5G Core AMF Function";
      reference "3GPP TS 28.541";
      key "id";
      uses top3gpp:Top_Grp;
      container attributes {
        uses AMFFunctionGrp;
      }
      uses mf3gpp:ManagedFunctionContainedClasses;
    }
  }
}
