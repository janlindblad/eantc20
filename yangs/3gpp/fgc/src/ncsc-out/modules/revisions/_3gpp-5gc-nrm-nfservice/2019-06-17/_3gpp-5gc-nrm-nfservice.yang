module _3gpp-5gc-nrm-nfservice {
  // Generated by yanger -t ncs
  tailf:mount-id fgc-nc-1.0:fgc-nc-1.0;
  tailf:ncs-device-type "netconf";

  yang-version 1.1;
  namespace "urn:3gpp:sa5:_3gpp-5gc-nrm-nfservice";
  prefix nfs3gpp;

  import _3gpp-common-yang-types {
    prefix types3gpp;
  }
  import ietf-yang-types {
    prefix yang;
  }
  import ietf-inet-types {
    prefix inet;
  }
  import "fgc-nc-1.0" {
    prefix "fgc-nc-1.0";
  }
  import tailf-ncs {
    prefix ncs;
  }
  import tailf-common {
    prefix tailf;
  }

  organization
    "3gpp SA5";
  description
    "NF service class.";
  reference "3GPP TS 29.510";

  revision 2019-06-17 {
    description
      "initial revision";
  }

  typedef NFServiceStatus {
    type enumeration {
      enum "REGISTERED";
      enum "SUSPENDED";
      enum "UNDISCOVERABLE";
    }
  }

  typedef UriScheme {
    type enumeration {
      enum "HTTP";
      enum "HTTPS";
    }
  }

  typedef ServiceName {
    type enumeration {
      enum "NNRF_NFM";
      enum "NNRF_DISC";
      enum "NUDM_SDM";
      enum "NUDM_UECM";
      enum "NUDM_UEAU";
      enum "NUDM_EE";
      enum "NUDM_PP";
      enum "NAMF_COMM";
      enum "NAMF_EVTS";
      enum "NAMF_MT";
      enum "NAMF_LOC";
      enum "NSMF_PDUSESSION";
      enum "NSMF_EVENT-EXPOSURE";
      enum "NAUSF_AUTH";
      enum "NAUSF_SORPROTECTION";
      enum "NNEF_PFDMANAGEMENT";
      enum "NPCF_AM-POLICY-CONTROL";
      enum "NPCF_SMPOLICYCONTROL";
      enum "NPCF_POLICYAUTHORIZATION";
      enum "NPCF_BDTPOLICYCONTROL";
      enum "NPCF_EVENTEXPOSURE";
      enum "NPCF_UE_POLICY_CONTROL";
      enum "NSMSF_SMS";
      enum "NNSSF_NSSELECTION";
      enum "NNSSF_NSSAIAVAILABILITY";
      enum "NUDR_DR";
      enum "NLMF_LOC";
      enum "N5G_EIR_EIC";
      enum "NBSF_MANAGEMENT";
      enum "NCHF_SPENDINGLIMITCONTROL";
      enum "NCHF_CONVERGEDCHARGING";
      enum "NNWDAF_EVENTSSUBSCRIPTION";
      enum "NNWDAF_ANALYTICSINFO";
    }
  }

  typedef TransportProtocol {
    type enumeration {
      enum "TCP";
      enum "STCP";
      enum "UDP";
    }
  }

  typedef SupportedFeatures {
    type string {
      pattern '[A-Fa-f0-9]*';
    }
  }

  grouping ncs_template_NFServiceGrp {
    leaf serviceInstanceID {
      description
        "Unique ID of the service instance within a given NF Instance.";
      // NCS drop mandatory statement
      type string;
    }
    leaf serviceName {
      description
        "Name of the service instance (e.g. 'nudm-sdm').";
      // NCS drop mandatory statement
      type string;
    }
    list versions {
      // NCS patched for predictable order
      ordered-by user;
      description
        "API versions supported by the NF Service and if available, the corresponding retirement date of the NF Service.";
      // NCS drop min-elements statement
      key "apiVersionInUri apiFullVersion";
      uses ncs_template_NFServiceVersion;
    }
    leaf scheme {
      description
        "URI scheme (e.g. 'http', 'https').";
      // NCS drop mandatory statement
      type string;
    }
    leaf nfServiceStatus {
      description
        "Status of the NF Service Instance.";
      // NCS drop mandatory statement
      type string;
    }
    leaf fqdn {
      description
        "FQDN of the NF Service Instance.";
      type string;
    }
    leaf interPlmnFqdn {
      description
        "If the NF service needs to be discoverable by other NFs in a different PLMN,
         then an FQDN that is used for inter PLMN routing.";
      type string;
    }
    list ipEndPoints {
      // NCS patched for predictable order
      ordered-by user;
      description
        "IP address(es) and port information of the Network Function (including IPv4 and/or IPv6 address)
         where the service is listening for incoming service requests.";
      key "idx";
      leaf idx {
        type string;
      }
      // NCS drop min-elements statement
      uses ncs_template_ipEndPoint;
    }
    leaf apiPrefix {
      description
        "Optional path segment(s) used to construct the {apiRoot} variable of the different API URIs.";
      type string;
    }
    list defaultNotificationSubscriptions {
      // NCS patched for predictable order
      ordered-by user;
      description
        "Notification endpoints for different notification types.";
      key "notificationType";
      // NCS drop min-elements statement
      uses types3gpp:ncs_template_DefaultNotificationSubscription;
    }
    list allowedPlmns {
      // NCS patched for predictable order
      ordered-by user;
      description
        "PLMNs allowed to access the service instance.
         The absence of this attribute indicates that any PLMN is allowed to access the service instance.";
      // NCS drop min-elements statement
      key "mcc mnc";
      uses types3gpp:ncs_template_PLMNId;
    }
    leaf-list allowedNfTypes {
      // NCS patched for predictable order
      ordered-by user;
      description
        "Type of the NFs allowed to access the service instance.
         The absence of this attribute indicates that any NF type is allowed to access the service instance.";
      // NCS drop min-elements statement
      type string;
    }
    leaf-list allowedNfDomains {
      // NCS patched for predictable order
      ordered-by user;
      description
        "Pattern representing the NF domain names allowed to access the service instance.";
      // NCS drop min-elements statement
      type string;
    }
    leaf-list allowedNssais {
      // NCS patched for predictable order
      ordered-by user;
      description
        "S-NSSAI of the allowed slices to access the service instance.
         The absence of this attribute indicates that any slice is allowed to access the service instance.";
      // NCS drop min-elements statement
      type string;
    }
    leaf priority {
      description
        "Priority (relative to other services of the same type) in the range of 0-65535,
         to be used for NF Service selection; lower values indicate a higher priority.";
      type string;
    }
    leaf capacity {
      description
        "Static capacity information in the range of 0-65535, expressed as a weight relative to other services of the same type.";
      type string;
    }
    leaf load {
      description
        "Dynamic load information, ranged from 0 to 100, indicates the current load percentage of the NF Service.";
      type string;
    }
    leaf recoveryTime {
      description
        "Timestamp when the NF was (re)started.";
      type string;
    }
    list chfServiceInfo {
      // NCS patched for predictable order
      ordered-by user;
      description
        "Specific data for a CHF service instance.";
      // NCS drop max-elements statement
      key "primaryChfServiceInstance secondaryChfServiceInstance";
      uses ncs_template_ChfServiceInfo;
    }
    leaf supportedFeatures {
      description
        "Supported Features of the NF Service instance.";
      type string;
    }
  }

  grouping ncs_template_ipEndPoint {
    choice address {
      leaf ipv4Address {
        type string;
      }
      leaf ipv6Address {
        type string;
      }
      leaf ipv6Prefix {
        type string;
      }
    }
    leaf transport {
      type string;
    }
    leaf port {
      type string;
    }
  }

  grouping ncs_template_NFServiceVersion {
    leaf apiVersionInUri {
      // NCS drop mandatory statement
      type string;
    }
    leaf apiFullVersion {
      // NCS drop mandatory statement
      type string;
    }
    leaf expiry {
      type string;
    }
  }

  grouping ncs_template_ChfServiceInfo {
    leaf primaryChfServiceInstance {
      description
        "Shall be present if the CHF service instance serves as a secondary CHF instance of another primary CHF service instance.";
      type string;
    }
    leaf secondaryChfServiceInstance {
      description
        "Shall be present if the CHF service instance serves as a primary CHF instance of another secondary CHF service instance.";
      type string;
    }
  }

  grouping ncs_rpc_notif_NFServiceGrp {
    leaf serviceInstanceID {
      description
        "Unique ID of the service instance within a given NF Instance.";
      mandatory true;
      type string;
    }
    leaf serviceName {
      description
        "Name of the service instance (e.g. 'nudm-sdm').";
      mandatory true;
      type ServiceName;
    }
    list versions {
      description
        "API versions supported by the NF Service and if available, the corresponding retirement date of the NF Service.";
      min-elements 1;
      key "apiVersionInUri apiFullVersion";
      uses ncs_rpc_notif_NFServiceVersion;
    }
    leaf scheme {
      description
        "URI scheme (e.g. 'http', 'https').";
      mandatory true;
      type UriScheme;
    }
    leaf nfServiceStatus {
      description
        "Status of the NF Service Instance.";
      mandatory true;
      type NFServiceStatus;
    }
    leaf fqdn {
      description
        "FQDN of the NF Service Instance.";
      type inet:domain-name;
    }
    leaf interPlmnFqdn {
      description
        "If the NF service needs to be discoverable by other NFs in a different PLMN,
         then an FQDN that is used for inter PLMN routing.";
      type inet:domain-name;
    }
    list ipEndPoints {
      description
        "IP address(es) and port information of the Network Function (including IPv4 and/or IPv6 address)
         where the service is listening for incoming service requests.";
      key "idx";
      leaf idx {
        type string;
      }
      min-elements 1;
      uses ncs_rpc_notif_ipEndPoint;
    }
    leaf apiPrefix {
      description
        "Optional path segment(s) used to construct the {apiRoot} variable of the different API URIs.";
      type string;
    }
    list defaultNotificationSubscriptions {
      description
        "Notification endpoints for different notification types.";
      key "notificationType";
      min-elements 1;
      uses types3gpp:ncs_rpc_notif_DefaultNotificationSubscription;
    }
    list allowedPlmns {
      description
        "PLMNs allowed to access the service instance.
         The absence of this attribute indicates that any PLMN is allowed to access the service instance.";
      min-elements 1;
      key "mcc mnc";
      uses types3gpp:ncs_rpc_notif_PLMNId;
    }
    leaf-list allowedNfTypes {
      description
        "Type of the NFs allowed to access the service instance.
         The absence of this attribute indicates that any NF type is allowed to access the service instance.";
      min-elements 1;
      type types3gpp:NfType;
    }
    leaf-list allowedNfDomains {
      description
        "Pattern representing the NF domain names allowed to access the service instance.";
      min-elements 1;
      type string;
    }
    leaf-list allowedNssais {
      description
        "S-NSSAI of the allowed slices to access the service instance.
         The absence of this attribute indicates that any slice is allowed to access the service instance.";
      min-elements 1;
      type types3gpp:SNssai;
    }
    leaf priority {
      description
        "Priority (relative to other services of the same type) in the range of 0-65535,
         to be used for NF Service selection; lower values indicate a higher priority.";
      type uint16;
    }
    leaf capacity {
      description
        "Static capacity information in the range of 0-65535, expressed as a weight relative to other services of the same type.";
      type uint16;
    }
    leaf load {
      description
        "Dynamic load information, ranged from 0 to 100, indicates the current load percentage of the NF Service.";
      type types3gpp:Load;
    }
    leaf recoveryTime {
      description
        "Timestamp when the NF was (re)started.";
      type yang:date-and-time;
    }
    list chfServiceInfo {
      description
        "Specific data for a CHF service instance.";
      max-elements 1;
      key "primaryChfServiceInstance secondaryChfServiceInstance";
      uses ncs_rpc_notif_ChfServiceInfo;
    }
    leaf supportedFeatures {
      description
        "Supported Features of the NF Service instance.";
      type SupportedFeatures;
    }
  }

  grouping ncs_rpc_notif_ipEndPoint {
    choice address {
      leaf ipv4Address {
        type inet:ipv4-address;
      }
      leaf ipv6Address {
        type inet:ipv6-address;
      }
      leaf ipv6Prefix {
        type inet:ipv6-prefix;
      }
    }
    leaf transport {
      type TransportProtocol;
    }
    leaf port {
      type uint16;
    }
  }

  grouping ncs_rpc_notif_NFServiceVersion {
    leaf apiVersionInUri {
      mandatory true;
      type string;
    }
    leaf apiFullVersion {
      mandatory true;
      type string;
    }
    leaf expiry {
      type yang:date-and-time;
    }
  }

  grouping ncs_rpc_notif_ChfServiceInfo {
    leaf primaryChfServiceInstance {
      description
        "Shall be present if the CHF service instance serves as a secondary CHF instance of another primary CHF service instance.";
      type string;
    }
    leaf secondaryChfServiceInstance {
      description
        "Shall be present if the CHF service instance serves as a primary CHF instance of another secondary CHF service instance.";
      type string;
    }
  }

  grouping live_ncs_NFServiceGrp {
    leaf serviceInstanceID {
      description
        "Unique ID of the service instance within a given NF Instance.";
      // NCS drop mandatory statement
      type string;
    }
    leaf serviceName {
      description
        "Name of the service instance (e.g. 'nudm-sdm').";
      // NCS drop mandatory statement
      type ServiceName;
    }
    list versions {
      description
        "API versions supported by the NF Service and if available, the corresponding retirement date of the NF Service.";
      // NCS drop min-elements statement
      key "apiVersionInUri apiFullVersion";
      uses live_ncs_NFServiceVersion;
    }
    leaf scheme {
      description
        "URI scheme (e.g. 'http', 'https').";
      // NCS drop mandatory statement
      type UriScheme;
    }
    leaf nfServiceStatus {
      description
        "Status of the NF Service Instance.";
      // NCS drop mandatory statement
      type NFServiceStatus;
    }
    leaf fqdn {
      description
        "FQDN of the NF Service Instance.";
      type inet:domain-name;
    }
    leaf interPlmnFqdn {
      description
        "If the NF service needs to be discoverable by other NFs in a different PLMN,
         then an FQDN that is used for inter PLMN routing.";
      type inet:domain-name;
    }
    list ipEndPoints {
      description
        "IP address(es) and port information of the Network Function (including IPv4 and/or IPv6 address)
         where the service is listening for incoming service requests.";
      key "idx";
      leaf idx {
        type string;
      }
      // NCS drop min-elements statement
      uses live_ncs_ipEndPoint;
    }
    leaf apiPrefix {
      description
        "Optional path segment(s) used to construct the {apiRoot} variable of the different API URIs.";
      type string;
    }
    list defaultNotificationSubscriptions {
      description
        "Notification endpoints for different notification types.";
      key "notificationType";
      // NCS drop min-elements statement
      uses types3gpp:live_ncs_DefaultNotificationSubscription;
    }
    list allowedPlmns {
      description
        "PLMNs allowed to access the service instance.
         The absence of this attribute indicates that any PLMN is allowed to access the service instance.";
      // NCS drop min-elements statement
      key "mcc mnc";
      uses types3gpp:live_ncs_PLMNId;
    }
    leaf-list allowedNfTypes {
      description
        "Type of the NFs allowed to access the service instance.
         The absence of this attribute indicates that any NF type is allowed to access the service instance.";
      // NCS drop min-elements statement
      type types3gpp:NfType;
    }
    leaf-list allowedNfDomains {
      description
        "Pattern representing the NF domain names allowed to access the service instance.";
      // NCS drop min-elements statement
      type string;
    }
    leaf-list allowedNssais {
      description
        "S-NSSAI of the allowed slices to access the service instance.
         The absence of this attribute indicates that any slice is allowed to access the service instance.";
      // NCS drop min-elements statement
      type types3gpp:SNssai;
    }
    leaf priority {
      description
        "Priority (relative to other services of the same type) in the range of 0-65535,
         to be used for NF Service selection; lower values indicate a higher priority.";
      type uint16;
    }
    leaf capacity {
      description
        "Static capacity information in the range of 0-65535, expressed as a weight relative to other services of the same type.";
      type uint16;
    }
    leaf load {
      description
        "Dynamic load information, ranged from 0 to 100, indicates the current load percentage of the NF Service.";
      type types3gpp:Load;
    }
    leaf recoveryTime {
      description
        "Timestamp when the NF was (re)started.";
      type yang:date-and-time;
    }
    list chfServiceInfo {
      description
        "Specific data for a CHF service instance.";
      // NCS drop max-elements statement
      key "primaryChfServiceInstance secondaryChfServiceInstance";
      uses live_ncs_ChfServiceInfo;
    }
    leaf supportedFeatures {
      description
        "Supported Features of the NF Service instance.";
      type SupportedFeatures;
    }
  }

  grouping live_ncs_ipEndPoint {
    choice address {
      leaf ipv4Address {
        type inet:ipv4-address;
      }
      leaf ipv6Address {
        type inet:ipv6-address;
      }
      leaf ipv6Prefix {
        type inet:ipv6-prefix;
      }
    }
    leaf transport {
      type TransportProtocol;
    }
    leaf port {
      type uint16;
    }
  }

  grouping live_ncs_NFServiceVersion {
    leaf apiVersionInUri {
      // NCS drop mandatory statement
      type string;
    }
    leaf apiFullVersion {
      // NCS drop mandatory statement
      type string;
    }
    leaf expiry {
      type yang:date-and-time;
    }
  }

  grouping live_ncs_ChfServiceInfo {
    leaf primaryChfServiceInstance {
      description
        "Shall be present if the CHF service instance serves as a secondary CHF instance of another primary CHF service instance.";
      type string;
    }
    leaf secondaryChfServiceInstance {
      description
        "Shall be present if the CHF service instance serves as a primary CHF instance of another secondary CHF service instance.";
      type string;
    }
  }

  grouping NFServiceGrp {
    leaf serviceInstanceID {
      description
        "Unique ID of the service instance within a given NF Instance.";
      mandatory true;
      type string;
    }
    leaf serviceName {
      description
        "Name of the service instance (e.g. 'nudm-sdm').";
      mandatory true;
      type ServiceName;
    }
    list versions {
      description
        "API versions supported by the NF Service and if available, the corresponding retirement date of the NF Service.";
      min-elements 1;
      key "apiVersionInUri apiFullVersion";
      uses NFServiceVersion;
    }
    leaf scheme {
      description
        "URI scheme (e.g. 'http', 'https').";
      mandatory true;
      type UriScheme;
    }
    leaf nfServiceStatus {
      description
        "Status of the NF Service Instance.";
      mandatory true;
      type NFServiceStatus;
    }
    leaf fqdn {
      description
        "FQDN of the NF Service Instance.";
      type inet:domain-name;
    }
    leaf interPlmnFqdn {
      description
        "If the NF service needs to be discoverable by other NFs in a different PLMN,
         then an FQDN that is used for inter PLMN routing.";
      type inet:domain-name;
    }
    list ipEndPoints {
      description
        "IP address(es) and port information of the Network Function (including IPv4 and/or IPv6 address)
         where the service is listening for incoming service requests.";
      key "idx";
      leaf idx {
        type string;
      }
      min-elements 1;
      uses ipEndPoint;
    }
    leaf apiPrefix {
      description
        "Optional path segment(s) used to construct the {apiRoot} variable of the different API URIs.";
      type string;
    }
    list defaultNotificationSubscriptions {
      description
        "Notification endpoints for different notification types.";
      key "notificationType";
      min-elements 1;
      uses types3gpp:DefaultNotificationSubscription;
    }
    list allowedPlmns {
      description
        "PLMNs allowed to access the service instance.
         The absence of this attribute indicates that any PLMN is allowed to access the service instance.";
      min-elements 1;
      key "mcc mnc";
      uses types3gpp:PLMNId;
    }
    leaf-list allowedNfTypes {
      description
        "Type of the NFs allowed to access the service instance.
         The absence of this attribute indicates that any NF type is allowed to access the service instance.";
      min-elements 1;
      type types3gpp:NfType;
    }
    leaf-list allowedNfDomains {
      description
        "Pattern representing the NF domain names allowed to access the service instance.";
      min-elements 1;
      type string;
    }
    leaf-list allowedNssais {
      description
        "S-NSSAI of the allowed slices to access the service instance.
         The absence of this attribute indicates that any slice is allowed to access the service instance.";
      min-elements 1;
      type types3gpp:SNssai;
    }
    leaf priority {
      description
        "Priority (relative to other services of the same type) in the range of 0-65535,
         to be used for NF Service selection; lower values indicate a higher priority.";
      type uint16;
    }
    leaf capacity {
      description
        "Static capacity information in the range of 0-65535, expressed as a weight relative to other services of the same type.";
      type uint16;
    }
    leaf load {
      description
        "Dynamic load information, ranged from 0 to 100, indicates the current load percentage of the NF Service.";
      type types3gpp:Load;
    }
    leaf recoveryTime {
      description
        "Timestamp when the NF was (re)started.";
      type yang:date-and-time;
    }
    list chfServiceInfo {
      description
        "Specific data for a CHF service instance.";
      max-elements 1;
      key "primaryChfServiceInstance secondaryChfServiceInstance";
      uses ChfServiceInfo;
    }
    leaf supportedFeatures {
      description
        "Supported Features of the NF Service instance.";
      type SupportedFeatures;
    }
  }

  grouping ipEndPoint {
    choice address {
      leaf ipv4Address {
        type inet:ipv4-address;
      }
      leaf ipv6Address {
        type inet:ipv6-address;
      }
      leaf ipv6Prefix {
        type inet:ipv6-prefix;
      }
    }
    leaf transport {
      type TransportProtocol;
    }
    leaf port {
      type uint16;
    }
  }

  grouping NFServiceVersion {
    leaf apiVersionInUri {
      mandatory true;
      type string;
    }
    leaf apiFullVersion {
      mandatory true;
      type string;
    }
    leaf expiry {
      type yang:date-and-time;
    }
  }

  grouping ChfServiceInfo {
    leaf primaryChfServiceInstance {
      description
        "Shall be present if the CHF service instance serves as a secondary CHF instance of another primary CHF service instance.";
      type string;
    }
    leaf secondaryChfServiceInstance {
      description
        "Shall be present if the CHF service instance serves as a primary CHF instance of another secondary CHF service instance.";
      type string;
    }
  }
}
