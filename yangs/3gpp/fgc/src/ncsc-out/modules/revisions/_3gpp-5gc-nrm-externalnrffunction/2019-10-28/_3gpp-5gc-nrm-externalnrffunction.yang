module _3gpp-5gc-nrm-externalnrffunction {
  // Generated by yanger -t ncs
  tailf:mount-id fgc-nc-1.0:fgc-nc-1.0;
  tailf:ncs-device-type "netconf";

  yang-version 1.1;
  namespace "urn:3gpp:sa5:_3gpp-5gc-nrm-externalnrffunction";
  prefix extnrf3gpp;

  import _3gpp-common-yang-types {
    prefix types3gpp;
  }
  import _3gpp-common-subnetwork {
    prefix subnet3gpp;
  }
  import _3gpp-common-top {
    prefix top3gpp;
  }
  import _3gpp-common-managed-function {
    prefix mf3gpp;
  }
  import "fgc-nc-1.0" {
    prefix "fgc-nc-1.0";
  }
  import tailf-ncs {
    prefix ncs;
  }
  import tailf-common {
    prefix tailf;
  }

  description
    "This IOC represents external NRF function controlled by another management domain.";

  revision 2019-10-28 {
    reference "S5-193518";
  }
  revision 2019-06-11 {
    description
      "Ericsson refactoring.";
  }

  grouping ncs_template_ExternalNRFFunctionGrp {
    uses mf3gpp:ncs_template_ManagedFunctionGrp;
    list pLMNIdList {
      // NCS patched for predictable order
      ordered-by user;
      description
        "List of at most six entries of PLMN Identifiers, but at least one (the primary PLMN Id).
         The PLMN Identifier is composed of a Mobile Country Code (MCC) and a Mobile Network Code (MNC).";
      // NCS drop min-elements statement
      // NCS drop max-elements statement
      key "mcc mnc";
      uses types3gpp:ncs_template_PLMNId;
    }
  }

  grouping ncs_rpc_notif_ExternalNRFFunctionGrp {
    uses mf3gpp:ncs_rpc_notif_ManagedFunctionGrp;
    list pLMNIdList {
      description
        "List of at most six entries of PLMN Identifiers, but at least one (the primary PLMN Id).
         The PLMN Identifier is composed of a Mobile Country Code (MCC) and a Mobile Network Code (MNC).";
      min-elements 1;
      max-elements 6;
      key "mcc mnc";
      uses types3gpp:ncs_rpc_notif_PLMNId;
    }
  }

  grouping live_ncs_ExternalNRFFunctionGrp {
    uses mf3gpp:live_ncs_ManagedFunctionGrp;
    list pLMNIdList {
      description
        "List of at most six entries of PLMN Identifiers, but at least one (the primary PLMN Id).
         The PLMN Identifier is composed of a Mobile Country Code (MCC) and a Mobile Network Code (MNC).";
      // NCS drop min-elements statement
      // NCS drop max-elements statement
      key "mcc mnc";
      uses types3gpp:live_ncs_PLMNId;
    }
  }

  grouping ExternalNRFFunctionGrp {
    uses mf3gpp:ManagedFunctionGrp;
    list pLMNIdList {
      description
        "List of at most six entries of PLMN Identifiers, but at least one (the primary PLMN Id).
         The PLMN Identifier is composed of a Mobile Country Code (MCC) and a Mobile Network Code (MNC).";
      min-elements 1;
      max-elements 6;
      key "mcc mnc";
      uses types3gpp:PLMNId;
    }
  }

  augment "/ncs:devices/ncs:template/ncs:ned-id/ncs:config/subnet3gpp:SubNetwork" {
    list ExternalNRFFunction {
      // NCS patched for predictable order
      ordered-by user;
      description
        "5G Core External NRF Function";
      reference "3GPP TS 28.541";
      key "id";
      uses top3gpp:ncs_template_Top_Grp;
      container attributes {
        uses ncs_template_ExternalNRFFunctionGrp;
      }
      uses mf3gpp:ncs_template_ManagedFunctionContainedClasses;
    }
  }
  augment "/ncs:devices/ncs:device/ncs:live-status/subnet3gpp:SubNetwork" {
    list ExternalNRFFunction {
      tailf:ncs-device-type "netconf";
      tailf:display-when "not(../../ncs:module) or ../../ncs:module[ncs:name='_3gpp-5gc-nrm-externalnrffunction'] or (../../ncs:live-status-protocol[not(ncs:capability)]) or (../../ncs:live-status-protocol/ncs:capability/ncs:module[.='_3gpp-5gc-nrm-externalnrffunction'])";
      description
        "5G Core External NRF Function";
      reference "3GPP TS 28.541";
      key "id";
      uses top3gpp:live_ncs_Top_Grp;
      container attributes {
        uses live_ncs_ExternalNRFFunctionGrp;
      }
      uses mf3gpp:live_ncs_ManagedFunctionContainedClasses;
    }
  }
  augment "/ncs:devices/ncs:device/ncs:config/subnet3gpp:SubNetwork" {
    list ExternalNRFFunction {
      tailf:ncs-device-type "netconf";
      tailf:display-when "not(../../ncs:module) or ../../ncs:module[ncs:name='_3gpp-5gc-nrm-externalnrffunction']";
      description
        "5G Core External NRF Function";
      reference "3GPP TS 28.541";
      key "id";
      uses top3gpp:Top_Grp;
      container attributes {
        uses ExternalNRFFunctionGrp;
      }
      uses mf3gpp:ManagedFunctionContainedClasses;
    }
  }
}
