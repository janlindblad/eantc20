module _3gpp-nr-nrm-eutranfrequency {
  // Generated by yanger -t ncs
  tailf:mount-id fgc-nc-1.0:fgc-nc-1.0;
  tailf:ncs-device-type "netconf";

  yang-version 1.1;
  namespace "urn:3gpp:sa5:_3gpp-nr-nrm-eutranfrequency";
  prefix eutraneteutranfreq3gpp;

  import _3gpp-common-managed-function {
    prefix mf3gpp;
  }
  import _3gpp-nr-nrm-eutranetwork {
    prefix eutranet3gpp;
  }
  import _3gpp-common-subnetwork {
    prefix subnet3gpp;
  }
  import _3gpp-common-top {
    prefix top3gpp;
  }
  import "fgc-nc-1.0" {
    prefix "fgc-nc-1.0";
  }
  import tailf-ncs {
    prefix ncs;
  }
  import tailf-common {
    prefix tailf;
  }

  organization
    "3GPP SA5";
  description
    "Defines the YANG mapping of the EUtranFrequency Information
     Object Class (IOC), that is part of the NR Network Resource Model (NRM).";
  reference
    "3GPP TS 28.541 5G Network Resource Model (NRM),
     3GPP TS 28.658 (E-UTRAN) Network Resource Model (NRM)";

  revision 2019-10-28 {
    reference "S5-193518";
  }
  revision 2019-06-17 {
    description
      "Initial revision";
  }

  grouping ncs_template_EUtranFrequencyGrp {
    description
      "Represents the EUtranFrequency IOC.";
    reference "3GPP TS 28.541";
    uses mf3gpp:ncs_template_ManagedFunctionGrp;
    leaf earfcnDL {
      description
        "Specifies the channel number for the central DL frequency.";
      reference "3GPP TS 36.101";
      // NCS drop mandatory statement
      type string;
    }
    // NCS drop config false leaf-list multiBandInfoListEutra
  }

  grouping ncs_template_EUtranFrequencyWrapper {
    list EUtranFrequency {
      // NCS patched for predictable order
      ordered-by user;
      description
        "Represents certain E-UTRAN frequency properties.";
      reference "3GPP TS 28.658";
      key "id";
      uses top3gpp:ncs_template_Top_Grp;
      container attributes {
        uses ncs_template_EUtranFrequencyGrp;
      }
      uses mf3gpp:ncs_template_ManagedFunctionContainedClasses;
    }
  }

  grouping ncs_rpc_notif_EUtranFrequencyGrp {
    description
      "Represents the EUtranFrequency IOC.";
    reference "3GPP TS 28.541";
    uses mf3gpp:ncs_rpc_notif_ManagedFunctionGrp;
    leaf earfcnDL {
      description
        "Specifies the channel number for the central DL frequency.";
      reference "3GPP TS 36.101";
      mandatory true;
      type uint32 {
        range "0..262143";
      }
    }
    leaf-list multiBandInfoListEutra {
      description
        "List of additional frequency bands the frequency belongs to.";
      config false;
      min-elements 0;
      type uint16 {
        range "1..256";
      }
    }
  }

  grouping ncs_rpc_notif_EUtranFrequencyWrapper {
    list EUtranFrequency {
      description
        "Represents certain E-UTRAN frequency properties.";
      reference "3GPP TS 28.658";
      key "id";
      uses top3gpp:ncs_rpc_notif_Top_Grp;
      container attributes {
        uses ncs_rpc_notif_EUtranFrequencyGrp;
      }
      uses mf3gpp:ncs_rpc_notif_ManagedFunctionContainedClasses;
    }
  }

  grouping live_ncs_EUtranFrequencyGrp {
    description
      "Represents the EUtranFrequency IOC.";
    reference "3GPP TS 28.541";
    uses mf3gpp:live_ncs_ManagedFunctionGrp;
    leaf earfcnDL {
      description
        "Specifies the channel number for the central DL frequency.";
      reference "3GPP TS 36.101";
      // NCS drop mandatory statement
      type uint32 {
        range "0..262143";
      }
    }
    leaf-list multiBandInfoListEutra {
      description
        "List of additional frequency bands the frequency belongs to.";
      // NCS drop min-elements statement
      type uint16 {
        range "1..256";
      }
    }
  }

  grouping live_ncs_EUtranFrequencyWrapper {
    list EUtranFrequency {
      description
        "Represents certain E-UTRAN frequency properties.";
      reference "3GPP TS 28.658";
      key "id";
      uses top3gpp:live_ncs_Top_Grp;
      container attributes {
        uses live_ncs_EUtranFrequencyGrp;
      }
      uses mf3gpp:live_ncs_ManagedFunctionContainedClasses;
    }
  }

  grouping EUtranFrequencyGrp {
    description
      "Represents the EUtranFrequency IOC.";
    reference "3GPP TS 28.541";
    uses mf3gpp:ManagedFunctionGrp;
    leaf earfcnDL {
      description
        "Specifies the channel number for the central DL frequency.";
      reference "3GPP TS 36.101";
      mandatory true;
      type uint32 {
        range "0..262143";
      }
    }
    // NCS drop config false leaf-list multiBandInfoListEutra
  }

  grouping EUtranFrequencyWrapper {
    list EUtranFrequency {
      description
        "Represents certain E-UTRAN frequency properties.";
      reference "3GPP TS 28.658";
      key "id";
      uses top3gpp:Top_Grp;
      container attributes {
        uses EUtranFrequencyGrp;
      }
      uses mf3gpp:ManagedFunctionContainedClasses;
    }
  }

  augment "/ncs:devices/ncs:template/ncs:ned-id/ncs:config/subnet3gpp:SubNetwork" {
    // NCS drop if-feature statement
    uses ncs_template_EUtranFrequencyWrapper;
  }
  augment "/ncs:devices/ncs:device/ncs:live-status/subnet3gpp:SubNetwork" {
    // NCS drop if-feature statement
    uses live_ncs_EUtranFrequencyWrapper {
      refine EUtranFrequency {
        tailf:ncs-device-type "netconf";
        tailf:display-when "not(../../ncs:module) or ../../ncs:module[ncs:name='_3gpp-nr-nrm-eutranfrequency'] or (../../ncs:live-status-protocol[not(ncs:capability)]) or (../../ncs:live-status-protocol/ncs:capability/ncs:module[.='_3gpp-nr-nrm-eutranfrequency'])";
      }
    }
  }
  augment "/ncs:devices/ncs:device/ncs:config/subnet3gpp:SubNetwork" {
    // NCS drop if-feature statement
    uses EUtranFrequencyWrapper {
      refine EUtranFrequency {
        tailf:ncs-device-type "netconf";
        tailf:display-when "not(../../ncs:module) or ../../ncs:module[ncs:name='_3gpp-nr-nrm-eutranfrequency']";
      }
    }
  }
  augment "/ncs:devices/ncs:template/ncs:ned-id/ncs:config/eutranet3gpp:EUtraNetwork" {
    // NCS drop if-feature statement
    uses ncs_template_EUtranFrequencyWrapper;
  }
  augment "/ncs:devices/ncs:device/ncs:live-status/eutranet3gpp:EUtraNetwork" {
    // NCS drop if-feature statement
    uses live_ncs_EUtranFrequencyWrapper {
      refine EUtranFrequency {
        tailf:ncs-device-type "netconf";
        tailf:display-when "not(../../ncs:module) or ../../ncs:module[ncs:name='_3gpp-nr-nrm-eutranfrequency'] or (../../ncs:live-status-protocol[not(ncs:capability)]) or (../../ncs:live-status-protocol/ncs:capability/ncs:module[.='_3gpp-nr-nrm-eutranfrequency'])";
      }
    }
  }
  augment "/ncs:devices/ncs:device/ncs:config/eutranet3gpp:EUtraNetwork" {
    // NCS drop if-feature statement
    uses EUtranFrequencyWrapper {
      refine EUtranFrequency {
        tailf:ncs-device-type "netconf";
        tailf:display-when "not(../../ncs:module) or ../../ncs:module[ncs:name='_3gpp-nr-nrm-eutranfrequency']";
      }
    }
  }
}
