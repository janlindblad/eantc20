module _3gpp-nr-nrm-externalenbfunction {
  // Generated by yanger -t ncs
  tailf:mount-id fgc-nc-1.0:fgc-nc-1.0;
  tailf:ncs-device-type "netconf";

  yang-version 1.1;
  namespace "urn:3gpp:sa5:_3gpp-nr-nrm-externalenbfunction";
  prefix extenb3gpp;

  import _3gpp-common-managed-function {
    prefix mf3gpp;
  }
  import _3gpp-nr-nrm-eutranetwork {
    prefix eutranet3gpp;
  }
  import _3gpp-common-subnetwork {
    prefix subnet3gpp;
  }
  import _3gpp-common-top {
    prefix top3gpp;
  }
  import "fgc-nc-1.0" {
    prefix "fgc-nc-1.0";
  }
  import tailf-ncs {
    prefix ncs;
  }
  import tailf-common {
    prefix tailf;
  }

  organization
    "3GPP SA5";
  description
    "Defines the YANG mapping of the ExternalENBFunction
     Information Object Class (IOC) that is part of the NR Network Resource
     Model (NRM).";
  reference
    "3GPP TS 28.541 5G Network Resource Model (NRM),
     3GPP TS 28.658 (E-UTRAN) Network Resource Model (NRM)";

  revision 2019-10-28 {
    reference "S5-193518";
  }
  revision 2019-06-17 {
    description
      "Initial revision";
  }

  grouping ncs_template_ExternalENBFunctionGrp {
    description
      "Represets the ExternalENBFunction IOC.";
    reference "3GPP TS 28.658";
    uses mf3gpp:ncs_template_ManagedFunctionGrp;
    leaf eNBId {
      description
        "Unambiguously identifies an eNodeB within a PLMN.";
      reference "3GPP TS 36.413, 3GPP TS 36.300";
      // NCS drop mandatory statement
      type string;
    }
  }

  grouping ncs_template_ExternalENBFunctionWrapper {
    list ExternalENBFunction {
      // NCS patched for predictable order
      ordered-by user;
      description
        "Represents an external eNB functionality.";
      reference "3GPP TS 28.658";
      key "id";
      uses top3gpp:ncs_template_Top_Grp;
      container attributes {
        uses ncs_template_ExternalENBFunctionGrp;
      }
      uses mf3gpp:ncs_template_ManagedFunctionContainedClasses;
    }
  }

  grouping ncs_rpc_notif_ExternalENBFunctionGrp {
    description
      "Represets the ExternalENBFunction IOC.";
    reference "3GPP TS 28.658";
    uses mf3gpp:ncs_rpc_notif_ManagedFunctionGrp;
    leaf eNBId {
      description
        "Unambiguously identifies an eNodeB within a PLMN.";
      reference "3GPP TS 36.413, 3GPP TS 36.300";
      mandatory true;
      type int32 {
        range "0..268435455";
      }
    }
  }

  grouping ncs_rpc_notif_ExternalENBFunctionWrapper {
    list ExternalENBFunction {
      description
        "Represents an external eNB functionality.";
      reference "3GPP TS 28.658";
      key "id";
      uses top3gpp:ncs_rpc_notif_Top_Grp;
      container attributes {
        uses ncs_rpc_notif_ExternalENBFunctionGrp;
      }
      uses mf3gpp:ncs_rpc_notif_ManagedFunctionContainedClasses;
    }
  }

  grouping live_ncs_ExternalENBFunctionGrp {
    description
      "Represets the ExternalENBFunction IOC.";
    reference "3GPP TS 28.658";
    uses mf3gpp:live_ncs_ManagedFunctionGrp;
    leaf eNBId {
      description
        "Unambiguously identifies an eNodeB within a PLMN.";
      reference "3GPP TS 36.413, 3GPP TS 36.300";
      // NCS drop mandatory statement
      type int32 {
        range "0..268435455";
      }
    }
  }

  grouping live_ncs_ExternalENBFunctionWrapper {
    list ExternalENBFunction {
      description
        "Represents an external eNB functionality.";
      reference "3GPP TS 28.658";
      key "id";
      uses top3gpp:live_ncs_Top_Grp;
      container attributes {
        uses live_ncs_ExternalENBFunctionGrp;
      }
      uses mf3gpp:live_ncs_ManagedFunctionContainedClasses;
    }
  }

  grouping ExternalENBFunctionGrp {
    description
      "Represets the ExternalENBFunction IOC.";
    reference "3GPP TS 28.658";
    uses mf3gpp:ManagedFunctionGrp;
    leaf eNBId {
      description
        "Unambiguously identifies an eNodeB within a PLMN.";
      reference "3GPP TS 36.413, 3GPP TS 36.300";
      mandatory true;
      type int32 {
        range "0..268435455";
      }
    }
  }

  grouping ExternalENBFunctionWrapper {
    list ExternalENBFunction {
      description
        "Represents an external eNB functionality.";
      reference "3GPP TS 28.658";
      key "id";
      uses top3gpp:Top_Grp;
      container attributes {
        uses ExternalENBFunctionGrp;
      }
      uses mf3gpp:ManagedFunctionContainedClasses;
    }
  }

  augment "/ncs:devices/ncs:template/ncs:ned-id/ncs:config/subnet3gpp:SubNetwork" {
    // NCS drop if-feature statement
    uses ncs_template_ExternalENBFunctionWrapper;
  }
  augment "/ncs:devices/ncs:device/ncs:live-status/subnet3gpp:SubNetwork" {
    // NCS drop if-feature statement
    uses live_ncs_ExternalENBFunctionWrapper {
      refine ExternalENBFunction {
        tailf:ncs-device-type "netconf";
        tailf:display-when "not(../../ncs:module) or ../../ncs:module[ncs:name='_3gpp-nr-nrm-externalenbfunction'] or (../../ncs:live-status-protocol[not(ncs:capability)]) or (../../ncs:live-status-protocol/ncs:capability/ncs:module[.='_3gpp-nr-nrm-externalenbfunction'])";
      }
    }
  }
  augment "/ncs:devices/ncs:device/ncs:config/subnet3gpp:SubNetwork" {
    // NCS drop if-feature statement
    uses ExternalENBFunctionWrapper {
      refine ExternalENBFunction {
        tailf:ncs-device-type "netconf";
        tailf:display-when "not(../../ncs:module) or ../../ncs:module[ncs:name='_3gpp-nr-nrm-externalenbfunction']";
      }
    }
  }
  augment "/ncs:devices/ncs:template/ncs:ned-id/ncs:config/eutranet3gpp:EUtraNetwork" {
    // NCS drop if-feature statement
    uses ncs_template_ExternalENBFunctionWrapper;
  }
  augment "/ncs:devices/ncs:device/ncs:live-status/eutranet3gpp:EUtraNetwork" {
    // NCS drop if-feature statement
    uses live_ncs_ExternalENBFunctionWrapper {
      refine ExternalENBFunction {
        tailf:ncs-device-type "netconf";
        tailf:display-when "not(../../ncs:module) or ../../ncs:module[ncs:name='_3gpp-nr-nrm-externalenbfunction'] or (../../ncs:live-status-protocol[not(ncs:capability)]) or (../../ncs:live-status-protocol/ncs:capability/ncs:module[.='_3gpp-nr-nrm-externalenbfunction'])";
      }
    }
  }
  augment "/ncs:devices/ncs:device/ncs:config/eutranet3gpp:EUtraNetwork" {
    // NCS drop if-feature statement
    uses ExternalENBFunctionWrapper {
      refine ExternalENBFunction {
        tailf:ncs-device-type "netconf";
        tailf:display-when "not(../../ncs:module) or ../../ncs:module[ncs:name='_3gpp-nr-nrm-externalenbfunction']";
      }
    }
  }
}
