module _3gpp-nr-nrm-nrfrequency {
  // Generated by yanger -t ncs
  tailf:mount-id fgc-nc-1.0:fgc-nc-1.0;
  tailf:ncs-device-type "netconf";

  yang-version 1.1;
  namespace "urn:3gpp:sa5:_3gpp-nr-nrm-nrnetwork-nrfrequency";
  prefix nrfreq3gpp;

  import _3gpp-common-managed-function {
    prefix mf3gpp;
  }
  import _3gpp-nr-nrm-nrnetwork {
    prefix nrnet3gpp;
  }
  import _3gpp-common-subnetwork {
    prefix subnet3gpp;
  }
  import _3gpp-common-top {
    prefix top3gpp;
  }
  import "fgc-nc-1.0" {
    prefix "fgc-nc-1.0";
  }
  import tailf-ncs {
    prefix ncs;
  }
  import tailf-common {
    prefix tailf;
  }

  organization
    "3GPP SA5";
  description
    "Defines the YANG mapping of the NRFrequency Information Object
     Class (IOC) that is part of the NR Network Resource Model (NRM).";
  reference "3GPP TS 28.541 5G Network Resource Model (NRM)";

  revision 2019-10-28 {
    reference "S5-193518";
  }
  revision 2019-06-17 {
    description
      "Initial revision";
  }

  grouping ncs_template_NRFrequencyGrp {
    description
      "Represents the NRFrequency IOC.";
    reference "3GPP TS 28.541";
    uses mf3gpp:ncs_template_ManagedFunctionGrp;
    leaf absoluteFrequencySSB {
      description
        "The absolute frequency applicable for a downlink NR carrier
         frequency associated with the SSB, in terms of NR-ARFCN.";
      // NCS drop mandatory statement
      type string;
    }
    leaf sSBSubCarrierSpacing {
      description
        "Sub-carrier spacing of the SSB.";
      // NCS drop mandatory statement
      type string;
      units "kHz";
    }
    // NCS drop config false leaf-list multiFrequencyBandListNR
  }

  grouping ncs_template_NRFrequencyWrapper {
    list NRFrequency {
      // NCS patched for predictable order
      ordered-by user;
      description
        "Represents certain NR frequency properties.";
      reference "3GPP TS 28.541";
      key "id";
      uses top3gpp:ncs_template_Top_Grp;
      container attributes {
        uses ncs_template_NRFrequencyGrp;
      }
      uses mf3gpp:ncs_template_ManagedFunctionContainedClasses;
    }
  }

  grouping ncs_rpc_notif_NRFrequencyGrp {
    description
      "Represents the NRFrequency IOC.";
    reference "3GPP TS 28.541";
    uses mf3gpp:ncs_rpc_notif_ManagedFunctionGrp;
    leaf absoluteFrequencySSB {
      description
        "The absolute frequency applicable for a downlink NR carrier
         frequency associated with the SSB, in terms of NR-ARFCN.";
      mandatory true;
      type uint32 {
        range "0.. 3279165";
      }
    }
    leaf sSBSubCarrierSpacing {
      description
        "Sub-carrier spacing of the SSB.";
      mandatory true;
      type uint8 {
        range "15 | 30 | 60 | 120";
      }
      units "kHz";
    }
    leaf-list multiFrequencyBandListNR {
      description
        "List of additional frequency bands the frequency belongs to.
         The list is automatically set by the gNB.";
      config false;
      min-elements 0;
      type uint16 {
        range "1..256";
      }
    }
  }

  grouping ncs_rpc_notif_NRFrequencyWrapper {
    list NRFrequency {
      description
        "Represents certain NR frequency properties.";
      reference "3GPP TS 28.541";
      key "id";
      uses top3gpp:ncs_rpc_notif_Top_Grp;
      container attributes {
        uses ncs_rpc_notif_NRFrequencyGrp;
      }
      uses mf3gpp:ncs_rpc_notif_ManagedFunctionContainedClasses;
    }
  }

  grouping live_ncs_NRFrequencyGrp {
    description
      "Represents the NRFrequency IOC.";
    reference "3GPP TS 28.541";
    uses mf3gpp:live_ncs_ManagedFunctionGrp;
    leaf absoluteFrequencySSB {
      description
        "The absolute frequency applicable for a downlink NR carrier
         frequency associated with the SSB, in terms of NR-ARFCN.";
      // NCS drop mandatory statement
      type uint32 {
        range "0.. 3279165";
      }
    }
    leaf sSBSubCarrierSpacing {
      description
        "Sub-carrier spacing of the SSB.";
      // NCS drop mandatory statement
      type uint8 {
        range "15 | 30 | 60 | 120";
      }
      units "kHz";
    }
    leaf-list multiFrequencyBandListNR {
      description
        "List of additional frequency bands the frequency belongs to.
         The list is automatically set by the gNB.";
      // NCS drop min-elements statement
      type uint16 {
        range "1..256";
      }
    }
  }

  grouping live_ncs_NRFrequencyWrapper {
    list NRFrequency {
      description
        "Represents certain NR frequency properties.";
      reference "3GPP TS 28.541";
      key "id";
      uses top3gpp:live_ncs_Top_Grp;
      container attributes {
        uses live_ncs_NRFrequencyGrp;
      }
      uses mf3gpp:live_ncs_ManagedFunctionContainedClasses;
    }
  }

  grouping NRFrequencyGrp {
    description
      "Represents the NRFrequency IOC.";
    reference "3GPP TS 28.541";
    uses mf3gpp:ManagedFunctionGrp;
    leaf absoluteFrequencySSB {
      description
        "The absolute frequency applicable for a downlink NR carrier
         frequency associated with the SSB, in terms of NR-ARFCN.";
      mandatory true;
      type uint32 {
        range "0.. 3279165";
      }
    }
    leaf sSBSubCarrierSpacing {
      description
        "Sub-carrier spacing of the SSB.";
      mandatory true;
      type uint8 {
        range "15 | 30 | 60 | 120";
      }
      units "kHz";
    }
    // NCS drop config false leaf-list multiFrequencyBandListNR
  }

  grouping NRFrequencyWrapper {
    list NRFrequency {
      description
        "Represents certain NR frequency properties.";
      reference "3GPP TS 28.541";
      key "id";
      uses top3gpp:Top_Grp;
      container attributes {
        uses NRFrequencyGrp;
      }
      uses mf3gpp:ManagedFunctionContainedClasses;
    }
  }

  augment "/ncs:devices/ncs:template/ncs:ned-id/ncs:config/subnet3gpp:SubNetwork" {
    // NCS drop if-feature statement
    uses ncs_template_NRFrequencyWrapper;
  }
  augment "/ncs:devices/ncs:device/ncs:live-status/subnet3gpp:SubNetwork" {
    // NCS drop if-feature statement
    uses live_ncs_NRFrequencyWrapper {
      refine NRFrequency {
        tailf:ncs-device-type "netconf";
        tailf:display-when "not(../../ncs:module) or ../../ncs:module[ncs:name='_3gpp-nr-nrm-nrfrequency'] or (../../ncs:live-status-protocol[not(ncs:capability)]) or (../../ncs:live-status-protocol/ncs:capability/ncs:module[.='_3gpp-nr-nrm-nrfrequency'])";
      }
    }
  }
  augment "/ncs:devices/ncs:device/ncs:config/subnet3gpp:SubNetwork" {
    // NCS drop if-feature statement
    uses NRFrequencyWrapper {
      refine NRFrequency {
        tailf:ncs-device-type "netconf";
        tailf:display-when "not(../../ncs:module) or ../../ncs:module[ncs:name='_3gpp-nr-nrm-nrfrequency']";
      }
    }
  }
  augment "/ncs:devices/ncs:template/ncs:ned-id/ncs:config/nrnet3gpp:NRNetwork" {
    // NCS drop if-feature statement
    uses ncs_template_NRFrequencyWrapper;
  }
  augment "/ncs:devices/ncs:device/ncs:live-status/nrnet3gpp:NRNetwork" {
    // NCS drop if-feature statement
    uses live_ncs_NRFrequencyWrapper {
      refine NRFrequency {
        tailf:ncs-device-type "netconf";
        tailf:display-when "not(../../ncs:module) or ../../ncs:module[ncs:name='_3gpp-nr-nrm-nrfrequency'] or (../../ncs:live-status-protocol[not(ncs:capability)]) or (../../ncs:live-status-protocol/ncs:capability/ncs:module[.='_3gpp-nr-nrm-nrfrequency'])";
      }
    }
  }
  augment "/ncs:devices/ncs:device/ncs:config/nrnet3gpp:NRNetwork" {
    // NCS drop if-feature statement
    uses NRFrequencyWrapper {
      refine NRFrequency {
        tailf:ncs-device-type "netconf";
        tailf:display-when "not(../../ncs:module) or ../../ncs:module[ncs:name='_3gpp-nr-nrm-nrfrequency']";
      }
    }
  }
}
