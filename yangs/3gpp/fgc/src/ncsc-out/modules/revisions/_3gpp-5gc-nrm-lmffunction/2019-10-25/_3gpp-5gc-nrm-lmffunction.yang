module _3gpp-5gc-nrm-lmffunction {
  // Generated by yanger -t ncs
  tailf:mount-id fgc-nc-1.0:fgc-nc-1.0;
  tailf:ncs-device-type "netconf";

  yang-version 1.1;
  namespace "urn:3gpp:sa5:_3gpp-5gc-nrm-lmffunction";
  prefix lmf3gpp;

  import _3gpp-common-managed-function {
    prefix mf3gpp;
  }
  import _3gpp-common-managed-element {
    prefix me3gpp;
  }
  import _3gpp-common-yang-types {
    prefix types3gpp;
  }
  import _3gpp-5g-common-yang-types {
    prefix types5g3gpp;
  }
  import _3gpp-common-top {
    prefix top3gpp;
  }
  import "fgc-nc-1.0" {
    prefix "fgc-nc-1.0";
  }
  import tailf-ncs {
    prefix ncs;
  }
  import tailf-common {
    prefix tailf;
  }

  organization
    "3gpp SA5";
  description
    "This IOC represents the LMF function defined in 3GPP TS 23.501.";
  reference "3GPP TS 28.541";

  revision 2019-10-25 {
    reference "S5-194457 S5193518";
  }
  revision 2019-05-15 {
    description
      "initial revision";
    reference
      "Based on
       3GPP TS 28.541 V15.X.XX";
  }

  grouping ncs_template_LMFFunctionGrp {
    uses mf3gpp:ncs_template_ManagedFunctionGrp;
    list pLMNIdList {
      // NCS patched for predictable order
      ordered-by user;
      description
        "List of at most six entries of PLMN Identifiers, but at least one (the primary PLMN Id).
         The PLMN Identifier is composed of a Mobile Country Code (MCC) and a Mobile Network Code (MNC).";
      // NCS drop min-elements statement
      // NCS drop max-elements statement
      key "mcc mnc";
      uses types3gpp:ncs_template_PLMNId;
    }
    list managedNFProfile {
      // NCS patched for predictable order
      ordered-by user;
      key "idx";
      // NCS drop min-elements statement
      uses types3gpp:ncs_template_ManagedNFProfile;
    }
    list commModelList {
      // NCS patched for predictable order
      ordered-by user;
      // NCS drop min-elements statement
      key "groupId";
      uses types5g3gpp:ncs_template_CommModel;
    }
  }

  grouping ncs_rpc_notif_LMFFunctionGrp {
    uses mf3gpp:ncs_rpc_notif_ManagedFunctionGrp;
    list pLMNIdList {
      description
        "List of at most six entries of PLMN Identifiers, but at least one (the primary PLMN Id).
         The PLMN Identifier is composed of a Mobile Country Code (MCC) and a Mobile Network Code (MNC).";
      min-elements 1;
      max-elements 6;
      key "mcc mnc";
      uses types3gpp:ncs_rpc_notif_PLMNId;
    }
    list managedNFProfile {
      key "idx";
      min-elements 1;
      uses types3gpp:ncs_rpc_notif_ManagedNFProfile;
    }
    list commModelList {
      min-elements 1;
      key "groupId";
      uses types5g3gpp:ncs_rpc_notif_CommModel;
    }
  }

  grouping live_ncs_LMFFunctionGrp {
    uses mf3gpp:live_ncs_ManagedFunctionGrp;
    list pLMNIdList {
      description
        "List of at most six entries of PLMN Identifiers, but at least one (the primary PLMN Id).
         The PLMN Identifier is composed of a Mobile Country Code (MCC) and a Mobile Network Code (MNC).";
      // NCS drop min-elements statement
      // NCS drop max-elements statement
      key "mcc mnc";
      uses types3gpp:live_ncs_PLMNId;
    }
    list managedNFProfile {
      key "idx";
      // NCS drop min-elements statement
      uses types3gpp:live_ncs_ManagedNFProfile;
    }
    list commModelList {
      // NCS drop min-elements statement
      key "groupId";
      uses types5g3gpp:live_ncs_CommModel;
    }
  }

  grouping LMFFunctionGrp {
    uses mf3gpp:ManagedFunctionGrp;
    list pLMNIdList {
      description
        "List of at most six entries of PLMN Identifiers, but at least one (the primary PLMN Id).
         The PLMN Identifier is composed of a Mobile Country Code (MCC) and a Mobile Network Code (MNC).";
      min-elements 1;
      max-elements 6;
      key "mcc mnc";
      uses types3gpp:PLMNId;
    }
    list managedNFProfile {
      key "idx";
      min-elements 1;
      uses types3gpp:ManagedNFProfile;
    }
    list commModelList {
      min-elements 1;
      key "groupId";
      uses types5g3gpp:CommModel;
    }
  }

  augment "/ncs:devices/ncs:template/ncs:ned-id/ncs:config/me3gpp:ManagedElement" {
    list LMFFunction {
      // NCS patched for predictable order
      ordered-by user;
      description
        "5G Core LMF Function";
      reference "3GPP TS 28.541";
      key "id";
      uses top3gpp:ncs_template_Top_Grp;
      container attributes {
        uses ncs_template_LMFFunctionGrp;
      }
      uses mf3gpp:ncs_template_ManagedFunctionContainedClasses;
    }
  }
  augment "/ncs:devices/ncs:device/ncs:live-status/me3gpp:ManagedElement" {
    list LMFFunction {
      tailf:ncs-device-type "netconf";
      tailf:display-when "not(../../ncs:module) or ../../ncs:module[ncs:name='_3gpp-5gc-nrm-lmffunction'] or (../../ncs:live-status-protocol[not(ncs:capability)]) or (../../ncs:live-status-protocol/ncs:capability/ncs:module[.='_3gpp-5gc-nrm-lmffunction'])";
      description
        "5G Core LMF Function";
      reference "3GPP TS 28.541";
      key "id";
      uses top3gpp:live_ncs_Top_Grp;
      container attributes {
        uses live_ncs_LMFFunctionGrp;
      }
      uses mf3gpp:live_ncs_ManagedFunctionContainedClasses;
    }
  }
  augment "/ncs:devices/ncs:device/ncs:config/me3gpp:ManagedElement" {
    list LMFFunction {
      tailf:ncs-device-type "netconf";
      tailf:display-when "not(../../ncs:module) or ../../ncs:module[ncs:name='_3gpp-5gc-nrm-lmffunction']";
      description
        "5G Core LMF Function";
      reference "3GPP TS 28.541";
      key "id";
      uses top3gpp:Top_Grp;
      container attributes {
        uses LMFFunctionGrp;
      }
      uses mf3gpp:ManagedFunctionContainedClasses;
    }
  }
}
