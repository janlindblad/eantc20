module _3gpp-nr-nrm-gnbcuupfunction {
  // Generated by yanger -t ncs
  tailf:mount-id fgc-nc-1.0:fgc-nc-1.0;
  tailf:ncs-device-type "netconf";

  yang-version 1.1;
  namespace "urn:3gpp:sa5:_3gpp-nr-nrm-gnbcuupfunction";
  prefix gnbcuup3gpp;

  import _3gpp-common-yang-types {
    prefix types3gpp;
  }
  import _3gpp-common-managed-function {
    prefix mf3gpp;
  }
  import _3gpp-common-managed-element {
    prefix me3gpp;
  }
  import _3gpp-common-top {
    prefix top3gpp;
  }
  import "fgc-nc-1.0" {
    prefix "fgc-nc-1.0";
  }
  import tailf-ncs {
    prefix ncs;
  }
  import tailf-common {
    prefix tailf;
  }

  organization
    "3GPP SA5";
  description
    "Defines the YANG mapping of the GNBCUUPFunction Information
     Object Class (IOC) that is part of the NR Network Resource Model (NRM).";
  reference "3GPP TS 28.541 5G Network Resource Model (NRM)";

  revision 2019-10-28 {
    reference "S5-193518";
  }
  revision 2019-08-21 {
    description
      "Initial revision";
  }

  grouping ncs_template_GNBCUUPFunctionGrp {
    description
      "Represents the GNBCUUPFunction IOC.";
    reference "3GPP TS 28.541";
    uses mf3gpp:ncs_template_ManagedFunctionGrp;
    // NCS drop config false leaf gNBCUUPId
    leaf gNBId {
      // NCS drop mandatory statement
      type string;
      description
        "Indicates the number of bits for encoding the gNB ID.";
      reference "gNB ID in 3GPP TS 38.300, Global gNB ID in 3GPP TS 38.413";
    }
    list pLMNIdList {
      // NCS patched for predictable order
      ordered-by user;
      key "mcc mnc";
      description
        "A list of PLMN identifiers. Defines from which set of PLMNs
         an UE must have as its serving PLMN to be allowed to use the
         gNB CU-UP.";
      uses types3gpp:ncs_template_PLMNId;
    }
  }

  grouping ncs_rpc_notif_GNBCUUPFunctionGrp {
    description
      "Represents the GNBCUUPFunction IOC.";
    reference "3GPP TS 28.541";
    uses mf3gpp:ncs_rpc_notif_ManagedFunctionGrp;
    leaf gNBCUUPId {
      type uint64 {
        range "0..68719476735";
      }
      config false;
      mandatory true;
      description
        "Identifies the gNB-CU-UP at least within a gNB-CU-CP";
      reference "'gNB-CU-UP ID' in subclause 9.3.1.15 of 3GPP TS 38.463";
    }
    leaf gNBId {
      mandatory true;
      type int32 {
        range "22..32";
      }
      description
        "Indicates the number of bits for encoding the gNB ID.";
      reference "gNB ID in 3GPP TS 38.300, Global gNB ID in 3GPP TS 38.413";
    }
    list pLMNIdList {
      key "mcc mnc";
      description
        "A list of PLMN identifiers. Defines from which set of PLMNs
         an UE must have as its serving PLMN to be allowed to use the
         gNB CU-UP.";
      uses types3gpp:ncs_rpc_notif_PLMNId;
    }
  }

  grouping live_ncs_GNBCUUPFunctionGrp {
    description
      "Represents the GNBCUUPFunction IOC.";
    reference "3GPP TS 28.541";
    uses mf3gpp:live_ncs_ManagedFunctionGrp;
    leaf gNBCUUPId {
      type uint64 {
        range "0..68719476735";
      }
      // NCS drop mandatory statement
      description
        "Identifies the gNB-CU-UP at least within a gNB-CU-CP";
      reference "'gNB-CU-UP ID' in subclause 9.3.1.15 of 3GPP TS 38.463";
    }
    leaf gNBId {
      // NCS drop mandatory statement
      type int32 {
        range "22..32";
      }
      description
        "Indicates the number of bits for encoding the gNB ID.";
      reference "gNB ID in 3GPP TS 38.300, Global gNB ID in 3GPP TS 38.413";
    }
    list pLMNIdList {
      key "mcc mnc";
      description
        "A list of PLMN identifiers. Defines from which set of PLMNs
         an UE must have as its serving PLMN to be allowed to use the
         gNB CU-UP.";
      uses types3gpp:live_ncs_PLMNId;
    }
  }

  grouping GNBCUUPFunctionGrp {
    description
      "Represents the GNBCUUPFunction IOC.";
    reference "3GPP TS 28.541";
    uses mf3gpp:ManagedFunctionGrp;
    // NCS drop config false leaf gNBCUUPId
    leaf gNBId {
      mandatory true;
      type int32 {
        range "22..32";
      }
      description
        "Indicates the number of bits for encoding the gNB ID.";
      reference "gNB ID in 3GPP TS 38.300, Global gNB ID in 3GPP TS 38.413";
    }
    list pLMNIdList {
      key "mcc mnc";
      description
        "A list of PLMN identifiers. Defines from which set of PLMNs
         an UE must have as its serving PLMN to be allowed to use the
         gNB CU-UP.";
      uses types3gpp:PLMNId;
    }
  }

  augment "/ncs:devices/ncs:template/ncs:ned-id/ncs:config/me3gpp:ManagedElement" {
    list GNBCUUPFunction {
      // NCS patched for predictable order
      ordered-by user;
      key "id";
      description
        "Represents the logical function CU-UP of gNB or en-gNB.";
      reference "3GPP TS 28.541";
      uses top3gpp:ncs_template_Top_Grp;
      container attributes {
        uses ncs_template_GNBCUUPFunctionGrp;
      }
      uses mf3gpp:ncs_template_ManagedFunctionContainedClasses;
    }
  }
  augment "/ncs:devices/ncs:device/ncs:live-status/me3gpp:ManagedElement" {
    list GNBCUUPFunction {
      tailf:ncs-device-type "netconf";
      tailf:display-when "not(../../ncs:module) or ../../ncs:module[ncs:name='_3gpp-nr-nrm-gnbcuupfunction'] or (../../ncs:live-status-protocol[not(ncs:capability)]) or (../../ncs:live-status-protocol/ncs:capability/ncs:module[.='_3gpp-nr-nrm-gnbcuupfunction'])";
      key "id";
      description
        "Represents the logical function CU-UP of gNB or en-gNB.";
      reference "3GPP TS 28.541";
      uses top3gpp:live_ncs_Top_Grp;
      container attributes {
        uses live_ncs_GNBCUUPFunctionGrp;
      }
      uses mf3gpp:live_ncs_ManagedFunctionContainedClasses;
    }
  }
  augment "/ncs:devices/ncs:device/ncs:config/me3gpp:ManagedElement" {
    list GNBCUUPFunction {
      tailf:ncs-device-type "netconf";
      tailf:display-when "not(../../ncs:module) or ../../ncs:module[ncs:name='_3gpp-nr-nrm-gnbcuupfunction']";
      key "id";
      description
        "Represents the logical function CU-UP of gNB or en-gNB.";
      reference "3GPP TS 28.541";
      uses top3gpp:Top_Grp;
      container attributes {
        uses GNBCUUPFunctionGrp;
      }
      uses mf3gpp:ManagedFunctionContainedClasses;
    }
  }
}
