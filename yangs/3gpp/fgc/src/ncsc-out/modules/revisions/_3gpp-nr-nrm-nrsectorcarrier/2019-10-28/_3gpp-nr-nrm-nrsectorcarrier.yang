module _3gpp-nr-nrm-nrsectorcarrier {
  // Generated by yanger -t ncs
  tailf:mount-id fgc-nc-1.0:fgc-nc-1.0;
  tailf:ncs-device-type "netconf";

  yang-version 1.1;
  namespace "urn:3gpp:sa5:_3gpp-nr-nrm-nrnetwork-nrsectorcarrier";
  prefix nrsectcarr3gpp;

  import _3gpp-common-yang-types {
    prefix types3gpp;
  }
  import _3gpp-common-managed-function {
    prefix mf3gpp;
  }
  import _3gpp-common-managed-element {
    prefix me3gpp;
  }
  import _3gpp-nr-nrm-gnbdufunction {
    prefix gnbdu3gpp;
  }
  import _3gpp-common-top {
    prefix top3gpp;
  }
  import "fgc-nc-1.0" {
    prefix "fgc-nc-1.0";
  }
  import tailf-ncs {
    prefix ncs;
  }
  import tailf-common {
    prefix tailf;
  }

  organization
    "3GPP SA5";
  description
    "Defines the YANG mapping of the NRSectorCarrier Information
     Object Class (IOC) that is part of the NR Network Resource Model (NRM).";
  reference "3GPP TS 28.541 5G Network Resource Model (NRM)";

  revision 2019-10-28 {
    reference "S5-193518";
  }
  revision 2019-06-17 {
    description
      "Initial revision";
  }

  grouping ncs_template_NRSectorCarrierGrp {
    description
      "Represents the NRSectorCarrier IOC.";
    reference "3GPP TS 28.541";
    uses mf3gpp:ncs_template_ManagedFunctionGrp;
    leaf txDirection {
      description
        "Indicates if the transmission direction is downlink,
         uplink, or both downlink and uplink.";
      // NCS drop mandatory statement
      type string;
    }
    leaf configuredMaxTxPower {
      description
        "Maximum possible transmisssion power for all downlink
         channels, used simultaneously in a sector-carrier, added together.";
      // NCS drop mandatory statement
      type string;
      units "mW";
    }
    leaf arfcnDL {
      description
        "NR Absolute Radio Frequency Channel Number (NR-ARFCN)
         for downlink.";
      reference "3GPP TS 38.104";
      // NCS drop mandatory statement
      type string;
    }
    leaf arfcnUL {
      description
        "NR Absolute Radio Frequency Channel Number (NR-ARFCN)
         for uplink.";
      reference "3GPP TS 38.104";
      // NCS drop mandatory statement
      type string;
    }
    leaf bSChannelBwDL {
      description
        "Base station channel bandwitdth for downlink.";
      reference "3GPP TS 38.104";
      // NCS drop mandatory statement
      type string;
      units "MHz";
    }
    leaf bSChannelBwUL {
      description
        "Base station channel bandwitdth for uplink.";
      reference "3GPP TS 38.104";
      // NCS drop mandatory statement
      type string;
      units "MHz";
    }
    leaf sectorEquipmentFunctionRef {
      description
        "Reference to corresponding SectorEquipmentFunction
         instance.";
      reference "3GPP TS 23.622";
      // NCS drop mandatory statement
      type string;
    }
  }

  grouping ncs_rpc_notif_NRSectorCarrierGrp {
    description
      "Represents the NRSectorCarrier IOC.";
    reference "3GPP TS 28.541";
    uses mf3gpp:ncs_rpc_notif_ManagedFunctionGrp;
    leaf txDirection {
      description
        "Indicates if the transmission direction is downlink,
         uplink, or both downlink and uplink.";
      mandatory true;
      type types3gpp:TxDirection;
    }
    leaf configuredMaxTxPower {
      description
        "Maximum possible transmisssion power for all downlink
         channels, used simultaneously in a sector-carrier, added together.";
      mandatory true;
      type int32;
      units "mW";
    }
    leaf arfcnDL {
      description
        "NR Absolute Radio Frequency Channel Number (NR-ARFCN)
         for downlink.";
      reference "3GPP TS 38.104";
      mandatory true;
      type int32 {
        range "0..3279165";
      }
    }
    leaf arfcnUL {
      description
        "NR Absolute Radio Frequency Channel Number (NR-ARFCN)
         for uplink.";
      reference "3GPP TS 38.104";
      mandatory true;
      type int32 {
        range "0..3279165";
      }
    }
    leaf bSChannelBwDL {
      description
        "Base station channel bandwitdth for downlink.";
      reference "3GPP TS 38.104";
      mandatory true;
      type int32 {
        range
          "5 | 10 | 15 | 20 | 30 | 40 | 50 | 60 | 70 | 80 |
           90 | 100";
      }
      units "MHz";
    }
    leaf bSChannelBwUL {
      description
        "Base station channel bandwitdth for uplink.";
      reference "3GPP TS 38.104";
      mandatory true;
      type int32 {
        range
          "5 | 10 | 15 | 20 | 30 | 40 | 50 | 60 | 70 | 80 |
           90 | 100";
      }
      units "MHz";
    }
    leaf sectorEquipmentFunctionRef {
      description
        "Reference to corresponding SectorEquipmentFunction
         instance.";
      reference "3GPP TS 23.622";
      mandatory true;
      type types3gpp:DistinguishedName;
    }
  }

  grouping live_ncs_NRSectorCarrierGrp {
    description
      "Represents the NRSectorCarrier IOC.";
    reference "3GPP TS 28.541";
    uses mf3gpp:live_ncs_ManagedFunctionGrp;
    leaf txDirection {
      description
        "Indicates if the transmission direction is downlink,
         uplink, or both downlink and uplink.";
      // NCS drop mandatory statement
      type types3gpp:TxDirection;
    }
    leaf configuredMaxTxPower {
      description
        "Maximum possible transmisssion power for all downlink
         channels, used simultaneously in a sector-carrier, added together.";
      // NCS drop mandatory statement
      type int32;
      units "mW";
    }
    leaf arfcnDL {
      description
        "NR Absolute Radio Frequency Channel Number (NR-ARFCN)
         for downlink.";
      reference "3GPP TS 38.104";
      // NCS drop mandatory statement
      type int32 {
        range "0..3279165";
      }
    }
    leaf arfcnUL {
      description
        "NR Absolute Radio Frequency Channel Number (NR-ARFCN)
         for uplink.";
      reference "3GPP TS 38.104";
      // NCS drop mandatory statement
      type int32 {
        range "0..3279165";
      }
    }
    leaf bSChannelBwDL {
      description
        "Base station channel bandwitdth for downlink.";
      reference "3GPP TS 38.104";
      // NCS drop mandatory statement
      type int32 {
        range
          "5 | 10 | 15 | 20 | 30 | 40 | 50 | 60 | 70 | 80 |
           90 | 100";
      }
      units "MHz";
    }
    leaf bSChannelBwUL {
      description
        "Base station channel bandwitdth for uplink.";
      reference "3GPP TS 38.104";
      // NCS drop mandatory statement
      type int32 {
        range
          "5 | 10 | 15 | 20 | 30 | 40 | 50 | 60 | 70 | 80 |
           90 | 100";
      }
      units "MHz";
    }
    leaf sectorEquipmentFunctionRef {
      description
        "Reference to corresponding SectorEquipmentFunction
         instance.";
      reference "3GPP TS 23.622";
      // NCS drop mandatory statement
      type types3gpp:DistinguishedName;
    }
  }

  grouping NRSectorCarrierGrp {
    description
      "Represents the NRSectorCarrier IOC.";
    reference "3GPP TS 28.541";
    uses mf3gpp:ManagedFunctionGrp;
    leaf txDirection {
      description
        "Indicates if the transmission direction is downlink,
         uplink, or both downlink and uplink.";
      mandatory true;
      type types3gpp:TxDirection;
    }
    leaf configuredMaxTxPower {
      description
        "Maximum possible transmisssion power for all downlink
         channels, used simultaneously in a sector-carrier, added together.";
      mandatory true;
      type int32;
      units "mW";
    }
    leaf arfcnDL {
      description
        "NR Absolute Radio Frequency Channel Number (NR-ARFCN)
         for downlink.";
      reference "3GPP TS 38.104";
      mandatory true;
      type int32 {
        range "0..3279165";
      }
    }
    leaf arfcnUL {
      description
        "NR Absolute Radio Frequency Channel Number (NR-ARFCN)
         for uplink.";
      reference "3GPP TS 38.104";
      mandatory true;
      type int32 {
        range "0..3279165";
      }
    }
    leaf bSChannelBwDL {
      description
        "Base station channel bandwitdth for downlink.";
      reference "3GPP TS 38.104";
      mandatory true;
      type int32 {
        range
          "5 | 10 | 15 | 20 | 30 | 40 | 50 | 60 | 70 | 80 |
           90 | 100";
      }
      units "MHz";
    }
    leaf bSChannelBwUL {
      description
        "Base station channel bandwitdth for uplink.";
      reference "3GPP TS 38.104";
      mandatory true;
      type int32 {
        range
          "5 | 10 | 15 | 20 | 30 | 40 | 50 | 60 | 70 | 80 |
           90 | 100";
      }
      units "MHz";
    }
    leaf sectorEquipmentFunctionRef {
      description
        "Reference to corresponding SectorEquipmentFunction
         instance.";
      reference "3GPP TS 23.622";
      mandatory true;
      type types3gpp:DistinguishedName;
    }
  }

  augment "/ncs:devices/ncs:template/ncs:ned-id/ncs:config/me3gpp:ManagedElement/gnbdu3gpp:GNBDUFunction" {
    list NRSectorCarrier {
      // NCS patched for predictable order
      ordered-by user;
      description
        "Represents the resources of each transmission point
         included in the cell.";
      reference "3GPP TS 28.541";
      key "id";
      uses top3gpp:ncs_template_Top_Grp;
      container attributes {
        uses ncs_template_NRSectorCarrierGrp;
      }
      uses mf3gpp:ncs_template_ManagedFunctionContainedClasses;
    }
  }
  augment "/ncs:devices/ncs:device/ncs:live-status/me3gpp:ManagedElement/gnbdu3gpp:GNBDUFunction" {
    list NRSectorCarrier {
      tailf:ncs-device-type "netconf";
      tailf:display-when "not(../../../ncs:module) or ../../../ncs:module[ncs:name='_3gpp-nr-nrm-nrsectorcarrier'] or (../../../ncs:live-status-protocol[not(ncs:capability)]) or (../../../ncs:live-status-protocol/ncs:capability/ncs:module[.='_3gpp-nr-nrm-nrsectorcarrier'])";
      description
        "Represents the resources of each transmission point
         included in the cell.";
      reference "3GPP TS 28.541";
      key "id";
      uses top3gpp:live_ncs_Top_Grp;
      container attributes {
        uses live_ncs_NRSectorCarrierGrp;
      }
      uses mf3gpp:live_ncs_ManagedFunctionContainedClasses;
    }
  }
  augment "/ncs:devices/ncs:device/ncs:config/me3gpp:ManagedElement/gnbdu3gpp:GNBDUFunction" {
    list NRSectorCarrier {
      tailf:ncs-device-type "netconf";
      tailf:display-when "not(../../../ncs:module) or ../../../ncs:module[ncs:name='_3gpp-nr-nrm-nrsectorcarrier']";
      description
        "Represents the resources of each transmission point
         included in the cell.";
      reference "3GPP TS 28.541";
      key "id";
      uses top3gpp:Top_Grp;
      container attributes {
        uses NRSectorCarrierGrp;
      }
      uses mf3gpp:ManagedFunctionContainedClasses;
    }
  }
}
