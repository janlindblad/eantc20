module _3gpp-nr-nrm-externalamffunction {
  // Generated by yanger -t ncs
  tailf:mount-id fgc-nc-1.0:fgc-nc-1.0;
  tailf:ncs-device-type "netconf";

  yang-version 1.1;
  namespace "urn:3gpp:sa5:_3gpp-nr-nrm-externalamffunction";
  prefix extamf3gpp;

  import _3gpp-common-managed-function {
    prefix mf3gpp;
  }
  import _3gpp-common-subnetwork {
    prefix subnet3gpp;
  }
  import _3gpp-nr-nrm-nrnetwork {
    prefix nrnet3gpp;
  }
  import _3gpp-common-top {
    prefix top3gpp;
  }
  import _3gpp-common-yang-types {
    prefix types3gpp;
  }
  import "fgc-nc-1.0" {
    prefix "fgc-nc-1.0";
  }
  import tailf-ncs {
    prefix ncs;
  }
  import tailf-common {
    prefix tailf;
  }

  organization
    "3GPP SA5";
  description
    "Defines the YANG mapping of the ExternalAMFFunction Information
     Object Class (IOC) that is part of the NR Network Resource Model (NRM).";
  reference "3GPP TS 28.541 5G Network Resource Model (NRM)";

  revision 2019-10-28 {
    reference "S5-193518";
  }
  revision 2019-06-17 {
    description
      "Initial revision";
  }

  grouping ncs_template_ExternalAMFFunctionGrp {
    description
      "Represents the ExternalAMFFunction IOC.";
    reference "3GPP TS 28.541";
    uses mf3gpp:ncs_template_ManagedFunctionGrp;
    list pLMNIdList {
      // NCS patched for predictable order
      ordered-by user;
      description
        "List of at most six entries of PLMN Identifiers, but at least
         one (the primary PLMN Id).
         The PLMN Identifier is composed of a Mobile Country Code (MCC) and a
         Mobile Network Code (MNC).";
      // NCS drop min-elements statement
      // NCS drop max-elements statement
      key "mcc mnc";
      uses types3gpp:ncs_template_PLMNId;
    }
    container aMFIdentifier {
      presence "true";
      description
        "An AMF identifier, comprising an AMF Region ID, an AMF Set ID and an AMF Pointer.";
      uses types3gpp:ncs_template_AmfIdentifier;
    }
  }

  grouping ncs_template_ExternalAMFFunctionWrapper {
    list ExternalAMFFunction {
      // NCS patched for predictable order
      ordered-by user;
      description
        "Represents the properties, known by the management
         function, of a AMFFunction managed by another management
         function.";
      reference "3GPP TS 28.541";
      key "id";
      uses top3gpp:ncs_template_Top_Grp;
      container attributes {
        uses ncs_template_ExternalAMFFunctionGrp;
      }
      uses mf3gpp:ncs_template_ManagedFunctionContainedClasses;
    }
  }

  grouping ncs_rpc_notif_ExternalAMFFunctionGrp {
    description
      "Represents the ExternalAMFFunction IOC.";
    reference "3GPP TS 28.541";
    uses mf3gpp:ncs_rpc_notif_ManagedFunctionGrp;
    list pLMNIdList {
      description
        "List of at most six entries of PLMN Identifiers, but at least
         one (the primary PLMN Id).
         The PLMN Identifier is composed of a Mobile Country Code (MCC) and a
         Mobile Network Code (MNC).";
      min-elements 1;
      max-elements 6;
      key "mcc mnc";
      uses types3gpp:ncs_rpc_notif_PLMNId;
    }
    container aMFIdentifier {
      presence "true";
      description
        "An AMF identifier, comprising an AMF Region ID, an AMF Set ID and an AMF Pointer.";
      uses types3gpp:ncs_rpc_notif_AmfIdentifier;
    }
  }

  grouping ncs_rpc_notif_ExternalAMFFunctionWrapper {
    list ExternalAMFFunction {
      description
        "Represents the properties, known by the management
         function, of a AMFFunction managed by another management
         function.";
      reference "3GPP TS 28.541";
      key "id";
      uses top3gpp:ncs_rpc_notif_Top_Grp;
      container attributes {
        uses ncs_rpc_notif_ExternalAMFFunctionGrp;
      }
      uses mf3gpp:ncs_rpc_notif_ManagedFunctionContainedClasses;
    }
  }

  grouping live_ncs_ExternalAMFFunctionGrp {
    description
      "Represents the ExternalAMFFunction IOC.";
    reference "3GPP TS 28.541";
    uses mf3gpp:live_ncs_ManagedFunctionGrp;
    list pLMNIdList {
      description
        "List of at most six entries of PLMN Identifiers, but at least
         one (the primary PLMN Id).
         The PLMN Identifier is composed of a Mobile Country Code (MCC) and a
         Mobile Network Code (MNC).";
      // NCS drop min-elements statement
      // NCS drop max-elements statement
      key "mcc mnc";
      uses types3gpp:live_ncs_PLMNId;
    }
    container aMFIdentifier {
      presence "true";
      description
        "An AMF identifier, comprising an AMF Region ID, an AMF Set ID and an AMF Pointer.";
      uses types3gpp:live_ncs_AmfIdentifier;
    }
  }

  grouping live_ncs_ExternalAMFFunctionWrapper {
    list ExternalAMFFunction {
      description
        "Represents the properties, known by the management
         function, of a AMFFunction managed by another management
         function.";
      reference "3GPP TS 28.541";
      key "id";
      uses top3gpp:live_ncs_Top_Grp;
      container attributes {
        uses live_ncs_ExternalAMFFunctionGrp;
      }
      uses mf3gpp:live_ncs_ManagedFunctionContainedClasses;
    }
  }

  grouping ExternalAMFFunctionGrp {
    description
      "Represents the ExternalAMFFunction IOC.";
    reference "3GPP TS 28.541";
    uses mf3gpp:ManagedFunctionGrp;
    list pLMNIdList {
      description
        "List of at most six entries of PLMN Identifiers, but at least
         one (the primary PLMN Id).
         The PLMN Identifier is composed of a Mobile Country Code (MCC) and a
         Mobile Network Code (MNC).";
      min-elements 1;
      max-elements 6;
      key "mcc mnc";
      uses types3gpp:PLMNId;
    }
    container aMFIdentifier {
      presence "true";
      description
        "An AMF identifier, comprising an AMF Region ID, an AMF Set ID and an AMF Pointer.";
      uses types3gpp:AmfIdentifier;
    }
  }

  grouping ExternalAMFFunctionWrapper {
    list ExternalAMFFunction {
      description
        "Represents the properties, known by the management
         function, of a AMFFunction managed by another management
         function.";
      reference "3GPP TS 28.541";
      key "id";
      uses top3gpp:Top_Grp;
      container attributes {
        uses ExternalAMFFunctionGrp;
      }
      uses mf3gpp:ManagedFunctionContainedClasses;
    }
  }

  augment "/ncs:devices/ncs:template/ncs:ned-id/ncs:config/subnet3gpp:SubNetwork" {
    // NCS drop if-feature statement
    uses ncs_template_ExternalAMFFunctionWrapper;
  }
  augment "/ncs:devices/ncs:device/ncs:live-status/subnet3gpp:SubNetwork" {
    // NCS drop if-feature statement
    uses live_ncs_ExternalAMFFunctionWrapper {
      refine ExternalAMFFunction {
        tailf:ncs-device-type "netconf";
        tailf:display-when "not(../../ncs:module) or ../../ncs:module[ncs:name='_3gpp-nr-nrm-externalamffunction'] or (../../ncs:live-status-protocol[not(ncs:capability)]) or (../../ncs:live-status-protocol/ncs:capability/ncs:module[.='_3gpp-nr-nrm-externalamffunction'])";
      }
    }
  }
  augment "/ncs:devices/ncs:device/ncs:config/subnet3gpp:SubNetwork" {
    // NCS drop if-feature statement
    uses ExternalAMFFunctionWrapper {
      refine ExternalAMFFunction {
        tailf:ncs-device-type "netconf";
        tailf:display-when "not(../../ncs:module) or ../../ncs:module[ncs:name='_3gpp-nr-nrm-externalamffunction']";
      }
    }
  }
  augment "/ncs:devices/ncs:template/ncs:ned-id/ncs:config/nrnet3gpp:NRNetwork" {
    // NCS drop if-feature statement
    uses ncs_template_ExternalAMFFunctionWrapper;
  }
  augment "/ncs:devices/ncs:device/ncs:live-status/nrnet3gpp:NRNetwork" {
    // NCS drop if-feature statement
    uses live_ncs_ExternalAMFFunctionWrapper {
      refine ExternalAMFFunction {
        tailf:ncs-device-type "netconf";
        tailf:display-when "not(../../ncs:module) or ../../ncs:module[ncs:name='_3gpp-nr-nrm-externalamffunction'] or (../../ncs:live-status-protocol[not(ncs:capability)]) or (../../ncs:live-status-protocol/ncs:capability/ncs:module[.='_3gpp-nr-nrm-externalamffunction'])";
      }
    }
  }
  augment "/ncs:devices/ncs:device/ncs:config/nrnet3gpp:NRNetwork" {
    // NCS drop if-feature statement
    uses ExternalAMFFunctionWrapper {
      refine ExternalAMFFunction {
        tailf:ncs-device-type "netconf";
        tailf:display-when "not(../../ncs:module) or ../../ncs:module[ncs:name='_3gpp-nr-nrm-externalamffunction']";
      }
    }
  }
}
