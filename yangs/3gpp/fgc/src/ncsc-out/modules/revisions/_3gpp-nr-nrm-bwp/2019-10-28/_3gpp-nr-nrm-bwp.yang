module _3gpp-nr-nrm-bwp {
  // Generated by yanger -t ncs
  tailf:mount-id fgc-nc-1.0:fgc-nc-1.0;
  tailf:ncs-device-type "netconf";

  yang-version 1.1;
  namespace "urn:3gpp:sa5:_3gpp-nr-nrm-bwp";
  prefix bwp3gpp;

  import _3gpp-common-managed-element {
    prefix me3gpp;
  }
  import _3gpp-common-managed-function {
    prefix mf3gpp;
  }
  import _3gpp-common-top {
    prefix top3gpp;
  }
  import _3gpp-nr-nrm-gnbdufunction {
    prefix gnbdu3gpp;
  }
  import "fgc-nc-1.0" {
    prefix "fgc-nc-1.0";
  }
  import tailf-ncs {
    prefix ncs;
  }
  import tailf-common {
    prefix tailf;
  }

  organization
    "3GPP SA5";
  description
    "Defines the YANG mapping of the BWP Information Object Class
     (IOC) that is part of the NR Network Resource Model (NRM).";
  reference "3GPP TS 28.541 5G Network Resource Model (NRM)";

  revision 2019-10-28 {
    reference "S5-193518";
  }
  revision 2019-06-17 {
    description
      "Initial revision";
  }

  typedef IsInitialBwp {
    type enumeration {
      enum "INITIAL";
      enum "OTHER";
    }
  }

  typedef BwpContext {
    type enumeration {
      enum "DL";
      enum "UL";
      enum "SUL";
    }
  }

  typedef CyclicPrefix {
    type enumeration {
      enum "NORMAL";
      enum "EXTENDED";
    }
  }

  grouping ncs_template_BWPGrp {
    description
      "Represents the BWP IOC.";
    reference "3GPP TS 28.541";
    uses mf3gpp:ncs_template_ManagedFunctionGrp;
    leaf bwpContext {
      description
        "Identifies whether the object is used for downlink, uplink
         or supplementary uplink.";
      // NCS drop mandatory statement
      type string;
    }
    leaf isInitialBwp {
      description
        "Identifies whether the object is used for initial or other
         BWP.";
      // NCS drop mandatory statement
      type string;
    }
    leaf subCarrierSpacing {
      description
        "Subcarrier spacing configuration for a BWP.";
      reference "3GPP TS 38.104";
      // NCS drop mandatory statement
      type string;
      units "kHz";
    }
    leaf cyclicPrefix {
      description
        "Cyclic prefix, which may be normal or extended.";
      reference "3GPP TS 38.211";
      // NCS drop mandatory statement
      type string;
    }
    leaf startRB {
      description
        "Offset in common resource blocks to common resource block 0
         for the applicable subcarrier spacing for a BWP.";
      reference "N_BWP_start in 3GPP TS 38.211";
      // NCS drop mandatory statement
      type string;
    }
    leaf numberOfRBs {
      description
        "Number of physical resource blocks for a BWP.";
      reference "N_BWP_size in 3GPP TS 38.211";
      // NCS drop mandatory statement
      type string;
    }
  }

  grouping ncs_rpc_notif_BWPGrp {
    description
      "Represents the BWP IOC.";
    reference "3GPP TS 28.541";
    uses mf3gpp:ncs_rpc_notif_ManagedFunctionGrp;
    leaf bwpContext {
      description
        "Identifies whether the object is used for downlink, uplink
         or supplementary uplink.";
      mandatory true;
      type BwpContext;
    }
    leaf isInitialBwp {
      description
        "Identifies whether the object is used for initial or other
         BWP.";
      mandatory true;
      type IsInitialBwp;
    }
    leaf subCarrierSpacing {
      description
        "Subcarrier spacing configuration for a BWP.";
      reference "3GPP TS 38.104";
      mandatory true;
      type uint32 {
        range "5 | 30 | 60 | 120";
      }
      units "kHz";
    }
    leaf cyclicPrefix {
      description
        "Cyclic prefix, which may be normal or extended.";
      reference "3GPP TS 38.211";
      mandatory true;
      type CyclicPrefix;
    }
    leaf startRB {
      description
        "Offset in common resource blocks to common resource block 0
         for the applicable subcarrier spacing for a BWP.";
      reference "N_BWP_start in 3GPP TS 38.211";
      mandatory true;
      type uint32;
    }
    leaf numberOfRBs {
      description
        "Number of physical resource blocks for a BWP.";
      reference "N_BWP_size in 3GPP TS 38.211";
      mandatory true;
      type uint32;
    }
  }

  grouping live_ncs_BWPGrp {
    description
      "Represents the BWP IOC.";
    reference "3GPP TS 28.541";
    uses mf3gpp:live_ncs_ManagedFunctionGrp;
    leaf bwpContext {
      description
        "Identifies whether the object is used for downlink, uplink
         or supplementary uplink.";
      // NCS drop mandatory statement
      type BwpContext;
    }
    leaf isInitialBwp {
      description
        "Identifies whether the object is used for initial or other
         BWP.";
      // NCS drop mandatory statement
      type IsInitialBwp;
    }
    leaf subCarrierSpacing {
      description
        "Subcarrier spacing configuration for a BWP.";
      reference "3GPP TS 38.104";
      // NCS drop mandatory statement
      type uint32 {
        range "5 | 30 | 60 | 120";
      }
      units "kHz";
    }
    leaf cyclicPrefix {
      description
        "Cyclic prefix, which may be normal or extended.";
      reference "3GPP TS 38.211";
      // NCS drop mandatory statement
      type CyclicPrefix;
    }
    leaf startRB {
      description
        "Offset in common resource blocks to common resource block 0
         for the applicable subcarrier spacing for a BWP.";
      reference "N_BWP_start in 3GPP TS 38.211";
      // NCS drop mandatory statement
      type uint32;
    }
    leaf numberOfRBs {
      description
        "Number of physical resource blocks for a BWP.";
      reference "N_BWP_size in 3GPP TS 38.211";
      // NCS drop mandatory statement
      type uint32;
    }
  }

  grouping BWPGrp {
    description
      "Represents the BWP IOC.";
    reference "3GPP TS 28.541";
    uses mf3gpp:ManagedFunctionGrp;
    leaf bwpContext {
      description
        "Identifies whether the object is used for downlink, uplink
         or supplementary uplink.";
      mandatory true;
      type BwpContext;
    }
    leaf isInitialBwp {
      description
        "Identifies whether the object is used for initial or other
         BWP.";
      mandatory true;
      type IsInitialBwp;
    }
    leaf subCarrierSpacing {
      description
        "Subcarrier spacing configuration for a BWP.";
      reference "3GPP TS 38.104";
      mandatory true;
      type uint32 {
        range "5 | 30 | 60 | 120";
      }
      units "kHz";
    }
    leaf cyclicPrefix {
      description
        "Cyclic prefix, which may be normal or extended.";
      reference "3GPP TS 38.211";
      mandatory true;
      type CyclicPrefix;
    }
    leaf startRB {
      description
        "Offset in common resource blocks to common resource block 0
         for the applicable subcarrier spacing for a BWP.";
      reference "N_BWP_start in 3GPP TS 38.211";
      mandatory true;
      type uint32;
    }
    leaf numberOfRBs {
      description
        "Number of physical resource blocks for a BWP.";
      reference "N_BWP_size in 3GPP TS 38.211";
      mandatory true;
      type uint32;
    }
  }

  augment "/ncs:devices/ncs:template/ncs:ned-id/ncs:config/me3gpp:ManagedElement/gnbdu3gpp:GNBDUFunction" {
    list BWP {
      // NCS patched for predictable order
      ordered-by user;
      description
        "Represents a bandwidth part (BWP).";
      key "id";
      uses top3gpp:ncs_template_Top_Grp;
      container attributes {
        uses ncs_template_BWPGrp;
      }
      uses mf3gpp:ncs_template_ManagedFunctionContainedClasses;
    }
  }
  augment "/ncs:devices/ncs:device/ncs:live-status/me3gpp:ManagedElement/gnbdu3gpp:GNBDUFunction" {
    list BWP {
      tailf:ncs-device-type "netconf";
      tailf:display-when "not(../../../ncs:module) or ../../../ncs:module[ncs:name='_3gpp-nr-nrm-bwp'] or (../../../ncs:live-status-protocol[not(ncs:capability)]) or (../../../ncs:live-status-protocol/ncs:capability/ncs:module[.='_3gpp-nr-nrm-bwp'])";
      description
        "Represents a bandwidth part (BWP).";
      key "id";
      uses top3gpp:live_ncs_Top_Grp;
      container attributes {
        uses live_ncs_BWPGrp;
      }
      uses mf3gpp:live_ncs_ManagedFunctionContainedClasses;
    }
  }
  augment "/ncs:devices/ncs:device/ncs:config/me3gpp:ManagedElement/gnbdu3gpp:GNBDUFunction" {
    list BWP {
      tailf:ncs-device-type "netconf";
      tailf:display-when "not(../../../ncs:module) or ../../../ncs:module[ncs:name='_3gpp-nr-nrm-bwp']";
      description
        "Represents a bandwidth part (BWP).";
      key "id";
      uses top3gpp:Top_Grp;
      container attributes {
        uses BWPGrp;
      }
      uses mf3gpp:ManagedFunctionContainedClasses;
    }
  }
}
