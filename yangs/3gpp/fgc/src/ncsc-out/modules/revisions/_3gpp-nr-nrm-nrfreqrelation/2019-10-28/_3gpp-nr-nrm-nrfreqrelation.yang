module _3gpp-nr-nrm-nrfreqrelation {
  // Generated by yanger -t ncs
  tailf:mount-id fgc-nc-1.0:fgc-nc-1.0;
  tailf:ncs-device-type "netconf";

  yang-version 1.1;
  namespace "urn:3gpp:sa5:_3gpp-nr-nrm-nrfreqrelation";
  prefix nrfreqrel3gpp;

  import _3gpp-common-yang-types {
    prefix types3gpp;
  }
  import _3gpp-common-managed-function {
    prefix mf3gpp;
  }
  import _3gpp-common-managed-element {
    prefix me3gpp;
  }
  import _3gpp-common-top {
    prefix top3gpp;
  }
  import _3gpp-nr-nrm-gnbcucpfunction {
    prefix gnbcucp3gpp;
  }
  import _3gpp-nr-nrm-nrcellcu {
    prefix nrcellcu3gpp;
  }
  import "fgc-nc-1.0" {
    prefix "fgc-nc-1.0";
  }
  import tailf-ncs {
    prefix ncs;
  }
  import tailf-common {
    prefix tailf;
  }

  organization
    "3GPP SA5";
  description
    "Defines the YANG mapping of the NRFreqRelation Information
     Object Class (IOC) that is part of the NR Network Resource Model (NRM).";
  reference "3GPP TS 28.541 5G Network Resource Model (NRM)";

  revision 2019-10-28 {
    reference "S5-193518";
  }
  revision 2019-06-17 {
    description
      "Initial revision";
  }

  grouping ncs_template_NRFreqRelationGrp {
    description
      "Represents the NRFreqRelation IOC.";
    reference "3GPP TS 28.541";
    uses mf3gpp:ncs_template_ManagedFunctionGrp;
    container offsetMO {
      description
        "A set of offset values applicable to all measured cells
         with reference signal(s) indicated in corresponding MeasObjectNR. It
         is used to indicate a cell, beam or measurement object specific offset
         to be applied when evaluating candidates for cell re-selection or when
         evaluating triggering conditions for measurement reporting. It is
         defined for rsrpOffsetSSB, rsrqOffsetSSB, sinrOffsetSSB,
         rsrpOffsetCSI-RS, rsrqOffsetCSI-RS and sinrOffsetCSI-RS.";
      reference "offsetMO in MeasObjectNR in 3GPP TS 38.331";
      leaf rsrpOffsetSsb {
        description
          "Offset value of rsrpOffsetSSB.";
        // NCS drop default statement
        type string;
      }
      leaf rsrqOffsetSsb {
        description
          "Offset value of rsrqOffsetSSB.";
        // NCS drop default statement
        type string;
      }
      leaf sinrOffsetSsb {
        description
          "Offset value of sinrOffsetSSB.";
        // NCS drop default statement
        type string;
      }
      leaf rsrpOffsetCsiRs {
        description
          "Offset value of rsrpOffsetCSI-RS.";
        // NCS drop default statement
        type string;
      }
      leaf rsrqOffsetCsiRs {
        description
          "Offset value of rsrqOffsetCSI-RS.";
        // NCS drop default statement
        type string;
      }
      leaf sinrOffsetCsiRs {
        description
          "Offset value of sinrOffsetCSI-RS.";
        // NCS drop default statement
        type string;
      }
    }
    leaf-list blackListEntry {
      // NCS patched for predictable order
      ordered-by user;
      description
        "A list of Physical Cell Identities (PCIs) that are
         blacklisted in NR measurements.";
      reference "3GPP TS 38.331";
      // NCS drop min-elements statement
      type string;
    }
    leaf-list blackListEntryIdleMode {
      // NCS patched for predictable order
      ordered-by user;
      description
        "A list of Physical Cell Identities (PCIs) that are
         blacklisted in SIB4 and SIB5.";
      // NCS drop min-elements statement
      type string;
    }
    leaf cellReselectionPriority {
      description
        "The absolute priority of the carrier frequency used by the
         cell reselection procedure. Value 0 means lowest priority. The value
         must not already used by other RAT, i.e. equal priorities between RATs
         are not supported. The UE behaviour when no value is entered is
         specified in subclause 5.2.4.1 of 3GPP TS 38.304.";
      reference
        "CellReselectionPriority in 3GPP TS 38.331, priority in
         3GPP TS 38.304";
      type string;
      // NCS drop default statement
    }
    leaf cellReselectionSubPriority {
      description
        "Indicates a fractional value to be added to the value of
         cellReselectionPriority to obtain the absolute priority of the
         concerned carrier frequency for E-UTRA and NR.";
      reference "3GPP TS 38.331";
      type string;
      units "0.1";
    }
    leaf pMax {
      description
        "Used for calculation of the parameter Pcompensation
         (defined in 3GPP TS 38.304), at cell reselection to a cell.";
      reference "PEMAX in 3GPP TS 38.101";
      // NCS drop mandatory statement
      type string;
      units "dBm";
    }
    leaf qOffsetFreq {
      description
        "The frequency specific offset applied when evaluating
         candidates for cell reselection.";
      // NCS drop mandatory statement
      type string;
      // NCS drop default statement
    }
    leaf qQualMin {
      description
        "Indicates the minimum required quality level in the cell.
         Value 0 means that it is not sent and UE applies in such case the
         (default) value of negative infinity for Qqualmin. Sent in SIB3 or
         SIB5.";
      reference "3GPP TS 38.304";
      type string;
      units "dB";
      // NCS drop default statement
    }
    leaf qRxLevMin {
      description
        "Indicates the required minimum received Reference Symbol
         Received Power (RSRP) level in the NR frequency for cell reselection.
         Broadcast in SIB3 or SIB5, depending on whether the related frequency
         is intra- or inter-frequency. Resolution is 2.";
      reference "3GPP TS 38.304";
      // NCS drop mandatory statement
      type string;
      units "dBm";
    }
    leaf threshXHighP {
      description
        "Specifies the Srxlev threshold used by the UE when
         reselecting towards a higher priority RAT/frequency than the current
         serving frequency. Each frequency of NR and E-UTRAN might have a
         specific threshold. Resolution is 2.";
      reference "ThreshX, HighP in 3GPP TS 38.304";
      // NCS drop mandatory statement
      type string;
      units "dB";
    }
    leaf threshXHighQ {
      description
        "Specifies the Squal threshold used by the UE when
         reselecting towards a higher priority RAT/frequency than the current
         serving frequency. Each frequency of NR and E-UTRAN might have a
         specific threshold.";
      reference "ThreshX, HighQ in 3GPP TS 38.304";
      // NCS drop mandatory statement
      type string;
      units "dB";
    }
    leaf threshXLowP {
      description
        "Specifies the Srxlev threshold used by the UE when
         reselecting towards a lower priority RAT/frequency than the current
         serving frequency. Each frequency of NR and E-UTRAN might have a
         specific threshold. Resolution is 2.";
      reference "ThreshX, LowP in 3GPP TS 38.304";
      // NCS drop mandatory statement
      type string;
      units "dB";
    }
    leaf threshXLowQ {
      description
        "Specifies the Squal threshold used by the UE when
         reselecting towards a lower priority RAT/frequency than the current
         serving frequency. Each frequency of NR and E-UTRAN might have a
         specific threshold.";
      reference "ThreshX, LowQ in 3GPP TS 38.304";
      // NCS drop mandatory statement
      type string;
      units "dB";
    }
    leaf tReselectionNR {
      description
        "Cell reselection timer for NR.";
      reference "TreselectionRAT for NR in 3GPP TS 38.331";
      // NCS drop mandatory statement
      type string;
      units "s";
    }
    leaf tReselectionNRSfHigh {
      description
        "The attribute tReselectionNr (parameter TreselectionNR in
         3GPP TS 38.304) is multiplied with this scaling factor if the UE is
         in high mobility state.";
      reference
        "Speed dependent ScalingFactor for TreselectionNR for high
         mobility state in 3GPP TS 38.304";
      // NCS drop mandatory statement
      type string;
      units "%";
    }
    leaf tReselectionNRSfMedium {
      description
        "The attribute tReselectionNr (parameter TreselectionNR in
         3GPP TS 38.304) multiplied with this scaling factor if the UE is in
         medium mobility state.";
      reference
        "Speed dependent ScalingFactor for TreselectionNR for medium
         mobility state in 3GPP TS 38.304";
      // NCS drop mandatory statement
      type string;
      units "%";
    }
    leaf nRFrequencyRef {
      description
        "Reference to a corresponding NRFrequency instance.";
      // NCS drop mandatory statement
      type string;
    }
  }

  grouping ncs_rpc_notif_NRFreqRelationGrp {
    description
      "Represents the NRFreqRelation IOC.";
    reference "3GPP TS 28.541";
    uses mf3gpp:ncs_rpc_notif_ManagedFunctionGrp;
    container offsetMO {
      description
        "A set of offset values applicable to all measured cells
         with reference signal(s) indicated in corresponding MeasObjectNR. It
         is used to indicate a cell, beam or measurement object specific offset
         to be applied when evaluating candidates for cell re-selection or when
         evaluating triggering conditions for measurement reporting. It is
         defined for rsrpOffsetSSB, rsrqOffsetSSB, sinrOffsetSSB,
         rsrpOffsetCSI-RS, rsrqOffsetCSI-RS and sinrOffsetCSI-RS.";
      reference "offsetMO in MeasObjectNR in 3GPP TS 38.331";
      leaf rsrpOffsetSsb {
        description
          "Offset value of rsrpOffsetSSB.";
        default "0";
        type types3gpp:QOffsetRange;
      }
      leaf rsrqOffsetSsb {
        description
          "Offset value of rsrqOffsetSSB.";
        default "0";
        type types3gpp:QOffsetRange;
      }
      leaf sinrOffsetSsb {
        description
          "Offset value of sinrOffsetSSB.";
        default "0";
        type types3gpp:QOffsetRange;
      }
      leaf rsrpOffsetCsiRs {
        description
          "Offset value of rsrpOffsetCSI-RS.";
        default "0";
        type types3gpp:QOffsetRange;
      }
      leaf rsrqOffsetCsiRs {
        description
          "Offset value of rsrqOffsetCSI-RS.";
        default "0";
        type types3gpp:QOffsetRange;
      }
      leaf sinrOffsetCsiRs {
        description
          "Offset value of sinrOffsetCSI-RS.";
        default "0";
        type types3gpp:QOffsetRange;
      }
    }
    leaf-list blackListEntry {
      description
        "A list of Physical Cell Identities (PCIs) that are
         blacklisted in NR measurements.";
      reference "3GPP TS 38.331";
      min-elements 0;
      type uint16 {
        range "0..1007";
      }
    }
    leaf-list blackListEntryIdleMode {
      description
        "A list of Physical Cell Identities (PCIs) that are
         blacklisted in SIB4 and SIB5.";
      min-elements 0;
      type uint16 {
        range "0..1007";
      }
    }
    leaf cellReselectionPriority {
      description
        "The absolute priority of the carrier frequency used by the
         cell reselection procedure. Value 0 means lowest priority. The value
         must not already used by other RAT, i.e. equal priorities between RATs
         are not supported. The UE behaviour when no value is entered is
         specified in subclause 5.2.4.1 of 3GPP TS 38.304.";
      reference
        "CellReselectionPriority in 3GPP TS 38.331, priority in
         3GPP TS 38.304";
      type uint32;
      default "0";
    }
    leaf cellReselectionSubPriority {
      description
        "Indicates a fractional value to be added to the value of
         cellReselectionPriority to obtain the absolute priority of the
         concerned carrier frequency for E-UTRA and NR.";
      reference "3GPP TS 38.331";
      type uint8 {
        range "2 | 4 | 6 | 8";
      }
      units "0.1";
    }
    leaf pMax {
      description
        "Used for calculation of the parameter Pcompensation
         (defined in 3GPP TS 38.304), at cell reselection to a cell.";
      reference "PEMAX in 3GPP TS 38.101";
      mandatory false;
      type int32 {
        range "-30..33";
      }
      units "dBm";
    }
    leaf qOffsetFreq {
      description
        "The frequency specific offset applied when evaluating
         candidates for cell reselection.";
      mandatory false;
      type types3gpp:QOffsetRange;
      default "0";
    }
    leaf qQualMin {
      description
        "Indicates the minimum required quality level in the cell.
         Value 0 means that it is not sent and UE applies in such case the
         (default) value of negative infinity for Qqualmin. Sent in SIB3 or
         SIB5.";
      reference "3GPP TS 38.304";
      type int32 {
        range "-34..-3 | 0";
      }
      units "dB";
      default "0";
    }
    leaf qRxLevMin {
      description
        "Indicates the required minimum received Reference Symbol
         Received Power (RSRP) level in the NR frequency for cell reselection.
         Broadcast in SIB3 or SIB5, depending on whether the related frequency
         is intra- or inter-frequency. Resolution is 2.";
      reference "3GPP TS 38.304";
      mandatory true;
      type int32 {
        range "-140..-44";
      }
      units "dBm";
    }
    leaf threshXHighP {
      description
        "Specifies the Srxlev threshold used by the UE when
         reselecting towards a higher priority RAT/frequency than the current
         serving frequency. Each frequency of NR and E-UTRAN might have a
         specific threshold. Resolution is 2.";
      reference "ThreshX, HighP in 3GPP TS 38.304";
      mandatory true;
      type int32 {
        range "0..62";
      }
      units "dB";
    }
    leaf threshXHighQ {
      description
        "Specifies the Squal threshold used by the UE when
         reselecting towards a higher priority RAT/frequency than the current
         serving frequency. Each frequency of NR and E-UTRAN might have a
         specific threshold.";
      reference "ThreshX, HighQ in 3GPP TS 38.304";
      mandatory true;
      type int32 {
        range "0..31";
      }
      units "dB";
    }
    leaf threshXLowP {
      description
        "Specifies the Srxlev threshold used by the UE when
         reselecting towards a lower priority RAT/frequency than the current
         serving frequency. Each frequency of NR and E-UTRAN might have a
         specific threshold. Resolution is 2.";
      reference "ThreshX, LowP in 3GPP TS 38.304";
      mandatory true;
      type int32 {
        range "0..62";
      }
      units "dB";
    }
    leaf threshXLowQ {
      description
        "Specifies the Squal threshold used by the UE when
         reselecting towards a lower priority RAT/frequency than the current
         serving frequency. Each frequency of NR and E-UTRAN might have a
         specific threshold.";
      reference "ThreshX, LowQ in 3GPP TS 38.304";
      mandatory true;
      type int32 {
        range "0..31";
      }
      units "dB";
    }
    leaf tReselectionNR {
      description
        "Cell reselection timer for NR.";
      reference "TreselectionRAT for NR in 3GPP TS 38.331";
      mandatory true;
      type int32 {
        range "0..7";
      }
      units "s";
    }
    leaf tReselectionNRSfHigh {
      description
        "The attribute tReselectionNr (parameter TreselectionNR in
         3GPP TS 38.304) is multiplied with this scaling factor if the UE is
         in high mobility state.";
      reference
        "Speed dependent ScalingFactor for TreselectionNR for high
         mobility state in 3GPP TS 38.304";
      mandatory true;
      type uint8 {
        range "25 | 50 | 75 | 100";
      }
      units "%";
    }
    leaf tReselectionNRSfMedium {
      description
        "The attribute tReselectionNr (parameter TreselectionNR in
         3GPP TS 38.304) multiplied with this scaling factor if the UE is in
         medium mobility state.";
      reference
        "Speed dependent ScalingFactor for TreselectionNR for medium
         mobility state in 3GPP TS 38.304";
      mandatory true;
      type uint8 {
        range "25 | 50 | 75 | 100";
      }
      units "%";
    }
    leaf nRFrequencyRef {
      description
        "Reference to a corresponding NRFrequency instance.";
      mandatory true;
      type types3gpp:DistinguishedName;
    }
  }

  grouping live_ncs_NRFreqRelationGrp {
    description
      "Represents the NRFreqRelation IOC.";
    reference "3GPP TS 28.541";
    uses mf3gpp:live_ncs_ManagedFunctionGrp;
    container offsetMO {
      description
        "A set of offset values applicable to all measured cells
         with reference signal(s) indicated in corresponding MeasObjectNR. It
         is used to indicate a cell, beam or measurement object specific offset
         to be applied when evaluating candidates for cell re-selection or when
         evaluating triggering conditions for measurement reporting. It is
         defined for rsrpOffsetSSB, rsrqOffsetSSB, sinrOffsetSSB,
         rsrpOffsetCSI-RS, rsrqOffsetCSI-RS and sinrOffsetCSI-RS.";
      reference "offsetMO in MeasObjectNR in 3GPP TS 38.331";
      leaf rsrpOffsetSsb {
        description
          "Offset value of rsrpOffsetSSB.";
        // NCS drop default statement
        type types3gpp:QOffsetRange;
      }
      leaf rsrqOffsetSsb {
        description
          "Offset value of rsrqOffsetSSB.";
        // NCS drop default statement
        type types3gpp:QOffsetRange;
      }
      leaf sinrOffsetSsb {
        description
          "Offset value of sinrOffsetSSB.";
        // NCS drop default statement
        type types3gpp:QOffsetRange;
      }
      leaf rsrpOffsetCsiRs {
        description
          "Offset value of rsrpOffsetCSI-RS.";
        // NCS drop default statement
        type types3gpp:QOffsetRange;
      }
      leaf rsrqOffsetCsiRs {
        description
          "Offset value of rsrqOffsetCSI-RS.";
        // NCS drop default statement
        type types3gpp:QOffsetRange;
      }
      leaf sinrOffsetCsiRs {
        description
          "Offset value of sinrOffsetCSI-RS.";
        // NCS drop default statement
        type types3gpp:QOffsetRange;
      }
    }
    leaf-list blackListEntry {
      description
        "A list of Physical Cell Identities (PCIs) that are
         blacklisted in NR measurements.";
      reference "3GPP TS 38.331";
      // NCS drop min-elements statement
      type uint16 {
        range "0..1007";
      }
    }
    leaf-list blackListEntryIdleMode {
      description
        "A list of Physical Cell Identities (PCIs) that are
         blacklisted in SIB4 and SIB5.";
      // NCS drop min-elements statement
      type uint16 {
        range "0..1007";
      }
    }
    leaf cellReselectionPriority {
      description
        "The absolute priority of the carrier frequency used by the
         cell reselection procedure. Value 0 means lowest priority. The value
         must not already used by other RAT, i.e. equal priorities between RATs
         are not supported. The UE behaviour when no value is entered is
         specified in subclause 5.2.4.1 of 3GPP TS 38.304.";
      reference
        "CellReselectionPriority in 3GPP TS 38.331, priority in
         3GPP TS 38.304";
      type uint32;
      // NCS drop default statement
    }
    leaf cellReselectionSubPriority {
      description
        "Indicates a fractional value to be added to the value of
         cellReselectionPriority to obtain the absolute priority of the
         concerned carrier frequency for E-UTRA and NR.";
      reference "3GPP TS 38.331";
      type uint8 {
        range "2 | 4 | 6 | 8";
      }
      units "0.1";
    }
    leaf pMax {
      description
        "Used for calculation of the parameter Pcompensation
         (defined in 3GPP TS 38.304), at cell reselection to a cell.";
      reference "PEMAX in 3GPP TS 38.101";
      // NCS drop mandatory statement
      type int32 {
        range "-30..33";
      }
      units "dBm";
    }
    leaf qOffsetFreq {
      description
        "The frequency specific offset applied when evaluating
         candidates for cell reselection.";
      // NCS drop mandatory statement
      type types3gpp:QOffsetRange;
      // NCS drop default statement
    }
    leaf qQualMin {
      description
        "Indicates the minimum required quality level in the cell.
         Value 0 means that it is not sent and UE applies in such case the
         (default) value of negative infinity for Qqualmin. Sent in SIB3 or
         SIB5.";
      reference "3GPP TS 38.304";
      type int32 {
        range "-34..-3 | 0";
      }
      units "dB";
      // NCS drop default statement
    }
    leaf qRxLevMin {
      description
        "Indicates the required minimum received Reference Symbol
         Received Power (RSRP) level in the NR frequency for cell reselection.
         Broadcast in SIB3 or SIB5, depending on whether the related frequency
         is intra- or inter-frequency. Resolution is 2.";
      reference "3GPP TS 38.304";
      // NCS drop mandatory statement
      type int32 {
        range "-140..-44";
      }
      units "dBm";
    }
    leaf threshXHighP {
      description
        "Specifies the Srxlev threshold used by the UE when
         reselecting towards a higher priority RAT/frequency than the current
         serving frequency. Each frequency of NR and E-UTRAN might have a
         specific threshold. Resolution is 2.";
      reference "ThreshX, HighP in 3GPP TS 38.304";
      // NCS drop mandatory statement
      type int32 {
        range "0..62";
      }
      units "dB";
    }
    leaf threshXHighQ {
      description
        "Specifies the Squal threshold used by the UE when
         reselecting towards a higher priority RAT/frequency than the current
         serving frequency. Each frequency of NR and E-UTRAN might have a
         specific threshold.";
      reference "ThreshX, HighQ in 3GPP TS 38.304";
      // NCS drop mandatory statement
      type int32 {
        range "0..31";
      }
      units "dB";
    }
    leaf threshXLowP {
      description
        "Specifies the Srxlev threshold used by the UE when
         reselecting towards a lower priority RAT/frequency than the current
         serving frequency. Each frequency of NR and E-UTRAN might have a
         specific threshold. Resolution is 2.";
      reference "ThreshX, LowP in 3GPP TS 38.304";
      // NCS drop mandatory statement
      type int32 {
        range "0..62";
      }
      units "dB";
    }
    leaf threshXLowQ {
      description
        "Specifies the Squal threshold used by the UE when
         reselecting towards a lower priority RAT/frequency than the current
         serving frequency. Each frequency of NR and E-UTRAN might have a
         specific threshold.";
      reference "ThreshX, LowQ in 3GPP TS 38.304";
      // NCS drop mandatory statement
      type int32 {
        range "0..31";
      }
      units "dB";
    }
    leaf tReselectionNR {
      description
        "Cell reselection timer for NR.";
      reference "TreselectionRAT for NR in 3GPP TS 38.331";
      // NCS drop mandatory statement
      type int32 {
        range "0..7";
      }
      units "s";
    }
    leaf tReselectionNRSfHigh {
      description
        "The attribute tReselectionNr (parameter TreselectionNR in
         3GPP TS 38.304) is multiplied with this scaling factor if the UE is
         in high mobility state.";
      reference
        "Speed dependent ScalingFactor for TreselectionNR for high
         mobility state in 3GPP TS 38.304";
      // NCS drop mandatory statement
      type uint8 {
        range "25 | 50 | 75 | 100";
      }
      units "%";
    }
    leaf tReselectionNRSfMedium {
      description
        "The attribute tReselectionNr (parameter TreselectionNR in
         3GPP TS 38.304) multiplied with this scaling factor if the UE is in
         medium mobility state.";
      reference
        "Speed dependent ScalingFactor for TreselectionNR for medium
         mobility state in 3GPP TS 38.304";
      // NCS drop mandatory statement
      type uint8 {
        range "25 | 50 | 75 | 100";
      }
      units "%";
    }
    leaf nRFrequencyRef {
      description
        "Reference to a corresponding NRFrequency instance.";
      // NCS drop mandatory statement
      type types3gpp:DistinguishedName;
    }
  }

  grouping NRFreqRelationGrp {
    description
      "Represents the NRFreqRelation IOC.";
    reference "3GPP TS 28.541";
    uses mf3gpp:ManagedFunctionGrp;
    container offsetMO {
      description
        "A set of offset values applicable to all measured cells
         with reference signal(s) indicated in corresponding MeasObjectNR. It
         is used to indicate a cell, beam or measurement object specific offset
         to be applied when evaluating candidates for cell re-selection or when
         evaluating triggering conditions for measurement reporting. It is
         defined for rsrpOffsetSSB, rsrqOffsetSSB, sinrOffsetSSB,
         rsrpOffsetCSI-RS, rsrqOffsetCSI-RS and sinrOffsetCSI-RS.";
      reference "offsetMO in MeasObjectNR in 3GPP TS 38.331";
      leaf rsrpOffsetSsb {
        description
          "Offset value of rsrpOffsetSSB.";
        default "0";
        type types3gpp:QOffsetRange;
      }
      leaf rsrqOffsetSsb {
        description
          "Offset value of rsrqOffsetSSB.";
        default "0";
        type types3gpp:QOffsetRange;
      }
      leaf sinrOffsetSsb {
        description
          "Offset value of sinrOffsetSSB.";
        default "0";
        type types3gpp:QOffsetRange;
      }
      leaf rsrpOffsetCsiRs {
        description
          "Offset value of rsrpOffsetCSI-RS.";
        default "0";
        type types3gpp:QOffsetRange;
      }
      leaf rsrqOffsetCsiRs {
        description
          "Offset value of rsrqOffsetCSI-RS.";
        default "0";
        type types3gpp:QOffsetRange;
      }
      leaf sinrOffsetCsiRs {
        description
          "Offset value of sinrOffsetCSI-RS.";
        default "0";
        type types3gpp:QOffsetRange;
      }
    }
    leaf-list blackListEntry {
      description
        "A list of Physical Cell Identities (PCIs) that are
         blacklisted in NR measurements.";
      reference "3GPP TS 38.331";
      min-elements 0;
      type uint16 {
        range "0..1007";
      }
    }
    leaf-list blackListEntryIdleMode {
      description
        "A list of Physical Cell Identities (PCIs) that are
         blacklisted in SIB4 and SIB5.";
      min-elements 0;
      type uint16 {
        range "0..1007";
      }
    }
    leaf cellReselectionPriority {
      description
        "The absolute priority of the carrier frequency used by the
         cell reselection procedure. Value 0 means lowest priority. The value
         must not already used by other RAT, i.e. equal priorities between RATs
         are not supported. The UE behaviour when no value is entered is
         specified in subclause 5.2.4.1 of 3GPP TS 38.304.";
      reference
        "CellReselectionPriority in 3GPP TS 38.331, priority in
         3GPP TS 38.304";
      type uint32;
      default "0";
    }
    leaf cellReselectionSubPriority {
      description
        "Indicates a fractional value to be added to the value of
         cellReselectionPriority to obtain the absolute priority of the
         concerned carrier frequency for E-UTRA and NR.";
      reference "3GPP TS 38.331";
      type uint8 {
        range "2 | 4 | 6 | 8";
      }
      units "0.1";
    }
    leaf pMax {
      description
        "Used for calculation of the parameter Pcompensation
         (defined in 3GPP TS 38.304), at cell reselection to a cell.";
      reference "PEMAX in 3GPP TS 38.101";
      mandatory false;
      type int32 {
        range "-30..33";
      }
      units "dBm";
    }
    leaf qOffsetFreq {
      description
        "The frequency specific offset applied when evaluating
         candidates for cell reselection.";
      mandatory false;
      type types3gpp:QOffsetRange;
      default "0";
    }
    leaf qQualMin {
      description
        "Indicates the minimum required quality level in the cell.
         Value 0 means that it is not sent and UE applies in such case the
         (default) value of negative infinity for Qqualmin. Sent in SIB3 or
         SIB5.";
      reference "3GPP TS 38.304";
      type int32 {
        range "-34..-3 | 0";
      }
      units "dB";
      default "0";
    }
    leaf qRxLevMin {
      description
        "Indicates the required minimum received Reference Symbol
         Received Power (RSRP) level in the NR frequency for cell reselection.
         Broadcast in SIB3 or SIB5, depending on whether the related frequency
         is intra- or inter-frequency. Resolution is 2.";
      reference "3GPP TS 38.304";
      mandatory true;
      type int32 {
        range "-140..-44";
      }
      units "dBm";
    }
    leaf threshXHighP {
      description
        "Specifies the Srxlev threshold used by the UE when
         reselecting towards a higher priority RAT/frequency than the current
         serving frequency. Each frequency of NR and E-UTRAN might have a
         specific threshold. Resolution is 2.";
      reference "ThreshX, HighP in 3GPP TS 38.304";
      mandatory true;
      type int32 {
        range "0..62";
      }
      units "dB";
    }
    leaf threshXHighQ {
      description
        "Specifies the Squal threshold used by the UE when
         reselecting towards a higher priority RAT/frequency than the current
         serving frequency. Each frequency of NR and E-UTRAN might have a
         specific threshold.";
      reference "ThreshX, HighQ in 3GPP TS 38.304";
      mandatory true;
      type int32 {
        range "0..31";
      }
      units "dB";
    }
    leaf threshXLowP {
      description
        "Specifies the Srxlev threshold used by the UE when
         reselecting towards a lower priority RAT/frequency than the current
         serving frequency. Each frequency of NR and E-UTRAN might have a
         specific threshold. Resolution is 2.";
      reference "ThreshX, LowP in 3GPP TS 38.304";
      mandatory true;
      type int32 {
        range "0..62";
      }
      units "dB";
    }
    leaf threshXLowQ {
      description
        "Specifies the Squal threshold used by the UE when
         reselecting towards a lower priority RAT/frequency than the current
         serving frequency. Each frequency of NR and E-UTRAN might have a
         specific threshold.";
      reference "ThreshX, LowQ in 3GPP TS 38.304";
      mandatory true;
      type int32 {
        range "0..31";
      }
      units "dB";
    }
    leaf tReselectionNR {
      description
        "Cell reselection timer for NR.";
      reference "TreselectionRAT for NR in 3GPP TS 38.331";
      mandatory true;
      type int32 {
        range "0..7";
      }
      units "s";
    }
    leaf tReselectionNRSfHigh {
      description
        "The attribute tReselectionNr (parameter TreselectionNR in
         3GPP TS 38.304) is multiplied with this scaling factor if the UE is
         in high mobility state.";
      reference
        "Speed dependent ScalingFactor for TreselectionNR for high
         mobility state in 3GPP TS 38.304";
      mandatory true;
      type uint8 {
        range "25 | 50 | 75 | 100";
      }
      units "%";
    }
    leaf tReselectionNRSfMedium {
      description
        "The attribute tReselectionNr (parameter TreselectionNR in
         3GPP TS 38.304) multiplied with this scaling factor if the UE is in
         medium mobility state.";
      reference
        "Speed dependent ScalingFactor for TreselectionNR for medium
         mobility state in 3GPP TS 38.304";
      mandatory true;
      type uint8 {
        range "25 | 50 | 75 | 100";
      }
      units "%";
    }
    leaf nRFrequencyRef {
      description
        "Reference to a corresponding NRFrequency instance.";
      mandatory true;
      type types3gpp:DistinguishedName;
    }
  }

  augment "/ncs:devices/ncs:template/ncs:ned-id/ncs:config/me3gpp:ManagedElement/gnbcucp3gpp:GNBCUCPFunction/nrcellcu3gpp:NRCellCU" {
    list NRFreqRelation {
      // NCS patched for predictable order
      ordered-by user;
      description
        "Together with the target NRFrequency, it represents the
         frequency properties applicable to the referencing NRFreqRelation.";
      reference "3GPP TS 28.541";
      key "id";
      uses top3gpp:ncs_template_Top_Grp;
      container attributes {
        uses ncs_template_NRFreqRelationGrp;
      }
      uses mf3gpp:ncs_template_ManagedFunctionContainedClasses;
    }
  }
  augment "/ncs:devices/ncs:device/ncs:live-status/me3gpp:ManagedElement/gnbcucp3gpp:GNBCUCPFunction/nrcellcu3gpp:NRCellCU" {
    list NRFreqRelation {
      tailf:ncs-device-type "netconf";
      tailf:display-when "not(../../../../ncs:module) or ../../../../ncs:module[ncs:name='_3gpp-nr-nrm-nrfreqrelation'] or (../../../../ncs:live-status-protocol[not(ncs:capability)]) or (../../../../ncs:live-status-protocol/ncs:capability/ncs:module[.='_3gpp-nr-nrm-nrfreqrelation'])";
      description
        "Together with the target NRFrequency, it represents the
         frequency properties applicable to the referencing NRFreqRelation.";
      reference "3GPP TS 28.541";
      key "id";
      uses top3gpp:live_ncs_Top_Grp;
      container attributes {
        uses live_ncs_NRFreqRelationGrp;
      }
      uses mf3gpp:live_ncs_ManagedFunctionContainedClasses;
    }
  }
  augment "/ncs:devices/ncs:device/ncs:config/me3gpp:ManagedElement/gnbcucp3gpp:GNBCUCPFunction/nrcellcu3gpp:NRCellCU" {
    list NRFreqRelation {
      tailf:ncs-device-type "netconf";
      tailf:display-when "not(../../../../ncs:module) or ../../../../ncs:module[ncs:name='_3gpp-nr-nrm-nrfreqrelation']";
      description
        "Together with the target NRFrequency, it represents the
         frequency properties applicable to the referencing NRFreqRelation.";
      reference "3GPP TS 28.541";
      key "id";
      uses top3gpp:Top_Grp;
      container attributes {
        uses NRFreqRelationGrp;
      }
      uses mf3gpp:ManagedFunctionContainedClasses;
    }
  }
}
