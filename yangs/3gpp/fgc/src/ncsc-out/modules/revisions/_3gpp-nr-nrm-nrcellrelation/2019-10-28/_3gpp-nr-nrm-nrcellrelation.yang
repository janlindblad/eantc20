module _3gpp-nr-nrm-nrcellrelation {
  // Generated by yanger -t ncs
  tailf:mount-id fgc-nc-1.0:fgc-nc-1.0;
  tailf:ncs-device-type "netconf";

  yang-version 1.1;
  namespace "urn:3gpp:sa5:_3gpp-nr-nrm-nrcellrelation";
  prefix nrcellrel3gpp;

  import _3gpp-common-yang-types {
    prefix types3gpp;
  }
  import _3gpp-common-managed-function {
    prefix mf3gpp;
  }
  import _3gpp-common-managed-element {
    prefix me3gpp;
  }
  import _3gpp-common-top {
    prefix top3gpp;
  }
  import _3gpp-nr-nrm-gnbcucpfunction {
    prefix gnbcucp3gpp;
  }
  import _3gpp-nr-nrm-nrcellcu {
    prefix nrcellcu3gpp;
  }
  import "fgc-nc-1.0" {
    prefix "fgc-nc-1.0";
  }
  import tailf-ncs {
    prefix ncs;
  }
  import tailf-common {
    prefix tailf;
  }

  organization
    "3GPP SA5";
  description
    "Defines the YANG mapping of the NRCellRelation Information
     Object Class (IOC) that is part of the NR Network Resource Model (NRM).";
  reference "3GPP TS 28.541 5G Network Resource Model (NRM)";

  revision 2019-10-28 {
    reference "S5-193518";
  }
  revision 2019-08-30 {
    description
      "Initial revision";
  }

  grouping ncs_template_NRCellRelationGrp {
    description
      "Represents the NRCellRelation IOC.";
    reference "3GPP TS 28.541";
    uses mf3gpp:ncs_template_ManagedFunctionGrp;
    leaf nRTCI {
      description
        "Target NR Cell Identifier. It consists of NR Cell
         Identifier (NCI) and Physical Cell Identifier of the target NR cell
         (nRPCI).";
      type string;
    }
    container cellIndividualOffset {
      description
        "A set of offset values for the neighbour cell. Used when
         UE is in connected mode. Defined for rsrpOffsetSSB, rsrqOffsetSSB,
         sinrOffsetSSB, rsrpOffsetCSI-RS, rsrqOffsetCSI-RS and
         sinrOffsetCSI-RS.";
      reference "cellIndividualOffset in MeasObjectNR in 3GPP TS 38.331";
      leaf rsrpOffsetSsb {
        description
          "Offset value of rsrpOffsetSSB.";
        // NCS drop default statement
        type string;
      }
      leaf rsrqOffsetSsb {
        description
          "Offset value of rsrqOffsetSSB.";
        // NCS drop default statement
        type string;
      }
      leaf sinrOffsetSsb {
        description
          "Offset value of sinrOffsetSSB.";
        // NCS drop default statement
        type string;
      }
      leaf rsrpOffsetCsiRs {
        description
          "Offset value of rsrpOffsetCSI-RS.";
        // NCS drop default statement
        type string;
      }
      leaf rsrqOffsetCsiRs {
        description
          "Offset value of rsrqOffsetCSI-RS.";
        // NCS drop default statement
        type string;
      }
      leaf sinrOffsetCsiRs {
        description
          "Offset value of sinrOffsetCSI-RS.";
        // NCS drop default statement
        type string;
      }
    }
    leaf nRFreqRelationRef {
      description
        "Reference to a corresponding NRFreqRelation instance.";
      // NCS drop mandatory statement
      type string;
    }
    leaf adjacentNRCellRef {
      description
        "Reference to an adjacent NR cell (NRCellCU or
         ExternalNRCellCU).";
      // NCS drop mandatory statement
      type string;
    }
    leaf isRemoveAllowed {
      type string;
      // NCS drop default statement
      description
        "True if the ANR function in the node is allowed to remove this relation.";
    }
    leaf isHOAllowed {
      type string;
      // NCS drop default statement
      description
        "True if handovers are allowed over this relation.";
    }
  }

  grouping ncs_rpc_notif_NRCellRelationGrp {
    description
      "Represents the NRCellRelation IOC.";
    reference "3GPP TS 28.541";
    uses mf3gpp:ncs_rpc_notif_ManagedFunctionGrp;
    leaf nRTCI {
      description
        "Target NR Cell Identifier. It consists of NR Cell
         Identifier (NCI) and Physical Cell Identifier of the target NR cell
         (nRPCI).";
      type uint64;
    }
    container cellIndividualOffset {
      description
        "A set of offset values for the neighbour cell. Used when
         UE is in connected mode. Defined for rsrpOffsetSSB, rsrqOffsetSSB,
         sinrOffsetSSB, rsrpOffsetCSI-RS, rsrqOffsetCSI-RS and
         sinrOffsetCSI-RS.";
      reference "cellIndividualOffset in MeasObjectNR in 3GPP TS 38.331";
      leaf rsrpOffsetSsb {
        description
          "Offset value of rsrpOffsetSSB.";
        default "0";
        type types3gpp:QOffsetRange;
      }
      leaf rsrqOffsetSsb {
        description
          "Offset value of rsrqOffsetSSB.";
        default "0";
        type types3gpp:QOffsetRange;
      }
      leaf sinrOffsetSsb {
        description
          "Offset value of sinrOffsetSSB.";
        default "0";
        type types3gpp:QOffsetRange;
      }
      leaf rsrpOffsetCsiRs {
        description
          "Offset value of rsrpOffsetCSI-RS.";
        default "0";
        type types3gpp:QOffsetRange;
      }
      leaf rsrqOffsetCsiRs {
        description
          "Offset value of rsrqOffsetCSI-RS.";
        default "0";
        type types3gpp:QOffsetRange;
      }
      leaf sinrOffsetCsiRs {
        description
          "Offset value of sinrOffsetCSI-RS.";
        default "0";
        type types3gpp:QOffsetRange;
      }
    }
    leaf nRFreqRelationRef {
      description
        "Reference to a corresponding NRFreqRelation instance.";
      mandatory true;
      type types3gpp:DistinguishedName;
    }
    leaf adjacentNRCellRef {
      description
        "Reference to an adjacent NR cell (NRCellCU or
         ExternalNRCellCU).";
      mandatory true;
      type types3gpp:DistinguishedName;
    }
    leaf isRemoveAllowed {
      type boolean;
      default "true";
      description
        "True if the ANR function in the node is allowed to remove this relation.";
    }
    leaf isHOAllowed {
      type boolean;
      default "true";
      description
        "True if handovers are allowed over this relation.";
    }
  }

  grouping live_ncs_NRCellRelationGrp {
    description
      "Represents the NRCellRelation IOC.";
    reference "3GPP TS 28.541";
    uses mf3gpp:live_ncs_ManagedFunctionGrp;
    leaf nRTCI {
      description
        "Target NR Cell Identifier. It consists of NR Cell
         Identifier (NCI) and Physical Cell Identifier of the target NR cell
         (nRPCI).";
      type uint64;
    }
    container cellIndividualOffset {
      description
        "A set of offset values for the neighbour cell. Used when
         UE is in connected mode. Defined for rsrpOffsetSSB, rsrqOffsetSSB,
         sinrOffsetSSB, rsrpOffsetCSI-RS, rsrqOffsetCSI-RS and
         sinrOffsetCSI-RS.";
      reference "cellIndividualOffset in MeasObjectNR in 3GPP TS 38.331";
      leaf rsrpOffsetSsb {
        description
          "Offset value of rsrpOffsetSSB.";
        // NCS drop default statement
        type types3gpp:QOffsetRange;
      }
      leaf rsrqOffsetSsb {
        description
          "Offset value of rsrqOffsetSSB.";
        // NCS drop default statement
        type types3gpp:QOffsetRange;
      }
      leaf sinrOffsetSsb {
        description
          "Offset value of sinrOffsetSSB.";
        // NCS drop default statement
        type types3gpp:QOffsetRange;
      }
      leaf rsrpOffsetCsiRs {
        description
          "Offset value of rsrpOffsetCSI-RS.";
        // NCS drop default statement
        type types3gpp:QOffsetRange;
      }
      leaf rsrqOffsetCsiRs {
        description
          "Offset value of rsrqOffsetCSI-RS.";
        // NCS drop default statement
        type types3gpp:QOffsetRange;
      }
      leaf sinrOffsetCsiRs {
        description
          "Offset value of sinrOffsetCSI-RS.";
        // NCS drop default statement
        type types3gpp:QOffsetRange;
      }
    }
    leaf nRFreqRelationRef {
      description
        "Reference to a corresponding NRFreqRelation instance.";
      // NCS drop mandatory statement
      type types3gpp:DistinguishedName;
    }
    leaf adjacentNRCellRef {
      description
        "Reference to an adjacent NR cell (NRCellCU or
         ExternalNRCellCU).";
      // NCS drop mandatory statement
      type types3gpp:DistinguishedName;
    }
    leaf isRemoveAllowed {
      type boolean;
      // NCS drop default statement
      description
        "True if the ANR function in the node is allowed to remove this relation.";
    }
    leaf isHOAllowed {
      type boolean;
      // NCS drop default statement
      description
        "True if handovers are allowed over this relation.";
    }
  }

  grouping NRCellRelationGrp {
    description
      "Represents the NRCellRelation IOC.";
    reference "3GPP TS 28.541";
    uses mf3gpp:ManagedFunctionGrp;
    leaf nRTCI {
      description
        "Target NR Cell Identifier. It consists of NR Cell
         Identifier (NCI) and Physical Cell Identifier of the target NR cell
         (nRPCI).";
      type uint64;
    }
    container cellIndividualOffset {
      description
        "A set of offset values for the neighbour cell. Used when
         UE is in connected mode. Defined for rsrpOffsetSSB, rsrqOffsetSSB,
         sinrOffsetSSB, rsrpOffsetCSI-RS, rsrqOffsetCSI-RS and
         sinrOffsetCSI-RS.";
      reference "cellIndividualOffset in MeasObjectNR in 3GPP TS 38.331";
      leaf rsrpOffsetSsb {
        description
          "Offset value of rsrpOffsetSSB.";
        default "0";
        type types3gpp:QOffsetRange;
      }
      leaf rsrqOffsetSsb {
        description
          "Offset value of rsrqOffsetSSB.";
        default "0";
        type types3gpp:QOffsetRange;
      }
      leaf sinrOffsetSsb {
        description
          "Offset value of sinrOffsetSSB.";
        default "0";
        type types3gpp:QOffsetRange;
      }
      leaf rsrpOffsetCsiRs {
        description
          "Offset value of rsrpOffsetCSI-RS.";
        default "0";
        type types3gpp:QOffsetRange;
      }
      leaf rsrqOffsetCsiRs {
        description
          "Offset value of rsrqOffsetCSI-RS.";
        default "0";
        type types3gpp:QOffsetRange;
      }
      leaf sinrOffsetCsiRs {
        description
          "Offset value of sinrOffsetCSI-RS.";
        default "0";
        type types3gpp:QOffsetRange;
      }
    }
    leaf nRFreqRelationRef {
      description
        "Reference to a corresponding NRFreqRelation instance.";
      mandatory true;
      type types3gpp:DistinguishedName;
    }
    leaf adjacentNRCellRef {
      description
        "Reference to an adjacent NR cell (NRCellCU or
         ExternalNRCellCU).";
      mandatory true;
      type types3gpp:DistinguishedName;
    }
    leaf isRemoveAllowed {
      type boolean;
      default "true";
      description
        "True if the ANR function in the node is allowed to remove this relation.";
    }
    leaf isHOAllowed {
      type boolean;
      default "true";
      description
        "True if handovers are allowed over this relation.";
    }
  }

  augment "/ncs:devices/ncs:template/ncs:ned-id/ncs:config/me3gpp:ManagedElement/gnbcucp3gpp:GNBCUCPFunction/nrcellcu3gpp:NRCellCU" {
    list NRCellRelation {
      // NCS patched for predictable order
      ordered-by user;
      description
        "Represents a neighbour cell relation from a source cell
         to a target cell, where the target cell is an NRCellCU or
         ExternalNRCellCU instance.";
      reference "3GPP TS 28.541";
      key "id";
      uses top3gpp:ncs_template_Top_Grp;
      container attributes {
        uses ncs_template_NRCellRelationGrp;
      }
      uses mf3gpp:ncs_template_ManagedFunctionContainedClasses;
    }
  }
  augment "/ncs:devices/ncs:device/ncs:live-status/me3gpp:ManagedElement/gnbcucp3gpp:GNBCUCPFunction/nrcellcu3gpp:NRCellCU" {
    list NRCellRelation {
      tailf:ncs-device-type "netconf";
      tailf:display-when "not(../../../../ncs:module) or ../../../../ncs:module[ncs:name='_3gpp-nr-nrm-nrcellrelation'] or (../../../../ncs:live-status-protocol[not(ncs:capability)]) or (../../../../ncs:live-status-protocol/ncs:capability/ncs:module[.='_3gpp-nr-nrm-nrcellrelation'])";
      description
        "Represents a neighbour cell relation from a source cell
         to a target cell, where the target cell is an NRCellCU or
         ExternalNRCellCU instance.";
      reference "3GPP TS 28.541";
      key "id";
      uses top3gpp:live_ncs_Top_Grp;
      container attributes {
        uses live_ncs_NRCellRelationGrp;
      }
      uses mf3gpp:live_ncs_ManagedFunctionContainedClasses;
    }
  }
  augment "/ncs:devices/ncs:device/ncs:config/me3gpp:ManagedElement/gnbcucp3gpp:GNBCUCPFunction/nrcellcu3gpp:NRCellCU" {
    list NRCellRelation {
      tailf:ncs-device-type "netconf";
      tailf:display-when "not(../../../../ncs:module) or ../../../../ncs:module[ncs:name='_3gpp-nr-nrm-nrcellrelation']";
      description
        "Represents a neighbour cell relation from a source cell
         to a target cell, where the target cell is an NRCellCU or
         ExternalNRCellCU instance.";
      reference "3GPP TS 28.541";
      key "id";
      uses top3gpp:Top_Grp;
      container attributes {
        uses NRCellRelationGrp;
      }
      uses mf3gpp:ManagedFunctionContainedClasses;
    }
  }
}
