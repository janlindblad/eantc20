module _3gpp-nr-nrm-externalupffunction {
  // Generated by yanger -t ncs
  tailf:mount-id fgc-nc-1.0:fgc-nc-1.0;
  tailf:ncs-device-type "netconf";

  yang-version 1.1;
  namespace "urn:3gpp:sa5:_3gpp-nr-nrm-externalupffunction";
  prefix extupf3gpp;

  import _3gpp-common-managed-function {
    prefix mf3gpp;
  }
  import _3gpp-common-subnetwork {
    prefix subnet3gpp;
  }
  import _3gpp-nr-nrm-nrnetwork {
    prefix nrnet3gpp;
  }
  import _3gpp-common-top {
    prefix top3gpp;
  }
  import "fgc-nc-1.0" {
    prefix "fgc-nc-1.0";
  }
  import tailf-ncs {
    prefix ncs;
  }
  import tailf-common {
    prefix tailf;
  }

  organization
    "3GPP SA5";
  description
    "Defines the YANG mapping of the ExternalUPFFunction Information
     Object Class (IOC) that is part of the NR Network Resource Model (NRM).";
  reference "3GPP TS 28.541 5G Network Resource Model (NRM)";

  revision 2019-10-28 {
    reference "S5-193518";
  }
  revision 2019-06-17 {
    description
      "Initial revision";
  }

  grouping ncs_template_ExternalUPFFunctionGrp {
    description
      "Represents the ExternalUPFFunction IOC.";
    reference "3GPP TS 28.541";
    uses mf3gpp:ncs_template_ManagedFunctionGrp;
  }

  grouping ncs_template_ExternalUPFFunctionWrapper {
    list ExternalUPFFunction {
      // NCS patched for predictable order
      ordered-by user;
      description
        "Represents the properties, known by the management
         function, of a UPFFunction managed by another management
         function.";
      reference "3GPP TS 28.541";
      key "id";
      uses top3gpp:ncs_template_Top_Grp;
      container attributes {
        uses ncs_template_ExternalUPFFunctionGrp;
      }
      uses mf3gpp:ncs_template_ManagedFunctionContainedClasses;
    }
  }

  grouping ncs_rpc_notif_ExternalUPFFunctionGrp {
    description
      "Represents the ExternalUPFFunction IOC.";
    reference "3GPP TS 28.541";
    uses mf3gpp:ncs_rpc_notif_ManagedFunctionGrp;
  }

  grouping ncs_rpc_notif_ExternalUPFFunctionWrapper {
    list ExternalUPFFunction {
      description
        "Represents the properties, known by the management
         function, of a UPFFunction managed by another management
         function.";
      reference "3GPP TS 28.541";
      key "id";
      uses top3gpp:ncs_rpc_notif_Top_Grp;
      container attributes {
        uses ncs_rpc_notif_ExternalUPFFunctionGrp;
      }
      uses mf3gpp:ncs_rpc_notif_ManagedFunctionContainedClasses;
    }
  }

  grouping live_ncs_ExternalUPFFunctionGrp {
    description
      "Represents the ExternalUPFFunction IOC.";
    reference "3GPP TS 28.541";
    uses mf3gpp:live_ncs_ManagedFunctionGrp;
  }

  grouping live_ncs_ExternalUPFFunctionWrapper {
    list ExternalUPFFunction {
      description
        "Represents the properties, known by the management
         function, of a UPFFunction managed by another management
         function.";
      reference "3GPP TS 28.541";
      key "id";
      uses top3gpp:live_ncs_Top_Grp;
      container attributes {
        uses live_ncs_ExternalUPFFunctionGrp;
      }
      uses mf3gpp:live_ncs_ManagedFunctionContainedClasses;
    }
  }

  grouping ExternalUPFFunctionGrp {
    description
      "Represents the ExternalUPFFunction IOC.";
    reference "3GPP TS 28.541";
    uses mf3gpp:ManagedFunctionGrp;
  }

  grouping ExternalUPFFunctionWrapper {
    list ExternalUPFFunction {
      description
        "Represents the properties, known by the management
         function, of a UPFFunction managed by another management
         function.";
      reference "3GPP TS 28.541";
      key "id";
      uses top3gpp:Top_Grp;
      container attributes {
        uses ExternalUPFFunctionGrp;
      }
      uses mf3gpp:ManagedFunctionContainedClasses;
    }
  }

  augment "/ncs:devices/ncs:template/ncs:ned-id/ncs:config/subnet3gpp:SubNetwork" {
    // NCS drop if-feature statement
    uses ncs_template_ExternalUPFFunctionWrapper;
  }
  augment "/ncs:devices/ncs:device/ncs:live-status/subnet3gpp:SubNetwork" {
    // NCS drop if-feature statement
    uses live_ncs_ExternalUPFFunctionWrapper {
      refine ExternalUPFFunction {
        tailf:ncs-device-type "netconf";
        tailf:display-when "not(../../ncs:module) or ../../ncs:module[ncs:name='_3gpp-nr-nrm-externalupffunction'] or (../../ncs:live-status-protocol[not(ncs:capability)]) or (../../ncs:live-status-protocol/ncs:capability/ncs:module[.='_3gpp-nr-nrm-externalupffunction'])";
      }
    }
  }
  augment "/ncs:devices/ncs:device/ncs:config/subnet3gpp:SubNetwork" {
    // NCS drop if-feature statement
    uses ExternalUPFFunctionWrapper {
      refine ExternalUPFFunction {
        tailf:ncs-device-type "netconf";
        tailf:display-when "not(../../ncs:module) or ../../ncs:module[ncs:name='_3gpp-nr-nrm-externalupffunction']";
      }
    }
  }
  augment "/ncs:devices/ncs:template/ncs:ned-id/ncs:config/nrnet3gpp:NRNetwork" {
    // NCS drop if-feature statement
    uses ncs_template_ExternalUPFFunctionWrapper;
  }
  augment "/ncs:devices/ncs:device/ncs:live-status/nrnet3gpp:NRNetwork" {
    // NCS drop if-feature statement
    uses live_ncs_ExternalUPFFunctionWrapper {
      refine ExternalUPFFunction {
        tailf:ncs-device-type "netconf";
        tailf:display-when "not(../../ncs:module) or ../../ncs:module[ncs:name='_3gpp-nr-nrm-externalupffunction'] or (../../ncs:live-status-protocol[not(ncs:capability)]) or (../../ncs:live-status-protocol/ncs:capability/ncs:module[.='_3gpp-nr-nrm-externalupffunction'])";
      }
    }
  }
  augment "/ncs:devices/ncs:device/ncs:config/nrnet3gpp:NRNetwork" {
    // NCS drop if-feature statement
    uses ExternalUPFFunctionWrapper {
      refine ExternalUPFFunction {
        tailf:ncs-device-type "netconf";
        tailf:display-when "not(../../ncs:module) or ../../ncs:module[ncs:name='_3gpp-nr-nrm-externalupffunction']";
      }
    }
  }
}
