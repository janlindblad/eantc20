module _3gpp-5gc-nrm-dnfunction {
  // Generated by yanger -t ncs
  tailf:mount-id fgc-nc-1.0:fgc-nc-1.0;
  tailf:ncs-device-type "netconf";

  yang-version 1.1;
  namespace "urn:3gpp:sa5_3gpp-5gc-nrm-dnfunction";
  prefix dn3gpp;

  import _3gpp-common-managed-function {
    prefix mf3gpp;
  }
  import _3gpp-common-managed-element {
    prefix me3gpp;
  }
  import _3gpp-common-top {
    prefix top3gpp;
  }
  import "fgc-nc-1.0" {
    prefix "fgc-nc-1.0";
  }
  import tailf-ncs {
    prefix ncs;
  }
  import tailf-common {
    prefix tailf;
  }

  organization
    "3gpp SA5";
  description
    "This IOC is defined only to describe the IOCs representing
     Data Network (DN) interaction interface with 5GC (i.e. EP_N6).
     It has no attributes defined.";
  reference "3GPP TS 28.541";

  revision 2019-10-28 {
    reference "S5-193518";
  }
  revision 2019-05-15 {
    description
      "initial revision";
  }

  grouping ncs_template_DNFunctionGrp {
    uses mf3gpp:ncs_template_ManagedFunctionGrp;
  }

  grouping ncs_rpc_notif_DNFunctionGrp {
    uses mf3gpp:ncs_rpc_notif_ManagedFunctionGrp;
  }

  grouping live_ncs_DNFunctionGrp {
    uses mf3gpp:live_ncs_ManagedFunctionGrp;
  }

  grouping DNFunctionGrp {
    uses mf3gpp:ManagedFunctionGrp;
  }

  augment "/ncs:devices/ncs:template/ncs:ned-id/ncs:config/me3gpp:ManagedElement" {
    list DNFunction {
      // NCS patched for predictable order
      ordered-by user;
      description
        "5G Core DN Function";
      reference "3GPP TS 28.541";
      key "id";
      uses top3gpp:ncs_template_Top_Grp;
      container attributes {
        uses ncs_template_DNFunctionGrp;
      }
      uses mf3gpp:ncs_template_ManagedFunctionContainedClasses;
    }
  }
  augment "/ncs:devices/ncs:device/ncs:live-status/me3gpp:ManagedElement" {
    list DNFunction {
      tailf:ncs-device-type "netconf";
      tailf:display-when "not(../../ncs:module) or ../../ncs:module[ncs:name='_3gpp-5gc-nrm-dnfunction'] or (../../ncs:live-status-protocol[not(ncs:capability)]) or (../../ncs:live-status-protocol/ncs:capability/ncs:module[.='_3gpp-5gc-nrm-dnfunction'])";
      description
        "5G Core DN Function";
      reference "3GPP TS 28.541";
      key "id";
      uses top3gpp:live_ncs_Top_Grp;
      container attributes {
        uses live_ncs_DNFunctionGrp;
      }
      uses mf3gpp:live_ncs_ManagedFunctionContainedClasses;
    }
  }
  augment "/ncs:devices/ncs:device/ncs:config/me3gpp:ManagedElement" {
    list DNFunction {
      tailf:ncs-device-type "netconf";
      tailf:display-when "not(../../ncs:module) or ../../ncs:module[ncs:name='_3gpp-5gc-nrm-dnfunction']";
      description
        "5G Core DN Function";
      reference "3GPP TS 28.541";
      key "id";
      uses top3gpp:Top_Grp;
      container attributes {
        uses DNFunctionGrp;
      }
      uses mf3gpp:ManagedFunctionContainedClasses;
    }
  }
}
