module _3gpp-nr-nrm-gnbcucpfunction {
  // Generated by yanger -t ncs
  tailf:mount-id fgc-nc-1.0:fgc-nc-1.0;
  tailf:ncs-device-type "netconf";

  yang-version 1.1;
  namespace "urn:3gpp:sa5:_3gpp-nr-nrm-gnbcucpfunction";
  prefix gnbcucp3gpp;

  import _3gpp-common-yang-types {
    prefix types3gpp;
  }
  import _3gpp-common-managed-function {
    prefix mf3gpp;
  }
  import _3gpp-common-managed-element {
    prefix me3gpp;
  }
  import _3gpp-common-top {
    prefix top3gpp;
  }
  import "fgc-nc-1.0" {
    prefix "fgc-nc-1.0";
  }
  import tailf-ncs {
    prefix ncs;
  }
  import tailf-common {
    prefix tailf;
  }

  organization
    "3GPP SA5";
  description
    "Defines the YANG mapping of the GNBCUCPFunction Information
     Object Class (IOC) that is part of the NR Network Resource Model (NRM).";
  reference "3GPP TS 28.541 5G Network Resource Model (NRM)";

  revision 2019-10-28 {
    reference "S5-193518";
  }
  revision 2019-06-17 {
    description
      "Initial revision";
  }

  grouping ncs_template_GNBCUCPFunctionGrp {
    description
      "Represents the GNBCUCPFunction IOC.";
    reference "3GPP TS 28.541";
    uses mf3gpp:ncs_template_ManagedFunctionGrp;
    leaf gNBId {
      description
        "Identifies a gNB within a PLMN. The gNB Identifier (gNB ID)
         is part of the NR Cell Identifier (NCI) of the gNB cells.";
      reference "gNB ID in 3GPP TS 38.300, Global gNB ID in 3GPP TS 38.413";
      // NCS drop mandatory statement
      type string;
    }
    leaf gNBIdLength {
      description
        "Indicates the number of bits for encoding the gNB ID.";
      reference "gNB ID in 3GPP TS 38.300, Global gNB ID in 3GPP TS 38.413";
      // NCS drop mandatory statement
      type string;
    }
    leaf gNBCUName {
      description
        "Identifies the Central Unit of an gNB.";
      reference "3GPP TS 38.473";
      // NCS drop mandatory statement
      type string;
    }
    list pLMNId {
      // NCS patched for predictable order
      ordered-by user;
      description
        "The PLMN identifier to be used as part of the global RAN
         node identity.";
      key "mcc mnc";
      // NCS drop min-elements statement
      // NCS drop max-elements statement
      uses types3gpp:ncs_template_PLMNId;
    }
    leaf-list x2BlackList {
      // NCS patched for predictable order
      ordered-by user;
      type string;
      description
        "List of nodes to which X2 connections are prohibited.";
    }
    leaf-list x2WhiteList {
      // NCS patched for predictable order
      ordered-by user;
      type string;
      description
        "List of nodes to which X2 connections are enforced.";
    }
    leaf-list xnBlackList {
      // NCS patched for predictable order
      ordered-by user;
      type string;
      description
        "List of nodes to which Xn connections are prohibited.";
    }
    leaf-list xnWhiteList {
      // NCS patched for predictable order
      ordered-by user;
      type string;
      description
        "List of nodes to which X2 connections are enforced.";
    }
    leaf-list x2XnHOBlackList {
      // NCS patched for predictable order
      ordered-by user;
      type string;
      description
        "List of nodes to which handovers over X2 or Xn are prohibited.";
    }
  }

  grouping ncs_rpc_notif_GNBCUCPFunctionGrp {
    description
      "Represents the GNBCUCPFunction IOC.";
    reference "3GPP TS 28.541";
    uses mf3gpp:ncs_rpc_notif_ManagedFunctionGrp;
    leaf gNBId {
      description
        "Identifies a gNB within a PLMN. The gNB Identifier (gNB ID)
         is part of the NR Cell Identifier (NCI) of the gNB cells.";
      reference "gNB ID in 3GPP TS 38.300, Global gNB ID in 3GPP TS 38.413";
      mandatory true;
      type int64 {
        range "0..4294967295";
      }
    }
    leaf gNBIdLength {
      description
        "Indicates the number of bits for encoding the gNB ID.";
      reference "gNB ID in 3GPP TS 38.300, Global gNB ID in 3GPP TS 38.413";
      mandatory true;
      type int32 {
        range "22..32";
      }
    }
    leaf gNBCUName {
      description
        "Identifies the Central Unit of an gNB.";
      reference "3GPP TS 38.473";
      mandatory true;
      type string {
        length "1..150";
      }
    }
    list pLMNId {
      description
        "The PLMN identifier to be used as part of the global RAN
         node identity.";
      key "mcc mnc";
      min-elements 1;
      max-elements 1;
      uses types3gpp:ncs_rpc_notif_PLMNId;
    }
    leaf-list x2BlackList {
      type types3gpp:DistinguishedName;
      description
        "List of nodes to which X2 connections are prohibited.";
    }
    leaf-list x2WhiteList {
      type types3gpp:DistinguishedName;
      description
        "List of nodes to which X2 connections are enforced.";
    }
    leaf-list xnBlackList {
      type types3gpp:DistinguishedName;
      description
        "List of nodes to which Xn connections are prohibited.";
    }
    leaf-list xnWhiteList {
      type types3gpp:DistinguishedName;
      description
        "List of nodes to which X2 connections are enforced.";
    }
    leaf-list x2XnHOBlackList {
      type types3gpp:DistinguishedName;
      description
        "List of nodes to which handovers over X2 or Xn are prohibited.";
    }
  }

  grouping live_ncs_GNBCUCPFunctionGrp {
    description
      "Represents the GNBCUCPFunction IOC.";
    reference "3GPP TS 28.541";
    uses mf3gpp:live_ncs_ManagedFunctionGrp;
    leaf gNBId {
      description
        "Identifies a gNB within a PLMN. The gNB Identifier (gNB ID)
         is part of the NR Cell Identifier (NCI) of the gNB cells.";
      reference "gNB ID in 3GPP TS 38.300, Global gNB ID in 3GPP TS 38.413";
      // NCS drop mandatory statement
      type int64 {
        range "0..4294967295";
      }
    }
    leaf gNBIdLength {
      description
        "Indicates the number of bits for encoding the gNB ID.";
      reference "gNB ID in 3GPP TS 38.300, Global gNB ID in 3GPP TS 38.413";
      // NCS drop mandatory statement
      type int32 {
        range "22..32";
      }
    }
    leaf gNBCUName {
      description
        "Identifies the Central Unit of an gNB.";
      reference "3GPP TS 38.473";
      // NCS drop mandatory statement
      type string {
        length "1..150";
      }
    }
    list pLMNId {
      description
        "The PLMN identifier to be used as part of the global RAN
         node identity.";
      key "mcc mnc";
      // NCS drop min-elements statement
      // NCS drop max-elements statement
      uses types3gpp:live_ncs_PLMNId;
    }
    leaf-list x2BlackList {
      type types3gpp:DistinguishedName;
      description
        "List of nodes to which X2 connections are prohibited.";
    }
    leaf-list x2WhiteList {
      type types3gpp:DistinguishedName;
      description
        "List of nodes to which X2 connections are enforced.";
    }
    leaf-list xnBlackList {
      type types3gpp:DistinguishedName;
      description
        "List of nodes to which Xn connections are prohibited.";
    }
    leaf-list xnWhiteList {
      type types3gpp:DistinguishedName;
      description
        "List of nodes to which X2 connections are enforced.";
    }
    leaf-list x2XnHOBlackList {
      type types3gpp:DistinguishedName;
      description
        "List of nodes to which handovers over X2 or Xn are prohibited.";
    }
  }

  grouping GNBCUCPFunctionGrp {
    description
      "Represents the GNBCUCPFunction IOC.";
    reference "3GPP TS 28.541";
    uses mf3gpp:ManagedFunctionGrp;
    leaf gNBId {
      description
        "Identifies a gNB within a PLMN. The gNB Identifier (gNB ID)
         is part of the NR Cell Identifier (NCI) of the gNB cells.";
      reference "gNB ID in 3GPP TS 38.300, Global gNB ID in 3GPP TS 38.413";
      mandatory true;
      type int64 {
        range "0..4294967295";
      }
    }
    leaf gNBIdLength {
      description
        "Indicates the number of bits for encoding the gNB ID.";
      reference "gNB ID in 3GPP TS 38.300, Global gNB ID in 3GPP TS 38.413";
      mandatory true;
      type int32 {
        range "22..32";
      }
    }
    leaf gNBCUName {
      description
        "Identifies the Central Unit of an gNB.";
      reference "3GPP TS 38.473";
      mandatory true;
      type string {
        length "1..150";
      }
    }
    list pLMNId {
      description
        "The PLMN identifier to be used as part of the global RAN
         node identity.";
      key "mcc mnc";
      min-elements 1;
      max-elements 1;
      uses types3gpp:PLMNId;
    }
    leaf-list x2BlackList {
      type types3gpp:DistinguishedName;
      description
        "List of nodes to which X2 connections are prohibited.";
    }
    leaf-list x2WhiteList {
      type types3gpp:DistinguishedName;
      description
        "List of nodes to which X2 connections are enforced.";
    }
    leaf-list xnBlackList {
      type types3gpp:DistinguishedName;
      description
        "List of nodes to which Xn connections are prohibited.";
    }
    leaf-list xnWhiteList {
      type types3gpp:DistinguishedName;
      description
        "List of nodes to which X2 connections are enforced.";
    }
    leaf-list x2XnHOBlackList {
      type types3gpp:DistinguishedName;
      description
        "List of nodes to which handovers over X2 or Xn are prohibited.";
    }
  }

  augment "/ncs:devices/ncs:template/ncs:ned-id/ncs:config/me3gpp:ManagedElement" {
    list GNBCUCPFunction {
      // NCS patched for predictable order
      ordered-by user;
      description
        "Represents the logical function CU-CP of gNB and en-gNB.";
      reference "3GPP TS 28.541";
      key "id";
      uses top3gpp:ncs_template_Top_Grp;
      container attributes {
        uses ncs_template_GNBCUCPFunctionGrp;
      }
      uses mf3gpp:ncs_template_ManagedFunctionContainedClasses;
    }
  }
  augment "/ncs:devices/ncs:device/ncs:live-status/me3gpp:ManagedElement" {
    list GNBCUCPFunction {
      tailf:ncs-device-type "netconf";
      tailf:display-when "not(../../ncs:module) or ../../ncs:module[ncs:name='_3gpp-nr-nrm-gnbcucpfunction'] or (../../ncs:live-status-protocol[not(ncs:capability)]) or (../../ncs:live-status-protocol/ncs:capability/ncs:module[.='_3gpp-nr-nrm-gnbcucpfunction'])";
      description
        "Represents the logical function CU-CP of gNB and en-gNB.";
      reference "3GPP TS 28.541";
      key "id";
      uses top3gpp:live_ncs_Top_Grp;
      container attributes {
        uses live_ncs_GNBCUCPFunctionGrp;
      }
      uses mf3gpp:live_ncs_ManagedFunctionContainedClasses;
    }
  }
  augment "/ncs:devices/ncs:device/ncs:config/me3gpp:ManagedElement" {
    list GNBCUCPFunction {
      tailf:ncs-device-type "netconf";
      tailf:display-when "not(../../ncs:module) or ../../ncs:module[ncs:name='_3gpp-nr-nrm-gnbcucpfunction']";
      description
        "Represents the logical function CU-CP of gNB and en-gNB.";
      reference "3GPP TS 28.541";
      key "id";
      uses top3gpp:Top_Grp;
      container attributes {
        uses GNBCUCPFunctionGrp;
      }
      uses mf3gpp:ManagedFunctionContainedClasses;
    }
  }
}
