module _3gpp-common-ep-rp {
  // Generated by yanger -t ncs
  tailf:mount-id fgc-nc-1.0:fgc-nc-1.0;
  tailf:ncs-device-type "netconf";

  yang-version 1.1;
  namespace "urn:3gpp:sa5:_3gpp-common-ep-rp";
  prefix eprp3gpp;

  import _3gpp-common-yang-types {
    prefix types3gpp;
  }
  import ietf-inet-types {
    prefix inet;
  }
  import _3gpp-common-measurements {
    prefix meas3gpp;
  }
  import "fgc-nc-1.0" {
    prefix "fgc-nc-1.0";
  }
  import tailf-ncs {
    prefix ncs;
  }
  import tailf-common {
    prefix tailf;
  }

  organization
    "3GPP SA5";
  description
    "Common/basic class/grouping to be inherited/reused.
     This IOC represents an end point of a link used across a reference
     point between two network entities.";
  reference
    "3GPP TS 28.622
     Generic Network Resource Model (NRM)
     Integration Reference Point (IRP);
     Information Service (IS)
     
     3GPP TS 28.620
     Umbrella Information Model (UIM)";

  revision 2019-06-17 {
    description
      "Initial revision";
  }

  grouping ncs_template_EP_RPGrp {
    description
      "Abstract class, represents an end point of a link used
       across a reference point between two network entities.
       
       For naming the subclasses of EP_RP, the following rules shall apply:
       -\tThe name of the subclassed IOC shall have the form 'EP_<rp>',
       where <rp> is a string that represents the name of the reference point.
       Thus, two valid examples of EP_RP subclassed IOC names would be:
       EP_S1 and EP_X2.";
    leaf userLabel {
      type string;
      description
        "A user-friendly (and user assignable) name of this object.";
    }
    // NCS drop config false leaf farEndEntity
  }

  grouping ncs_template_EP_Common {
    uses ncs_template_EP_RPGrp;
    uses meas3gpp:ncs_template_Measurements;
    list localAddress {
      // NCS patched for predictable order
      ordered-by user;
      description
        "Local IP address and VLAN ID.";
      key "ipAddress vlanId";
      // NCS drop min-elements statement
      // NCS drop max-elements statement
      uses types3gpp:ncs_template_AddressWithVlan;
    }
    leaf remoteAddress {
      description
        "Remote IP address.";
      // NCS drop mandatory statement
      type string;
    }
  }

  grouping ncs_rpc_notif_EP_RPGrp {
    description
      "Abstract class, represents an end point of a link used
       across a reference point between two network entities.
       
       For naming the subclasses of EP_RP, the following rules shall apply:
       -\tThe name of the subclassed IOC shall have the form 'EP_<rp>',
       where <rp> is a string that represents the name of the reference point.
       Thus, two valid examples of EP_RP subclassed IOC names would be:
       EP_S1 and EP_X2.";
    leaf userLabel {
      type string;
      description
        "A user-friendly (and user assignable) name of this object.";
    }
    leaf farEndEntity {
      config false;
      type types3gpp:DistinguishedName;
    }
  }

  grouping ncs_rpc_notif_EP_Common {
    uses ncs_rpc_notif_EP_RPGrp;
    uses meas3gpp:ncs_rpc_notif_Measurements;
    list localAddress {
      description
        "Local IP address and VLAN ID.";
      key "ipAddress vlanId";
      min-elements 1;
      max-elements 1;
      uses types3gpp:ncs_rpc_notif_AddressWithVlan;
    }
    leaf remoteAddress {
      description
        "Remote IP address.";
      mandatory true;
      type inet:ip-address;
    }
  }

  grouping live_ncs_EP_RPGrp {
    description
      "Abstract class, represents an end point of a link used
       across a reference point between two network entities.
       
       For naming the subclasses of EP_RP, the following rules shall apply:
       -\tThe name of the subclassed IOC shall have the form 'EP_<rp>',
       where <rp> is a string that represents the name of the reference point.
       Thus, two valid examples of EP_RP subclassed IOC names would be:
       EP_S1 and EP_X2.";
    leaf userLabel {
      type string;
      description
        "A user-friendly (and user assignable) name of this object.";
    }
    leaf farEndEntity {
      type types3gpp:DistinguishedName;
    }
  }

  grouping live_ncs_EP_Common {
    uses live_ncs_EP_RPGrp;
    uses meas3gpp:live_ncs_Measurements;
    list localAddress {
      description
        "Local IP address and VLAN ID.";
      key "ipAddress vlanId";
      // NCS drop min-elements statement
      // NCS drop max-elements statement
      uses types3gpp:live_ncs_AddressWithVlan;
    }
    leaf remoteAddress {
      description
        "Remote IP address.";
      // NCS drop mandatory statement
      type inet:ip-address;
    }
  }

  grouping EP_RPGrp {
    description
      "Abstract class, represents an end point of a link used
       across a reference point between two network entities.
       
       For naming the subclasses of EP_RP, the following rules shall apply:
       -\tThe name of the subclassed IOC shall have the form 'EP_<rp>',
       where <rp> is a string that represents the name of the reference point.
       Thus, two valid examples of EP_RP subclassed IOC names would be:
       EP_S1 and EP_X2.";
    leaf userLabel {
      type string;
      description
        "A user-friendly (and user assignable) name of this object.";
    }
    // NCS drop config false leaf farEndEntity
  }

  grouping EP_Common {
    uses EP_RPGrp;
    uses meas3gpp:Measurements;
    list localAddress {
      description
        "Local IP address and VLAN ID.";
      key "ipAddress vlanId";
      min-elements 1;
      max-elements 1;
      uses types3gpp:AddressWithVlan;
    }
    leaf remoteAddress {
      description
        "Remote IP address.";
      mandatory true;
      type inet:ip-address;
    }
  }
}
