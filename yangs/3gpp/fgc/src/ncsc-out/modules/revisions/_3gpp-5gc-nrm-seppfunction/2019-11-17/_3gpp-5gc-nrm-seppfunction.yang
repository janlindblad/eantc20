module _3gpp-5gc-nrm-seppfunction {
  // Generated by yanger -t ncs
  tailf:mount-id fgc-nc-1.0:fgc-nc-1.0;
  tailf:ncs-device-type "netconf";

  yang-version 1.1;
  namespace "urn:3gpp:sa5:_3gpp-5gc-nrm-seppfunction";
  prefix sepp3gpp;

  import _3gpp-common-managed-function {
    prefix mf3gpp;
  }
  import _3gpp-common-managed-element {
    prefix me3gpp;
  }
  import _3gpp-common-yang-types {
    prefix types3gpp;
  }
  import _3gpp-common-top {
    prefix top3gpp;
  }
  import ietf-inet-types {
    prefix inet;
  }
  import "fgc-nc-1.0" {
    prefix "fgc-nc-1.0";
  }
  import tailf-ncs {
    prefix ncs;
  }
  import tailf-common {
    prefix tailf;
  }

  organization
    "3gpp SA5";
  description
    "This IOC represents the SEPP function which support message filtering
     and policing on inter-PLMN control plane interface. For more information about the SEPP, see 3GPP TS 23.501.";
  reference "3GPP TS 28.541";

  revision 2019-10-28 {
    reference "S5-193518";
  }
  revision 2019-11-17 {
    description
      "initial revision";
  }

  typedef SEPPType {
    reference "3GPP TS 23501";
    type enumeration {
      enum "CSEPP" {
        value 0;
        description
          "consumer SEPP";
      }
      enum "PSEPP" {
        value 1;
        description
          "producer SEPP";
      }
    }
  }

  grouping ncs_template_SEPPFunctionGrp {
    uses mf3gpp:ncs_template_ManagedFunctionGrp;
    container pLMNId {
      description
        "PLMN Identifiers of the sepp.
         The PLMN Identifier is composed of a Mobile Country Code (MCC) and a Mobile Network Code (MNC).";
      uses types3gpp:ncs_template_PLMNId;
    }
    leaf sEPPType {
      type string;
    }
    leaf sEPPId {
      type string;
    }
    leaf fqdn {
      description
        "The domain name of the SEPP.";
      type string;
    }
  }

  grouping ncs_rpc_notif_SEPPFunctionGrp {
    uses mf3gpp:ncs_rpc_notif_ManagedFunctionGrp;
    container pLMNId {
      description
        "PLMN Identifiers of the sepp.
         The PLMN Identifier is composed of a Mobile Country Code (MCC) and a Mobile Network Code (MNC).";
      uses types3gpp:ncs_rpc_notif_PLMNId;
    }
    leaf sEPPType {
      type sepp3gpp:SEPPType;
    }
    leaf sEPPId {
      type uint16;
    }
    leaf fqdn {
      description
        "The domain name of the SEPP.";
      type inet:domain-name;
    }
  }

  grouping live_ncs_SEPPFunctionGrp {
    uses mf3gpp:live_ncs_ManagedFunctionGrp;
    container pLMNId {
      description
        "PLMN Identifiers of the sepp.
         The PLMN Identifier is composed of a Mobile Country Code (MCC) and a Mobile Network Code (MNC).";
      uses types3gpp:live_ncs_PLMNId;
    }
    leaf sEPPType {
      type sepp3gpp:SEPPType;
    }
    leaf sEPPId {
      type uint16;
    }
    leaf fqdn {
      description
        "The domain name of the SEPP.";
      type inet:domain-name;
    }
  }

  grouping SEPPFunctionGrp {
    uses mf3gpp:ManagedFunctionGrp;
    container pLMNId {
      description
        "PLMN Identifiers of the sepp.
         The PLMN Identifier is composed of a Mobile Country Code (MCC) and a Mobile Network Code (MNC).";
      uses types3gpp:PLMNId;
    }
    leaf sEPPType {
      type sepp3gpp:SEPPType;
    }
    leaf sEPPId {
      type uint16;
    }
    leaf fqdn {
      description
        "The domain name of the SEPP.";
      type inet:domain-name;
    }
  }

  augment "/ncs:devices/ncs:template/ncs:ned-id/ncs:config/me3gpp:ManagedElement" {
    list SEPPFunction {
      // NCS patched for predictable order
      ordered-by user;
      description
        "5G Core SEPP Function";
      reference "3GPP TS 28.541";
      key "id";
      uses top3gpp:ncs_template_Top_Grp;
      container attributes {
        uses ncs_template_SEPPFunctionGrp;
      }
      uses mf3gpp:ncs_template_ManagedFunctionContainedClasses;
    }
  }
  augment "/ncs:devices/ncs:device/ncs:live-status/me3gpp:ManagedElement" {
    list SEPPFunction {
      tailf:ncs-device-type "netconf";
      tailf:display-when "not(../../ncs:module) or ../../ncs:module[ncs:name='_3gpp-5gc-nrm-seppfunction'] or (../../ncs:live-status-protocol[not(ncs:capability)]) or (../../ncs:live-status-protocol/ncs:capability/ncs:module[.='_3gpp-5gc-nrm-seppfunction'])";
      description
        "5G Core SEPP Function";
      reference "3GPP TS 28.541";
      key "id";
      uses top3gpp:live_ncs_Top_Grp;
      container attributes {
        uses live_ncs_SEPPFunctionGrp;
      }
      uses mf3gpp:live_ncs_ManagedFunctionContainedClasses;
    }
  }
  augment "/ncs:devices/ncs:device/ncs:config/me3gpp:ManagedElement" {
    list SEPPFunction {
      tailf:ncs-device-type "netconf";
      tailf:display-when "not(../../ncs:module) or ../../ncs:module[ncs:name='_3gpp-5gc-nrm-seppfunction']";
      description
        "5G Core SEPP Function";
      reference "3GPP TS 28.541";
      key "id";
      uses top3gpp:Top_Grp;
      container attributes {
        uses SEPPFunctionGrp;
      }
      uses mf3gpp:ManagedFunctionContainedClasses;
    }
  }
}
