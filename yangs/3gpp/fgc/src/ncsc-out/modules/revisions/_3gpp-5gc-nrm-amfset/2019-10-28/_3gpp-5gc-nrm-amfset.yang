module _3gpp-5gc-nrm-amfset {
  // Generated by yanger -t ncs
  tailf:mount-id fgc-nc-1.0:fgc-nc-1.0;
  tailf:ncs-device-type "netconf";

  yang-version 1.1;
  namespace "urn:3gpp:sa5:_3gpp-5gc-nrm-amfset";
  prefix amfset3gpp;

  import _3gpp-common-yang-types {
    prefix types3gpp;
  }
  import _3gpp-common-subnetwork {
    prefix subnet3gpp;
  }
  import _3gpp-common-top {
    prefix top3gpp;
  }
  import _3gpp-common-managed-function {
    prefix mf3gpp;
  }
  import "fgc-nc-1.0" {
    prefix "fgc-nc-1.0";
  }
  import tailf-ncs {
    prefix ncs;
  }
  import tailf-common {
    prefix tailf;
  }

  description
    "This IOC represents the AMF Set which consists of some AMFs that serve a given area and Network Slice.";

  revision 2019-10-28 {
    reference "S5-193518";
  }
  revision 2019-06-11 {
    description
      "Ericsson refactoring.";
  }

  grouping ncs_template_AMFSetGrp {
    uses mf3gpp:ncs_template_ManagedFunctionGrp;
    list pLMNIdList {
      // NCS patched for predictable order
      ordered-by user;
      description
        "List of at most six entries of PLMN Identifiers, but at least one (the primary PLMN Id).
         The PLMN Identifier is composed of a Mobile Country Code (MCC) and a Mobile Network Code (MNC).";
      // NCS drop min-elements statement
      // NCS drop max-elements statement
      key "mcc mnc";
      uses types3gpp:ncs_template_PLMNId;
    }
    // NCS drop config false leaf-list nRTACList
    leaf-list sNSSAIList {
      // NCS patched for predictable order
      ordered-by user;
      description
        "List of S-NSSAIs the managed object is capable of supporting.
         (Single Network Slice Selection Assistance Information)
         An S-NSSAI has an SST (Slice/Service type) and an optional SD
         (Slice Differentiator) field.";
      reference "3GPP TS 23.003";
      type string;
    }
    leaf aMFRegion {
      description
        "The AMFRegion that the AFMSet is associated with.";
      type string;
    }
    leaf-list aMFSetMemberList {
      // NCS patched for predictable order
      ordered-by user;
      description
        "List of DNs of AMFFunction instances of the AMFSet.";
      // NCS drop min-elements statement
      // NCS drop max-elements statement
      type string;
    }
  }

  grouping ncs_rpc_notif_AMFSetGrp {
    uses mf3gpp:ncs_rpc_notif_ManagedFunctionGrp;
    list pLMNIdList {
      description
        "List of at most six entries of PLMN Identifiers, but at least one (the primary PLMN Id).
         The PLMN Identifier is composed of a Mobile Country Code (MCC) and a Mobile Network Code (MNC).";
      min-elements 1;
      max-elements 6;
      key "mcc mnc";
      uses types3gpp:ncs_rpc_notif_PLMNId;
    }
    leaf-list nRTACList {
      description
        "List of Tracking Area Codes (legacy TAC or extended TAC)
         where the represented management function is serving.";
      reference "TS 38.413 clause 9.3.3.10";
      min-elements 1;
      config false;
      type types3gpp:Tac;
    }
    leaf-list sNSSAIList {
      description
        "List of S-NSSAIs the managed object is capable of supporting.
         (Single Network Slice Selection Assistance Information)
         An S-NSSAI has an SST (Slice/Service type) and an optional SD
         (Slice Differentiator) field.";
      reference "3GPP TS 23.003";
      type types3gpp:SNssai;
    }
    leaf aMFRegion {
      description
        "The AMFRegion that the AFMSet is associated with.";
      type instance-identifier;
    }
    leaf-list aMFSetMemberList {
      description
        "List of DNs of AMFFunction instances of the AMFSet.";
      min-elements 1;
      max-elements 1;
      type types3gpp:DistinguishedName;
    }
  }

  grouping live_ncs_AMFSetGrp {
    uses mf3gpp:live_ncs_ManagedFunctionGrp;
    list pLMNIdList {
      description
        "List of at most six entries of PLMN Identifiers, but at least one (the primary PLMN Id).
         The PLMN Identifier is composed of a Mobile Country Code (MCC) and a Mobile Network Code (MNC).";
      // NCS drop min-elements statement
      // NCS drop max-elements statement
      key "mcc mnc";
      uses types3gpp:live_ncs_PLMNId;
    }
    leaf-list nRTACList {
      description
        "List of Tracking Area Codes (legacy TAC or extended TAC)
         where the represented management function is serving.";
      reference "TS 38.413 clause 9.3.3.10";
      // NCS drop min-elements statement
      type types3gpp:Tac;
    }
    leaf-list sNSSAIList {
      description
        "List of S-NSSAIs the managed object is capable of supporting.
         (Single Network Slice Selection Assistance Information)
         An S-NSSAI has an SST (Slice/Service type) and an optional SD
         (Slice Differentiator) field.";
      reference "3GPP TS 23.003";
      type types3gpp:SNssai;
    }
    leaf aMFRegion {
      description
        "The AMFRegion that the AFMSet is associated with.";
      type instance-identifier;
    }
    leaf-list aMFSetMemberList {
      description
        "List of DNs of AMFFunction instances of the AMFSet.";
      // NCS drop min-elements statement
      // NCS drop max-elements statement
      type types3gpp:DistinguishedName;
    }
  }

  grouping AMFSetGrp {
    uses mf3gpp:ManagedFunctionGrp;
    list pLMNIdList {
      description
        "List of at most six entries of PLMN Identifiers, but at least one (the primary PLMN Id).
         The PLMN Identifier is composed of a Mobile Country Code (MCC) and a Mobile Network Code (MNC).";
      min-elements 1;
      max-elements 6;
      key "mcc mnc";
      uses types3gpp:PLMNId;
    }
    // NCS drop config false leaf-list nRTACList
    leaf-list sNSSAIList {
      description
        "List of S-NSSAIs the managed object is capable of supporting.
         (Single Network Slice Selection Assistance Information)
         An S-NSSAI has an SST (Slice/Service type) and an optional SD
         (Slice Differentiator) field.";
      reference "3GPP TS 23.003";
      type types3gpp:SNssai;
    }
    leaf aMFRegion {
      description
        "The AMFRegion that the AFMSet is associated with.";
      type instance-identifier;
    }
    leaf-list aMFSetMemberList {
      description
        "List of DNs of AMFFunction instances of the AMFSet.";
      min-elements 1;
      max-elements 1;
      type types3gpp:DistinguishedName;
    }
  }

  augment "/ncs:devices/ncs:template/ncs:ned-id/ncs:config/subnet3gpp:SubNetwork" {
    list AMFSet {
      // NCS patched for predictable order
      ordered-by user;
      description
        "5G Core AMFSet IOC";
      reference "3GPP TS 28.541";
      key "id";
      uses top3gpp:ncs_template_Top_Grp;
      container attributes {
        uses ncs_template_AMFSetGrp;
      }
      uses mf3gpp:ncs_template_ManagedFunctionContainedClasses;
    }
  }
  augment "/ncs:devices/ncs:device/ncs:live-status/subnet3gpp:SubNetwork" {
    list AMFSet {
      tailf:ncs-device-type "netconf";
      tailf:display-when "not(../../ncs:module) or ../../ncs:module[ncs:name='_3gpp-5gc-nrm-amfset'] or (../../ncs:live-status-protocol[not(ncs:capability)]) or (../../ncs:live-status-protocol/ncs:capability/ncs:module[.='_3gpp-5gc-nrm-amfset'])";
      description
        "5G Core AMFSet IOC";
      reference "3GPP TS 28.541";
      key "id";
      uses top3gpp:live_ncs_Top_Grp;
      container attributes {
        uses live_ncs_AMFSetGrp;
      }
      uses mf3gpp:live_ncs_ManagedFunctionContainedClasses;
    }
  }
  augment "/ncs:devices/ncs:device/ncs:config/subnet3gpp:SubNetwork" {
    list AMFSet {
      tailf:ncs-device-type "netconf";
      tailf:display-when "not(../../ncs:module) or ../../ncs:module[ncs:name='_3gpp-5gc-nrm-amfset']";
      description
        "5G Core AMFSet IOC";
      reference "3GPP TS 28.541";
      key "id";
      uses top3gpp:Top_Grp;
      container attributes {
        uses AMFSetGrp;
      }
      uses mf3gpp:ManagedFunctionContainedClasses;
    }
  }
}
