module _3gpp-nr-nrm-eutranetwork {
  // Generated by yanger -t ncs
  tailf:mount-id fgc-nc-1.0:fgc-nc-1.0;
  tailf:ncs-device-type "netconf";

  yang-version 1.1;
  namespace "urn:3gpp:sa5:_3gpp-nr-nrm-eutranetwork";
  prefix eutranet3gpp;

  import _3gpp-common-subnetwork {
    prefix subnet3gpp;
  }
  import _3gpp-common-top {
    prefix top3gpp;
  }
  import "fgc-nc-1.0" {
    prefix "fgc-nc-1.0";
  }
  import tailf-ncs {
    prefix ncs;
  }
  import tailf-common {
    prefix tailf;
  }

  organization
    "3GPP SA5";
  description
    "Defines the YANG mapping of the EUtraNetwork Information Object
     Class (IOC) that is part of the NR Network Resource Model (NRM).";
  reference "3GPP TS 28.541 5G Network Resource Model (NRM)";

  revision 2019-06-17 {
    description
      "Initial revision";
  }

  grouping ncs_template_EUtraNetworkGrp {
    description
      "Represents the EUtraNetwork IOC.";
    reference "3GPP TS 28.541";
    uses subnet3gpp:ncs_template_SubNetworkGrp;
  }

  grouping ncs_rpc_notif_EUtraNetworkGrp {
    description
      "Represents the EUtraNetwork IOC.";
    reference "3GPP TS 28.541";
    uses subnet3gpp:ncs_rpc_notif_SubNetworkGrp;
  }

  grouping live_ncs_EUtraNetworkGrp {
    description
      "Represents the EUtraNetwork IOC.";
    reference "3GPP TS 28.541";
    uses subnet3gpp:live_ncs_SubNetworkGrp;
  }

  grouping EUtraNetworkGrp {
    description
      "Represents the EUtraNetwork IOC.";
    reference "3GPP TS 28.541";
    uses subnet3gpp:SubNetworkGrp;
  }

  augment "/ncs:devices/ncs:device/ncs:config" {
    list EUtraNetwork {
      tailf:ncs-device-type "netconf";
      tailf:display-when "not(../ncs:module) or ../ncs:module[ncs:name='_3gpp-nr-nrm-eutranetwork']";
      description
        "A subnetwork containing gNB external E-UTRAN entities.";
      reference "3GPP TS 28.541";
      key "id";
      uses top3gpp:Top_Grp;
      container attributes {
        uses EUtraNetworkGrp;
        leaf-list parents {
          description
            "Reference to all containg EUtraNetwork instances
             in strict order from the root EUtraNetwork down to the immediate
             parent EUtraNetwork.
             If EUtraNetworks form a containment hierarchy this is
             modeled using references between the child EUtraNetwork and the parent
             EUtraNetworks.
             This reference MUST NOT be present for the top level EUtraNetwork and
             MUST be present for other EUtraNetworks.";
          type leafref {
            path "../../../EUtraNetwork/id";
          }
        }
        leaf-list containedChildren {
          description
            "Reference to all directly contained EUtraNetwork instances.
             If EUtraNetworks form a containment hierarchy this is
             modeled using references between the child EUtraNetwork and the parent
             EUtraNetwork.";
          type leafref {
            path "../../../EUtraNetwork/id";
          }
        }
      }
    }
  }
  augment "/ncs:devices/ncs:device/ncs:live-status" {
    list EUtraNetwork {
      tailf:ncs-device-type "netconf";
      tailf:display-when "not(../ncs:module) or ../ncs:module[ncs:name='_3gpp-nr-nrm-eutranetwork'] or (../ncs:live-status-protocol[not(ncs:capability)]) or (../ncs:live-status-protocol/ncs:capability/ncs:module[.='_3gpp-nr-nrm-eutranetwork'])";
      description
        "A subnetwork containing gNB external E-UTRAN entities.";
      reference "3GPP TS 28.541";
      key "id";
      uses top3gpp:live_ncs_Top_Grp;
      container attributes {
        uses live_ncs_EUtraNetworkGrp;
        leaf-list parents {
          description
            "Reference to all containg EUtraNetwork instances
             in strict order from the root EUtraNetwork down to the immediate
             parent EUtraNetwork.
             If EUtraNetworks form a containment hierarchy this is
             modeled using references between the child EUtraNetwork and the parent
             EUtraNetworks.
             This reference MUST NOT be present for the top level EUtraNetwork and
             MUST be present for other EUtraNetworks.";
          type leafref {
            path "../../../EUtraNetwork/id";
          }
        }
        leaf-list containedChildren {
          description
            "Reference to all directly contained EUtraNetwork instances.
             If EUtraNetworks form a containment hierarchy this is
             modeled using references between the child EUtraNetwork and the parent
             EUtraNetwork.";
          type leafref {
            path "../../../EUtraNetwork/id";
          }
        }
      }
    }
  }
  augment "/ncs:devices/ncs:template/ncs:ned-id/ncs:config" {
    list EUtraNetwork {
      // NCS patched for predictable order
      ordered-by user;
      description
        "A subnetwork containing gNB external E-UTRAN entities.";
      reference "3GPP TS 28.541";
      key "id";
      uses top3gpp:ncs_template_Top_Grp;
      container attributes {
        uses ncs_template_EUtraNetworkGrp;
        leaf-list parents {
          // NCS patched for predictable order
          ordered-by user;
          description
            "Reference to all containg EUtraNetwork instances
             in strict order from the root EUtraNetwork down to the immediate
             parent EUtraNetwork.
             If EUtraNetworks form a containment hierarchy this is
             modeled using references between the child EUtraNetwork and the parent
             EUtraNetworks.
             This reference MUST NOT be present for the top level EUtraNetwork and
             MUST be present for other EUtraNetworks.";
          type string;
        }
        leaf-list containedChildren {
          // NCS patched for predictable order
          ordered-by user;
          description
            "Reference to all directly contained EUtraNetwork instances.
             If EUtraNetworks form a containment hierarchy this is
             modeled using references between the child EUtraNetwork and the parent
             EUtraNetwork.";
          type string;
        }
      }
    }
  }

  feature ExternalsUnderEUtraNetwork {
    description
      "Classes representing external entities like EUtranFrequency,
       ExternalENBFunction are contained under a EUtraNetwork list/class.";
  }
}
