module tgpp-nc-1.0 {
  yang-version 1.1;
  namespace "http://tail-f.com/ns/ned-id/tgpp-nc-1.0";
  prefix tgpp-nc-1.0;

  import tgpp-nc {
    prefix family;
  }

  identity tgpp-nc-1.0 {
    base family:tgpp-nc;
  }
}
