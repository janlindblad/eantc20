module tgpp-nc {
  yang-version 1.1;
  namespace "http://tail-f.com/ns/ned-id/tgpp-nc";
  prefix tgpp-nc;

  import tailf-common {
    prefix tailf;
  }

  import tailf-ncs-ned {
    prefix ned;
  }

  identity tgpp-nc {
    tailf:abstract;
    base ned:netconf-ned-id;
  }
}
