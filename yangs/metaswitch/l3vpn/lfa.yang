module lfa {

  namespace "http://metaswitch.com/yang/nbu/lfa/201703280000Z";

  prefix lfa;

  import user-extensions { prefix "user-ext"; }
  import interfaces { prefix "interfaces"; }
  import metaswitch-yang-types { prefix meta; }

  organization "Metaswitch Networks";

  contact "Postal: Metaswitch Networks
                   100 Church Street
                   Enfield
                   EN2 6BQ
                   United Kingdom
           Tel:    +44 20 8366 1177
           E-mail: info@metaswitch.com";

  description
    "Loop-Free Alternate";

  revision 2017-03-28 {
    description "Initial revision.";
  }

  typedef lfa-protocol-t {
    type enumeration {
      enum isis                             { value 1; }
      enum ospfv2                           { value 2; }
      enum ospfv3                           { value 3; }
    }
    description
      "LFA protocol type";
  }

  typedef lfa-afi-t {
    type enumeration {
      enum ipv4                             { value 1; }
      enum ipv6                             { value 2; }
    }
    description
      "LFA AFI type";
  }

  typedef lfa-router-id-t {
    type string {
      pattern
        '(((([0-9]|[1-9][0-9]|1[0-9][0-9]|2[0-4][0-9]|25[0-5])\.){3}' +
         '([0-9]|[1-9][0-9]|1[0-9][0-9]|2[0-4][0-9]|25[0-5]))|' +
         '(([0-9A-Fa-f]{4}\.){2}[0-9A-Fa-f]{4}))?';

    }
    description
      "LFA Router id.  This can be an OSPF router ID (A.B.C.D) or an ISIS
      router ID (XXXX.XXXX.XXXX) or empty";
  }

  typedef lfa-reason-t {
    type enumeration {
      enum best-candidate                   { value 0; }
      enum primary-excluded                 { value 1; }
      enum candidate-excluded               { value 2; }
      enum not-loop-free                    { value 3; }
      enum overloaded                       { value 4; }
      enum tie-metric                       { value 5; }
      enum tie-node-prot                    { value 6; }
      enum tie-router-id                    { value 7; }
      enum tie-if-index                     { value 8; }
      enum no-tunnel                        { value 9; }
      enum tie-remote-lfa                   { value 10; }
      enum primary-hop                      { value 11; }
    }
    description
      "Reasons for decisions about candidate LFAs.";
  }

  grouping lfa-global-config {

    // Low-level model info: Corresponds to lfaEntEnable.  The MIB default is true.
    leaf include-all {
      type empty;
      description
        "Whether or not LFA calculations should be enabled on all
        interfaces by default.

        If this field is set to true, then DC-LFA will attempt to
        compute an LFA for any primary next hop, unless a more
        specific policy disables LFA calculation for that next
        hop.

        If this field is set to false, then DC-LFA will not
        compute an LFA for any primary next hop, unless a more
        specific policy enables LFA calculation for that next hop.";

      user-ext:CLI-comm-help "Enable LFA calculations on all interfaces";
      user-ext:CLI-no-comm-help "Disable LFA calculations on all interfaces";
    }

    // Low-level model info: Corresponds to lfaEntCalcRemoteLfas.  The MIB default is false.
    leaf remote {
      type empty;
      description
        "Whether DC-LFA should calculate remote (that is,
        indirectly connected) loop-free alternates for
        destinations that cannot be protected using a local
        (directly connected) loop-free alternate.  This feature is
        described in RFC 7490.";

      user-ext:CLI-comm-help "Enable calculation of remote LFAs";
      user-ext:CLI-no-comm-help "Disable calculation of remote LFAs";
    }

  } // lfa-global-config

  grouping lfa-global-stats {

    container lfa-stats {

      // Low-level model info: Corresponds to fields in AMB_LFA_STATS (lfaStatsTable).

      description
        "DC-LFA global statistics.";

      config false;

      // Low-level model info: Corresponds to lfaStatsTotalRoutes.
      leaf total-routes {
        type uint32;
        description
          "The total number of routes that this DC-LFA entity has
          tried to find loop-free alternates for.";
        config false;
      }

      // Low-level model info: Corresponds to lfaStatsUnprotectedRoutes.
      leaf unprotected-routes {
        type uint32;
        description
          "The number of routes that are not protected by any
          loop-free alternate or ECMP next hop.";
        config false;
      }

      // Low-level model info: Corresponds to lfaStatsLfaProtectedRoutes.
      leaf protected-lfa-routes {
        type uint32;
        description
          "The number of routes that are protected by a loop-free
          alternate.";
        config false;
      }

      // Low-level model info: Corresponds to lfaStatsEcmpProtectedRoutes.
      leaf protected-ecmp-routes {
        type uint32;
        description
          "The number of routes that are protected by equal-cost
          multipath next hops.";
        config false;
      }

      // Low-level model info: Corresponds to lfaStatsLocalLfaProtectedRoutes.
      leaf protected-local-lfa-routes {
        type uint32;
        description
          "The number of routes that are protected by a local (that
          is, directly connected) loop-free alternate.";
        config false;
      }

      // Low-level model info: Corresponds to lfaStatsRemoteLfaProtectedRoutes.
      leaf protected-remote-lfa-routes {
        type uint32;
        description
          "The number of routes that are protected by a remote (that
          is, indirectly connected) loop-free alternate.";
        config false;
      }

    } // lfa-stats

  } // lfa-global-stats

  grouping lfa-interface-config {

    // Low-level model info: Corresponds to configuration fields in AMB_LFA_IF (lfaIfTable).

    container lfa {

      description
        "Each entry in this table represents a network interface.";

      user-ext:CLI-comm-help "Configure LFA on interface";
      user-ext:CLI-no-comm-help "Configure LFA on interface";

      presence "Enable LFA";

      container protection {

        user-ext:CLI-comm-help "Configure LFA protection for interface";
        user-ext:CLI-no-comm-help "Configure LFA protection for interface";

        // Low-level model info: Corresponds to lfaIfEnable.  The MIB default for lfaIfEnable is true.
        leaf disable {
          type empty;
          description
            "Whether or not LFA calculation should be enabled for
            primary next hops that use this interface.

            If this field is set to true, then DC-LFA will attempt to
            compute an LFA for any primary next hop that uses this
            interface.

            If this field is set to false, then DC-LFA will not
            compute an LFA for any primary next hop that uses this
            interface.

            For any interface that is not configured in this table,
            DC-LFA uses the lfaEntEnable field in the entity table to
            decide whether or not to compute LFAs.";

          user-ext:CLI-comm-help "Disable LFA calculation for primary next hops";
          user-ext:CLI-no-comm-help "Enable LFA calculation for primary next hops";
        }

      } // protection

      // Low-level model info: Corresponds to lfaIfExclude.  The MIB default is false.
      leaf exclude {
        type empty;
        description
          "Whether or not this interface should be excluded from
          providing LFA protection for other interfaces.

          If this field is set to true, then DC-LFA will not use
          this interface as an LFA for any primary next hop.

          If this field is set to false, then DC-LFA will include
          this interface as a candidate for providing LFA protection
          to any primary next hop.

          For any interface that is not configured in this table,
          DC-LFA uses the lfaEntExcludeAll field in the entity table
          to decide whether or not the interface should be a
          candidate.";

        user-ext:CLI-comm-help "Exclude interface from giving LFA protection for other interfaces";
        user-ext:CLI-no-comm-help "Include interface in giving LFA protection for other interfaces";
      }

    } // lfa

  } // lfa-interface-config

  grouping lfa-database-stats {

    // Low-level model info: Corresponds to fields in AMB_LFA_DB_STATS (lfaDbStatsTable).

    description
      "DC-LFA read-only table containing statistics about the LFAs
      available to the local router, with a separate row per
      routing protocol-specific database identifier:

      -  If the routing protocol is OSPFv2 or OSPFv3, the
      protocol-specific database identifier is the OSPF area
      ID.
      -  If the routing protocol is IS-IS, the protocol-specific
      database identifier is the IS-IS level.

      The global statistics in the lfaStatsTable row for a given
      DC-LFA entity do not necessarily match the sum of the
      statistics in the different lfaDbStatsTable rows for the
      same entity:

      -  There may be a route to a given prefix in multiple
      databases (for example, in both the level 1 and level 2
      IS-IS databases).  In this case, this prefix will be
      included once in the set of global statistics, and once
      in each of the corresponding sets of per-database
      statistics.

      -  The global unprotected routes counter
      (lfaStatsUnprotectedRoutes) may include routes that
      DC-LFA has been asked to protect, but whose destination
      prefix does not exist in any of the databases provided by
      the RPM.  In this case, the prefix will not be included
      in the statistics in any lfaDbStatsTable row.";

    // Low-level model info: Corresponds to lfaDbStatsRpmType.
    leaf protocol {
      type lfa-protocol-t;
      description
        "The type of Routing Protocol Manager (RPM) that this
        routing information was learned from.

        The RPM is one of DC-OSPFv2, DC-OSPFv3, or DC-ISIS.";
      config false;
    }

    // Low-level model info: Corresponds to lfaDbStatsAddressType.
    leaf address-family {
      type lfa-afi-t;
      description
        "The address family for this set of routing information.";
      config false;
    }

    // Low-level model info: Corresponds to lfaDbStatsDatabaseId.
    leaf database-id {
      type uint32;
      description
        "Protocol-specific database identifier.

        When the Routing Protocol Manager is DC-OSPFv2 or
        DC-OSPFv3, this is the OSPF area ID.

        When the Routing Protocol Manager is DC-ISIS, this is the
        IS-IS level (which is either 1 or 2).";
      config false;
    }

    // Low-level model info: Corresponds to lfaDbStatsTotalRts.
    leaf total-routes {
      type uint32;
      description
        "For this particular protocol-specific database, this is
        the total number of routes that this DC-LFA entity has
        tried to find loop-free alternates for.";
      config false;
    }

    // Low-level model info: Corresponds to lfaDbStatsUnprotectedRts.
    leaf unprotected-routes {
      type uint32;
      description
        "For this particular protocol-specific database, this is
        the number of routes that are not protected by any
        loop-free alternate or ECMP next hop.";
      config false;
    }

    // Low-level model info: Corresponds to lfaDbStatsLfaProtectedRts.
    leaf protected-lfa-routes {
      type uint32;
      description
        "For this particular protocol-specific database, this is
        the number of routes that are protected by a loop-free
        alternate.";
      config false;
    }

    // Low-level model info: Corresponds to lfaDbStatsEcmpProtectedRts.
    leaf protected-ecmp-routes {
      type uint32;
      description
        "For this particular protocol-specific database, this is
        the number of routes that are protected by equal-cost
        multipath next hops.";
      config false;
    }

    // Low-level model info: Corresponds to lfaDbStatsLocalLfaProtectedRts.
    leaf protected-local-lfa-routes {
      type uint32;
      description
        "For this particular protocol-specific database, this is
        the number of routes that are protected by a local (that
        is, directly connected) loop-free alternate.";
      config false;
    }

    // Low-level model info: Corresponds to lfaDbStatsRemoteLfaProtectedRts.
    leaf protected-remote-lfa-routes {
      type uint32;
      description
        "For this particular protocol-specific database, this is
        the number of routes that are protected by a remote (that
        is, indirectly connected) loop-free alternate.";
      config false;
    }

  } // lfa-database-stats

  grouping lfa-path-state {

    // Low-level model info: Corresponds to fields in AMB_LFA_PATH (lfaPathTable).

    description
      "DC-LFA path table.

      This table contains information about all primary paths that
      have been considered by DC-LFA.  The information in this
      table documents the reasons why DC-LFA has, or has not,
      selected each neighbor as the LFA for each primary path.

      For every primary hext hop that DC-LFA has been asked to
      provide protection for, there is a row in this table for
      every other adjacent next hop and every potential remote
      (indirectly connected) next hop.";

    // Low-level model info: Corresponds to lfaPathDestAddr(Type) and lfaPathDestPrefixLen.
    leaf prefix {
      type interfaces:iface-ip-prefix-t;
      description
        "The destination Internet address prefix.";
      config false;
    }

    // Low-level model info: Corresponds to lfaPathPriNHAddr(Type).
    leaf primary-nexthop-address {
      type interfaces:iface-ip-address-t;
      description
        "The primary next hop router address.";
      config false;
    }

    // Low-level model info: Corresponds to lfaPathPriNHIfIndex.
    leaf primary-nexthop-if-index {
      type meta:ro-if-index-or-zero;
      description
        "The index of the local network interface of the primary next
        hop.";
      config false;
    }

    // Low-level model info: Corresponds to lfaPathPriNHIfIndex.
    leaf primary-nexthop-if-base-name {
      type interfaces:iface-base-name;
      description
        "The base name of the local network interface of the primary next
        hop.";
      config false;
    }

    // Low-level model info: Corresponds to lfaPathPriNHIfIndex.
    leaf primary-nexthop-if-ext-id {
      type interfaces:iface-ext-id;
      description
        "The extended ID of the local network interface of the primary next
        hop.";
      config false;
    }

    // Low-level model info: Corresponds to lfaPathCandAddr(Type).
    leaf candidate-address {
      type interfaces:iface-ip-address-t;
      description
        "The candidate LFA router address.";
      config false;
    }

    // Low-level model info: Corresponds to lfaPathCandIfIndex.
    leaf candidate-if-index {
      type meta:ro-if-index-or-zero;
      description
        "The index of the local network interface of the candidate LFA.
        An interface of 0 is used for remote candidates which have
        no tunnel.";
      config false;
    }

    // Low-level model info: Corresponds to lfaPathCandIfIndex.
    leaf candidate-if-base-name {
      type interfaces:iface-base-name;
      description
        "The base name of the local network interface of the candidate LFA.
        An interface of 0 is used for remote candidates which have
        no tunnel.";
      config false;
    }

    // Low-level model info: Corresponds to lfaPathCandIfIndex.
    leaf candidate-if-ext-id {
      type interfaces:iface-ext-id;
      description
        "The extended ID of the local network interface of the candidate LFA.
        An interface of 0 is used for remote candidates which have
        no tunnel.";
      config false;
    }

    // Low-level model info: Corresponds to lfaPathAttachedRouterId.
    leaf attached-router-id {
      type lfa-router-id-t;
      description
        "If this is a remote (indirectly connected) candidate path,
        the router ID of the directly attached neighbor used to
        reach the candidate next-hop.

        The length for this field is given in bytes.  It is set to
        zero length for local (directly attached) candidate paths.";
      config false;
    }

    // Low-level model info: Corresponds to lfaPathAttachedIfIndex.
    leaf attached-if-index {
      type meta:ro-if-index-or-zero;
      description
        "If this is a remote (indirectly connected) candidate path,
        the index of the local network interface used to reach the
        attached neighbor.

        This field is set to zero for local (directly attached)
        candidate paths.";
      config false;
    }

    // Low-level model info: Corresponds to lfaPathAttachedIfIndex.
    leaf attached-if-base-name {
      type interfaces:iface-base-name;
      description
        "If this is a remote (indirectly connected) candidate path,
        the base name of the local network interface used to reach the
        attached neighbor.

        This field is set to zero for local (directly attached)
        candidate paths.";
      config false;
    }

    // Low-level model info: Corresponds to lfaPathAttachedIfIndex.
    leaf attached-if-ext-id {
      type interfaces:iface-ext-id;
      description
        "If this is a remote (indirectly connected) candidate path,
        the extended ID of the local network interface used to reach the
        attached neighbor.

        This field is set to zero for local (directly attached)
        candidate paths.";
      config false;
    }

    // Low-level model info: Corresponds to lfaPathProvidingProtection.
    leaf providing-protection {
      type boolean;
      description
        "If this candidate is providing LFA protection to the
        primary path, then this field is set to true.
        Otherwise, it is set to false.";
      config false;
    }

    // Low-level model info: Corresponds to lfaPathReason.
    leaf reason {
      type lfa-reason-t;
      description
        "The reason for the decision that DC-LFA has taken for this
        candidate.  If lfaPathProvidingProtection is true, this is
        set to lfaRsnBestCandidate.  Otherwise, it gives the
        reason why the candidate was rejected.

        The other path properties given in this row contain the
        detailed data that DC-LFA used when reaching this
        decision.";
      config false;
    }

    // Low-level model info: Corresponds to lfaPathPrimaryExcluded.
    leaf primary-excluded {
      type boolean;
      description
        "Whether or not this primary path is excluded from being
        protected by an LFA because of a policy.";
      config false;
    }

    // Low-level model info: Corresponds to lfaPathCandidateExcluded.
    leaf candidate-excluded {
      type boolean;
      description
        "Whether or not this candidate is excluded from being an
        LFA because of a policy.

        If lfaPathRemoteLfa is true, the policy used is a
        combination of the policy applied to the
        lfaPathCandIfIndex and the lfaPathAttachedIfIndex.";
      config false;
    }

    // Low-level model info: Corresponds to lfaPathLoopFree.
    leaf loop-free {
      type boolean;
      description
        "Whether or not this candidate is loop-free for this
        destination.";
      config false;
    }

    // Low-level model info: Corresponds to lfaPathOverloaded.
    leaf overloaded {
      type boolean;
      description
        "Whether or not this candidate is a path via an overloaded
        neighbor router.";
      config false;
    }

    // Low-level model info: Corresponds to lfaPathPrimary.
    leaf primary {
      type boolean;
      description
        "Whether or not this candidate is a primary path.  Primary
        paths are least-cost paths via non-overloaded next hops.";
      config false;
    }

    // Low-level model info: Corresponds to lfaPathRemoteLfa.
    leaf remote-lfa {
      type boolean;
      description
        "Whether or not this candidate is a remote (indirectly
        attached) LFA path.";
      config false;
    }

    // Low-level model info: Corresponds to lfaPathMetric.
    leaf metric {
      type uint32;
      description
        "For a local (directly attached) LFA, the total IGP metric
        of this path.

        If lfaPathRemoteLfa is True then the path is indirectly
        attached and this is the tunnel metric to reach the remote
        LFA hop.";
      config false;
    }

    // Low-level model info: Corresponds to lfaPathNodeProt.
    leaf node-protecting {
      type boolean;
      description
        "Whether or not this path protects against the failure of
        the next-hop router.";
      config false;
    }

    // Low-level model info: Corresponds to lfaPathRouterId.
    leaf router-id {
      type lfa-router-id-t;
      description
        "The router ID of the next hop router on this path.

        The length for this field is given in bytes.";
      config false;
    }

  } // lfa-path-state

  grouping dest-list-state {

    // Low-level model info: Corresponds to fields in AMB_LFA_LFA (lfaLfaTable).

    description
      "A destination and primary path protected by an LFA.";

    // Low-level model info: Corresponds to lfaLfaDestAddr(Type) and lfaLfaDestPrefixLen.
    leaf prefix {
      type interfaces:iface-ip-prefix-t;
      description
        "The destination IP prefix.";
      config false;
    }

    // Low-level model info: Corresponds to lfaLfaPriNHAddr(Type).
    leaf primary-nexthop-address {
      type interfaces:iface-ip-address-t;
      description
        "The primary next hop IP address.";
      config false;
    }
  } // dest-list-state

  grouping lfa-list-state {

    // Low-level model info: Corresponds to fields in AMB_LFA_LFA (lfaLfaTable).

    description
      "A Loop Free Alternate next hop and the destinations and primary paths
       protected by each.";

    // Low-level model info: Corresponds to lfaLfaAddr(Type).
    leaf lfa-address {
      type interfaces:iface-ip-address-t;
      description
        "The LFA IP address.";
      config false;
    }

    // Low-level model info: Corresponds to lfaLfaRemote.
    leaf remote {
      type boolean;
      description
        "Whether or not this LFA is a remote (indirectly attached) path.";
      config false;
    }

    list dest-list {
      description "Destinations protected by this LFA.";
      uses dest-list-state;
    }
  }

  grouping lfa-global-state {

    description
      "Global LFA state.";

    container lfa-database-stats-list {

      description
        "Container to hold LFA Database Statistics.";

      config false;

      list lfa-database-stats {

        // Low-level model info: Corresponds to fields in AMB_LFA_DB_STATS (lfaDbStatsTable).

        description
          "LFA Database Statistics.";

        uses lfa-database-stats;

      } // lfa-database-stats

    } // lfa-database-stats-list

    container lfa-path-list {

      description
        "Container to hold LFA Path Table.";

      config false;

      list lfa-path {

        // Low-level model info: Corresponds to fields in AMB_LFA_PATH (lfaPathTable).

        description
          "DC-LFA path table.";

        uses lfa-path-state;

      } // lfa-path

    } // lfa-path-list

    container lfa-list {

      description
        "Container to hold the LFA list.";

      config false;

      list lfa {

        // Low-level model info: Corresponds to fields in AMB_LFA_LFA (lfaLfaTable).

        description
          "List of LFAs and the destinations protected by each.";

        uses lfa-list-state;

      } // lfa-list

    } // lfas

  } // lfa-global-state

} // lfa
