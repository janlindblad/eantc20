module l3vpn {

  namespace "http://metaswitch.com/yang/nbu/l3vpn/201511130000Z";

  prefix l3vpn;

  import user-extensions { prefix "user-ext"; }
  import metaswitch-yang-types { prefix meta; }
  import routing { prefix "routing"; }

  organization "Metaswitch Networks";

  contact "Postal: Metaswitch Networks
                   100 Church Street
                   Enfield
                   EN2 6BQ
                   United Kingdom
           Tel:    +44 20 8366 1177
           E-mail: info@metaswitch.com";

  description
    "Layer-3 Multiprotocol Label Switching Virtual Private Networks";

  revision 2016-07-07 {
    description "Restructure following customer feedback.";
  }

  revision 2016-05-16 {
    description "Initial revision.";
  }

  typedef l3vpn-vrf-max-prefix-t {
    type uint32 {
      range "0..4294967295";
    }
    description
      "(0-4294967295)";
  }

  feature l3vpns {
    description
      "This feature means that the device supports Layer 3 VPNs";
  }

  grouping vrf-config {

    // Low-level model info: Corresponds to AMB_BVM_ENT (mplsVpnEntTable) and
    // AMB_BVM_VRF (mplsVpnVrfTable).

    leaf vpn-id {
      type meta:vpn-id;
      description
        "The VPN ID as specified in RFC 2685.";

      must "(../rd)" {
        error-message "An L3VPN route distinguisher must be defined if the VPN ID has been configured";
      }

      user-ext:CLI-comm-help "Set VPN id";
      user-ext:CLI-no-comm-help "Remove VPN id";
      user-ext:CLI-param-help "Set VPN id";
    }

    leaf rd {
      type meta:bgp-route-distinguisher;
      description
        "The route distinguisher to use for this VRF.";

      user-ext:CLI-comm-help "Set route distinguisher";
      user-ext:CLI-no-comm-help "Remove route distinguisher";
      user-ext:CLI-param-help "Set route distinguisher";
    }

    container maximum {

      user-ext:CLI-comm-help "Set maximum prefix configuration";
      user-ext:CLI-no-comm-help "Remove maximum prefix configuration";

      leaf prefix {
        type l3vpn-vrf-max-prefix-t;
        description
          "The maximum number of prefixes that can be stored in this VRF.
          Setting the value 0 means that there is no limit.";

        must "(../../rd)" {
          error-message "An L3VPN route distinguisher must be defined if the maximum prefix count has been configured";
        }

        user-ext:CLI-comm-help "Set maximum number of routes for VRF.";
        user-ext:CLI-no-comm-help "Set maximum number of routes for VRF to default.";
        user-ext:CLI-param-help "Set maximum number of routes for VRF. The value
                                 0 means there is no limit.";
      }

    } // maximum

  } // vrf-config


  /*
   * Augments the routing model with additional L3VPN properties for an IP-VRF.
   */
  augment "/routing:router/routing:vrf" {

    description
      "Augments the routing model with additional L3VPN properties for an
       IP-VRF";

      uses vrf-config;

  } // augment - L3VPN properties for an IP-VRF

} // l3vpn
