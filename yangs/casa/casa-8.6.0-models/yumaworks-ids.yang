module yumaworks-ids {

    namespace "http://yumaworks.com/ns/yumaworks-ids";
    prefix "yid";

    import ietf-netconf-monitoring { prefix mon; }

    organization "YumaWorks, Inc.";

    contact
        "Support <support@yumaworks.com>";

    description
         "YumaPro Common Identities

     Copyright (c) 2012 - 2014 YumaWorks, Inc. All rights reserved.

     Redistribution and use in source and binary forms, with or
     without modification, is permitted pursuant to, and subject
     to the license terms contained in, the BSD 3-Clause License
     http://opensource.org/licenses/BSD-3-Clause";


   revision 2014-07-12 {
       description
         "Add netconf-tcp-ncx.";
    }

    revision 2013-09-29 {
       description 
         "Add netconf-local and netconf-aflocal.";
    }

    revision 2012-06-28 {
       description 
         "Initial version.";
    }

    identity netconf-http {
      base mon:transport;
      description
        "REST API over HTTP.";
    }

    identity netconf-cli {
      base mon:transport;
      description
        "CLI over ???, probably SSH.";
    }

    identity netconf-aflocal {
      base mon:transport;
      description
        "AF_LOCAL file socket. <ncx-connect> protocol";
    }

    identity netconf-local {
      base mon:transport;
      description
        "TCP socket. tail-f connect protocol.";
    }

    identity netconf-tcp-ncx {
      base mon:transport;
      description
        "TCP socket. YumaWorks <ncx-connect> protocol.";
    }

}
