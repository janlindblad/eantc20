module arcos-classifier-filter {
  yang-version 1.1;
  namespace "http://yang.arrcus.com/arcos/classifier/filter";
  prefix arc-cfr-fltr;

  import arcos-classifier-filter-types {
    prefix arc-cfr-fltr-types;
  }
  import ietf-inet-types {
    prefix inet;
  }

  organization
    "Arrcus, Inc.";
  contact
    "Arrcus, Inc.
     Customer Service
     Postal: 2077 Gateway Place
     San Jose, CA 95110
     Tel: +1 1XXX XXX-XXXX
     E-mail: xxx@arrcus.com";
  description
    "YANG data-model for classifier filters";

  /*
   * cos filter type
   *
   * Here we define cos parameters but do not directly use inside filter
   * We will let app specific data-model decide which filter types to be
   * included for app specific classifier container
   */

  grouping cos-top {
    description
      "Grouping for Layer-2 802.1p Class Of Service values";
    leaf-list cos-value {
      type uint8 {
        range "0..7";
      }
      description
        "List of Layer-2 802.1p Class Of Service values";
    }
  }

  /*
   * dscp filter type
   *
   * Here we define dscp parameters but do not directly use inside filter
   * We will let app specific data-model decide which filter types to be
   * included for app specific classifier container
   */

  grouping dscp-top {
    description
      "Grouping for Layer-3 IP Diffserv Code-Point values";
    leaf-list dscp-value {
      type inet:dscp;
      description
        "List of Layer-3 IP Diffserv Code-Points";
    }
  }

  /*
   * local-tc filter type
   *
   * Here we define local-tc parameters but do not directly use inside filter
   * We will let app specific data-model decide which filter types to be
   * included for app specific classifier container
   */

  grouping local-tc-top {
    description
      "Grouping for local priority Traffic Class values";
    leaf-list local-tc-value {
      type uint8 {
        range "0..7";
      }
      description
        "List of local priority Traffic Classes";
    }
  }

  /*
   * mpls-tc filter type
   *
   * Here we define mpls-tc parameters but do not directly use inside filter
   * We will let app specific data-model decide which filter types to be
   * included for app specific classifier container
   */

  grouping mpls-tc-top {
    description
      "Grouping for MPLS Traffic Class values";
    leaf-list mpls-tc-value {
      type uint8 {
        range "0..7";
      }
      description
        "List of MPLS Traffic Class values";
    }
  }

  /*
   * acl filter type
   *
   * Here we just define this filter type but do not directly use in filter
   * We will let app specific data-model decide which filter types to be
   * included for app specific classifier container
   */

  grouping acl-top {
    description
      "Grouping for ACL reference";
    leaf acl-name {
      type string;
      mandatory true;
      description
        "reference to acl name";
    }
  }

  /*
   * exception filter type
   *
   * Here we just define this filter type but do not directly use in filter
   * We will let app specific data-model decide which filter types to be
   * included for app specific classifier container
   */

  grouping exception-top {
    description
      "Grouping for Exception filter types";
    leaf exception-type {
      type identityref {
        base arc-cfr-fltr-types:EXCEPTION_TYPE;
      }
      mandatory true;
      description
        "packets that fail ip destination lookup in the forwarding";
    }
  }
}
