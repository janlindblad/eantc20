module arcos-mpls {
  yang-version 1.1;
  namespace "http://yang.arrcus.com/arcos/mpls";
  prefix arc-mpls;

  grouping label-range-top {
    description
      "Top-level grouping for configured MPLS label ranges.";

    container label-range {
      description
        "A range of labels configured for label reservation";

      leaf base {
        type uint32 {
          range "16..max";
        }
        mandatory true;
        description
          "Starting label of the label range";
      }

      leaf range {
        type uint32;
        mandatory true;
        description
          "Number of labels in the label range";
      }

      leaf description {
        type string;
        description
          "Description, or comment, for the label range";
      }
    }
  }

  grouping label-ranges-top {
    description
      "Top-level grouping for label ranges";

    list mpls-label-ranges {
      key "route-type";

      description
        "Configuration data for MPLS label ranges";

      leaf route-type {
        type enumeration {
          enum connected-route {
            description
              "MPLS label ranges for connected routes";
          }
          enum static-route {
            description
              "MPLS label ranges for static routes";
          }
        }
      }

      uses label-range-top;
    }
  }

  uses label-ranges-top;
}
