module arcos-openconfig-lacp-deviations {
  yang-version 1.1;
  namespace "http://yang.arrcus.com/arcos/openconfig/lacp/deviations";
  prefix arc-oc-lacp-dev;

  import openconfig-lacp {
    prefix oc-lacp;
  }

  import openconfig-interfaces {
    prefix oc-if;
  }

  deviation "/oc-lacp:lacp/oc-lacp:config" {
    deviate not-supported;
    description "Not supported in this release";
  }
  deviation "/oc-lacp:lacp/oc-lacp:state" {
    deviate not-supported;
    description "Not supported in this release";
  }
  deviation "/oc-lacp:lacp/oc-lacp:interfaces/oc-lacp:interface" +
            "/oc-lacp:config/oc-lacp:lacp-mode" {
    deviate not-supported;
    description "Not supported in this release";
  }
  deviation "/oc-lacp:lacp/oc-lacp:interfaces/oc-lacp:interface" +
            "/oc-lacp:config/oc-lacp:interval" {
    deviate replace {
      default FAST;
    }
  }
  deviation "/oc-lacp:lacp/oc-lacp:interfaces/oc-lacp:interface" +
            "/oc-lacp:config/oc-lacp:system-id-mac" {
    deviate not-supported;
    description "Not supported in this release";
  }
  deviation "/oc-lacp:lacp/oc-lacp:interfaces/oc-lacp:interface" +
            "/oc-lacp:config/oc-lacp:system-priority" {
    deviate not-supported;
    description "Not supported in this release";
  }
  deviation "/oc-lacp:lacp/oc-lacp:interfaces/oc-lacp:interface" +
            "/oc-lacp:state/oc-lacp:system-id-mac" {
    deviate not-supported;
    description "Not supported in this release";
  }
  deviation "/oc-lacp:lacp/oc-lacp:interfaces/oc-lacp:interface" +
            "/oc-lacp:state/oc-lacp:lacp-mode" {
    deviate not-supported;
    description "Not supported in this release";
  }
  deviation "/oc-lacp:lacp/oc-lacp:interfaces/oc-lacp:interface" +
            "/oc-lacp:state/oc-lacp:system-priority" {
    deviate not-supported;
    description "Not supported in this release";
  }
  deviation "/oc-lacp:lacp/oc-lacp:interfaces/oc-lacp:interface" +
            "/oc-lacp:members/oc-lacp:member/oc-lacp:state" +
            "/oc-lacp:activity" {
    deviate not-supported;
    description "Not supported in this release";
  }
  deviation "/oc-lacp:lacp/oc-lacp:interfaces/oc-lacp:interface" +
            "/oc-lacp:members/oc-lacp:member/oc-lacp:state" +
            "/oc-lacp:system-id" {
    deviate not-supported;
    description "Not supported in this release";
  }
  deviation "/oc-lacp:lacp/oc-lacp:interfaces/oc-lacp:interface" +
            "/oc-lacp:members/oc-lacp:member/oc-lacp:state" +
            "/oc-lacp:oper-key" {
    deviate not-supported;
    description "Not supported in this release";
  }
  deviation "/oc-lacp:lacp/oc-lacp:interfaces/oc-lacp:interface" +
            "/oc-lacp:members/oc-lacp:member/oc-lacp:state" +
            "/oc-lacp:partner-id" {
    deviate not-supported;
    description "Not supported in this release";
  }
  deviation "/oc-lacp:lacp/oc-lacp:interfaces/oc-lacp:interface" +
            "/oc-lacp:members/oc-lacp:member/oc-lacp:state" +
            "/oc-lacp:partner-key" {
    deviate not-supported;
    description "Not supported in this release";
  }
  deviation "/oc-lacp:lacp/oc-lacp:interfaces/oc-lacp:interface" +
            "/oc-lacp:members/oc-lacp:member/oc-lacp:state" +
            "/oc-lacp:port-num" {
    deviate not-supported;
    description "Not supported in this release";
  }
  deviation "/oc-lacp:lacp/oc-lacp:interfaces/oc-lacp:interface" +
            "/oc-lacp:members/oc-lacp:member/oc-lacp:state" +
            "/oc-lacp:partner-port-num" {
    deviate not-supported;
    description "Not supported in this release";
  }
  deviation "/oc-lacp:lacp/oc-lacp:interfaces/oc-lacp:interface" +
            "/oc-lacp:members/oc-lacp:member/oc-lacp:state" +
            "/oc-lacp:counters" {
    deviate not-supported;
    description "Not supported in this release";
  }
}
