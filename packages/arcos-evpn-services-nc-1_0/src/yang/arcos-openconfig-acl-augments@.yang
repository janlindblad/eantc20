module arcos-openconfig-acl-augments {
  yang-version 1.1;
  namespace "http://yang.arrcus.com/arcos/openconfig/acl/augments";
  prefix arc-oc-acl-aug;

  import openconfig-acl {
    prefix oc-acl;
  }

  import iana-if-type {
    prefix ianaift;
  }

  import openconfig-yang-types {
    prefix oc-yang;
  }

  import openconfig-interfaces {
    prefix oc-if;
  }

  import openconfig-if-ethernet {
    prefix oc-eth;
  }

  import openconfig-if-aggregate {
    prefix oc-lag;
  }

  grouping interface-acl-sets-top {
    description
      "Top-level grouping for per-interface per-direction ACL data";

    list acl-set {
      key "type";
      description
        "List of per-direction ACLs on the interface";

      leaf type {
        type identityref {
          base oc-acl:ACL_TYPE;
        }
        description
          "Reference to the ACL set type (ACL_IPV4, ACL_IPV6 or ACL_L2)
          applied on the interface direction.";
      }

      leaf set-name {
        type leafref {
          path "/oc-acl:acl/oc-acl:acl-sets" +
               "/oc-acl:acl-set[oc-acl:type=current()/../type]/oc-acl:config" +
               "/oc-acl:name";
        }
        mandatory true;
        description
          "Reference to the ACL set name applied on interface direction";
      }
    }
  }

  grouping acl-service-policies-top {
    description
      "Top-level grouping for per-interface ACL data";

    list acl-service-policies {
      key "direction";
      description
        "Direction of traffic the ACL polices take effect on";

      leaf direction {
        type enumeration {
          enum ingress-acl-sets {
            description
              "ACL per-interface policies for incoming traffic";
          }
          enum egress-acl-sets {
            description
              "ACL per-interface policies for outgoing traffic";
          }
        }
      }

      uses interface-acl-sets-top;
    }
  }

  augment "/oc-if:interfaces/oc-if:interface" {
    uses acl-service-policies-top {
      when "((current()/oc-if:config/oc-if:type = 'ianaift:softwareLoopback') or " +
           " (current()/oc-if:config/oc-if:type = 'ianaift:l3ipvlan') or " +
           " (current()/oc-if:config/oc-if:type = 'ianaift:ieee8023adLag') or " +
           " ((current()/oc-if:config/oc-if:type = 'ianaift:ethernetCsmacd') and (boolean(current()/oc-eth:ethernet/oc-eth:config/oc-lag:aggregate-id) != 'true')))";
    }
  }

  augment "/oc-acl:acl/oc-acl:acl-sets/oc-acl:acl-set/oc-acl:acl-entries" +
          "/oc-acl:acl-entry/oc-acl:state" {
    leaf matched-ingress-packets {
      type oc-yang:counter64;
      description
        "Aggregate count of the number of packets matching the current ACL
        entry on ingress direction accross all interfaces.";
    }
    leaf matched-egress-packets {
      type oc-yang:counter64;
      description
        "Aggregate count of the number of packets matching the current ACL
        entry on egress direction accross all interfaces.";
    }
    leaf matched-ingress-octets {
      type oc-yang:counter64;
      description
        "Aggregate count of the number of octets (bytes) matching the current
        ACL entry on ingress direction accross all interfaces.";
    }
    leaf matched-egress-octets {
      type oc-yang:counter64;
      description
        "Aggregate count of the number of octets (bytes) matching the current
        ACL entry on ingress direction accross all interfaces.";
    }
  }


  augment "/oc-acl:acl" {
    container system-defined {
      config false;
      description
        "Display system defined ACLs.These ACLs can not be re-used or modified";
      list acl-set {
        key "name type";
        description
          "List of ACL sets, each comprising of a list of ACL
          entries";

        uses oc-acl:acl-set-config;
        uses oc-acl:access-list-entries-top;
      }
    }
  }
}
