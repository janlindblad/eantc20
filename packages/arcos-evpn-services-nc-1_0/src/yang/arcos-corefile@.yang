module arcos-corefile {
  yang-version 1.1;
  namespace "http://yang.arrcus.com/arcos/corefile";
  prefix arc-corefile;

  list core {
    key "corefile";

    description
      "Display system process generated coredump files";

    config false;

    leaf corefile {
      type string;
      description
        "Name of the corefile";
    }

    leaf time {
      type string;
      description
        "Time and date when the coredump file was generated";
    }
  }
}
