module arcos-openconfig-policy-types {
  yang-version 1.1;
  namespace "http://yang.arrcus.com/arcos/openconfig/policy-types";
  prefix arc-oc-pol-types;

  import openconfig-policy-types {
    prefix oc-pol-types;
  }

  identity ADJACENCY {
    base oc-pol-types:INSTALL_PROTOCOL_TYPE;
    description
      "Adjacency route";
  }
 }
