module arcos-qos-policy-deviations {
  yang-version 1.1;
  namespace "http://yang.arrcus.com/arcos/qos/policy/deviations";
  prefix arc-qos-pol-dev;

  import arcos-qos {
    prefix arc-qos;
  }
  import arcos-qos-classifier {
    prefix arc-qos-cfr;
  }
  import arcos-qos-policy {
    prefix arc-qos-pol;
  }

  organization
    "Arrcus, Inc.";
  contact
    "Arrcus, Inc.
     Customer Service
     Postal: 2077 Gateway Place
     San Jose, CA 95110
     Tel: +1 1XXX XXX-XXXX
     E-mail: xxx@arrcus.com";
  description
    "YANG data-model for qos policy validations
     Expanded from the qos policy data model";

  deviation "/arc-qos:qos/arc-qos-pol:policies/arc-qos-pol:policy"
          + "/arc-qos-pol:classifiers/arc-qos-pol:classifier"
          + "/arc-qos-pol:name" {
    deviate replace {
      type leafref {
        path "/arc-qos:qos/arc-qos-cfr:classifiers/arc-qos-cfr:classifier/arc-qos-cfr:name";
      }
    }
    description
      "Leafref to qos classifier database";
  }

  deviation "/arc-qos:qos/arc-qos-pol:policies/arc-qos-pol:policy"
          + "/arc-qos-pol:classifiers/arc-qos-pol:classifier"
          + "/arc-qos-pol:actions/arc-qos-pol:action"
          + "/arc-qos-pol:rate-min/arc-qos-pol:config/arc-qos-pol:percent" {
    deviate not-supported;
    description
      "Not supported in this release";
  }
}
