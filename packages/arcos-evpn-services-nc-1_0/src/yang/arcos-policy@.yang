module arcos-policy {
  yang-version 1.1;
  namespace "http://yang.arrcus.com/arcos/policy";
  prefix arc-pol;

  import arcos-policy-action-types {
    prefix arc-pol-actn-types;
  }

  organization
    "Arrcus, Inc.";
  contact
    "Arrcus, Inc.
     Customer Service
     Postal: 2077 Gateway Place
     San Jose, CA 95110
     Tel: +1 1XXX XXX-XXXX
     E-mail: xxx@arrcus.com";
  description
    "YANG data-model for generic policy definitions.
     This is a base data model for policy that different apps
     can make use of.    This base data model itself does not
     expose container for policy (For an example look at
     arrcus-qos-policy.yang)";

  grouping action-attributes {
    description
      "Grouping for action attributes like action type";
    leaf type {
      type identityref {
        base arc-pol-actn-types:ACTION_TYPE;
      }
      description
        "This defines action type ";
    }
  }

  grouping actions-state-top {
    description
      "Grouping for an action when used in a policy instance";
    container actions {
      description
        "Container for action data-base in a specific policy/classifier";
      list action {
        min-elements 1;
        key "type";
        description
          "Configuration of classifier associated actions";
        leaf type {
          type identityref {
            base arc-pol-actn-types:ACTION_TYPE;
          }
          description
            "unique type identifying action";
        }
        container state {
          config false;
          description
            "Operational state parameters relating to action";
          uses action-attributes;
        }
      }
    }
  }

  grouping actions-top {
    description
      "Grouping for an action definition. An action holds action specific attributes";
    container actions {
      description
        "Container for action data-base in a specific policy/classifier";
      list action {
        min-elements 1;
        key "type";
        description
          "Configuration of classifier associated actions";
        leaf type {
          type leafref {
            path "../config/type";
          }
          description
            "unique type identifying action";
        }
        container config {
          description
            "Configuration parameters relating to action";
          uses action-attributes;
        }
        container state {
          config false;
          description
            "Operational state parameters relating to action";
          uses action-attributes;
        }
      }
    }
  }

  grouping policy-classifier-state {
    description
      "Grouping for policy classifier instance statistics";

    leaf match-packets {
      type uint64;
      description "Number of packets matched";
    }
    leaf match-bytes {
      type uint64;
      description "Number of bytes matched";
    }
  }

  grouping policy-classifier-attributes {
    description
      "Grouping for classifier attributes like name, description, logical operation";
    leaf name {
      type string {
        length "1..79";
      }
      description
        "Name of a Classifier entry in a list of Classifiers";
    }
    leaf description {
      type string {
        length "1..254";
      }
      description
        "Description of a Classifier entry in a list of Classifiers";
    }
  }

  grouping policy-classifiers-state-top {
    description
      "Top-level grouping for set of classifiers/actions potentially to be used in policy instance";
    container classifiers {
      config false;
      description
        "Set of classifiers/actions configured";

      list classifier {
        key "name";
        ordered-by user;
        description
          "Classifier entry in a policy";
        leaf name {
          type string;
          description
            "unique name identifying classifier <string, min:1 chars, max: 79 chars>";
        }
        container state {
          config false;
          description
            "Operational state parameters relating to classifier";
          uses policy-classifier-attributes;
          uses policy-classifier-state;
        }
        uses actions-state-top;
      }
    }
  }

  grouping policy-classifiers-top {
    description
      "Top-level grouping for set of classifiers/actions in a policy";
    container classifiers {
      description
        "Set of classifiers/actions configured";
      list classifier {
        key "name";
        ordered-by user;
        description
          "Classifier entry in a policy";
        leaf name {
          type leafref {
            path "../config/name";
          }
          description
            "unique name identifying classifier <string, min:1 chars, max: 79 chars>";
        }
        container config {
          description
            "Configuration parameters relating to classifier";
          uses policy-classifier-attributes;
        }
        container state {
          config false;
          description
            "Operational state parameters relating to classifier";
          uses policy-classifier-attributes;
        }
        uses actions-top;
      }
    }
  }

  grouping policy-attributes {
    description
      "Policy attributes like name, description";
    leaf name {
      type string {
        length "1..79";
      }
      description
        "Name of a Policy entry in a list of Policies";
    }
    leaf description {
      type string {
        length "1..254";
      }
      description
        "Description of a Policy entry in a list of Policies";
    }
  }

  grouping policies-top {
    description
      "Grouping for generic definition of Policies";
    container policies {
      description
        "Container for policy data-base";
      list policy {
        key "name";
        ordered-by user;
        description
          "A specific policy in the policy data-base";
        leaf name {
          type leafref {
            path "../config/name";
          }
          description
            "unique name identifying policy <string, min:1 chars, max: 79 chars>";
        }
        container config {
          description
            "Configuration parameters relating to policy";
          uses policy-attributes;
        }
        container state {
          config false;
          description
            "Operational state parameters relating to policy";
          uses policy-attributes;
        }
        uses policy-classifiers-top;
      }
    }
  }
}
