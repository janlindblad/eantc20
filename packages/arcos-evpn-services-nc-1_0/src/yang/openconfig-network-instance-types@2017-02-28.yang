module openconfig-network-instance-types {

  yang-version "1";

  // namespace
  namespace "http://openconfig.net/yang/network-instance-types";

  prefix "oc-ni-types";

  import openconfig-extensions { prefix "oc-ext"; }

  // meta
  organization "OpenConfig working group";

  contact
    "OpenConfig working group
    www.openconfig.net";

  description
    "Types associated with a network instance";

  oc-ext:openconfig-version "0.8.0";

  revision "2017-02-28" {
    description
      "Add OSPFv2 to network instance";
    reference "0.8.0";
  }

  revision "2017-01-26" {
    description
      "Add policy forwarding to network instance";
    reference "0.7.0";
  }

  revision "2017-01-13" {
    description
      "Add AFT to the network instance";
    reference "0.6.0";
  }

  revision "2016-12-15" {
    description
      "Add segment routing to network instance";
    reference "0.5.0";
  }

  revision "2016-11-10" {
    description
      "Update model to include IS-IS.";
    reference "0.4.1";
  }

  revision "2016-10-12" {
    description
      "Update table connections";
    reference "0.4.0";
  }

  revision "2016-09-28" {
    description
      "Change L2 instance to submodule; add MAC table";
    reference "0.3.0";
  }

  revision "2016-08-11" {
    description
      "Resolve repeated container names in routing protocols";
    reference "0.2.3";
  }

  revision "2016-07-08" {
    description
      "Updated with refactored routing protocol models";
    reference "0.2.1";
  }

  revision "2016-03-29" {
    description
      "Initial revision";
    reference "0.2.0";
  }

  revision "2015-10-18" {
    description
      "Initial revision";
    reference "0.1.0";
  }

  // identity statements
  identity NETWORK_INSTANCE_TYPE {
  	description
  	 "A base identity which can be extended to indicate different
     types of network instance supported by a device.";
  }

  identity DEFAULT_INSTANCE {
    base NETWORK_INSTANCE_TYPE;
    description
      "A special routing instance which acts as the 'default' or
      'global' routing instance for a network device.";
  }

  identity L3VRF {
    base NETWORK_INSTANCE_TYPE;
    description
      "A private Layer 3 only routing instance which is formed of
      one or more RIBs";
  }

  identity L2VSI {
    base NETWORK_INSTANCE_TYPE;
    description
      "A private Layer 2 only switch instance which is formed of
      one or more L2 forwarding tables";
  }

  identity L2VLAN {
    base NETWORK_INSTANCE_TYPE;
    description
      "A private Layer 2 only switch instance for VLAN based
       service. formed of a single L2 forwarding tables";
  }

  identity L2P2P {
    base NETWORK_INSTANCE_TYPE;
    description
      "A private Layer 2 only forwarding instance which acts as
      a point to point connection between two endpoints";
  }

  identity L2L3 {
    base NETWORK_INSTANCE_TYPE;
    description
      "A private Layer 2 and Layer 2 forwarding instance";
  }

  identity ENDPOINT_TYPE {
    description
      "Specification of the type of endpoint that is being associated
      with a network instance";
  }

  identity LOCAL {
    base ENDPOINT_TYPE;
    description
      "A local interface which is being associated with the endpoint";
  }

  identity REMOTE {
    base ENDPOINT_TYPE;
    description
      "A remote interface which is being associated with the
      endpoint";
  }

  identity LABEL_ALLOCATION_MODE {
    description
      "Base identity to be used to express types of label allocation
      strategies to be used within a network instance";
  }

  identity PER_PREFIX {
    base LABEL_ALLOCATION_MODE;
    description
      "A label is to be allocated per prefix entry in the RIB for the
      network instance";
  }

  identity PER_NEXTHOP {
    base LABEL_ALLOCATION_MODE;
    description
      "A label is to be allocated per nexthop entry in the RIB for
      the network instance";
  }

  identity INSTANCE_LABEL {
    base LABEL_ALLOCATION_MODE;
    description
      "A single label is to be used for the instance";
  }

  identity ENCAPSULATION {
    description
      "On the wire encapsulations that can be used when
      differentiating network instances";
  }

  identity MPLS {
    base ENCAPSULATION;
    description
      "Use MPLS labels to distinguish network instances on the wire";
  }

  identity VXLAN {
    base ENCAPSULATION;
    description
      "Use VXLAN (RFC7348) VNIs to distinguish network instances on
      the wire";
  }

  identity SIGNALLING_PROTOCOL {
    description
      "The signalling protocol that should be used to diseminate
      entries within a forwarding instance";
  }

  identity LDP {
    base SIGNALLING_PROTOCOL;
    description
      "Use LDP-based setup for signalling. Where the instance is
      a point-to-point service this refers to RFC4447 ('Martini')
      setup. Where the service is an L2VSI, or L2L3 instance it
      refers to RFC4762 LDP-signalled VPLS instances";
  }

  identity BGP_VPLS {
    base SIGNALLING_PROTOCOL;
    description
      "Use BGP-based signalling and autodiscovery for VPLS instances
      as per RFC4761";
  }

  identity BGP_EVPN {
    base SIGNALLING_PROTOCOL;
    description
      "Use BGP-based Ethernet VPN (RFC7432) based signalling for
      the network instance";
  }

  // rjs note:
  // this should move to openconfig-types when merged
  typedef route-distinguisher {
    type union {
      // type 0: <2-byte administrator>:<4-byte assigned number>
      type string {
        pattern '(65[0-5][0-3][0-5]|[1-5][1-5][0-9][0-9][0-9]|'
                + '[1-9]?[1-9]?[0-9][0-9]|[1-9]):'
                + '(4[0-2][0-9][0-4][0-9][0-6][0-7][0-2][0-9][0-5]|'
                + '[0-3][0-9]{9}|[1-9][0-9]{1,8}|[1-9])';
      }
      // type 1: <ip-address>:<2-byte assigned number>
      type string {
        pattern
          '(([0-9]|[1-9][0-9]|1[0-9][0-9]|2[0-4][0-9]|25[0-5])\.){3}'
          +  '([0-9]|[1-9][0-9]|1[0-9][0-9]|2[0-4][0-9]|25[0-5]):'
          +  '(65[0-5][0-3][0-5]|[1-5][1-5][0-9][0-9][0-9]|'
          +  '[1-9]?[1-9]?[0-9][0-9]|[1-9])';
      }
      // type 2: <4-byte as-number>:<2-byte assigned number>
      type string {
        pattern
          '(4[0-2][0-9][0-4][0-9][0-6][0-7][0-2][0-9][0-5]|'
          + '[0-3][0-9]{9}|[1-9][0-9]{1,8}|[1-9]):'
          + '(65[0-5][0-3][0-5]|[1-5]{2}[0-9]{3}|'
          + '[1-9]{0,2}[0-9][0-9]|[1-9])';
      }
    }
    description "A route distinguisher value";
    reference "RFC4364";
  }

  typedef route-target {
     type string {
       pattern
         '([0:]?(6553[0-5]|655[0-2][0-9]|65[0-4][0-9]{2}|'
       +     '6[0-4][0-9]{3}|'
       +     '[1-5][0-9]{4}|[1-9][0-9]{0,3}|0):(429496729[0-5]|'
       +     '42949672[0-8][0-9]|'
       +     '4294967[01][0-9]{2}|429496[0-6][0-9]{3}|'
       +     '42949[0-5][0-9]{4}|'
       +     '4294[0-8][0-9]{5}|429[0-3][0-9]{6}|'
       +     '42[0-8][0-9]{7}|4[01][0-9]{8}|'
       +     '[1-3][0-9]{9}|[1-9][0-9]{0,8}|0))|'
       + '([1:]?((([0-9]|[1-9][0-9]|1[0-9]{2}|2[0-4][0-9]|'
       +     '25[0-5])\.){3}([0-9]|[1-9][0-9]|'
       +     '1[0-9]{2}|2[0-4][0-9]|25[0-5])):(6553[0-5]|'
       +     '655[0-2][0-9]|'
       +     '65[0-4][0-9]{2}|6[0-4][0-9]{3}|'
       +     '[1-5][0-9]{4}|[1-9][0-9]{0,3}|0))|'
       + '([2:]?(429496729[0-5]|42949672[0-8][0-9]|'
       +     '4294967[01][0-9]{2}|'
       +     '429496[0-6][0-9]{3}|42949[0-5][0-9]{4}|'
       +     '4294[0-8][0-9]{5}|'
       +     '429[0-3][0-9]{6}|42[0-8][0-9]{7}|4[01][0-9]{8}|'
       +     '[1-3][0-9]{9}|[1-9][0-9]{0,8}|0):'
       +     '(6553[0-5]|655[0-2][0-9]|65[0-4][0-9]{2}|'
       +     '6[0-4][0-9]{3}|'
       +     '[1-5][0-9]{4}|[1-9][0-9]{0,3}|0))|'
       + '(6(:[a-fA-F0-9]{2}){6})|'
       + '(([3-57-9a-fA-F]|[1-9a-fA-F][0-9a-fA-F]{1,3}):'
       +     '[0-9a-fA-F]{1,12})';
     }

     description
       "A Route Target is an 8-octet BGP extended community
        initially identifying a set of sites in a BGP VPN
        (RFC 4364).  However, it has since taken on a more general
        role in BGP route filtering.  A Route Target consists of two
        or three fields: a 2-octet Type field, an administrator
        field, and, optionally, an assigned number field.

        According to the data formats for types 0, 1, 2, and 6 as
        defined in RFC 4360, RFC 5668, and RFC 7432, the encoding
        pattern is defined as:

        0:2-octet-asn:4-octet-number
        1:4-octet-ipv4addr:2-octet-number
        2:4-octet-asn:2-octet-number
        6:6-octet-mac-address

        Additionally, a generic pattern is defined for future
        Route Target types:

        2-octet-other-hex-number:6-octet-hex-number

        Some valid examples are 0:100:100, 1:1.1.1.1:100,
        2:1234567890:203, and 6:26:00:08:92:78:00.";
     reference
       "RFC 8294: Common YANG Data Types for the Routing Area
        RFC 4360: BGP Extended Communities Attribute.
        RFC 4364: BGP/MPLS IP Virtual Private Networks (VPNs).
        RFC 5668: 4-Octet AS Specific BGP Extended Community.
        RFC 7432: BGP MPLS-Based Ethernet VPN.";
  }

  typedef route-target-type {
    type enumeration {
      enum import {
        value 0;
        description
         "The Route Target applies to route import.";
      }
      enum export {
        value 1;
        description
         "The Route Target applies to route export.";
      }
      enum both {
        value 2;
        description
         "The Route Target applies to both route import and
          route export.";
      }
    }
    description
      "Indicates the role a Route Target takes in route filtering.";
    reference
      "RFC 8294: Common YANG Data Types for the Routing Area
      RFC 4364: BGP/MPLS IP Virtual Private Networks (VPNs).";
  }
}
