module arcos-bgp-auto-peer-group {
  yang-version 1.1;
  namespace "http://yang.arrcus.com/arcos/bgp/auto-peer-group";
  prefix arc-bgp-auto-peer-grp;

  import openconfig-types {
    prefix oc-types;
  }

  import ietf-inet-types {
    prefix oc-inet;
  }

  grouping auto-peer-group {
    description
      "Parameters related to a BGP group";
    leaf peer-grp-index {
      type uint32;
      description
        "peer-group index";
    }

    leaf peer-grp-session-type {
      type string;
      description
        "peer-group type";
    }

    leaf peer-grp-name {
      type string;
      description
        "Name of the BGP peer-group";
    }

    leaf peer-grp-neighbor-count {
      type uint32;
      description
        "Number of neighbors in peer-group";
    }

    leaf peer-grp-in-use {
      type boolean;
      description
        "peer-group in use";
    }

    leaf peer-grp-route-reflector-client {
      type boolean;
      description
        "peer-group is RR client";
    }

    leaf peer-grp-as-type {
      type string;
      description
        "peer-group AS type.";
    }
    leaf peer-grp-local-as {
      type oc-inet:as-number;
      description
        "peer-group local AS number";
    }
    leaf peer-grp-addpath {
      type boolean;
      description
        "peer-group add-paths support.";
    }
    leaf peer-grp-addpath-send {
      type string;
      description
        "peer-group add-paths send option.";
    }
    leaf peer-grp-remove-private-as {
      type boolean;
      description
        "peer-group remove-private-as support.";
    }
    leaf peer-grp-replace-private-as {
      type boolean;
      description
        "peer-group replace-private-as support.";
    }
    leaf peer-grp-aigp {
      type boolean;
      description
        "peer-group AIGP metric support.";
    }
    leaf peer-grp-graceful-shutdown-enable {
      type boolean;
      description
        "peer-group graceful-shutdown enable support.";
    }
    leaf peer-grp-graceful-shutdown-local-preference {
      type boolean;
      description
        "peer-group graceful-shutdown local preference support.";
    }
    leaf peer-grp-graceful-shutdown-med {
      type boolean;
      description
        "peer-group graceful-shutdown MED support.";
    }
    leaf peer-grp-version {
      type uint32;
      description
        "peer-group version.";
    }
    leaf peer-grp-nlri-sent {
      type uint32;
      description
        "peer-group prefix sent count.";
    }
    leaf peer-grp-unreach-nlri-sent {
      type uint32;
      description
        "peer-group unreachable prefix sent count.";
    }
    leaf peer-grp-labels-sent {
      type uint32;
      description
        "peer-group labels sent count.";
    }
    leaf peer-grp-export-policy {
      type string;
      description
        "peer-group export policy.";
    }
    leaf-list peer-grp-neighbors {
      type string;
      description
       "Neighbors in this peer-group";
    }
    leaf peer-grp-pending-updates {
      type uint32;
      description
        "Total number of outstanding update messages.";
    }
    leaf peer-grp-update-delays {
      type uint32;
      description
        "Total number of delays due to too many outstanding updates.";
    }
    leaf peer-grp-neighbor-type {
      type identityref {
        base "oc-types:ADDRESS_FAMILY";
      }
      description
        "Neighbor type i.e IPV4 or IPV6";
    }
  }

  grouping bgp-auto-peer-group-list {
    description
      "The list of BGP peer groups";

    container auto-peer-groups {
      config false;
      list auto-peer-group {
        key "peer-grp-index peer-grp-session-type";
        description
          "List of BGP peer-groups configured on the local system -
          uniquely identified by peer-group name";

        uses auto-peer-group;
      }
    }
  }
}
