module arcos-rib {
  yang-version 1.1;
  namespace "http://yang.arrcus.com/arcos/rib";
  prefix arc-rib;

  import openconfig-policy-types {
    prefix oc-pol-types;
  }
  import openconfig-network-instance {
    prefix oc-netinst;
  }
  import openconfig-network-instance-types {
    prefix oc-ni-types;
  }
  import ietf-inet-types {
    prefix inet;
  }
  import openconfig-mpls-types {
    prefix oc-mplst;
  }
  import openconfig-interfaces {
    prefix oc-if;
  }
  import openconfig-types {
    prefix oc-types;
  }
  import ietf-interfaces {
    prefix ietf-if;
  }
  import ietf-yang-types {
    prefix yang;
  }
  import openconfig-yang-types {
    prefix oc-yang;
  }

  typedef rib-path-type {
    type enumeration {
      enum "RECURSIVE" {
        value 1;
      }
      enum "CONNECTED_V4" {
        value 2;
      }
      enum "GLEAN_V4" {
        value 3;
      }
      enum "LOCAL_V4" {
        value 4;
      }
      enum "CONNECTED_V6" {
        value 5;
      }
      enum "LOCAL_V6" {
        value 6;
      }
      enum "GLEAN_V6" {
        value 7;
      }
    }
  }

  grouping rib-config {
    description
      "Configuration parameters relating to RIB 
       for a particular address family.";
    leaf address-family {
      type identityref {
        base oc-types:ADDRESS_FAMILY;
      }
      description
        "The address family of entries that are described by the
         RIB.";
    }
  }

  // identity statements

  identity RIB_DEFINED_NEXT_HOP {
    description
      "A base identity type of local defined next-hops";
  }

  identity DROP {
    base RIB_DEFINED_NEXT_HOP;
    description
      "Discard traffic for the corresponding destination";
  }

  // typedef statements

  typedef rib-defined-next-hop {
    type identityref {
      base RIB_DEFINED_NEXT_HOP;
    }
    description
      "Pre-defined next-hop designation for locally generated
       routes";
  }

  grouping rib-entry-state {
    description
      "Operational state parameters relating to a RIB entry";
    leaf origin-protocol {
      type identityref {
        base oc-pol-types:INSTALL_PROTOCOL_TYPE;
      }
      description
        "The protocol from which the RIB entry was learned.";
    }
    leaf metric {
      type uint32;
      description
        "A metric which is utilised to specify the preference of route";
    }
    leaf pref {
      type uint32;
      description
        "A preference which is utilised to select best owner among multiple
         producers of the same prefix";
    }
    leaf tag {
      type uint32;
      description
        " This can be used by protocols to filter the redistributed route
          as per the protocol redistribution policy";
    }
  }

  grouping rib-entry-nexthop-state {
    description
      "Parameters relating to a next-hop within the RIB entry";
    leaf next-hop {
      type union {
        type inet:ip-address-no-zone;
        type rib-defined-next-hop;
      }
      description
        "The next-hop that is to be used for the  route
         - this may be specified as an IP address, an interface
         or a pre-defined next-hop type - for instance, DROP.";
    }
    leaf recurse {
      type boolean;
      default "false";
      description
        "Determines whether the next-hop should be allowed to
         be looked up recursively.";
    }
    leaf weight {
      type uint32;
      description
        "The weight of the next-hop. Traffic is balanced according to
         the ratio described by the relative weights of the next hops
         that exist for the RIB entry. Note that all next-hops that are
         specified are assumed to be active next-hops and therefore
         eligible (and selected) to be installed in the FIB, and hence
         used for packet forwarding.";
    }
    leaf-list pushed-mpls-label-stack {
      type oc-mplst:mpls-label;
      ordered-by user;
      description
        "The MPLS label stack imposed when forwarding packets to the
         next-hop
         - the stack is encoded as a leaf list whereby the order of the
          entries is such that the first entry in the list is the
          label at the bottom of the stack to be pushed.

         To this end, a packet which is to forwarded to a device using
         a service label of 42, and a transport label of 8072 will be
         represented with a label stack list of [42, 8072].

         The MPLS label stack list is ordered by the user, such that no
         system re-ordering of leaves is permitted by the system.

         A swap operation is reflected by entries in the
         popped-mpls-label-stack and pushed-mpls-label-stack nodes.";
    }
    leaf interface {
      type string;
    }
    leaf vxlan {
      type boolean;
      default "false";
      description
        "recursive path pointing to a VXLAN tunnel next-hop";
    }
    leaf nh-tunnel-id {
      type uint32;
      description
        "tunnel-id for remote tunnel next-hop";
    }
    leaf rtep-mac {
      type oc-yang:mac-address;
      description
        "remote tunnel-endpoint MAC address for a vxlan tunnel next-hop";
    }
    leaf pathid {
      type uint64;
      description
        " This is pathid assigned to this path";
    }
  }

  grouping next-hops {
    description
      "Grouping for next hops";
    container next-hops {
      config false;
      description
        "Enclosing container for the list of next-hops associated
                   with the forwarding entry";
      list next-hop {
        uses rib-entry-nexthop-state;
      }
    }
  }

  grouping origin {
    description
      "Grouping for route producer";
    container origins {
      config false;
      description
        "Enclosing container for the list of next-hops associated
                   with the forwarding entry";
      list origin {
        leaf origin-protocol {
          type identityref {
            base oc-pol-types:INSTALL_PROTOCOL_TYPE;
          }
          description
            "The protocol from which the RIB entry was learned.";
        }
        leaf metric {
          type uint32;
          description
            "A metric which is utilised to specify the preference of route";
        }
        leaf pref {
          type uint32;
          description
            "A preference which is utilised to select best owner among multiple
             producers of the same prefix";
        }
        leaf tag {
          type uint32;
          description
            " This can be used by protocols to filter the redistributed route
              as per the protocol redistribution policy";
        }
        leaf route-type {
          type enumeration {
            enum "NONE" {
              description
                "None";
            }
            enum "ISIS_L1" {
              description
                "ISIS L1";
            }
            enum "ISIS_L2" {
              description
                "ISIS L2";
            }
            enum "IBGP" {
              description
                "IBGP";
            }
            enum "EBGP" {
              description
                "EBGP";
            }
          }
          description
            "Route type";
        }
        leaf local-label {
          type uint32;
          description
            " This is incoming label assigned to this route";
        }
        leaf nhid {
          type uint64;
          description
            " This is nhid assigned to paths added by this client";
        }
        leaf last-updated {
          type yang:date-and-time;
          description
            "Indicates the last time the entry was update.";
        }
        leaf flags {
          type uint64;
          description
            " This can be used to show internal state eg. stale etc";
        }
        uses next-hops;
      }
    }
  }

  grouping rnh-cookies {
    description
      "cookies for rnh";
    container cookies {
      config false;
      list cookie {
        leaf cookie-value {
          type uint64;
          description
            "cookie assosiated with rnh";
        }
      }
    }
  }

  grouping rnh-tracker {
    description
      "Grouping for route producer";
    container trackers {
      config false;
      description
        "Enclosing container for the list of next-hops associated
                   with the forwarding entry";
      list tracker {
        leaf tracking-protocol {
          type identityref {
            base oc-pol-types:INSTALL_PROTOCOL_TYPE;
          }
          description
            "The protocol from which the RIB entry was learned.";
        }
        uses rnh-cookies;
      }
    }
  }

  grouping v6-rnh-tracker {
    description
      "Grouping for route producer";
    container trackers {
      config false;
      description
        "Enclosing container for the list of next-hops associated
                   with the forwarding entry";
      list tracker {
        leaf tracking-protocol {
          type identityref {
            base oc-pol-types:INSTALL_PROTOCOL_TYPE;
          }
          description
            "The protocol from which the RIB entry was learned.";
        }
        uses rnh-cookies;
      }
    }
  }

  grouping ipv4-entries {
    description
      "Grouping for forwarding entries by lookup keys";
    container ipv4-entries {
      config false;
      list entry {
        key "prefix";
        description
          "IPv4 prefix used for lookup";
        leaf prefix {
          type inet:ipv4-prefix;
          description
            "The IPv4 prefix corresponding to the route";
        }
        leaf best-protocol {
          type identityref {
            base oc-pol-types:INSTALL_PROTOCOL_TYPE;
          }
          description
            "The protocol which is best and its paths are used for forwarding.";
        }
        uses origin;
      }
    }
  }

  grouping ipv6-entries {
    description
      "Grouping for forwarding entries by lookup keys";
    container ipv6-entries {
      config false;
      list entry {
        key "prefix";
        leaf prefix {
          type inet:ipv6-prefix;
          description
            "The IPv6 prefix corresponding to the route";
        }
        leaf best-protocol {
          type identityref {
            base oc-pol-types:INSTALL_PROTOCOL_TYPE;
          }
          description
            "The protocol which is best and its paths are used for forwarding.";
        }
        uses origin;
      }
    }
  }

  grouping ipv4-rnh-entries {
    description
      "Grouping for forwarding entries by lookup keys";
    container ipv4-rnh-entries {
      list entry {
        key "prefix";
        config false;
        description
          "IPv4 prefix used for lookup";
        leaf prefix {
          type inet:ipv4-prefix;
          description
            "The IPv4 prefix corresponding to the route";
        }
        leaf res-state {
          type boolean;
          description
            "True if RNH is resolved";
        }
        leaf metric {
          type uint32;
          description
            "A metric which is utilised to specify the preference of route";
        }
        leaf res-prefix {
          type inet:ipv4-prefix;
          description
            "The IPv4 prefix corresponding to the route";
        }
        uses rnh-tracker;
      }
    }
  }

  grouping ipv6-rnh-entries {
    description
      "Grouping for forwarding entries by lookup keys";
    container ipv6-rnh-entries {
      list v6entry {
        key "prefix";
        leaf prefix {
          type inet:ipv6-prefix;
          description
            "The IPv6 prefix corresponding to the route";
        }
        leaf res-state {
          type boolean;
          description
            "True if RNH is resolved";
        }
        leaf metric {
          type uint32;
          description
            "A metric which is utilised to specify the preference of route";
        }
        leaf res-prefix {
          type inet:ipv6-prefix;
          description
            "The IPv6 prefix corresponding to the route";
        }
        uses v6-rnh-tracker;
      }
    }
  }

  grouping stats {
    description
      "Client specific counters";
    leaf routes {
      type yang:counter32;
      description
        "Number of Routes";
    }
    leaf paths {
      type yang:counter32;
      description
        "Number of Paths";
    }
    leaf rnhs {
      type yang:counter32;
      description
        "Number of RNHs";
    }
    leaf route-add-msg {
      type yang:counter64;
      description
        "Number of Add route msgs rcvd";
    }
    leaf route-delete-msg {
      type yang:counter64;
      description
        "Number of Delete route msgs rcvd";
    }
    leaf rnh-add-msg {
      type yang:counter64;
      description
        "Number of Add rnh msgs rcvd";
    }
    leaf rnh-delete-msg {
      type yang:counter64;
      description
        "Number of Delete rnh msgs rcvd";
    }
  }

  grouping stats-entries {
    description
      "grouping for RIB statistics";
    container stats-entries {
      config false;
      description
        "container for RIB stats";
      uses stats;
      list clients {
        key "name";
        config false;
        description
          "The list of RIB clients.";
        leaf name {
          type identityref {
            base oc-pol-types:INSTALL_PROTOCOL_TYPE;
          }
          description
            "Name of RIB client";
        }
        uses stats;
      }
    }
  }

  grouping client-info {
    description
      "Grouping for RIB clients";
    container client-info {
      config false;
      list clients {
        key "client";
        description
          "client information";
        leaf client {
          type identityref {
            base oc-pol-types:INSTALL_PROTOCOL_TYPE;
          }
          description
            "The client protocol.";
        }
        leaf-list redistribution-sources {
          type identityref {
            base oc-pol-types:INSTALL_PROTOCOL_TYPE;
          }
          description
            "list of redistrbution sources for this client ";
        }
        leaf hw-update-requested {
          type boolean;
          description
            "whether the update-wait-data-plane attribute is enabled for this client";
        }
        leaf nh-info-requested {
          type boolean;
          description
            "whether this client expects nh info to be sent along with redistributed prefixes";
        }
      }
    }
  }

  grouping nhid {
    description
      "Parameters relating to a nhid within the RIB entry";
    leaf count {
      type uint8;
      description
        "Number of pathids ";
    }
    leaf-list pathids-list {
      type uint64;
      ordered-by user;
      description
        "pathids ";
    }
  }

  grouping ipv4-nhids {
    description
      "Grouping for nhid entries by lookup keys";
    container ipv4-nhids {
      list ipv4-nhids {
        key "nhid";
        description
          "NH id";
        leaf nhid {
          type uint64;
          description
            "NHD id allocated to set of path";
        }
        uses nhid;
      }
    }
  }

  grouping ipv6-nhids {
    description
      "Grouping for NHID entries by lookup keys";
    container ipv6-nhids {
      list v6nhids {
        key "nhid";
        description
          "nh id";
        leaf nhid {
          type uint64;
          description
            "NH id allocated to path";
        }
        uses nhid;
      }
    }
  }

  grouping path {
    description
      "Parameters relating to a next-hop within the RIB entry";
    leaf af {
      type uint32;
    }
    leaf nh-tableid {
      type uint32;
    }
    leaf next-hop {
      type inet:ip-address-no-zone;
      description
        "The next-hop that is to be used for the  route
         - this may be specified as an IP address, an interface
         or a pre-defined next-hop type - for instance, DROP.";
    }
    leaf ifindex {
      type uint64;
    }
    leaf weight {
      type uint32;
      description
        "The weight of the next-hop";
    }
    leaf flags {
      type uint32;
    }
    leaf label-cnt {
      type uint8;
    }
    leaf-list pushed-mpls-label-stack {
      type oc-mplst:mpls-label;
      ordered-by user;
      description
        "The MPLS label stack imposed";
    }
  }

  grouping ipv4-pathids {
    description
      "Grouping for forwarding entries by lookup keys";
    container ipv4-pathids {
      list pathids {
        key "pathid";
        description
          "path id";
        leaf pathid {
          type uint64;
          description
            "Path id allocated to path";
        }
        uses path;
      }
    }
  }

  grouping ipv6-pathids {
    description
      "Grouping for forwarding entries by lookup keys";
    container ipv6-pathids {
      list v6pathids {
        key "pathid";
        description
          "path id";
        leaf pathid {
          type uint64;
          description
            "Path id allocated to path";
        }
        uses path;
      }
    }
  }

  grouping ipv4-tunnels {
    description
      "Grouping for tunnel entries by lookup keys";
    container ipv4-tunnels {
      config false;
      list entry {
        key "tunnel-id";
        description
          "tunnel-id used for lookup";
        leaf tunnel-id {
          type uint32;
          description
            "tunnel-ID associated with this tunnel";
        }
        leaf ltep-ip {
          type inet:ipv4-address-no-zone;
          description
            "local tunnel-endpoint ipv4 address";
        }
        leaf rtep-ip {
          type inet:ipv4-address-no-zone;
          description
            "remote tunnel-endpoint ipv4 address";
        }
        leaf tunnel-table-id {
          type uint32;
          description
            "underlay table-id for this tunnel";
        }
        leaf l4port {
          type uint32;
          description
            "UDP port for this tunnel";
        }
        leaf tunnel-encap {
          type enumeration {
            enum "VXLAN" {
              description
                "VXLAN tunnel encapsulation";
            }
          }
          description
            "tunnel encapsulation";
        }
      }
    }
  }

  grouping ids-cmn {
    description
      "Container ID information";
    leaf id-type {
      type string;
      description
        "Specifies if the ID allocated is for path or NH ";
    }
    leaf refcount {
      type uint32;
      description
        "Refcount for  the ID";
    }
    leaf path-type {
      type uint32;
      description
        "Indicates Path type  if the ID corresponds to a path";
    }
    leaf-list pathids {
      type uint32;
    }
    leaf nh-addr {
      type inet:ip-address-no-zone;
      description
        "Specifies the NH address corresponding to the path
         if applicable";
    }
    leaf tunnel-id {
      type uint32;
      description
        "Tunnel id corresponding to the path if applicable";
    }
  }

  grouping ipv4-ids {
    container ipv4-id-list {
      config false;
      list ipv4-container-id {
        description
          "Container ID Information  for IPV4 RIB table";
        key "id";
        leaf id {
          type uint32;
          description
            "Container ID allocated by RIB";
        }
        uses ids-cmn;
      }
    }
  }

  grouping ipv6-ids {
    container ipv6-id-list {
      config false;
      list ipv6-container-id {
        description
          "Container ID Information  for IPV6 RIB table";
        key "id";
        leaf id {
          type uint32;
          description
            "Container ID allocated by RIB";
        }
        uses ids-cmn;
      }
    }
  }

  grouping rib-top {
    description
      "Top-level grouping for rib routes";
    list rib {
      key "address-family";
      config false;
      description
        "An individual routing table associated with a
         an address family.";
      leaf address-family {
        type leafref {
          path "../state/address-family";
        }
        mandatory true;
        config false;
        description
          "Reference to the address family with which the RIB is
           associated";
      }
      container state {
        description
          "Configuration parameters relating to the RIB.";
        uses rib-config;
      }
      uses ipv4-entries {
        when "address-family = 'oc-types:IPV4'";
      }
      uses ipv6-entries {
        when "address-family = 'oc-types:IPV6'";
      }
      uses ipv4-rnh-entries {
        when "address-family = 'oc-types:IPV4'";
      }
      uses ipv6-rnh-entries {
        when "address-family = 'oc-types:IPV6'";
      }
      uses ipv4-nhids {
        when "address-family = 'oc-types:IPV4'";
      }
      uses ipv6-nhids {
        when "address-family = 'oc-types:IPV6'";
      }
      uses ipv4-pathids {
        when "address-family = 'oc-types:IPV4'";
      }
      uses ipv6-pathids {
        when "address-family = 'oc-types:IPV6'";
      }
      uses ipv4-tunnels {
        when "address-family = 'oc-types:IPV4'";
      }
      uses ipv4-ids {
        when "address-family = 'oc-types:IPV4'";
      }
      uses ipv6-ids {
        when "address-family = 'oc-types:IPV6'";
      }
      uses stats-entries;
      uses client-info;
    }
  }

  augment "/oc-netinst:network-instances/oc-netinst:network-instance" {
    uses rib-top {
      when "./oc-netinst:config/oc-netinst:type = 'oc-ni-types:L3VRF'";
    }
  }
}
