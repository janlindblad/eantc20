module arcos-openconfig-network-instance-augments {
  yang-version 1.1;
  namespace "http://yang.arrcus.com/arcos/openconfig/network-instance/augments";
  prefix arc-oc-netinst-aug;

  import openconfig-network-instance {
    prefix oc-netinst;
  }

  import openconfig-interfaces {
    prefix oc-if;
  }

  import openconfig-aft {
    prefix oc-aft;
  }

  import openconfig-aft-types {
    prefix oc-aftt;
  }

  import arcos-aft-types {
    prefix arc-aft-types;
  }

  import ietf-inet-types {
    prefix inet;
  }

  grouping ip-tunnel-state {
    description
      "Operational state parameters for IP tunnels";
    list tunnels {
      key tunnel-id;
      description
        "List of IP tunnels";

      leaf tunnel-id {
        type uint32;
        description
          "Tunnel identifier";
      }

      container state {
        leaf tunnel-type {
          type oc-aftt:encapsulation-header-type;
          description
            "Type of IP tunnel";
        }

        leaf src-ip-address {
          type inet:ip-address;
          description
            "Source IP address of tunnel";
        }

        leaf dst-ip-address {
          type inet:ip-address;
          description
            "Destination IP address of tunnel";
        }

        leaf ing-ucast-packets {
          type uint64;
          description
            "Destination ingress packets of ucast";
        }

        leaf ing-mcast-packets {
          type uint64;
          description
            "Destination ingress packets of mcast";
        }

        leaf ing-bcast-packets {
          type uint64;
          description
            "Destination ingress packets of bcast";
        }

        leaf egr-ucast-packets {
          type uint64;
          description
            "Destination egress packets of ucast";
        }

        leaf egr-mcast-packets {
          type uint64;
          description
            "Destination egress packets of mcast";
        }

        leaf egr-bcast-packets {
          type uint64;
          description
            "Destination egress packets of bcast";
        }

        leaf ing-ucast-bytes {
          type uint64;
          description
            "Destination ingress bytes of ucast";
        }

        leaf ing-mcast-bytes {
          type uint64;
          description
            "Destination ingress bytes of mcast";
        }

        leaf ing-bcast-bytes {
          type uint64;
          description
            "Destination ingress bytes of bcast";
        }

        leaf egr-ucast-bytes {
          type uint64;
          description
            "Destination egress bytes of ucast";
        }

        leaf egr-mcast-bytes {
          type uint64;
          description
            "Destination egress bytes of mcast";
        }

        leaf egr-bcast-bytes {
          type uint64;
          description
            "Destination egress bytes of bcast";
        }
      }

      uses oc-aft:aft-common-nhop-structural;
    }
  }

  grouping ip-tunnel-state-units {
    description
      "Per forwarding unit view of ip tunnels";

    container ip-tunnels-units {
      config false;
      description
        "Per forwarding unit view of ip tunnels";

      list ip-tunnel-unit-entry {
        key "unit-id";
        description
          "List of forwarding units";

        leaf unit-id {
          type uint32;
          description
            "Uniquely identifies a forwarding unit";
        }

        uses ip-tunnel-state;
      }
    }
  }

  grouping l2ni-mac-table-state-top {
    description
      "Top-level grouping for MAC table state list";


    container mac-table-state {
      config false;

      description
        "Table of learned or statically configured MAC addresses and
        corresponding VLANs in the bridge domain";

      container entries {
        description
          "Enclosing container for list of MAC table entries";

        list entry {
          key "mac-address";
          description
            "List of learned MAC addresses";

          leaf mac-address {
            type leafref {
              path "../state/mac-address";
            }
            description
              "Reference to mac-address list key";
          }

          container state {


            description
              "Operational state data for MAC table entries";

            uses oc-netinst:l2ni-mac-table-config;
            uses oc-netinst:l2ni-mac-table-state;
            leaf nexthop-tunnel-id {
              type leafref {
                path "/oc-netinst:network-instances/oc-netinst:network-instance/" +
                     "arc-oc-netinst-aug:ip-tunnels/arc-oc-netinst-aug:tunnels/" +
                     "arc-oc-netinst-aug:tunnel-id";
                }
              description
                "ID of tunnel that nexthop recurses over";
             }
          }
          container interface {
            description
              "Reference to the base and/or subinterface for the
              MAC table entry";

            uses oc-if:interface-ref;
          }
        }
      }
    }
  }

  grouping fdb-units-top {
    description
      "Top-level grouping for MAC table state list per unit";


    container fdb-units {
      config false;

      description
        "Table of learned or statically configured MAC addresses and
        corresponding VLANs in the bridge domain per asic unit";

      list fdb-unit-entry {
        key "unit-id";
        description
          "List of learned MAC addresses";

        leaf unit-id {
          type uint32;
          description
            "Device unit number";
        }
        uses l2ni-mac-table-state-top;
      }
    }
  }

  augment "/oc-netinst:network-instances/oc-netinst:network-instance" {
    container ip-tunnels {
      config false;
      description
        "Operation state parameters for IP tunnels";
      uses ip-tunnel-state;
    }
  }

  augment "/oc-netinst:network-instances/oc-netinst:network-instance" {
    uses ip-tunnel-state-units;
  }

  augment "/oc-netinst:network-instances/oc-netinst:network-instance" +
          "/arc-oc-netinst-aug:ip-tunnels/arc-oc-netinst-aug:tunnels" +
          "/arc-oc-netinst-aug:next-hops/arc-oc-netinst-aug:next-hop" +
          "/arc-oc-netinst-aug:state" {
    leaf nexthop-type {
      type arc-aft-types:dpal-nexthop-type;
      description
        "nexthop type";
    }
  }

  augment "/oc-netinst:network-instances/oc-netinst:network-instance" +
          "/arc-oc-netinst-aug:ip-tunnels-units" +
          "/arc-oc-netinst-aug:ip-tunnel-unit-entry/arc-oc-netinst-aug:tunnels" +
          "/arc-oc-netinst-aug:next-hops/arc-oc-netinst-aug:next-hop" +
          "/arc-oc-netinst-aug:state" {
    leaf nexthop-type {
      type arc-aft-types:dpal-nexthop-type;
      description
        "nexthop type";
    }
  }

  augment "/oc-netinst:network-instances/oc-netinst:network-instance/oc-netinst:fdb" {
    uses l2ni-mac-table-state-top;
  }

  augment "/oc-netinst:network-instances/oc-netinst:network-instance" {
    uses fdb-units-top;
  }
}
