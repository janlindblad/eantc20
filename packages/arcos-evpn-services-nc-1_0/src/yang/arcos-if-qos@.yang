module arcos-if-qos {
  yang-version 1.1;
  namespace "http://yang.arrcus.com/arcos/interface/qos";
  prefix arc-if-qos;

  import openconfig-interfaces {
    prefix oc-if;
  }
  import arcos-platform {
    prefix arc-platform;
  }

  organization
    "Arrcus, Inc.";
  contact
    "Arrcus, Inc.
     Customer Service
     Postal: 2077 Gateway Place
     San Jose, CA 95110
     Tel: +1 1XXX XXX-XXXX
     E-mail: xxx@arrcus.com";
  description
    "YANG data-model for qos specific policy instance on interfaces";

  grouping if-qos-top {
    description
      "Top level grouping for interface-based QoS";
    container qos {
      description
        "Quality of Service";
    }
  }

  augment "/oc-if:interfaces/oc-if:interface" {
    uses if-qos-top {
      when "(/arc-platform:platform/arc-platform:asic != 'arc-platform:X86_64')";
    }
  }
}
