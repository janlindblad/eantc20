module arcos-qos-policy-action-types {
  yang-version 1.1;
  namespace "http://yang.arrcus.com/arcos/qos/policy/action/types";
  prefix arc-qos-pol-actn-types;

  import arcos-policy-action-types {
    prefix arc-pol-actn-types;
  }

  organization
    "Arrcus, Inc.";

  contact
    "Arrcus, Inc.
     Customer Service
     Postal: 2077 Gateway Place
     San Jose, CA 95110
     Tel: +1 1XXX XXX-XXXX
     E-mail: xxx@arrcus.com";

  description
    "YANG data-model for qos policy action types";



  identity RATE_MAX {
    base arc-pol-actn-types:ACTION_TYPE;
    description
      "maximum rate (aka shape) service action type";
  }

  identity RATE_MIN {
    base arc-pol-actn-types:ACTION_TYPE;
    description
      "minimum guaranteed rate service action type";
  }

  identity RATE_EXCESS {
    base arc-pol-actn-types:ACTION_TYPE;
    description
      "excess (remaining) rate service action type";
  }

  identity PRIORITY {
    base arc-pol-actn-types:ACTION_TYPE;
    description
      "priority (aka low-latency) service action type";
  }
}
