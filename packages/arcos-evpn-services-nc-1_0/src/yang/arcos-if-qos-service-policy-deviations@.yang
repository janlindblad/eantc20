module arcos-if-qos-service-policy-deviations {
  yang-version 1.1;
  namespace "http://yang.arrcus.com/arcos/interface/qos/service-policy/deviations";
  prefix arc-if-qos-svc-pol-dev;

  import arcos-if-qos {
    prefix arc-if-qos;
  }
  import openconfig-interfaces {
    prefix oc-if;
  }
  import arcos-qos {
    prefix arc-qos;
  }
  import arcos-qos-policy {
    prefix arc-qos-pol;
  }
  import arcos-if-qos-service-policy {
    prefix arc-if-qos-svc-pol;
  }

  organization
    "Arrcus, Inc.";
  contact
    "Arrcus, Inc.
     Customer Service
     Postal: 2077 Gateway Place
     San Jose, CA 95110
     Tel: +1 1XXX XXX-XXXX
     E-mail: xxx@arrcus.com";
  description
    "YANG data-model for qos service policy annotation";

  deviation "/oc-if:interfaces/oc-if:interface/arc-if-qos:qos"
          + "/arc-if-qos-svc-pol:service-policies"
          + "/arc-if-qos-svc-pol:service-policy"
          + "/arc-if-qos-svc-pol:config/arc-if-qos-svc-pol:name" {
    deviate replace {
      type leafref {
        path "/arc-qos:qos/arc-qos-pol:policies/arc-qos-pol:policy/arc-qos-pol:name";
      }
    }
  }
}
