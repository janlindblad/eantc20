module arcos-openconfig-relay-agent-deviations {
  yang-version 1.1;
  namespace "http://yang.arrcus.com/arcos/openconfig/relay-agent/deviations";
  prefix arc-oc-relay-dev;

  import openconfig-relay-agent {
    prefix oc-relay;
  }

  deviation "/oc-relay:relay-agent/oc-relay:dhcp" +
            "/oc-relay:config/oc-relay:enable-relay-agent" {
    deviate not-supported;
    description "Not supported in this release";
  }

  deviation "/oc-relay:relay-agent/oc-relay:dhcpv6" +
            "/oc-relay:config/oc-relay:enable-relay-agent" {
    deviate not-supported;
    description "Not supported in this release";
  }

  deviation "/oc-relay:relay-agent/oc-relay:dhcp/oc-relay:interfaces" +
            "/oc-relay:interface/oc-relay:config/oc-relay:helper-address" {
    deviate not-supported;
    description "Not supported in this release";
  }

  deviation "/oc-relay:relay-agent/oc-relay:dhcp/oc-relay:interfaces" +
            "/oc-relay:interface/oc-relay:config/oc-relay:enable" {
    deviate add {
      default true;
    }
  }

  deviation "/oc-relay:relay-agent/oc-relay:dhcp/oc-relay:interfaces" +
            "/oc-relay:interface/oc-relay:agent-information-option" +
            "/oc-relay:config/oc-relay:circuit-id" {
    deviate replace {
      type string {
        pattern '[A-Za-z0-9/:\-\+\._#@\[\]~\{\}=\^]{1,63}';
      }
    }
  }

  deviation "/oc-relay:relay-agent/oc-relay:dhcp/oc-relay:interfaces" +
            "/oc-relay:interface/oc-relay:state/oc-relay:helper-address" {
    deviate not-supported;
    description "Not supported in this release";
  }

  deviation "/oc-relay:relay-agent/oc-relay:dhcp/oc-relay:interfaces" +
            "/oc-relay:interface/oc-relay:state/oc-relay:counters" {
    deviate not-supported;
    description "Not supported in this release";
  }

  deviation "/oc-relay:relay-agent/oc-relay:dhcp/oc-relay:interfaces" +
            "/oc-relay:interface/oc-relay:agent-information-option" +
            "/oc-relay:config/oc-relay:enable" {
    deviate not-supported;
    description "Not supported in this release";
  }

  deviation "/oc-relay:relay-agent/oc-relay:dhcp/oc-relay:interfaces" +
            "/oc-relay:interface/oc-relay:agent-information-option" +
            "/oc-relay:config/oc-relay:remote-id" {
    deviate not-supported;
    description "Not supported in this release";
  }

  deviation "/oc-relay:relay-agent/oc-relay:dhcp/oc-relay:interfaces" +
            "/oc-relay:interface/oc-relay:agent-information-option" +
            "/oc-relay:state/oc-relay:enable" {
    deviate not-supported;
    description "Not supported in this release";
  }

  deviation "/oc-relay:relay-agent/oc-relay:dhcp/oc-relay:interfaces" +
            "/oc-relay:interface/oc-relay:agent-information-option" +
            "/oc-relay:state/oc-relay:remote-id" {
    deviate not-supported;
    description "Not supported in this release";
  }

  deviation "/oc-relay:relay-agent/oc-relay:dhcp/oc-relay:interfaces" +
            "/oc-relay:interface/oc-relay:agent-information-option" +
            "/oc-relay:state/oc-relay:sent-remote-id" {
    deviate not-supported;
    description "Not supported in this release";
  }

  deviation "/oc-relay:relay-agent/oc-relay:dhcpv6/oc-relay:options" {
    deviate not-supported;
    description "Options not supported in this release";
  }

  deviation "/oc-relay:relay-agent/oc-relay:dhcpv6/oc-relay:interfaces" +
            "/oc-relay:interface/oc-relay:config/oc-relay:helper-address" {
    deviate not-supported;
    description "Not supported in this release";
  }

  deviation "/oc-relay:relay-agent/oc-relay:dhcpv6/oc-relay:interfaces" +
            "/oc-relay:interface/oc-relay:config/oc-relay:enable" {
    deviate add {
      default true;
    }
  }

  deviation "/oc-relay:relay-agent/oc-relay:dhcpv6/oc-relay:interfaces" +
            "/oc-relay:interface/oc-relay:state/oc-relay:helper-address" {
    deviate not-supported;
    description "Not supported in this release";
  }

  deviation "/oc-relay:relay-agent/oc-relay:dhcpv6/oc-relay:interfaces" +
            "/oc-relay:interface/oc-relay:state/oc-relay:counters" {
    deviate not-supported;
    description "Not supported in this release";
  }

  deviation "/oc-relay:relay-agent/oc-relay:dhcpv6/oc-relay:interfaces" +
            "/oc-relay:interface/oc-relay:options" {
    deviate not-supported;
    description "Not supported in this release";
  }

}
