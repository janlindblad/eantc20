module arcos-storm-control {
  yang-version 1.1;
  namespace "http://yang.arrcus.com/arcos/storm-control";
  prefix arc-strm-ctl;

  import iana-if-type {
    prefix ianaift;
  }

  import openconfig-interfaces {
    prefix oc-if;
  }

  import openconfig-yang-types {
    prefix oc-yang;
  }

  import openconfig-if-ethernet {
    prefix oc-eth;
  }

  import openconfig-if-aggregate {
    prefix oc-lag;
  }


  grouping storm-control-top {
    description
      "Top-level grouping for layer 2 storm control feature";

    container storm-control {
      description
        "Storm control feature for a port";
      leaf broadcast-level {
        type decimal64 {
          fraction-digits 1;
          range "0.1..100";
        }
        description "broadcast traffic rate limit as percentage of port speed";
      }
      leaf multicast-level {
        type decimal64 {
          fraction-digits 1;
          range "0.1..100";
        }
        description "multicast traffic rate limit as percentage of port speed";
      }
      leaf unknown-unicast-level {
        type decimal64 {
          fraction-digits 1;
          range "0.1..100";
        }
        description "unknown-unicast traffic rate limit as percentage of port speed";
      }
      container state {
        config false;
        leaf bcast-Kbps {
          type uint32;
          description "broadcast rate limit in Kbps";
        }
        leaf mcast-Kbps {
          type uint32;
          description "multicast rate limit in Kbps";
        }
        leaf uucast-Kbps {
          type uint32;
          description "unknown unicast rate limit in Kbps";
        }
      }
    }
  }

  augment "/oc-if:interfaces/oc-if:interface" {
    uses storm-control-top {
      when "(current()/oc-if:name != 'ma1' and " +
           "(((current()/oc-if:config/oc-if:type = 'ianaift:ethernetCsmacd') or " +
           "(current()/oc-if:config/oc-if:type = 'ianaift:ieee8023adLag')) and " +
           "(boolean(current()/oc-eth:ethernet/oc-eth:config/oc-lag:aggregate-id) != 'true')))";
    }
  }
}
