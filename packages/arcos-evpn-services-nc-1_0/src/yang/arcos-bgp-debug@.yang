module arcos-bgp-debug {
  yang-version 1.1;
  namespace "http://yang.arrcus.com/arcos/bgp/debug";
  prefix arc-bgp-dbg;

  import ietf-inet-types {
    prefix oc-inet;
  }

  typedef bgp-debug-state {
    type enumeration {
      enum off {
        description
          "Disable debug";
      }
      enum on {
        description
          "Enable debug";
      }
    }
  }

  typedef bgp-debug-type {
    type enumeration {
      enum fsm {
        description
          "BGP FSM debugs";
      }
      enum events {
        description
          "BGP Events debugs";
      }
      enum updates {
        description
          "BGP Updates debugs";
      }
      enum updates-in {
        description
          "BGP Updates In debugs";
      }
      enum updates-out {
        description
          "BGP Updates Out debugs";
      }
      enum prefix {
        description
          "BGP Prefix debugs";
      }
      enum keepalives {
        description
          "BGP Keepalives debugs";
      }
      enum rpol {
        description
          "BGP RPOL debugs";
      }
      enum packets {
        description
          "BGP packets debugs";
      }
      enum neighbors {
        description
          "BGP neighbors debugs";
      }
      enum rib {
        description
          "BGP rib debugs";
      }
      enum cleanup {
        description
          "BGP cleanup debugs";
      }
      enum rtr {
        description
          "BGP rtr debugs";
      }
      enum route-import {
        description
          "BGP route import debugs";
      }
      enum route-export {
        description
          "BGP route export debugs";
      }
      enum all {
        description
          "BGP All debugs";
      }
    }
  }

  container bgp-debug {
    description
      "BGP debug control";

    action protocol {
      input {
        leaf debug {
          type bgp-debug-type;
          mandatory true;
          description
            "Debug to be controlled";
        }

        leaf op {
          type bgp-debug-state;
          mandatory true;
          description
            "Turn on/off operation";
        }
      }
      output {
        leaf result {
          type string;
          description
            "The status of operation";
        }
      }
    }

    action neighbor {
      input {
        leaf address {
          type oc-inet:ip-address;
          description
            "Address of the BGP peer, either in IPv4 or IPv6";
        }

        leaf op {
          type bgp-debug-state;
          mandatory true;
          description
            "Turn on/off operation";
        }
      }
      output {
        leaf result {
          type string;
          description
            "The status of operation";
        }
      }
    }
  }
}
