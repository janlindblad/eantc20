module arcos-platform {
  yang-version 1.1;
  namespace "http://yang.arrcus.com/arcos/platform";
  prefix arc-platform;

  identity ASIC_VENDOR_DEVICE_FAMILY {
    description
      "Base type for device family";
  }

  identity BROADCOM_XGS {
    base ASIC_VENDOR_DEVICE_FAMILY;
    description
      "Broadcom XGS device family";
  }

  identity BROADCOM_DNX {
    base ASIC_VENDOR_DEVICE_FAMILY;
    description
      "Broadcom DNX device family";
  }

  identity VIRTUAL {
    base ASIC_VENDOR_DEVICE_FAMILY;
    description
      "Virtual device";
  }

  identity ASIC_VENDOR_DEVICE_TYPE {
    description
      "Base type for asic device type";
  }

  identity BROADCOM_TRIDENT2 {
    base ASIC_VENDOR_DEVICE_TYPE;
    description
      "Broadcom TD2 device";
  }

  identity BROADCOM_TOMAHAWK {
    base ASIC_VENDOR_DEVICE_TYPE;
    description
      "Broadcom TH device";
  }

  identity BROADCOM_HELIX4 {
    base ASIC_VENDOR_DEVICE_TYPE;
    description
      "Broadcom HX4 device";
  }

  identity BROADCOM_TRIDENT3 {
    base ASIC_VENDOR_DEVICE_TYPE;
    description
      "Broadcom TD3 device";
  }

  identity BROADCOM_JERICHOPLUS {
    base ASIC_VENDOR_DEVICE_TYPE;
    description
      "Broadcom JPLUS device";
  }

  identity BROADCOM_TOMAHAWK3 {
    base ASIC_VENDOR_DEVICE_TYPE;
    description
      "Broadcom TH3 device";
  }

  identity X86_64 {
    base ASIC_VENDOR_DEVICE_TYPE;
    description
      "Intel x86_64 device";
  }

  identity ARCOS_PLATFORM {
    description
      "Base type for ARCOS platform";
  }

  identity REDSTONE_XP {
    base ARCOS_PLATFORM;
    description
      "Celestica sysid x86-64-cel-redstone-xp-r0";
  }
  identity SEASTONE_XP {
    base ARCOS_PLATFORM;
    description
      "Celestica sysid x86-64-cel-seastone-r0";
  }
  identity AS5712 {
    base ARCOS_PLATFORM;
    description
      "Accton sysid x86-64-accton-as5712-54x-r0";
  }
  identity AS7712 {
    base ARCOS_PLATFORM;
    description
      "Accton sysid x86-64-accton-as7712-32x-r0";
  }
  identity HALIBURTON {
    base ARCOS_PLATFORM;
    description
      "Celestica sysid x86-64-cel-e1031-r0";
  }
  identity IX7 {
    base ARCOS_PLATFORM;
    description
      "Quanta sysid x86-64-quanta-ix7-rglbmc-r0";
  }
  identity IX8 {
    base ARCOS_PLATFORM;
    description
      "Quanta sysid x86-64-quanta-ix8-rglbmc-r0";
  }
  identity IX8A {
    base ARCOS_PLATFORM;
    description
      "Quanta sysid x86-64-quanta-ix8a-dnv-r0";
  }
  identity SEASTONE_2 {
    base ARCOS_PLATFORM;
    description
      "Celestica sysid x86-64-cel-seastone-2-r0";
  }
  identity AGC5648S {
    base ARCOS_PLATFORM;
    description
      "Delta sysid x86-64-delta-agc5648s-r0";
  }
  identity QUESTONE_2 {
    base ARCOS_PLATFORM;
    description
      "Celestica sysid x86-64-cel-questone-2-r0";
  }
  identity AGC9020S {
    base ARCOS_PLATFORM;
    description
      "Delta sysid x86-64-delta-agc9020s-r0";
  }
  identity AS7326 {
    base ARCOS_PLATFORM;
    description
      "Accton sysid x86-64-accton-as7326-56x-r0";
  }
  identity AS7726 {
    base ARCOS_PLATFORM;
    description
      "Accton sysid x86-64-accton-as7726-32x-r0";
  }
  identity VM {
    base ARCOS_PLATFORM;
    description
      "Virtual machine";
  }
  identity SILVERSTONE {
    base ARCOS_PLATFORM;
    description
      "Celestica sysid x86-64-cel-silverstone-r0";
  }
  identity AS9716 {
    base ARCOS_PLATFORM;
    description
      "Accton sysid x86-64-accton-as9716-32d-r0";
  }
  identity IVYSTONE {
    base ARCOS_PLATFORM;
    description
      "Celestica sysid x86-64-cel-ivystone-r0";
  }

  container platform {
    leaf type {
      type identityref {
        base ARCOS_PLATFORM;
      }
      description
        "Name of platform";
    }

    leaf family {
      type identityref {
        base ASIC_VENDOR_DEVICE_FAMILY;
      }
      description
        "Name of asic device family";
    }

    leaf asic {
      type identityref {
        base ASIC_VENDOR_DEVICE_TYPE;
      }
      description
        "Type of asic device";
    }

    leaf form-factor {
      type enumeration {
        enum UNKNOWN;
        enum 48x10GbE+6x40GbE;
        enum 48x25GbE+8x100GbE;
        enum 32x100GbE;
        enum 32x400GbE;
        enum 48x1GbE+4x10GbE;
        enum 48x25GbE+6x100GbE;
        enum 20x100GbE;
        enum 128x100GbE;
        enum FF_VIRTUAL;
      }
      description
        "Form factor of device";
    }
  }
}
