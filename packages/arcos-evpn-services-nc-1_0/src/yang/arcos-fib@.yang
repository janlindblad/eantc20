module arcos-fib {
  yang-version 1.1;
  namespace "http://yang.arrcus.com/arcos/fib";
  prefix arc-fib;

  import openconfig-network-instance {
    prefix oc-netinst;
  }
  import openconfig-network-instance-types {
    prefix oc-ni-types;
  }
  import openconfig-yang-types {
    prefix oc-yang;
  }
  import ietf-inet-types {
    prefix inet;
  }
  import openconfig-mpls-types {
    prefix oc-mplst;
  }
  import openconfig-types {
    prefix oc-types;
  }
  import ietf-yang-types {
    prefix yang;
  }

  typedef fib-path-type {
    type enumeration {
      enum "RECURSIVE" {
        value 1;
      }
      enum "CONNECTED_V4" {
        value 2;
      }
      enum "ADJ_RNH_V4" {
        value 3;
      }
      enum "LOCAL_V4" {
        value 4;
      }
      enum "GLEAN_V4" {
        value 5;
      }
      enum "CONNECTED_V6" {
        value 6;
      }
      enum "ADJ_RNH_V6" {
        value 7;
      }
      enum "LOCAL_V6" {
        value 8;
      }
      enum "GLEAN_V6" {
        value 9;
      }
      enum "DROP" {
        value 10;
      }
      enum "VXLAN_V4" {
        value 11;
      }
    }
  }

  grouping v4-next-hop-info {
    container paths {
      list ipv4-path {
        key "path-id";
        leaf path-id {
          type uint32;
          description
            "ID of the Path";
        }
        leaf path-type {
          type fib-path-type;
          description
            "Type of the Path";
        }
        leaf ip-address {
          type inet:ip-address-no-zone;
          description
            "IP address of the Path";
        }
        leaf-list push-label {
          type oc-mplst:mpls-label;
          description
            "The MPLS label stack imposed when forwarding packets
             to the next-hop  ";
        }
        leaf nh-tunnel-id {
          type uint32;
          description
            "VXLAN Tunnel id for the nexthop";
        }
        leaf nh-tunnel-vni-id {
          type uint32;
          description
            "VXLAN Tunnel vni id for the nexthop";
        }
        leaf rtep-mac {
          type oc-yang:mac-address;
          description
            "Remote tunnel-endpoint MAC address for a vxlan tunnel next-hop";
        }
        leaf interface {
          type string;
          description
            "Name of the interface for the connected nexthop type";
        }
        leaf num-coll-paths {
          type uint32;
          description
            "Number of collapsed paths downloaded to hardware.
             Applicable only if this path is a recursive path";
        }
        leaf-list coll-path-id {
          type uint32;
          description
            "List of collapsed Path ids downloaded to hardware";
        }
        leaf-list igp-path-id {
          type uint32;
          description
            "List of underlying igp path ids. Applicable only
             if the path is a a recursive path";
        }
      }
    }
  }

  grouping v6-next-hop-info {
    container paths {
      list ipv6-path {
        key "path-id";
        leaf path-id {
          type uint32;
          description
            "ID of the Path";
        }
        leaf path-type {
          type fib-path-type;
          description
            "Type of the Path";
        }
        leaf ip-address {
          type inet:ip-address-no-zone;
          description
            "IP address of the Path";
        }
        leaf-list push-label {
          type oc-mplst:mpls-label;
          description
            "The MPLS label stack imposed when forwarding packets
             to the next-hop  ";
        }
        leaf nh-tunnel-id {
          type uint32;
          description
            "VXLAN Tunnel id for the nexthop";
        }
        leaf nh-tunnel-vni-id {
          type uint32;
          description
            "VXLAN Tunnel vni id for the nexthop";
        }
        leaf rtep-mac {
          type oc-yang:mac-address;
          description
            "remote tunnel-endpoint MAC address for a vxlan tunnel next-hop";
        }
        leaf interface {
          type string;
          description
            "Name of the interface for the connected nexthop type";
        }
        leaf num-coll-paths {
          type uint32;
          description
            "Number of collapsed paths downloaded to hardware.
             Applicable only if this path is a recursive path";
        }
        leaf-list coll-path-id {
          type uint32;
          description
            "List of collapsed Path ids downloaded to hardware";
        }
        leaf-list igp-path-id {
          type uint32;
          description
            "List of underlying igp path ids. Applicable only
             if the path is a a recursive path";
        }
      }
    }
  }

  grouping v6-adj-info {
    container adjs {
      list ipv6-adj-entry {
        key "ipaddr";
        leaf ipaddr {
          type inet:ip-address-no-zone;
          description
            "Layer 3 ip address";
        }
        leaf hwaddr {
          type oc-yang:mac-address;
          description
            "Layer 2 address";
        }
        leaf l2ifindex {
          type uint64;
          description
            "Layer 2 ifindex";
        }
      }
    }
  }

  grouping v6-nht-info {
    container nhts {
      list ipv6-nht-entry {
        key "nht-ip";
        leaf nht-ip {
          type inet:ipv6-address-no-zone;
          description
            "Layer 3 ip address";
        }
        leaf path-id {
          type uint32;
          description
            "The Path id corresponding to the tracked ip and interface ";
        }
      }
    }
  }

  grouping v4-adj-info {
    container adjs {
      list ipv4-adj-entry {
        key "ipaddr";
        leaf ipaddr {
          type inet:ip-address-no-zone;
          description
            "Layer 3 ip address";
        }
        leaf hwaddr {
          type oc-yang:mac-address;
          description
            "Layer 2 address";
        }
        leaf l2ifindex {
          type uint64;
          description
            "Layer 2 ifindex";
        }
      }
    }
  }

  grouping v4-nht-info {
    container nhts {
      list ipv4-nht-entry {
        key "nht-ip";
        leaf nht-ip {
          type inet:ip-address-no-zone;
          description
            "Layer 3 ip address";
        }
        leaf path-id {
          type uint32;
          description
            "The Path id corresponding to the tracked ip and interface ";
        }
      }
    }
  }

  grouping ipv4-next-hops {
    container ipv4-next-hops {
      config false;
      list ipv4-nexthop-entry {
        description
          "List of Nexthops in  the IPV4 fib table";
        key "index";
        leaf index {
          type uint32;
          description
            "Id of the nexthop (NHID)";
        }
        uses v4-next-hop-info;
      }
    }
  }

  grouping ipv6-next-hops {
    container ipv6-next-hops {
      config false;
      list ipv6-nexthop-entry {
        description
          "List of Nexthops in  the IPV6 fib table";
        key "index";
        leaf index {
          type uint32;
          description
            "Id of the nexthop (NHID)";
        }
        uses v6-next-hop-info;
      }
    }
  }

  grouping ipv4-adj {
    container ipv4-adj {
      config false;
      list ipv4-adjacency {
        description
          "IPV4 adjacency information, IP to MAC binding";
        key "if-index";
        leaf if-index {
          type uint64;
          description
            "Interface Index";
        }
        leaf interface {
          type string;
          description
            "Interface Name";
        }
        leaf link-status {
          type string;
          description
            "Interface status";
        }
        leaf vrf-id {
          type uint32;
          description
            "VRF id which the interface belongs to";
        }
        uses v4-adj-info;
        uses v4-nht-info;
      }
    }
  }

  grouping ipv6-adj {
    container ipv6-adj {
      config false;
      list ipv6-adjacency {
        description
          "IPV6 adjacency information, IP to MAC binding";
        key "if-index";
        leaf if-index {
          type uint64;
          description
            "Interface Index";
        }
        leaf interface {
          type string;
          description
            "Interface Name";
        }
        leaf link-status {
          type string;
          description
            "Interface status";
        }
        leaf vrf-id {
          type uint32;
          description
            "VRF id which the interface belongs to";
        }
        uses v6-adj-info;
        uses v6-nht-info;
      }
    }
  }

  grouping pub-info {
    leaf next-hop-id {
      type uint32;
    }
    leaf publish-id {
      type uint32;
      description
        "Path/Nexthop ID published to  forwarding layer";
    }
  }

  grouping ipv4-entries {
    container ipv4-entries {
      list ipv4-prefix-entry {
        description
          "List of IPV4 prefix entries in the fib table";
        key "prefix";
        leaf prefix {
          type inet:ipv4-prefix;
          description
            "The IPv4 prefix corresponding to the route";
        }
        leaf ack-required {
          type boolean;
          description
            "Forwarding status ack was requested for this route";
        }
        leaf forwarding-status-valid {
          type boolean;
          description
            "The forwarding status reflects the status of the latest issued
             operation";
        }
        leaf forwarding-status {
          type uint32;
          description
            "Last reported forwarding status";
        }
        leaf cookie {
          type uint64;
          description
            "Last received opaque cookie for this route";
        }
        uses pub-info;
      }
    }
  }

  grouping rnh-info {
    leaf next-hop-id {
      type uint32;
      description
        "Nexthop ID corresponding to rnh prefix given by rib";
    }
    leaf rnh-res-state {
      type string;
      description
        "RNH resolution state";
    }
    leaf ip-adj-next-hop-id {
      type uint32;
      description
        "Nexthop ID created by fib for IP paths";
    }
    leaf mpls-adj-next-hop-id {
      type uint32;
      description
        "Nexthop ID created by fib for MPLS paths";
    }
    leaf num-ip-igp-paths {
      type uint32;
      description
        "Number of underlay IP IGP paths";
    }
    leaf-list ip-igp-path-id {
      type uint32;
      description
        "List  of IP IGP path IDs";
    }
    leaf num-mpls-igp-paths {
      type uint32;
      description
        "Number of underlay MPLS IGP paths";
    }
    leaf-list mpls-igp-path-id {
      type uint32;
      description
        "List  of MPLS IGP path IDs";
    }
  }

  grouping ipv4-rnh-entries {
    container ipv4-rnh-entries {
      list ipv4-rnh-entry {
        description
          "List  of IPV4 rnh entries";
        key "ip-address";
        leaf ip-address {
          type inet:ip-address-no-zone;
          description
            "The IP address corresponding to the rnh";
        }
        uses rnh-info;
      }
    }
  }

  grouping ipv4-nht-entries {
    container ipv4-nht-entries {
      list ipv4-nht-entry {
        description
          "List of Nexthop tracking requests in IPV4 fib table";
        key "nht";
        leaf nht {
          type inet:ip-address-no-zone;
          description
            "IPV4 address of the tracked Nexthop ";
        }
        leaf res-route {
          type inet:ipv4-prefix;
          description
            "The IPv4 prefix corresponding to the tracked nexthop ";
        }
        leaf-list clients {
          type string;
          description
            "List of clients tracking nexthop";
        }
      }
    }
  }

  grouping ipv4-label-entries {
    container ipv4-label-entries {
      list ipv4-label-entry {
        description
          "Label entries in the IPV4 fib table";
        key "local-label";
        leaf local-label {
          type uint32;
          description
            "The FEC Label entry (ILM) associated with the IPV4 fib table";
        }
        uses pub-info;
      }
    }
  }

  grouping ipv6-entries {
    container ipv6-entries {
      list ipv6-prefix-entry {
        description
          "List of IPV6 prefix entries in the fib table";
        key "prefix";
        leaf prefix {
          type inet:ipv6-prefix;
          description
            "The IPv6 prefix corresponding to the route";
        }
        leaf ack-required {
          type boolean;
          description
            "Forwarding status ack was requested for this route";
        }
        leaf forwarding-status-valid {
          type boolean;
          description
            "The forwarding status reflects the status of the latest issued
             operation";
        }
        leaf forwarding-status {
          type uint32;
          description
            "Last reported forwarding status";
        }
        leaf cookie {
          type uint64;
          description
            "Last received opaque cookie for this route";
        }
        uses pub-info;
      }
    }
  }

  grouping ipv6-rnh-entries {
    container ipv6-rnh-entries {
      list ipv6-rnh-entry {
        description
          "List of IPV6 RNH entries";
        key "ip-address";
        leaf ip-address {
          type inet:ip-address-no-zone;
          description
            "The IP address corresponding to the RNH";
        }
        uses rnh-info;
      }
    }
  }

  grouping ipv6-nht-entries {
    container ipv6-nht-entries {
      list ipv6-nht-entry {
        description
          "List of Nexthop tracking requests in IPV6 fib table";
        key "nht";
        leaf nht {
          type inet:ipv6-address-no-zone;
          description
            "IPV6 address of the Tracked Nexthop ";
        }
        leaf res-route {
          type inet:ipv6-prefix;
          description
            "The IPv6 prefix corresponding to the tracked nexthop ";
        }
        leaf-list clients {
          type string;
          description
            "List of clients tracking nexthop";
        }
      }
    }
  }

  grouping ipv6-label-entries {
    container ipv6-label-entries {
      list ipv6-label-entry {
        description
          "Label entries in the IPV6 fib table";
        key "local-label";
        leaf local-label {
          type uint32;
          description
            "The FEC Label entry (ILM) associated with the ipv4 prefix";
        }
        uses pub-info;
      }
    }
  }

  grouping total-stats {
    container all-stats {
      leaf total-count {
        type yang:counter64;
        description
          "Total number of objects present in the fib table";
      }
      leaf total-creates {
        type yang:counter64;
        description
          "Total number of creates received  for the object";
      }
      leaf total-updates {
        type yang:counter64;
        description
          "Total number of updates  received for the object";
      }
      leaf total-deletes {
        type yang:counter64;
        description
          "Total number of deletes  received for the object";
      }
      leaf total-drop-suppress {
        type yang:counter64;
      }
      leaf total-duplicate-updates {
        type yang:counter64;
        description
          "Total number of duplicate updates  received for the object";
      }
    }
  }

  grouping curr-ids {
    container all-ids {
      leaf id-count {
        type yang:counter32;
        description
          "Total number of container IDs in use";
      }
    }
  }

  grouping txl-stats {
    container txlist-stats {
      leaf retry-count {
        type yang:counter64;
        description
          "Total number of ipc retries";
      }
    }
  }

  grouping restart-stats {
    container all-stats {
      leaf stale-marks {
        type yang:counter64;
        description
          "Total number of objects marked stale";
      }
      leaf stale-refreshes {
        type yang:counter64;
        description
          "Total number of objects refreshed";
      }
      leaf stale-sweeps {
        type yang:counter64;
        description
          "Total number of objects swept";
      }
      leaf last-stale-marks {
        type yang:counter64;
      }
      leaf last-stale-refreshes {
        type yang:counter64;
      }
      leaf last-stale-sweeps {
        type yang:counter64;
      }
    }
  }

  grouping stats {
    description
      "Table specific counters";
    container routes {
      description
        "Number of Routes";
      uses total-stats;
    }
    container rnhs {
      description
        "Number of RNHs";
      uses total-stats;
    }
    container cross-af-rnhs {
      description
        "Number of Cross AF RNHs";
      uses total-stats;
    }
    container labels {
      description
        "Number of Labels";
      uses total-stats;
    }
    container adj-routes {
      description
        "Number of adj Routes";
      uses total-stats;
    }
    container nexthops {
      description
        "Number of Nexthops (nhids)";
      uses total-stats;
    }
    container paths {
      description
        "Number of Paths (path-ctx)";
      uses total-stats;
    }
    container tables {
      description
        "Number of Tables ";
      uses total-stats;
    }
    container ids {
      description
        "Current Number of Containers Ids allocated ";
      uses curr-ids;
    }
    container txlist {
      description
        "Txlist statistics";
      uses txl-stats;
    }
  }

  grouping rib-restart-stats {
    description
      "RIB restartability Table specific counters";
    container routes {
      description
        "Number of Routes";
      uses restart-stats;
    }
    container rnhs {
      description
        "Number of RNHs";
      uses restart-stats;
    }
    container labels {
      description
        "Number of Labels";
      uses restart-stats;
    }
    container nexthops-recursive {
      description
        "Number of Recursive Nexthops (nhids)";
      uses restart-stats;
    }
    container nexthops-non-recursive {
      description
        "Number of Non-Recursive Nexthops (nhids)";
      uses restart-stats;
    }
  }

  grouping stats-entries {
    description
      "grouping for FIB statistics";
    container stats-entries {
      config false;
      description
        "container for FIB stats";
      uses stats;
    }
    container rib-restart-stats {
      config false;
      description
        "FIB Counters related to RIB restartability ";
      uses rib-restart-stats;
    }
  }

  grouping path-ctx-cmn {
    description
      "Path  information";
    leaf path-type {
      type fib-path-type;
      description
        " Indicates Path type ";
    }
    leaf mpls-path {
      type string;
      description
        "Indicates if the path is mpls or Not";
    }
    leaf vxlan-path {
      type string;
      description
        "Indicates if the path is vxlan or Not";
    }
    leaf refcount {
      type uint32;
      description
        "Indicates number of nexthops using this path";
    }
  }

  grouping ipv4-path-ctx {
    container ipv4-path-ctx {
      config false;
      list ipv4-path {
        description
          "List of Paths present in IPV4 fib table";
        key "path-id";
        leaf path-id {
          type uint32;
          description
            "Indicates the ID of the path";
        }
        uses path-ctx-cmn;
      }
    }
  }

  grouping ipv6-path-ctx {
    container ipv6-path-ctx {
      config false;
      list ipv6-path {
        description
          "List of Paths present in IPV6 fib table";
        key "path-id";
        leaf path-id {
          type uint32;
          description
            "Indicates the ID of the path";
        }
        uses path-ctx-cmn;
      }
    }
  }

  grouping ids-cmn {
    description
      "Container ID information";
    leaf id-type {
      type string;
      description
        "Specifies if the ID allocated is for path or NH ";
    }
    leaf refcount {
      type uint32;
      description
        "Refcount for  the ID";
    }
    leaf path-type {
      type fib-path-type;
      description
        "Indicates Path type  if the ID corresponds to a path";
    }
    leaf-list pathids {
      type uint32;
    }
    leaf rnh-addr {
      type inet:ip-address-no-zone;
      description
        "Specifies the RNH address corresponding to the path
         if applicable";
    }
  }

  grouping ipv4-ids {
    container ipv4-id-list {
      config false;
      list ipv4-container-id {
        description
          "Container ID Information  for IPV4 FIB table";
        key "id";
        leaf id {
          type uint32;
          description
            "Container ID allocated by FIB";
        }
        uses ids-cmn;
      }
    }
  }

  grouping ipv6-ids {
    container ipv6-id-list {
      config false;
      list ipv6-container-id {
        description
          "Container ID Information  for IPV6 FIB table";
        key "id";
        leaf id {
          type uint32;
          description
            "Container ID allocated by FIB";
        }
        uses ids-cmn;
      }
    }
  }

  grouping fib-lpm-top {
    container fib-lpm {
      description
        "Perform a Longest Prefix Match lookup in the FIB";
      action v4-route {
        input {
          leaf address {
            type inet:ipv4-address;
            mandatory true;
            description
              "The IPv4 address to be looked from FIB";
          }
        }
        output {
          leaf prefix {
            type inet:ipv4-prefix;
            description
              "The IPv4 prefix corresponding to the route";
          }
          uses pub-info;
        }
      }
      action v6-route {
        input {
          leaf address {
            type inet:ipv6-address;
            mandatory true;
            description
              "The IPv6 address to be looked from FIB";
          }
        }
        output {
          leaf prefix {
            type inet:ipv6-prefix;
            description
              "The IPv6 prefix corresponding to the route";
          }
          uses pub-info;
        }
      }
    }
  }

  grouping ipv4-tunnels {
    description
      "Grouping for tunnel entries by lookup keys";
    container ipv4-tunnels {
      config false;
      list entry {
        key "tunnel-id";
        description
          "tunnel-id used for lookup";
        leaf tunnel-id {
          type uint32;
          description
            "tunnel-ID associated with this tunnel";
        }
        leaf ltep-ip {
          type inet:ipv4-address-no-zone;
          description
            "local tunnel-endpoint ipv4 address";
        }
        leaf rtep-ip {
          type inet:ipv4-address-no-zone;
          description
            "remote tunnel-endpoint ipv4 address";
        }
        leaf tunnel-table-id {
          type uint32;
          description
            "underlay table-id for this tunnel";
        }
        leaf l4port {
          type uint32;
          description
            "UDP port for this tunnel";
        }
        leaf tunnel-encap {
          type enumeration {
            enum "VXLAN" {
              description
                "VXLAN tunnel encapsulation";
            }
          }
          description
            "tunnel encapsulation";
        }
        uses pub-info;
      }
    }
  }

  grouping fib-top {
    description
      "Top level grouping for fib control plane routes";
    list fib {
      key "address-family";
      config false;
      description
        " The Control plane Forwarding table associated with an address family.";
      leaf address-family {
        type identityref {
          base oc-types:ADDRESS_FAMILY;
        }
        mandatory true;
        config false;
      }
      uses ipv4-entries {
        when "address-family = 'oc-types:IPV4'";
      }
      uses ipv4-rnh-entries {
        when "address-family = 'oc-types:IPV4'";
      }
      uses ipv4-nht-entries {
        when "address-family = 'oc-types:IPV4'";
      }
      uses ipv4-next-hops {
        when "address-family = 'oc-types:IPV4'";
      }
      uses ipv4-label-entries {
        when "address-family = 'oc-types:IPV4'";
      }
      uses ipv4-adj {
        when "address-family = 'oc-types:IPV4'";
      }
      uses ipv4-path-ctx {
        when "address-family = 'oc-types:IPV4'";
      }
      uses ipv4-ids {
        when "address-family = 'oc-types:IPV4'";
      }
      uses ipv4-tunnels {
        when "address-family = 'oc-types:IPV4'";
      }
      uses ipv6-entries {
        when "address-family = 'oc-types:IPV6'";
      }
      uses ipv6-rnh-entries {
        when "address-family = 'oc-types:IPV6'";
      }
      uses ipv6-nht-entries {
        when "address-family = 'oc-types:IPV6'";
      }
      uses ipv6-next-hops {
        when "address-family = 'oc-types:IPV6'";
      }
      uses ipv6-label-entries {
        when "address-family = 'oc-types:IPV6'";
      }
      uses ipv6-adj {
        when "address-family = 'oc-types:IPV6'";
      }
      uses ipv6-path-ctx {
        when "address-family = 'oc-types:IPV6'";
      }
      uses ipv6-ids {
        when "address-family = 'oc-types:IPV6'";
      }
      uses stats-entries;
    }
  }

  augment "/oc-netinst:network-instances/oc-netinst:network-instance" {
    uses fib-top {
      when "./oc-netinst:config/oc-netinst:type = 'oc-ni-types:L3VRF'";
    }
    uses fib-lpm-top {
      when "./oc-netinst:config/oc-netinst:type = 'oc-ni-types:L3VRF'";
    }
  }
}
