module arcos-openconfig-interfaces-augments {
  yang-version 1.1;
  namespace "http://yang.arrcus.com/arcos/openconfig/interfaces/augments";
  prefix arc-oc-if-aug;

  import openconfig-interfaces {
    prefix oc-if;
  }

  import openconfig-yang-types {
    prefix oc-yang;
  }

  import openconfig-network-instance {
    prefix oc-ni;
  }

  import ietf-yang-types {
    prefix yang;
  }

  import ietf-inet-types {
    prefix inet;
  }

  import iana-if-type {
    prefix ianaift;
  }

  import arcos-features {
    prefix arc-features;
  }

  import arcos-platform {
    prefix arc-platform;
  }

  typedef fec-types {
    type enumeration {
      enum fec-none {
        value 1;
      }
      enum base-r {
        value 2;
      }
      enum rs {
        value 3;
      }
      enum rs-108 {
        value 4;
      }
      enum rs-206 {
        value 5;
      }
      enum rs-272 {
        value 6;
      }
      enum rs-304 {
        value 7;
      }
      enum rs-544 {
        value 8;
      }
      enum rs-545 {
        value 9;
      }
      enum rs-272-2xn {
        value 10;
      }
      enum rs-544-2xn {
        value 11;
      }
    }
  }

  grouping dynamic-ipv4-address {
    description
      "Per IPv4 address configuration data for the
       interface.";

    leaf ip {
      type inet:ipv4-address-no-zone;
      description
        "[adapted from IETF IP model RFC 7277]

         The IPv4 address on the interface.";
    }
    leaf prefix-length {
      type uint8 {
        range "0..32";
      }
      description
        "[adapted from IETF IP model RFC 7277]

         The length of the subnet prefix.";
    }
  }

  grouping dynamic-ipv6-address {
    description
      "Per IPv6 address configuration data for the
       interface.";

    leaf ipv6 {
      type inet:ipv6-address-no-zone;
      description
        "[adapted from IETF IP model RFC 7277]

         The IPv6 address on the interface.";
    }
    leaf ipv6-prefix-length {
      type uint8 {
        range "0..128";
      }
      description
        "[adapted from IETF IP model RFC 7277]

         The length of the subnet prefix.";
    }
  }

  grouping ipv6-link-local-address {
    description
      "IPv6 link-local address for the interface.";

    leaf ipv6-link-local {
      type inet:ipv6-address-no-zone;
      description
        "[adapted from IETF IP model RFC 7277]

         The IPv6 link-local address on the
         interface.";
    }
  }

  grouping dynamic-address-top {
    description
      "Subinterface data for logical interfaces
       associated with a physical interface.";

    container dynamic {
      config false;
      description
        "Enclosing container for the list of subinterfaces
         associated with a physical interface.";

      uses dynamic-ipv4-address;
      uses dynamic-ipv6-address;
      uses ipv6-link-local-address;
    }
  }

  grouping interface-segment-routing-config {
    container segment-routing {
      description
        "Parameters related to Segment Routing";

      leaf label-index {
        type uint32;
        description
          "Label index";
      }
    }

    leaf network-instance {
      type string;
      description
        "The L3 network-instance that this subinterface is associated
         with.  When this leaf is unspecified, the subinterface is
         associated with the default network instance.";
    }
  }

  grouping if-error-counters {
    description
      "Error counters";

    leaf fcs-error {
      when "/oc-if:interfaces/oc-if:interface/oc-if:config/" +
           "oc-if:type = 'ianaift:ethernetCsmacd'" {
        description
        "FCS Error count";
      }
      type yang:counter64;
    }
    leaf align-error {
      when "/oc-if:interfaces/oc-if:interface/oc-if:config/" +
           "oc-if:type = 'ianaift:ethernetCsmacd'" {
        description
        "Alignment Error count";
      }
      type yang:counter64;
    }
    leaf symbol-error {
      when "/oc-if:interfaces/oc-if:interface/oc-if:config/" +
           "oc-if:type = 'ianaift:ethernetCsmacd'" {
        description
        "Symbol Error count";
      }
      type yang:counter64;
    }
    leaf giant-pkts {
      when "/oc-if:interfaces/oc-if:interface/oc-if:config/" +
           "oc-if:type = 'ianaift:ethernetCsmacd'" {
        description
        "Oversize pkt count";
      }
      type yang:counter64;
    }
    leaf runt-pkts {
      when "/oc-if:interfaces/oc-if:interface/oc-if:config/" +
           "oc-if:type = 'ianaift:ethernetCsmacd'" {
        description
        "Undersize pkt count";
      }
      type yang:counter64;
    }
  }

  augment "/oc-if:interfaces/oc-if:interface/oc-if:subinterfaces/" +
          "oc-if:subinterface/oc-if:config" {
    uses interface-segment-routing-config;
  }

  augment "/oc-if:interfaces/oc-if:interface/oc-if:subinterfaces/" +
          "oc-if:subinterface/oc-if:state" {
    container segment-routing {
      description
      "Parameters related to Segment Routing";

      leaf label-index {
        type uint32;
        description
        "Label index";
      }
      leaf label {
        type uint32;
        description
        "Label";
      }
    }
    leaf network-instance {
      type oc-ni:network-instance-ref;
      description
        "The L3 network-instance that this subinterface is associated with.
         When this leaf is unspecified, subinterface is associated with the
         the default network instance.";
    }
  }

  augment "/oc-if:interfaces/oc-if:interface/oc-if:state/oc-if:counters" {
    leaf in-bits-rate {
      type yang:counter64;
      description
      "input rate in bits";
    }
    leaf in-bits-rate-brief {
      type string;
      description
      "input rate in bits in string format";
    }
    leaf in-pkts-rate {
      type yang:counter64;
      description
      "input pkts rate";
    }
    leaf out-bits-rate {
      type yang:counter64;
      description
      "output rate in bits";
    }
    leaf out-bits-rate-brief {
      type string;
      description
      "output rate in bits in string format";
    }
    leaf out-bits-rate-unit {
      type string;
      description
      "output rate unit";
    }
    leaf out-pkts-rate {
      type yang:counter64;
      description
      "output pkts rate";
    }
    leaf queue-drop-pkts {
      when "/oc-if:interfaces/oc-if:interface/oc-if:config/" +
           "oc-if:type = 'ianaift:ethernetCsmacd' and " +
           "/arc-features:features/arc-features:feature[arc-features:name='arc-features:ARCOS_QoS']" +
           "/arc-features:supported = 'true'" {
        description
        "Count of Queue Drop Packets";
      }
      type yang:counter64;
    }
    container errors {
      config false;
      description
        "Error counters";
      uses if-error-counters;
    }
  }

  augment "/oc-if:interfaces/oc-if:interface/oc-if:config" {
    leaf fec {
      when "/oc-if:interfaces/oc-if:interface/oc-if:config/" +
           "oc-if:type = 'ianaift:ethernetCsmacd'";
      description
      "Forward error correction type to use for this ethernet interface";
      type fec-types;
    }

    leaf load-interval {
      type uint16 {
        range 5..300;
      }
      description "Interface counter load interval in seconds";
    }
  }

  augment "/oc-if:interfaces/oc-if:interface/oc-if:state" {
    leaf load-interval {
      type uint16;
      description "Interface counter load interval in seconds";
    }

    leaf media-type {
      type string;
      description "Media type of the interface";
    }

    leaf module-type {
      type string;
      description "Module type of the interface";
    }

    leaf fec {
      when "/oc-if:interfaces/oc-if:interface/oc-if:config/" +
           "oc-if:type = 'ianaift:ethernetCsmacd'";
      description
      "Operational value of forward error correction type in use for this interface";
      type fec-types;
    }

    leaf fec-corrected-errors {
      when "/oc-if:interfaces/oc-if:interface/oc-if:config/" +
           "oc-if:type = 'ianaift:ethernetCsmacd'";
      description
      "Count of FEC corrected errors";
      type uint64;
    }

    leaf fec-uncorrected-errors {
      when "/oc-if:interfaces/oc-if:interface/oc-if:config/" +
           "oc-if:type = 'ianaift:ethernetCsmacd'";
      description
      "Count of FEC uncorrected errors";
      type uint64;
    }

    leaf speed-group {
      when "/oc-if:interfaces/oc-if:interface/oc-if:config/" +
           "oc-if:type = 'ianaift:ethernetCsmacd'" {
        description
        "Speed group that this interface belongs to";
      }
      type uint8;
    }

    leaf errDisable {
      type string;
      description
        "STP disable reason";
    }
    leaf time-elapsed-since-last-change {
      type string;
      description
      "Time Elapsed since last state change";
    }

    uses dynamic-address-top;
  }

}
