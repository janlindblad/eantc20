module arcos-license {
  yang-version "1.1";
  namespace "http://yang.arrcus.com/arcos/license";
  prefix arc-lic;

  import ietf-yang-types { 
    prefix yang; 
  }

  import arcos-common-types { 
    prefix arc-common-types; 
  }

  grouping license-state {
    description
      "Global operational state data for Licenses";

    leaf license-key {
      type string {
        length 25..56;
      }
      description
        "License key";
    }

    leaf product-id {
      type string {
        length 1..32;
      }

      description
        "Product ID/SKU";
    }

    leaf expiration-date {
      type union {
        type enumeration {
          enum PERPETUAL;
        }

        type yang:date-and-time;
      }
      description
        "License expiration date";
    }
  }

  grouping license-rpc-input-params {
    leaf license-key {
      type string {
        length 25..56;
      }
      mandatory true;
      description
        "License key";
    }
  }

  grouping license-top {
    description
      "Top level grouping for license data and structure";
  
    container licenses {
      config false;
      description
        "Top level enclosing container for license operational state data";

      list license {
        description
          "Global operational state data for licenses";
  
        key "license-key";
        uses license-state;
      }
    }
  }

  uses license-top;

  rpc request-license-add {
    description
      "Add license key";

    input {
      uses license-rpc-input-params;
    }

    output {
      uses arc-common-types:generic-rpc-response;
    }
  }

  rpc request-license-remove {
    description
      "Remove license key";

    input {
      uses license-rpc-input-params;
    }

    output {
      uses arc-common-types:generic-rpc-response;
    }
  }
}
