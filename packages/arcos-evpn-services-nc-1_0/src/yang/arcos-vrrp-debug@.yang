module arcos-vrrp-debug {
  yang-version 1.1;
  namespace "http://yang.arrcus.com/arcos/vrrp/debug";
  prefix arc-vrrp-dbg;

  typedef vrrp-debug-state {
    type enumeration {
      enum off {
        description
          "Disable debug";
      }
      enum on {
        description
          "Enable debug";
      }
    }
  }

  typedef vrrp-debug-type {
    type enumeration {
      enum all {
        description
          "VRRP All debugs";
      }
      enum event {
        description
          "VRRP Event debugs";
      }
      enum timer {
        description
          "VRRP Timer debugs";
      }
      enum packet {
        description
          "VRRP packet debugs";
      }
      enum rib {
        description
          "VRRP RIB debugs";
      }
      enum bfd {
        description
          "VRRP BFD debugs";
      }
      enum ui {
        description
          "VRRP UI debugs";
      }
      enum memlock {
        description
          "VRRP memlock debugs";
      }
    }
  }

  container vrrp-debug {
    description
      "VRRP debug control";
    action protocol {
      input {
        leaf debug {
        type vrrp-debug-type;
        mandatory true;
          description
          "Debug to be controlled";
        }
        leaf op {
        type vrrp-debug-state;
        mandatory true;
          description
          "turn on/off operation";
        }
      }
      output {
        leaf result {
        type string;
          description
          "The status of operation";
        }
      }
    }
  }
}
