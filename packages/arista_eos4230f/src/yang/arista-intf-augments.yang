module arista-intf-augments {
  namespace "http://arista.com/yang/openconfig/interfaces/augments";
  prefix arista-intf-augments;

  import openconfig-interfaces {
    prefix oc-if;
  }
  import openconfig-if-ethernet {
    prefix oc-eth;
  }
  import openconfig-if-aggregate {
    prefix oc-lag;
  }
  import openconfig-vlan {
    prefix oc-vlan;
  }
  import openconfig-vlan-types {
    prefix oc-vlan-types;
  }
  import iana-if-type {
    prefix ift;
  }
  import openconfig-if-ip {
    prefix oc-ip;
  }
  import openconfig-inet-types {
    prefix oc-inet;
  }

  organization
    "Arista Networks <http://arista.com/>";
  contact
    "Arista Networks, Inc.
     Product Support";
  description
    "This module contains OpenConfig interface augments in Arista EOS.

     Copyright (c) 2017 Arista Networks, Inc. All rights reserved.";

  revision "2019-07-31" {
    description
      "Correct oc-if:type path in when statement";
    reference "1.2.1";
  }

  revision 2019-01-20 {
    description
      "Add support for reflector interfaces (RFC2544)";
    reference
      "1.2.0";
  }
  revision 2018-10-02 {
    description
      "Add tpid range, trunk groups as interface members. support for
       50G-1, 100G-2, 200G and 400G ethernet speeds. Config for 1000BASE-T,
       fec encoding, load-interval and inactive flag for interfaces.";
    reference
      "1.1.0";
  }
  revision 2017-10-01 {
    description
      "Initial augment file.";
    reference
      "1.0.0";
  }

  typedef fallback-enum {
    type enumeration {
      enum none {
        description
          "Fallback not enabled on this interface";
      }
      enum static {
        description
          "Static fallback enabled on this interface";
      }
      enum individual {
        description
          "Individual fallback enabled on this interface";
      }
    }
    description
      "type definition for fallback on the interface";
  }

  typedef fallback-state-enum {
    type enumeration {
      enum fallbackStateUnconfigured {
        description
          "Fallback not enabled on this interface";
      }
      enum fallbackStateConfigured {
        description
          "Static fallback enabled on this interface";
      }
      enum fallbackStateInitialized {
        description
          "Individual fallback enabled on this interface";
      }
      enum fallbackStateMonitoring {
        description
          "Individual fallback enabled on this interface";
      }
      enum fallbackStateEnabled {
        description
          "Individual fallback enabled on this interface";
      }
    }
    description
      "type definition for fallback state on the interface";
  }

  typedef arista-addr-type {
    type enumeration {
      enum PRIMARY;
      enum SECONDARY;
      enum IPV6;
    }
  }

  augment "/oc-if:interfaces/oc-if:interface/oc-lag:aggregation/oc-lag:config" {
    leaf fallback {
      type fallback-enum;
      description
        "fallback type on this interface.";
    }
    leaf fallback-timeout {
      type uint16 {
        range "0..300";
      }
      default "90";
      description
        "fallback timeout on this interface.";
    }
    description
      "Adds fallback type on this interface.";
  }

  augment "/oc-if:interfaces/oc-if:interface/oc-lag:aggregation/oc-lag:state" {
    leaf fallback {
      type fallback-enum;
      description
        "Fallback status on this interface.";
    }
    leaf fallback-state {
      type fallback-state-enum;
      description
        "Fallback status on this interface.";
    }
    description
      "Adds fallback state on this interface.";
  }

  grouping trunkGroupsEOSConfig {
    leaf-list trunk-groups {
      type string;
      description
        "Set of trunk groups the interface is a member of";
    }
    description
      "grouping of a list of trunk groups";
  }

  augment "/oc-if:interfaces/oc-if:interface/oc-lag:aggregation/oc-vlan:switched-vlan/oc-vlan:config" {
    when "../../../oc-if:config/oc-if:type = 'ift:ieee8023adLag'" { //JLINDBLA

      description
        "Active when the interface is a LAG";
    }
    uses trunkGroupsEOSConfig;
    description
      "Adds trunk group settings to a LAG interface";
  }

  augment "/oc-if:interfaces/oc-if:interface/oc-eth:ethernet/oc-vlan:switched-vlan/oc-vlan:config" {
    when "../../../oc-if:config/oc-if:type = 'ift:ethernetCsmacd'" { //JLINDBLA
      description
        "Active when the interface is Ethernet";
    }
    uses trunkGroupsEOSConfig;
    description
      "Adds trunk group settings to an Ethernet interface";
  }

  augment "/oc-if:interfaces/oc-if:interface/oc-if:state" {
    description
      "Add leaf for tracking inactive interfaces.";
    leaf inactive {
      type boolean;
      description
        "Interface may be inactive due to configuration.";
    }
  }

  augment "/oc-if:interfaces/oc-if:interface/oc-lag:aggregation/oc-lag:config" {
    leaf mlag {
      type uint16 {
        range "1..2000";
      }
      description
        "Configure mlag on this interface.";
    }
  }

  augment "/oc-if:interfaces/oc-if:interface/oc-if:config" {
    description
      "Add leaf for configuring load interval on this interface.";
    leaf load-interval {
      type uint16 {
        range "0..600";
      }
      default "300";
      description
        "Configure load-interval on this interface.";
    }
  }

  augment "/oc-if:interfaces/oc-if:interface/oc-if:config" {
    description
      "Add leaf for allowing TPID values in the range 0x600-0xFFFF";
    leaf arista-tpid {
      type union {
        type identityref {
          base oc-vlan-types:TPID_TYPES;
        }
        type uint16 {
          range "1536..65535";
        }
        type string;//JLINDBLA
      }
      //default "oc-vlan-types:TPID_0X8100";//JLINDBLA
      description
        "EOS allows additional TPID values in the range 0x600-0xFFFF";
    }
  }

  augment "/oc-if:interfaces/oc-if:interface/oc-eth:ethernet/oc-eth:config" {
    description
      "Add container for configuring FEC encodings on this interface.";
    container fec-encoding {
      leaf disabled {
        type boolean;
        description
          "fec-encoding is disabled.";
      }
      leaf reed-solomon544 {
        type boolean;
        description
          "reed-solomon544 fec.";
      }
      leaf reed-solomon {
        type boolean;
        description
          "reed-solomon fec.";
      }
      leaf fire-code {
        type boolean;
        description
          "fire-code fec.";
      }
      leaf coherent-fec-encoding {
        type enumeration {
          enum COHERENT_DEFAULT {
            description
              "coherent default fec.";
          }
          enum COHERENT_SD25 {
            description
              "coherent SD25 fec.";
          }
          enum COHERENT_SD25_BCH {
            description
              "coherent SD25_BCH fec.";
          }
          enum COHERENT_SD20 {
            description
              "coherent SD20 fec.";
          }
          enum COHERENT_SD15 {
            description
              "coherent SD15 fec.";
          }
          enum COHERENT_HD7 {
            description
              "coherent HD7 fec.";
          }
          enum COHERENT_G709 {
            description
              "coherent G709 fec.";
          }
        }
        description
          "coherent fec encoding.";
      }
      description
        "container for configuring FEC encodings on an interface.";
    }
  }

  augment "/oc-if:interfaces/oc-if:interface/oc-eth:ethernet/oc-eth:config" {
    leaf sfp-1000base-t {
      type boolean;
      description
        "Leaf for tracking whether the advertised modes were configured specifically for a 1000BASE-T interface.";
    }
    description
      "Add a leaf for tracking a 1000BASE-T interface.";
  }

  identity SPEED_50GB_1LANE {
    base oc-eth:ETHERNET_SPEED;
    description
      "ethernet Speed of 50GB 1 lane.";
  }

  identity SPEED_100GB_2LANE {
    base oc-eth:ETHERNET_SPEED;
    description
      "ethernet Speed of 100GB 2 lane.";
  }

  identity SPEED_200GB {
    base oc-eth:ETHERNET_SPEED;
    description
      "ethernet Speed of 200GB";
  }

  identity SPEED_200GB_4LANE {
    base oc-eth:ETHERNET_SPEED;
    description
      "ethernet Speed of 200GB 4 lane.";
  }

  identity SPEED_200GB_8LANE {
    base oc-eth:ETHERNET_SPEED;
    description
      "ethernet Speed of 200GB 8 lane.";
  }

  identity SPEED_400GB {
    base oc-eth:ETHERNET_SPEED;
    description
      "ethernet Speed of 400GB";
  }

  augment "/oc-if:interfaces/oc-if:interface/oc-if:subinterfaces/oc-if:subinterface/oc-ip:ipv4/oc-ip:addresses/oc-ip:address/oc-ip:config" {
    description
      "Add leaf to indicate the type of this address.";
    leaf addr-type {
      type arista-addr-type;
    }
  }

  augment "/oc-if:interfaces/oc-if:interface/oc-if:subinterfaces/oc-if:subinterface/oc-ip:ipv4/oc-ip:addresses/oc-ip:address/oc-ip:state" {
    description
      "Add leaf to indicate the type of this address.";
    leaf addr-type {
      type arista-addr-type;
    }
  }

  augment "/oc-if:interfaces/oc-if:interface/oc-vlan:routed-vlan/oc-ip:ipv4/oc-ip:addresses/oc-ip:address/oc-ip:config" {
    description
      "Add leaf to indicate the type of this address.";
    leaf addr-type {
      type arista-addr-type;
    }
  }

  augment "/oc-if:interfaces/oc-if:interface/oc-vlan:routed-vlan/oc-ip:ipv4/oc-ip:addresses/oc-ip:address/oc-ip:state" {
    description
      "Add leaf to indicate the type of this address.";
    leaf addr-type {
      type arista-addr-type;
    }
  }

  grouping arista-virtual-addresses {
    description
      "VRRP group's virtual-address";
    list virtual-addresses {
      key "addr";
      leaf addr {
        type leafref {
          path "../virtual-address/addr";
        }
        description
          "VRRP group's virtual-address";
      }
      container virtual-address {
        description
          "The address type to indicate the purpose of this address.";
        leaf addr {
          type oc-inet:ip-address;
          description
            "An virtual address of an VRRP group";
        }
        leaf addr-type {
          type arista-addr-type;
        }
      }
    }
  }

  augment "/oc-if:interfaces/oc-if:interface/oc-if:subinterfaces/oc-if:subinterface/oc-ip:ipv4/oc-ip:addresses/oc-ip:address/oc-ip:vrrp/oc-ip:vrrp-group/oc-ip:config" {
    uses arista-virtual-addresses;
  }

  augment "/oc-if:interfaces/oc-if:interface/oc-if:subinterfaces/oc-if:subinterface/oc-ip:ipv4/oc-ip:addresses/oc-ip:address/oc-ip:vrrp/oc-ip:vrrp-group/oc-ip:state" {
    uses arista-virtual-addresses;
  }

  augment "/oc-if:interfaces/oc-if:interface/oc-if:subinterfaces/oc-if:subinterface/oc-ip:ipv6/oc-ip:addresses/oc-ip:address/oc-ip:vrrp/oc-ip:vrrp-group/oc-ip:config" {
    uses arista-virtual-addresses;
  }

  augment "/oc-if:interfaces/oc-if:interface/oc-if:subinterfaces/oc-if:subinterface/oc-ip:ipv6/oc-ip:addresses/oc-ip:address/oc-ip:vrrp/oc-ip:vrrp-group/oc-ip:state" {
    uses arista-virtual-addresses;
  }

  augment "/oc-if:interfaces/oc-if:interface/oc-vlan:routed-vlan/oc-ip:ipv4/oc-ip:addresses/oc-ip:address/oc-ip:vrrp/oc-ip:vrrp-group/oc-ip:config" {
    uses arista-virtual-addresses;
  }

  augment "/oc-if:interfaces/oc-if:interface/oc-vlan:routed-vlan/oc-ip:ipv4/oc-ip:addresses/oc-ip:address/oc-ip:vrrp/oc-ip:vrrp-group/oc-ip:state" {
    uses arista-virtual-addresses;
  }

  augment "/oc-if:interfaces/oc-if:interface/oc-vlan:routed-vlan/oc-ip:ipv6/oc-ip:addresses/oc-ip:address/oc-ip:vrrp/oc-ip:vrrp-group/oc-ip:config" {
    uses arista-virtual-addresses;
  }

  augment "/oc-if:interfaces/oc-if:interface/oc-vlan:routed-vlan/oc-ip:ipv6/oc-ip:addresses/oc-ip:address/oc-ip:vrrp/oc-ip:vrrp-group/oc-ip:state" {
    uses arista-virtual-addresses;
  }

  typedef reflector-direction {
    type enumeration {
      enum none {
        description
          "Reflector interface direction not configured.";
      }
      enum in {
        description
          "Reflect on ingress on this interface.";
      }
      enum out {
        description
          "Reflect on egress on this interface.";
      }
    }
    description
      "type definition for reflector interface direction.";
  }

  typedef reflector-mac-action {
    type enumeration {
      enum none {
        description
          "Reflector interface mac action not configured.";
      }
      enum swap {
        description
          "Swap source and destination MAC addresses on reflection.";
      }
    }
    description
      "type definition for reflector interface MAC action.";
  }

  typedef reflector-hw-status {
    type enumeration {
      enum active {
        description
          "Reflector interface active.";
      }
      enum inactive {
        description
          "Reflector interface not active.";
      }
    }
    description
      "type definition for reflector interface status.";
  }

  grouping reflector-config {
    description
      "Configuration parameters relating to a reflector interface.";
    leaf direction {
      type reflector-direction;
      description
        "reflector interface direction.";
    }
    leaf mac-action {
      type reflector-mac-action;
      description
        "reflector interface MAC action.";
    }
  }

  augment "/oc-if:interfaces/oc-if:interface/oc-eth:ethernet" {
    description
      "Add container for configuring reflector on this interface.";
    container reflector {
      container config {
        description
          "Configuration parameters associated with the reflector interface.";
        uses reflector-config;
      }
      container state {
        config false;
        description
          "Operational state parameters associated with the reflector interface.";
        uses reflector-config;
        leaf status {
          type reflector-hw-status;
          description
            "Reflector interface status.";
        }
        leaf status-reason {
          type string;
          description
            "Reflector interface status reason.";
        }
      }
    }
  }
  augment "/oc-if:interfaces/oc-if:interface/oc-eth:ethernet/oc-eth:state" {
    leaf-list supported-speeds {
      type string;
      description
        "Leaf list containing supported speeds for this interface. 
         Note that if transceiver for this interface is not present, then the supported speed is unknown";
    }
  }
}
