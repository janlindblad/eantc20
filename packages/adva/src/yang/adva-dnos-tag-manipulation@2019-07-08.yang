module adva-dnos-tag-manipulation {
  namespace "http://www.advaoptical.com/cim/adva-dnos-tag-manipulation";
  prefix tman;

  import openconfig-vlan-types {
    prefix oc-vlan-types;
  }

  import adva-dnos-types {
    prefix adva-types;
  }

  organization
    "Adva Optical Networking";
  contact
    "For technical support, please contact your service channel";
  description
    "Definitions for tag manipulation profile.";

  revision 2019-07-08 {
    description
      "Integrating to ADVA YANG models.";
  }
  revision 2015-09-10 {
    description
      "First draft version.";
  }

  container profile_objects {
    description
      "Tag manipulation profiles.";
    list profile {
      key "name";
      description
        "Tag manipulation profile configuration.";
      leaf name {
        type adva-types:profile-name;
        description
          "Profile name";
      }

      container egress-inner-tag-action {
        description
          "Egress inner tag action.";
        choice action {
          description
            "Tag action command";
          case add {
            description
              "Add tag action command";
            leaf add_tag {
              type adva-types:vlan-tag-optional;
              description
                "Add tag value";
            }
          }

          case replace {
            description
              "Replace tag action command";
            leaf replace_tag {
              type adva-types:vlan-tag-optional;
              description
                "Replace tag value";
            }
          }

          case remove {
            description
              "Remove tag action command";
            leaf remove_tag {
              type adva-types:vlan-tag-optional {
                range "0";
              }
              description
                "Enable remove tag";
            }
          }
        }
      }

      container egress-outer-tag-action {
        description
          "Egress outer tag action.";
        choice action {
          description
            "Tag action command";
          case add {
            description
              "Add tag action command";
            leaf add_tag {
              type adva-types:vlan-tag-optional;
              description
                "Add tag value";
            }

            leaf add_tpid {
              type identityref {
                base oc-vlan-types:TPID_TYPES;
              }
              description
                "TPID configuration";
            }
          }

          case replace {
            description
              "Replace tag action command";
            leaf replace_tag {
              type adva-types:vlan-tag-optional;
              description
                "Replace tag value";
            }

            leaf replace_tpid {
              type identityref {
                base oc-vlan-types:TPID_TYPES;
              }
              description
                "TPID configuration";
            }
          }

          case remove {
            description
              "Remove tag action command";
            leaf remove_tag {
              type adva-types:vlan-tag-optional {
                range "0";
              }
              description
                "Enable remove tag";
            }
          }
        }
      }

      container ingress-inner-tag-action {
        description
          "Ingress inner tag action.";
        choice action {
          description
            "Tag action command";
          case add {
            description
              "Add tag action command";
            leaf add_tag {
              type adva-types:vlan-tag-optional;
              description
                "Add tag value";
            }
          }

          case replace {
            description
              "Replace tag action command";
            leaf replace_tag {
              type adva-types:vlan-tag-optional;
              description
                "Replace tag value";
            }
          }

          case remove {
            description
              "Remove tag action command";
            leaf remove_tag {
              type adva-types:vlan-tag-optional {
                range "0";
              }
              description
                "Enable remove tag";
            }
          }
        }
      }

      container ingress-outer-tag-action {
        description
          "Ingress outer tag action.";
        choice action {
          description
            "Tag action command";
          case add {
            description
              "Add tag action command";
            leaf add_tag {
              type adva-types:vlan-tag-optional;
              description
                "Add tag value";
            }
          }

          case replace {
            description
              "Replace tag action command";
            leaf replace_tag {
              type adva-types:vlan-tag-optional;
              description
                "Replace tag value";
            }
          }

          case remove {
            description
              "Remove tag action command";
            leaf remove_tag {
              type adva-types:vlan-tag-optional {
                range "0";
              }
              description
                "Enable remove tag";
            }
          }
        }
      }
    }
  }
}
