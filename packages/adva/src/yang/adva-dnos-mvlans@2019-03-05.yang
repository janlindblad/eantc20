module adva-dnos-mvlans {
  yang-version 1;
  namespace "http://www.advaoptical.com/cim/adva-dnos-mvlans";
  prefix adva-dnos-mvlans;

  import iana-if-type {
    prefix ift;
  }

  import openconfig-inet-types {
    prefix oc-inet;
  }

  import openconfig-interfaces {
    prefix oc-if;
  }

  import openconfig-if-ip {
    prefix oc-ip;
  }

  import openconfig-extensions {
    prefix oc-ext;
  }

  organization
    "ADVA Optical Networking";
  contact
    "ADVA Optical Networking
     www.advaoptical.com";
  description
    "This module defines data related to ADVA Management VLAN components in the
     OpenConfig VLAN model for Agema family.";

  revision 2019-03-05 {
    description
      "Initial revision.";
    reference
      "0.1.0";
  }

  oc-ext:openconfig-version "0.1.1";
}
