module adva-dnos-routing-policy {
  yang-version 1;
  namespace "http://www.advaoptical.com/cim/adva-dnos-routing-policy";
  prefix adva-rpol;

  import openconfig-routing-policy {
    prefix oc-rpol;
  }

  organization
    "ADVA Optical Networking";
  contact
    "ADVA Optical Networking
     www.advaoptical.com";
  description
    "This module defines data related to ADVA components in
     the openconfig-routing-policy model for Agema family.";

  revision 2019-10-09 {
    description
      "Initial revision.";
    reference
      "0.1.0";
  }

  deviation "/oc-rpol:routing-policy/oc-rpol:policy-definitions/oc-rpol:policy-definition/oc-rpol:config/oc-rpol:name" {
    deviate replace {
      type string {
        pattern "[1-9][0-9]{0,8}";
      }
    }
  }
}
