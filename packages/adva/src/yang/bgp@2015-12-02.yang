module bgp {
  yang-version 1.1;
  namespace "http://metaswitch.com/yang/nbu/bgp/201512020000Z";
  prefix bgp;

  import metaswitch-custom-yang-types {
    prefix custom;
  }

  import user-extensions {
    prefix user-ext;
  }

  import interfaces {
    prefix interfaces;
  }

  import metaswitch-yang-types {
    prefix meta;
  }

  import ethernet-segment {
    prefix es;
  }

  import redist {
    prefix redist;
  }

  organization
    "Metaswitch Networks";
  contact
    "Postal: Metaswitch Networks
             100 Church Street
             Enfield
             EN2 6BQ
             United Kingdom
     Tel:    +44 20 8366 1177
     E-mail: info@metaswitch.com";
  description
    "Border Gateway Protocol";

  revision 2015-12-02 {
    description
      "Initial revision.";
  }

  identity bgp-error-code {
    description
      "Indicates the error type in a BGP NOTIFICATION message";
    reference
      "RFC 4271 - A Border Gateway Protocol 4 (BGP-4)";
  }

  identity unspecific {
    base bgp-error-code;
    description
      "No specific error was indicated in the BGP Notification message";
  }

  identity message-header-error {
    base bgp-error-code;
    description
      "An error was detected while processing a BGP Message Header";
  }

  identity open-message-error {
    base bgp-error-code;
    description
      "An error was detected while processing a BGP OPEN message";
  }

  identity update-message-error {
    base bgp-error-code;
    description
      "An error was detected while processing a BGP UPDATE message";
  }

  identity hold-timer-expired {
    base bgp-error-code;
    description
      "Indicates that the system did not receive a KEEPALIVE, UPDATE, and/or
       NOTIFICATION message within the specified Hold Time";
  }

  identity fsm-error {
    base bgp-error-code;
    description
      "An error was detected by the BGP Finite State Machine (for example,
       receipt of an unexpected event)";
  }

  identity cease {
    base bgp-error-code;
    description
      "A BGP speaker has closed its BGP connection in the absence of any
       fatal errors";
  }

  identity route-refresh-message-error {
    base bgp-error-code;
    description
      "An error was detected while processing a BGP ROUTE-REFRESH message";
    reference
      "RFC 7313 - Enhanced Route Refresh Capability for BGP-4";
  }

  identity bgp-error-subcode {
    description
      "Provides more specific information about the error reported in a
       NOTIFICATION message.";
    reference
      "RFC 4271 - A Border Gateway Protocol 4 (BGP-4)";
  }

  identity no-subcode {
    base bgp-error-subcode;
    description
      "No specific error subcode was indicated in the BGP Notification
       message";
  }

  identity message-header-subcode {
    base bgp-error-subcode;
    description
      "Error subcode definitions for Message Header error notifications";
  }

  identity connection-not-synchronised {
    base message-header-subcode;
    description
      "Marker field of the message header is not all ones as expected";
  }

  identity bad-message-length {
    base message-header-subcode;
    description
      "Indicates the message has an erroneous length with one or more of the
       following:
       - the Length field of the message header is less than 19 or greater
         than 4096
       - the Length field of an OPEN message is less than the minimum length
         of the OPEN message
       - the Length field of an UPDATE message is less than the minimum
         length of the UPDATE message
       - the Length field of a KEEPALIVE message is not equal to 19
       - the Length field of a NOTIFICATION message is less than the minimum
         length of the NOTIFICATION message";
  }

  identity bad-message-type {
    base message-header-subcode;
    description
      "Message type is not recognised.";
  }

  identity open-message-subcode {
    base bgp-error-subcode;
    description
      "Error subcode definitions for OPEN message error notifications";
  }

  identity unsupported-version-number {
    base open-message-subcode;
    description
      "Version number of the received OPEN message is not supported";
  }

  identity bad-peer-as {
    base open-message-subcode;
    description
      "Autonomous System field of the received OPEN message is unacceptable";
  }

  identity bad-bgp-identifier {
    base open-message-subcode;
    description
      "BGP Identifier field of the received OPEN message is syntactically
       incorrect";
  }

  identity unsupported-optional-parameter {
    base open-message-subcode;
    description
      "One or more of the Optional Parameters in the received OPEN message
       is not recognized";
  }

  identity authentication-failure {
    base open-message-subcode;
    description
      "Authentication procedure has failed";
  }

  identity unacceptable-hold-time {
    base open-message-subcode;
    description
      "Hold Time field of the received OPEN message is unacceptable";
  }

  identity unsupported-capability {
    base open-message-subcode;
    description
      "Indicates that the peer does not support capabilities
       advertisement.";
    reference
      "RFC 5492 - Capabilities Advertisement with BGP-4";
  }

  identity update-message-subcode {
    base bgp-error-subcode;
    description
      "Error subcode definitions for UPDATE message error notifications";
  }

  identity malformed-attribute-list {
    base update-message-subcode;
    description
      "Inidicates Withdrawn Routes Length or Total Attribute Length is too
       large, or an attribute appears more than once in the UPDATE message";
  }

  identity unrecognized-well-known-attribute {
    base update-message-subcode;
    description
      "One or more of the well-known mandatory attributes are not
       recognized";
  }

  identity missing-well-known-attribute {
    base update-message-subcode;
    description
      "One or more of the well-known mandatory attributes are not present";
  }

  identity attribute-flags-error {
    base update-message-subcode;
    description
      "Attribute has Attribute Flags that conflict with the Attribute Type
       Code";
  }

  identity attribute-length-error {
    base update-message-subcode;
    description
      "Attribute has an Attribute Length that conflicts with the expected
       length based on the attribute type code";
  }

  identity invalid-origin-attribute {
    base update-message-subcode;
    description
      "ORIGIN attribute has an undefined value";
  }

  identity invalid-next-hop-attribute {
    base update-message-subcode;
    description
      "The NEXT_HOP attribute field is syntactically incorrect";
  }

  identity optional-attribute-error {
    base update-message-subcode;
    description
      "An error is detected in the value of a recognized optional attribute";
  }

  identity invalid-network-field {
    base update-message-subcode;
    description
      "The NLRI field in the UPDATE message is syntactically incorrect";
  }

  identity malformed-as-path {
    base update-message-subcode;
    description
      "The AS_PATH attribute is syntactically incorrect";
  }

  identity finite-state-machine-subcode {
    base bgp-error-subcode;
    description
      "Error subcode definitions for BGP finite state machine errors.";
    reference
      "RFC 6608 - Subcodes for BGP Finite State Machine Error";
  }

  identity cease-subcode {
    base bgp-error-subcode;
    description
      "Error subcode definitions for Cease notification messages";
    reference
      "RFC 4486 - Subcodes for BGP Cease Notification Message";
  }

  identity max-num-prefixes-reached {
    base cease-subcode;
    description
      "The BGP speaker terminated its peering with the peer because the
       number of address prefixes received exceeds the configured upper
       bound";
  }

  identity administrative-shutdown {
    base cease-subcode;
    description
      "The BGP speaker administratively shut down the peer session";
  }

  identity peer-de-configured {
    base cease-subcode;
    description
      "The BGP speaker de-configured the peer session";
  }

  identity administrative-reset {
    base cease-subcode;
    description
      "The BGP speaker administratively reset the peer session";
  }

  identity connection-rejected {
    base cease-subcode;
    description
      "The BGP speaker disallowed the BGP peer session after the BGP speaker
       accepted a transport protocol connection";
  }

  identity other-config-change {
    base cease-subcode;
    description
      "The BGP speaker administratively reset the peer session due to a
       configuration change that is not covered by another subcode.";
  }

  identity conn-collision-resolution {
    base cease-subcode;
    description
      "The BGP speaker sent a CEASE NOTIFICATION as a result of the collision
       resolution procedure";
  }

  identity out-of-resources {
    base cease-subcode;
    description
      "The BGP speaker ran out of resources (for example, memory) and reset
       the peer session";
  }

  identity route-refresh-subcode {
    base bgp-error-subcode;
    description
      "Error subcode definitions for the ROUTE-REFRESH message error";
  }

  identity invalid-message-length {
    base route-refresh-subcode;
    description
      "The length, excluding the fixed-size message header, of the received
       ROUTE-REFRESH message with Message Subtype 1 and 2 is not 4";
  }

  typedef router-bgp-ttl {
    type int32 {
      range "1..255";
    }
    description
      "TTL (1-255)";
  }

  typedef router-bgp-ttl-sec-min-ttl {
    type int32 {
      range "0..255";
    }
    description
      "MIN TTL (0-255)";
  }

  typedef router-bgp-as {
    type uint32 {
      range "0..4294967295";
    }
    description
      "INT (0-4294967295)";
  }

  typedef router-bgp-password-string {
    type string {
      length "1..128";
    }
    description
      "WORD (1-128)";
  }

  typedef router-bgp-maximum-paths {
    type int32 {
      range "1..32";
    }
    description
      "PATHS LIMIT (1-32)";
  }

  typedef router-bgp-best-n-paths {
    type int32 {
      range "1..255";
    }
    description
      "BEST N PATHS (1-255)";
  }

  typedef router-bgp-local-preference {
    type uint32 {
      range "0..4294967295";
    }
    description
      "INT (0-4294967295)";
  }

  typedef router-bgp-retain-local-label {
    type int32 {
      range "3..60";
    }
    description
      "DELAY (3-60 min)";
  }

  typedef router-bgp-graceful-restart-restart-time {
    type int32 {
      range "1..3600";
    }
    description
      "SEC (1-3600)";
  }

  typedef router-bgp-max-ecmp-paths {
    type int32 {
      range "1..255";
    }
  }

  typedef router-bgp-max-afi-safi-ecmp-paths {
    type int32 {
      range "0..255";
    }
  }

  typedef router-bgp-update-delay {
    type int32 {
      range "0..3600";
    }
    description
      "SEC (0-3600)";
  }

  typedef router-bgp-orf-prefix {
    type enumeration {
      enum "none" {
        value 1;
        description
          "ORF entries not supported in either direction";
      }
      enum "both" {
        value 2;
        description
          "Send and receive ORF entries";
      }
      enum "send" {
        value 3;
        description
          "Would like to send ORF entries to peer";
      }
      enum "receive" {
        value 4;
        description
          "Willing to receive ORF entries from peer";
      }
    }
    description
      "ORF prefix";
  }

  typedef router-bgp-adv-interval {
    type int32 {
      range "0..600";
    }
    description
      "SEC (0-600)";
  }

  typedef router-bgp-wd-interval {
    type int32 {
      range "0..600";
    }
    description
      "SEC (0-600)";
  }

  typedef router-bgp-ses-timer-keepalive {
    type int32 {
      range "0..65535";
    }
    description
      "SEC (0-65535)";
  }

  typedef router-bgp-ses-timer-holdtime {
    type int32 {
      range "0 | 3..65535";
    }
    description
      "SEC (0 or 3-65535)";
  }

  typedef router-bgp-ses-timer-connect-retry {
    type int32 {
      range "1..65535";
    }
    description
      "SEC (1-65535)";
  }

  typedef router-bgp-max-prefixes {
    type uint32 {
      range "0..2147483647";
    }
    description
      "(0-2147483647)";
  }

  typedef router-bgp-prefix-threshold {
    type uint32 {
      range "0..100";
    }
    description
      "(0-100%)";
  }

  typedef router-bgp-sess-drop-warning {
    type enumeration {
      enum "drop" {
        value 1;
        description
          "The session is dropped";
      }
      enum "warn" {
        value 2;
        description
          "A warning is produced";
      }
    }
    description
      "Session action";
  }

  typedef router-bgp-max-prefix-hold {
    type int32 {
      range "0 | 30..86400";
    }
    description
      "SEC (0 or 30-86400)";
  }

  typedef bgp-restart-exit-reason {
    type enumeration {
      enum "none" {
        value 1;
      }
      enum "in-progress" {
        value 2;
      }
      enum "completed" {
        value 3;
      }
      enum "timed-out" {
        value 4;
      }
      enum "failed" {
        value 5;
      }
      enum "completedPeerNoSupport" {
        value 6;
      }
    }
    description
      "BGP restart exit reason";
  }

  typedef bgp-last-error {
    type string {
      length "4";
    }
    description
      "BGP last error string";
  }

  typedef bgp-last-error-data {
    type string {
      length "0..256";
    }
    description
      "BGP last error data string";
  }

  typedef bgp-user-data-t {
    type string {
      length "8";
    }
    description
      "BGP user data";
  }

  typedef router-bgp-allow-local-as {
    type uint32 {
      range "0..10";
    }
    description
      "INT (0-10)";
  }

  typedef bgp-peer-events {
    type enumeration {
      enum "no-event" {
        value 0;
      }
      enum "start" {
        value 1;
      }
      enum "stop" {
        value 2;
      }
      enum "transport-open" {
        value 3;
      }
      enum "transport-closed" {
        value 4;
      }
      enum "transport-open-failed" {
        value 5;
      }
      enum "transport-fatal-error" {
        value 6;
      }
      enum "connect-retry-timer" {
        value 7;
      }
      enum "hold-retry-timer" {
        value 8;
      }
      enum "keepalive-timer" {
        value 9;
      }
      enum "recv-open" {
        value 10;
      }
      enum "recv-keepalive" {
        value 11;
      }
      enum "recv-update" {
        value 12;
      }
      enum "recv-notification" {
        value 13;
      }
    }
    description
      "BGP Peer events";
  }

  typedef bgp-peer-restart-support {
    type enumeration {
      enum "none" {
        value 1;
      }
      enum "aware-only" {
        value 2;
      }
      enum "enabled" {
        value 3;
      }
    }
    description
      "BGP Peer restart support types";
  }

  typedef bgp-peer-state {
    type enumeration {
      enum "idle" {
        value 1;
      }
      enum "connect" {
        value 2;
      }
      enum "active" {
        value 3;
      }
      enum "open-sent" {
        value 4;
      }
      enum "open-confirm" {
        value 5;
      }
      enum "established" {
        value 6;
      }
    }
    description
      "BGP Peer states";
  }

  typedef bgp-peer-restart-status {
    type enumeration {
      enum "not-restarting" {
        value 1;
      }
      enum "restart-timer-running" {
        value 2;
      }
      enum "stale-path-timer-running" {
        value 3;
      }
    }
    description
      "BGP Peer restart status values";
  }

  typedef bgp-peer-config-states {
    type enumeration {
      enum "state-up-to-date" {
        value 1;
      }
      enum "state-out-of-date-admin-down" {
        value 2;
      }
      enum "state-out-of-date-row-inactive" {
        value 3;
      }
    }
    description
      "BGP Peer config states";
  }

  typedef bgp-peer-reflector-client {
    type enumeration {
      enum "non-client" {
        value 1;
        description
          "Non client";
      }
      enum "client" {
        value 2;
        description
          "Client";
      }
      enum "meshed-client" {
        value 3;
        description
          "Meshed client";
      }
    }
    description
      "BGP Reflector Client type";
  }

  typedef bgp-alt-loc-as-mode {
    type enumeration {
      enum "mode1" {
        value 1;
      }
      enum "mode2" {
        value 2;
      }
      enum "mode3" {
        value 3;
      }
    }
    description
      "BGP alternative local AS modes.";
  }

  typedef bgp-peer-or-afm {
    type enumeration {
      enum "peer" {
        value 1;
      }
      enum "afm" {
        value 2;
      }
    }
    description
      "BGP Peer or AFM type";
  }

  typedef bgp-afi {
    type enumeration {
      enum "other" {
        value 0;
      }
      enum "ipv4" {
        value 1;
      }
      enum "ipv6" {
        value 2;
      }
      enum "l2vpn" {
        value 25;
      }
    }
    description
      "BGP Afi types";
  }

  typedef bgp-safi {
    type enumeration {
      enum "none" {
        value 0;
      }
      enum "unicast" {
        value 1;
      }
      enum "multicast" {
        value 2;
      }
      enum "unicast-multicast" {
        value 3;
      }
      enum "labeled" {
        value 4;
      }
      enum "vpls" {
        value 65;
      }
      enum "evpn" {
        value 70;
      }
      enum "vpn" {
        value 128;
      }
    }
    description
      "BGP Safi types";
  }

  typedef bgp-as-size-t {
    type enumeration {
      enum "two-octet" {
        value 1;
      }
      enum "four-octet" {
        value 2;
      }
    }
    description
      "BGP AS size values";
  }

  typedef bgp-origin-codes {
    type enumeration {
      enum "igp" {
        value 0;
      }
      enum "egp" {
        value 1;
      }
      enum "incomplete" {
        value 2;
      }
    }
    description
      "BGP origin codes";
  }

  typedef bgp-nlri-peer-type {
    type enumeration {
      enum "none" {
        value 0;
      }
      enum "ibgp" {
        value 1;
      }
      enum "ebgp" {
        value 2;
      }
    }
    description
      "Type of BGP peer";
  }

  typedef bgp-path-attr-atomic-agg {
    type enumeration {
      enum "present" {
        value 1;
      }
      enum "absent" {
        value 2;
      }
    }
    description
      "BGP Path attribute atomic aggregate types";
  }

  typedef bgp-nlri-is-active {
    type enumeration {
      enum "not-tracked" {
        value 1;
      }
      enum "inactive" {
        value 2;
      }
      enum "active" {
        value 3;
      }
    }
    description
      "BGP NLRI is active values";
  }

  typedef bgp-half-life-t {
    type uint32 {
      range "1..45";
    }
    description
      "MINS (1-45)";
  }

  typedef bgp-flap-threshold-t {
    type uint32 {
      range "1..20000";
    }
    description
      "(1-20000)";
  }

  typedef bgp-max-suppress-time-t {
    type uint32 {
      range "1..255";
    }
    description
      "MINS (1-255)";
  }

  typedef l2vpn-ve-id-t {
    type uint32 {
      range "1..65535";
    }
    description
      "(1-65535)";
  }

  typedef bgp-add-path-caps-router {
    type enumeration {
      enum "disable" {
        value 1;
        description
          "Neither send or receive";
      }
      enum "receive" {
        value 2;
        description
          "Receive only";
      }
      enum "send" {
        value 3;
        description
          "Send only";
      }
      enum "both" {
        value 4;
        description
          "Both send and receive";
      }
    }
    description
      "BGP Add Path Capabilities configurable at the router level";
  }

  typedef bgp-add-path-capabilities {
    type enumeration {
      enum "disable" {
        value 1;
        description
          "Neither send or receive";
      }
      enum "receive" {
        value 2;
        description
          "Receive only";
      }
      enum "send" {
        value 3;
        description
          "Send only";
      }
      enum "both" {
        value 4;
        description
          "Both send and receive";
      }
      enum "inherit" {
        value 5;
        description
          "Use BGP address-family value";
      }
    }
    description
      "BGP Add Path Capabilities";
  }

  typedef bgp-peer-group-name {
    type meta:ascii-string {
      length "1..32";
    }
    description
      "WORD (1-32)";
  }

  typedef bgp-listen-range-max-peers-t {
    type uint32 {
      range "0..4294967295";
    }
    description
      "(0-4294967295)";
  }

  typedef bgp-peer-group-area-type {
    type enumeration {
      enum "ibgp" {
        value 1;
        description
          "Internal BGP";
      }
      enum "ebgp" {
        value 2;
        description
          "External BGP";
      }
      enum "ebgp-confederation" {
        value 3;
        description
          "External BGP confederation";
      }
    }
    description
      "BGP Peer Group Area type";
  }

  typedef bgp-peering-type {
    type enumeration {
      enum "unspecified" {
        value 1;
        description
          "Unspecified";
      }
      enum "provider" {
        value 2;
        description
          "Provider";
      }
      enum "customer" {
        value 3;
        description
          "Customer";
      }
      enum "bilateral" {
        value 4;
        description
          "Bilateral";
      }
    }
    description
      "BGP Peering Type";
  }

  typedef bgp-aro-advert-status-t {
    type enumeration {
      enum "advertised" {
        value 1;
      }
      enum "suppressed" {
        value 2;
      }
      enum "pending-withdrawal" {
        value 3;
      }
      enum "withdrawn" {
        value 4;
      }
    }
    description
      "BGP ARO advertisement status";
  }

  typedef bgp-aro-aggr-status-t {
    type enumeration {
      enum "no-aggregation" {
        value 1;
      }
      enum "aggregate-route" {
        value 2;
      }
      enum "unsuppressed-aggregated-route" {
        value 3;
      }
      enum "suppressed-aggregated-route" {
        value 4;
      }
    }
    description
      "BGP ARO aggregation status";
  }

  typedef bgp-oper-status-t {
    type enumeration {
      enum "up" {
        value 1;
        description
          "Up";
      }
      enum "down" {
        value 2;
        description
          "Down";
      }
      enum "going-up" {
        value 3;
        description
          "Going up";
      }
      enum "going-down" {
        value 4;
        description
          "Going down";
      }
      enum "activation-failed" {
        value 5;
        description
          "Activation failed";
      }
    }
    description
      "BGP operational status";
  }

  typedef router-bgp-next-hop-self {
    type enumeration {
      enum "true" {
        value 1;
        description
          "Set self as next hop for advertised routes (except when
           reflecting routes)";
      }
      enum "false" {
        value 2;
        description
          "Do not set self as next hop for advertised routes";
      }
      enum "all" {
        value 3;
        description
          "Set self as next hop for both eBGP and iBGP advertised routes
           including when acting as a route reflector";
      }
    }
    description
      "BGP Next Hop Calculation Actions";
  }

  grouping bgp-capabilities-bits {
    description
      "A set of capabilities used to report state.";
    leaf mp-ipv4-unicast {
      type empty;
      description
        "Multiprotocol BGP support for IPv4 unicast routes.";
    }

    leaf mp-ipv4-multicast {
      type empty;
      description
        "Multiprotocol BGP support for IPv4 multicast routes.";
    }

    leaf mp-ipv4-vpn {
      type empty;
      description
        "Multiprotocol BGP support for IPv4 VPN routes.";
    }

    leaf mp-ipv4-label {
      type empty;
      description
        "Multiprotocol BGP support for labeled IPv4 routes.";
    }

    leaf mp-ipv6-unicast {
      type empty;
      description
        "Multiprotocol BGP support for IPv6 unicast routes.";
    }

    leaf mp-ipv6-multicast {
      type empty;
      description
        "Multiprotocol BGP support for IPv6 multicast routes.";
    }

    leaf mp-ipv6-vpn {
      type empty;
      description
        "Multiprotocol BGP support for IPv6 VPN routes.";
    }

    leaf mp-ipv6-label {
      type empty;
      description
        "Multiprotocol BGP support for labeled IPv6 routes.";
    }

    leaf route-refresh {
      type empty;
      description
        "Support for Route Refresh messages.";
    }

    leaf graceful-restart {
      type empty;
      description
        "Support for graceful restart processing.";
    }

    leaf route-refresh-cisco {
      type empty;
      description
        "Support for pre-standard (Cisco) Route Refresh messages.";
    }

    leaf outbound-route-filter {
      type empty;
      description
        "Support for Outbound Route Filtering, for one or more";
    }

    leaf outbound-route-filter-cisco {
      type empty;
      description
        "Support for pre-standard (Cisco) Outbound Route Filtering,";
    }

    leaf four-octet-as {
      type empty;
      description
        "Support for four-octet AS numbers.";
    }

    leaf mp-l2vpn-vpls {
      type empty;
      description
        "Multiprotocol BGP support for AFI/SAFI = L2VPN/VPLS.";
    }

    leaf mp-l2vpn-evpn {
      type empty;
      description
        "Multiprotocol BGP support for AFI/SAFI = L2VPN/EVPN.";
    }

    leaf add-path {
      type empty;
      description
        "Support for additional BGP paths.";
    }

    leaf enhanced-route-refresh {
      type empty;
      description
        "Support for enhanced route refresh (RFC7313).";
    }

    leaf extended-next-hop-ipv4-unicast {
      type empty;
      description
        "Support for extended next-hop encoding for IPv4 unicast routes (RFC5549).";
    }

    leaf extended-next-hop-ipv4-multicast {
      type empty;
      description
        "Support for extended next-hop encoding for IPv4 multicast routes (RFC5549).";
    }

    leaf extended-next-hop-ipv4-label {
      type empty;
      description
        "Support for extended next-hop encoding for labeled IPv4 routes (RFC5549).";
    }

    leaf extended-next-hop-ipv4-vpn {
      type empty;
      description
        "Support for extended next-hop encoding for IPv4 VPN routes (RFC5549).";
    }
  }

  grouping bgp-afi-safi-bits {
    description
      "A set of address and subaddress families used to report state.";
    leaf ipv4-unicast {
      type empty;
    }

    leaf ipv4-multicast {
      type empty;
    }

    leaf ipv4-mpls-bgp-vpn {
      type empty;
    }

    leaf ipv6-unicast {
      type empty;
    }

    leaf ipv6-multicast {
      type empty;
    }

    leaf ipv6-mpls-bgp-vpn {
      type empty;
    }

    leaf ipv4-labeled {
      type empty;
    }

    leaf ipv6-labeled {
      type empty;
    }

    leaf l2vpn-vpls {
      type empty;
    }

    leaf l2vpn-evpn {
      type empty;
    }
  }

  grouping bgp-ext-community {
    choice extcommunity-type {
      case rt {
        container rt {
          user-ext:CLI-comm-help "Configure Route Target parameters";
          user-ext:CLI-no-comm-help "Configure Route Target parameters";
          leaf value {
            user-ext:CLI-comm-help "Set extended community value";
            user-ext:CLI-no-comm-help "Remove extended community value";
            user-ext:CLI-param-help "Set extended community value";
            type meta:bgp-extended-community;
            description
              "BGP extended community number used when executing the action
               on the extended community.";
          }
        }
      }

      case soo {
        container soo {
          user-ext:CLI-comm-help "Configure Site of Origin parameters";
          user-ext:CLI-no-comm-help "Configure Site of Origin parameters";
          leaf value {
            user-ext:CLI-comm-help "Set extended community value";
            user-ext:CLI-no-comm-help "Remove extended community value";
            user-ext:CLI-param-help "Set extended community value";
            type meta:bgp-extended-community;
            description
              "BGP extended community number used when executing the action
               on the extended community.";
          }
        }
      }
    }
  }

  grouping bgp-redist {
    leaf new-community {
      user-ext:CLI-comm-help "Set BGP community number";
      user-ext:CLI-no-comm-help "Remove BGP community number";
      user-ext:CLI-param-help "Set BGP community number";
      type meta:bgp-community;
      description
        "BGP community number to set in routing information sent to
         destination.";
    }

    container new-extcommunity {
      user-ext:CLI-comm-help "Set BGP extended community number";
      user-ext:CLI-no-comm-help "Remove BGP extended community number";
      description
        "Extended BGP community number to set in routing information sent to
         destination.";
      uses bgp-ext-community;
    }

    leaf new-med {
      user-ext:CLI-comm-help "Set BGP MED";
      user-ext:CLI-no-comm-help "Set BGP MED to default";
      user-ext:CLI-param-help "Set BGP MED";
      type uint32 {
        range "0..4294967295";
      }
      description
        "BGP Multi-Exit Discriminator to set in routing information sent to destination.";
    }

    leaf new-weight {
      user-ext:CLI-comm-help "Set BGP weight";
      user-ext:CLI-no-comm-help "Set BGP weight to default";
      user-ext:CLI-param-help "Set BGP weight";
      type uint32 {
        range "0..4294967295";
      }
      default "32768";
      description
        "BGP weight to set in routing information sent to destination.";
    }

    leaf new-local-preference {
      user-ext:CLI-comm-help "Set BGP local preference";
      user-ext:CLI-no-comm-help "Set BGP local preference to default";
      user-ext:CLI-param-help "Set BGP local preference";
      type uint32 {
        range "0..4294967295";
      }
      description
        "BGP local preference to set in routing information sent to destination.";
    }
  }

  grouping global-graceful-restart-state-for-bgp {
    description
      "BGP graceful restart state.";
    leaf graceful-restart-remaining-time {
      type uint32;
      units "seconds";
      config false;
      description
        "Remaining time before BGP graceful restart times out.";
    }

    leaf graceful-restart-exit-reason {
      type bgp-restart-exit-reason;
      config false;
      description
        "Describes the outcome of the last attempt at a graceful
         restart.  If the value is 'none', no restart has yet been
         attempted.  If the value is 'in-progress', a restart
         attempt is currently underway.";
    }

    leaf graceful-restart-time {
      type router-bgp-graceful-restart-restart-time;
      config false;
      description
        "Restart time announced to neighbors";
    }
  }

  grouping global-state-for-bgp {
    description
      "BGP state.";
    leaf number-aro-routes {
      type uint32;
      config false;
      description
        "The total number of Adj-RIB-Out routes currently allocated
         across all Adj-RIBs-Out.

         When additional paths are enabled, routes with different
         path ID values count as different prefixes.";
    }

    leaf peak-number-aro-routes {
      type uint32;
      config false;
      description
        "The peak number of Adj-RIB-Out routes that have been
         allocated at any one time.

         When additional paths are enabled, routes with different
         path ID values count as different prefixes.";
    }

    leaf remain-delay-time {
      type uint32;
      config false;
      description
        "The maximum time remaining until route selection takes
         place following a restart, in hundredths of a second.";
    }

    leaf path-attrs {
      type uint32;
      config false;
      description
        "The total number of path attributes present.";
    }

    leaf enforce-first-as {
      type boolean;
      config false;
      description
        "Enabled first AS in path and peer AS equal proof";
    }

    leaf update-delay {
      type router-bgp-update-delay;
      config false;
      description
        "BGP update delay";
    }

    uses global-graceful-restart-state-for-bgp;
  }

  grouping neighbor-state {
    description
      "BGP neighbor state.";
    leaf remote-address {
      type interfaces:iface-ip-address-t;
      config false;
      description
        "The remote address for the peering session.

         For configured peers this field has the same value as
         the remote address configured for the peer.

         For dynamic peers this field is the address of the BGP peer
         as determined from the incoming connection.";
    }

    leaf local-address {
      type interfaces:iface-ip-address-allow-zero-t;
      config false;
      description
        "The local address configured for the peering session, or
         a zero length address if not specified.

         For configured peers this field has the same value as
         the local address configured for the peer.

         For dynamic peers this field is a zero-length address.

         The selected-local-address shows the local address actually in use.";
    }

    leaf local-port {
      type uint32 {
        range "0..65535";
      }
      config false;
      description
        "The local port configured for the peering session, or zero
         if not specified.

         For configured peers this field has the same value as
         local port configured.

         For dynamic peers this field is zero.

         The selected-local-port shows the local port actually in use.";
    }

    leaf remote-port {
      type uint32 {
        range "0..65535";
      }
      config false;
      description
        "The remote port configured for the peering session, or
         zero if not specified.

         For configured peers this field has the same value as
         remote port configured for the peer.

         For dynamic peers this field is zero.

         The selected-remote-port shows the remote port actually in use.";
    }

    leaf local-address-scope-id {
      type uint32;
      config false;
      description
        "The scope ID of the local and remote adresses.  The scope ID is
         required if the address is an IPv6 link-local address.  Otherwise,
         this field must be set to zero.

         For configured peers this field has the same value as
         configured scope ID.

         For dynamic peers this field is the scope ID of the
         remote address as determined from the incoming connection.";
    }

    leaf interface {
      type interfaces:iface-name;
      config false;
      description
        "The name of the interface on which the address is reachable.
         For neighbors configured by interface name, this matches the
         neighbor-interface key and is otherwise absent.";
    }

    leaf identifier {
      type meta:router-id;
      config false;
      description
        "The BGP Identifier of this entry's BGP peer.

         This entry is zero unless the state is open-confirm or established.";
    }

    leaf state {
      type bgp-peer-state;
      config false;
      description
        "The BGP peer's FSM state.";
    }

    leaf dynamic-peer {
      type boolean;
      config false;
      description
        "Whether the peer is dynamic (true) or individually
         configured (false).";
    }

    leaf remote-as {
      type uint32;
      config false;
      description
        "The remote autonomous system number in use on the session.
         For configured peers not yet active, this is the
         configured value.

         This value may be different from the configured value
         if the configured value has been changed since the peer session
         was started.";
    }

    leaf index {
      type uint32;
      config false;
      description
        "The peer index.

         The peer index is a unique index for the peer.  It is used to
         provide an index value for other lists whose data is
         logically per-peer.

         The peer index value is fixed until the entry in the
         peer is destroyed, but it changes if the entry is destroyed and
         recreated.

         For a dynamic BGP peer, if the BGP session terminates and
         then restarts outside the graceful restart period, the
         peer index value may change.";
    }

    leaf capabilities-supported {
      type boolean;
      config false;
      description
        "Whether or not this peer accepted our local capabilities
         optional parameter sent on the OPEN message.  This field
         will not be relevant until the peer has reached open-confirm
         state.  Note that this field indicates support or otherwise
         of the capabilities optional parameter, not a specific
         capability.";
    }

    leaf last-error {
      type bgp-last-error;
      config false;
      description
        "The last error code and subcode sent or received on this
         connection.  If no error has occurred, this field is zero.
         Otherwise, the first byte of this two byte string
         contains the error code, and the second byte contains the
         subcode.";
    }

    leaf last-error-data {
      type bgp-last-error-data;
      config false;
      description
        "The last error code's data seen by this peer on this
         connection.";
    }

    leaf fsm-established-time {
      type uint32;
      units "seconds";
      config false;
      description
        "This timer indicates how long in seconds this peer has
         been in the Established state or how long since this peer
         was last in the Established state.  It is set to zero when
         a new peer is configured or the router is booted.";
    }

    leaf in-updates-elapsed-time {
      type uint32;
      units "seconds";
      config false;
      description
        "Elapsed time in seconds since the last BGP message was
         received from the peer.  Each time in-updates is
         incremented, the value of this object is set to zero (0).";
    }

    leaf hold-time {
      type int32;
      units "seconds";
      config false;
      description
        "Time interval in seconds for the Hold Timer established
         with the peer.

         The Hold Timer interval is calculated by this BGP speaker by
         using the smaller of the configured hold-time
         value and the Hold Time received in the OPEN message.

         A value of zero indicates that the Hold Timer has not been
         established with the peer.";
    }

    leaf keepalive-time {
      type int32;
      units "seconds";
      config false;
      description
        "Time interval in seconds for the KeepAlive Timer
         established with the peer.

         The KeepAlive Timer interval is calculated by this BGP
         speaker such that, when compared with the Hold Time,
         it has the same proportion as the configured keep-alive value has
         when compared with the configured hold-time value.

         A value of zero indicates that the KeepAlive Timer has not
         been established with the peer.";
    }

    leaf in-opens {
      type uint32;
      config false;
      description
        "The number of BGP OPEN messages received on this
         connection.  This object is initialized to zero when the
         connection is established.";
    }

    leaf out-opens {
      type uint32;
      config false;
      description
        "The number of BGP OPEN messages transmitted on this
         connection.  This object is initialized to zero when the
         connection is established.";
    }

    leaf in-notifications {
      type uint32;
      config false;
      description
        "The number of BGP NOTIFICATION messages received on this
         connection.  This object is initialized to zero when the
         connection is established.";
    }

    leaf out-notifications {
      type uint32;
      config false;
      description
        "The number of BGP NOTIFICATION messages transmitted on
         this connection.  This object is initialized to zero when
         the connection is established.";
    }

    leaf in-updates {
      type uint32;
      config false;
      description
        "The number of BGP UPDATE messages received on this
         connection.  This object is initialized to zero when the
         connection is established.";
    }

    leaf out-updates {
      type uint32;
      config false;
      description
        "The number of BGP UPDATE messages transmitted on this
         connection.  This object is initialized to zero when the
         connection is established.";
    }

    leaf in-keepalives {
      type uint32;
      config false;
      description
        "The number of BGP KEEPALIVE messages received on this
         connection.  This object is initialized to zero when the
         connection is established.";
    }

    leaf out-keepalives {
      type uint32;
      config false;
      description
        "The number of BGP KEEPALIVE messages transmitted on this
         connection.  This object is initialized to zero when the
         connection is established.";
    }

    leaf in-refreshes {
      type uint32;
      config false;
      description
        "The number of BGP ROUTE REFRESH messages received on this
         connection.  This object is initialized to zero when the
         connection is established.";
    }

    leaf out-refreshes {
      type uint32;
      config false;
      description
        "The number of BGP ROUTE REFRESH messages transmitted on
         this connection.  This object is initialized to zero when
         the connection is established.";
    }

    leaf in-total-messages {
      type uint32;
      config false;
      description
        "The total number of messages received from the remote peer
         on this connection.  This object is initialized to zero when
         the connection is established.";
    }

    leaf out-total-messages {
      type uint32;
      config false;
      description
        "The total number of messages transmitted to the remote
         peer on this connection.  This object is initialized to zero
         when the connection is established.";
    }

    leaf fsm-established-transitions {
      type uint32;
      config false;
      description
        "The total number of times the BGP FSM transitioned into
         the established state for this peer.";
    }

    leaf connect-retry-count {
      type uint32;
      config false;
      description
        "The current connect retry count of this peer.

         This is incremented each time the peer session flaps, and is
         used to determine the time to wait before retrying the
         session.

         Note this is only incremented when an active session
         terminates abnormally, and not when it simply fails to come
         up.

         This field is not used for dynamic peers.";
    }

    leaf peer-group {
      type uint32;
      config false;
      description
        "The index of the peer group this neighbor belongs to, or
         zero if this neighbor does not belong to a peer group.";
    }

    leaf stale-path-time {
      type uint32;
      units "seconds";
      config false;
      description
        "The maximum time in seconds that BGP will wait
         following a peer restart or peer session failure before
         removing stale routes from that peer.

         This is advertised by the peer in its OPEN message if it
         supports graceful restart.  If the advertised value is
         greater than the configured reatart-time, then that value
         will be used in preference.";
    }

    leaf orf-entry-count {
      type uint32;
      config false;
      description
        "The current number of ORF entries of all types that have
         been received from the peer.";
    }

    leaf last-error-rcvd {
      type bgp-last-error;
      config false;
      description
        "The last error code and subcode received from the peer on
         this connection.

         If no error has been received from the peer, this field is
         zero.  Otherwise, the first byte of this two byte string
         contains the error code, and the second byte contains
         the subcode.";
    }

    leaf last-error-rcvd-time {
      type uint32;
      config false;
      description
        "The value of sysUpTime when the last error was received
         from the peer on this connection.

         If no error has been received from the peer, this field is
         zero.";
    }

    leaf last-error-sent {
      type bgp-last-error;
      config false;
      description
        "The last error code and subcode sent to the peer on this
         connection.

         If no error has been sent to the peer, this field is zero.
         Otherwise, the first byte of this two byte string
         contains the error code, and the second byte contains the
         subcode.";
    }

    leaf last-error-sent-time {
      type uint32;
      config false;
      description
        "The value of sysUpTime when the last error was sent to the
         peer on this connection.

         If no error has been sent to the peer, this field is zero.";
    }

    leaf last-state {
      type bgp-peer-state;
      config false;
      description
        "The BGP peer's previous FSM state.";
    }

    leaf last-event {
      type bgp-peer-events;
      config false;
      description
        "The last input to be made to the BGP peer's FSM.";
    }

    container caps-sent {
      config false;
      description
        "The capabilities announced to the peer on the most recent
         Open message sent to the peer.  This field is set to zero
         before the first Open message is sent to the peer, and
         is unchanged if the session comes down.";
      uses bgp-capabilities-bits;
    }

    container caps-rcvd {
      config false;
      description
        "The capabilities received on the most recent Open message
         received from the peer.  This field is set to zero before
         the first Open message is received from the peer, and is
         unchanged if the session comes down.

         In the event that the peer signals a capability that DC-BGP
         does not recognize, this field will only contain those
         capabilities that BGP recognizes.";
      uses bgp-capabilities-bits;
    }

    container caps-negotiated {
      config false;
      description
        "The capabilities negotiated for the session with the peer.
         This field is set to zero before Open messages have been
         exchanged with the peer, and is unchanged if the session
         comes down.";
      uses bgp-capabilities-bits;
    }

    leaf restart-support {
      type bgp-peer-restart-support;
      config false;
      description
        "Whether the peer supports graceful restart.  This field is
         set to 'none' before an Open message has been received from
         a peer, and is unchanged if the session comes down.";
    }

    container restart-family {
      config false;
      description
        "The address and subaddress families for which the peer
         supports graceful restart.  This field is set to zero before
         an Open message has been received from a peer, and is
         unchanged if the session comes down.";
      uses bgp-afi-safi-bits;
    }

    leaf restart-restart {
      type boolean;
      config false;
      description
        "Whether the peer is currently in the process of
         restarting.";
    }

    leaf restart-status {
      type bgp-peer-restart-status;
      config false;
      description
        "The current state of the peer's restart processing.  If
         bgpPeerStatusRstrRestarting is false, this is set to
         notRestarting.";
    }

    leaf restart-remain-time {
      type uint32;
      units "hundredths of a second";
      config false;
      description
        "The time remaining in the current restart state, in
         hundredths of a second.  If bgpPeerStatusRstrStatus is
         notRestarting, this is set to zero.";
    }

    leaf rcvd-msg-elapsed-time {
      type uint32;
      units "hundredths of a second";
      config false;
      description
        "The elapsed time in hundredths of a second since anything
         was received from this peer.  If nothing has been received
         from this peer, this field is set to zero.  If the session
         comes down this value continues to increase.";
    }

    leaf idle-hold-remain-time {
      type uint32;
      units "hundredths of a second";
      config false;
      description
        "For a peer in 'idle' state, the time remaining in
         hundredths of a second until BGP will try to reactivate
         the connection.  If the peer is not in 'idle' state, this is
         set to zero.";
    }

    leaf route-refresh-sent {
      type uint32;
      config false;
      description
        "The number of Route Refresh messages sent to the peer.

         If the session comes down this value is unchanged, and will
         continue to increment if the session is reestablished.

         However, for dynamic peers the peer status entry is lost
         if the BGP session is not re-established within the graceful
         restart period, and in this case the value of this field
         is lost.";
    }

    leaf route-refresh-received {
      type uint32;
      config false;
      description
        "The number of Route Refresh messages received from the
         peer.

         If the session comes down this value is unchanged, and will
         continue to increment if the session is reestablished.

         However, for dynamic peers the peer status entry is lost
         if the BGP session is not re-established within the graceful
         restart period, and in this case the value of this field
         is lost.";
    }

    leaf selected-local-addr {
      type interfaces:iface-ip-address-allow-zero-t;
      config false;
      description
        "The local address used by the transport connection for the
         peering session.

         If a connection exists and a local-address is configured
         then these two fields will be identical.";
    }

    leaf selected-local-port {
      type uint32 {
        range "0..65535";
      }
      config false;
      description
        "The local port used by the transport connection for the
         peering session.

         If a connection exists and a local-port is configured then
         these two fields will be identical.

         A value of zero implies that there is currently no
         connection to this peer.";
    }

    leaf selected-remote-port {
      type uint32 {
        range "0..65535";
      }
      config false;
      description
        "The remote port used by the transport connection for the
         peering session.

         If a connection exists and a remote-port is configured
         then these two fields will be identical.

         A value of zero implies that there is currently no
         connection to this peer.";
    }

    leaf bfd-status {
      type meta:bfd-sess-states;
      config false;
      description
        "BFD session state for this peer.";
    }

    leaf selected-local-as {
      type uint32;
      config false;
      description
        "The local AS number used on this session or zero if the session
         is not established";
    }

    leaf selected-remote-as {
      type uint32;
      config false;
      description
        "The remote AS number used on this session or zero if the
         session is not established.";
    }

    leaf in-prefixes {
      type uint32;
      config false;
      description
        "The total number of prefixes received from this peer.

         When additional paths are enabled, routes with different
         path ID values count as different prefixes.";
    }

    leaf out-prefixes {
      type uint32;
      config false;
      description
        "The number of prefixes that are installed in all of this
         peer's Adj-RIBs-Out.

         When additional paths are enabled, routes with different
         path ID values count as different prefixes.";
    }

    leaf out-prefixes-advertised {
      type uint32;
      config false;
      description
        "The total number of prefixes advertised to this peer.

         When additional paths are enabled, routes with different
         path ID values count as different prefixes.

         Note that the value of this field may differ from out-prefixes
         since that field includes recently withdrawn routes which
         are undergoing suppression procedures.";
    }

    leaf in-prefixes-denied-by-pol {
      type uint32;
      config false;
      description
        "The number of times a received prefix has been denied, and
         therefore not installed in the Adj-RIB-In, because of
         local filter policy.

         When additional paths are enabled, routes with different
         path ID values count as different prefixes.";
    }

    leaf out-prefixes-denied {
      type uint32;
      config false;
      description
        "This is the number of prefixes in the Loc-RIB that have
         have failed export policy checks and so have not been
         installed in the Adj-RIB-Out.

         When additional paths are enabled, routes with different
         path ID values count as different prefixes.";
    }

    leaf config-state {
      type bgp-peer-config-states;
      config false;
      description
        "This field reports the state of the peer configuration.
         The peer configuration may be in one of the following
         states.

         -  Up to date.  That is, all configuration for
         this peer has been applied to the current peer session
         (if it exists).

         -  Out of date, requiring the peer's admin status to be
         set to down before all the current configuration
         for this peer can be applied.

         -  Out of date, requiring the peer's row status to be set
         to inactive before all the current configuration
         for this peer can be applied.

         A peer's configuration can become out of date for several
         reasons, including the following.

         -  Configuration has changed and the new value cannot be applied
         while the peer session is active.";
    }

    leaf confederation-member {
      type boolean;
      config false;
      description
        "The currently active value which indicates whether or not
         the peer is a member of the same confederation that this
         router is in.

         This value may be different from the current configured
         value for the peer if the value has been changed since the peer
         session was started.";
    }

    leaf reflector-client {
      type bgp-peer-reflector-client;
      config false;
      description
        "The currently active value which indicates whether the
         given peer is a reflector client of this router, or not.

         This value may be different from the current configured
         value for the peer if the value has been changed since the peer
         session was started.";
    }

    leaf trap-established {
      type boolean;
      config false;
      description
        "The currently active value which indicates whether or not
         the Established notification is used.

         This value may be different from the current configured
         value for the peer if the value has been changed since the peer
         session was started.";
    }

    leaf trap-backward {
      type boolean;
      config false;
      description
        "The currently active value which indicates whether or not
         the Backward Transition notification is used.

         This value may be different from the current configured
         value for the peer if the value has been changed since the peer
         session was started.";
    }

    leaf connect-retry-interval {
      type uint32;
      units "seconds";
      config false;
      description
        "The currently active time interval for the Connect Retry
         timer.

         This value may be different from the current configured
         value for the peer if the value has been changed since the peer
         session was started.";
    }

    leaf passive {
      type boolean;
      config false;
      description
        "The current in use value of the passive flag.  If true, then no
         outbound connections will be initiated and only incoming
         connections will be accepted.  If false, then outbound
         connections will be attempted to this peer and incoming
         connections will be accepted from this peer.

         This value may be different from the current configured
         value for the peer if the value has been changed since the peer
         session was started.

         For dynamic peers this field is always true.";
    }

    leaf open-delay {
      type uint32;
      units "seconds";
      config false;
      description
        "The currently active delay to enforce in between a TCP
         connection with this peer becoming established and a BGP
         Open message being sent.

         This value may be different from the current configured
         value for the peer if the value has been changed since the peer
         session was started.";
    }

    leaf idle-hold-time {
      type uint32;
      units "seconds";
      config false;
      description
        "The currently active time to hold this peer in Idle state
         after a BGP session has progressed beyond Idle state
         initially and then returned to it.

         This value may be different from the current configured
         value for the peer if the value has been changed since the peer
         session was started.";
    }

    leaf time-to-live {
      type int32;
      config false;
      description
        "The currently active Time To Live used by the connection
         on this peer.

         This value may be different from the current configured
         value for the peer if the value has been changed since the peer
         session was started.";
    }

    leaf conf-alt-local-as {
      type uint32;
      config false;
      description
        "The currently active alternative local AS number that can
         be used to establish a session with this peer.  This is
         used when merging two ASs into a single AS.

         This value may be different from the current configured
         value for the peer if the value has been changed since the peer
         session was started.";
    }

    leaf conf-alt-local-as-mode {
      type bgp-alt-loc-as-mode;
      config false;
      description
        "The currently active AS number mode.

         This value may be different from the current configured
         value for the peer if the value has been changed since the peer
         session was started.";
    }

    leaf disable-route-refresh {
      type boolean;
      config false;
      description
        "The currently active disable route refresh flag.  This
         indicates whether BGP should advertise support for
         Route Refresh messages to this peer.

         This value may be different from the current configured
         value for the peer if the value has been changed since the peer
         session was started.";
    }

    leaf bfd-desired {
      type boolean;
      config false;
      description
        "The currently active flag which indicates whether
         Bidirectional Forwarding Detection (BFD) is desired for
         this peer.

         This value may be different from the current configured
         value for the peer if the value has been changed since the peer
         session was started.";
    }

    leaf configured-hold-time {
      type uint32 {
        range "0..65535";
      }
      units "seconds";
      config false;
      description
        "The currently active time interval in seconds for the Hold
         Time configured for this BGP speaker with this peer.

         This value may be different from the current configured
         value for the peer if the value has been changed since the peer
         session was started.

         The time interval in seconds for the Hold Timer actually
         established with the peer is given by hold-time.";
    }

    leaf configured-keepalive-time {
      type uint32 {
        range "0..65535";
      }
      units "seconds";
      config false;
      description
        "The currently active time interval in seconds for the
         KeepAlive configured for this BGP speaker with this peer.

         This value may be different from the current configured
         value for the peer if the value has been changed since the peer
         session was started.

         The time interval in seconds for the Keep Alive actually
         established with the peer is given by keepalive-time.";
    }

    container address-family {
      config false;
      description
        "State for address-family";
      container ipv4 {
        config false;
        description
          "State for IPv4";
        container unicast {
          config false;
          description
            "State for unicast";
          uses router-bgp-neighbor-af-common-state;
        }
      }

      container ipv6 {
        config false;
        description
          "State for IPv6";
        container unicast {
          config false;
          description
            "State for unicast";
          uses router-bgp-neighbor-af-common-state;
        }
      }
    }
  }

  grouping neighbor-state-actions {
    action clear-peer {
      user-ext:CLI-param-help "Clear peer session";
      description
        "Clear peer session.";
    }

    action send-route-refresh {
      user-ext:CLI-param-help "Send Route-Refresh message to peer";
      description
        "Send Route-Refresh message to peer.";
    }
  }

  grouping neighbor-group-config {
    leaf advertisement-interval {
      user-ext:CLI-comm-help "Set min interval between sending updates in seconds";
      user-ext:CLI-no-comm-help "Set default min interval between sending updates";
      user-ext:CLI-param-help "Set interval in seconds";
      type router-bgp-adv-interval;
      units "seconds";
      description
        "Minimal interval between sending BGP updates";
    }

    leaf withdraw-interval {
      user-ext:CLI-comm-help "Set min interval from route advert to withdraw (secs)";
      user-ext:CLI-no-comm-help "Set default min interval from route advert to withdraw";
      user-ext:CLI-param-help "Set interval in seconds";
      type router-bgp-wd-interval;
      units "seconds";
      description
        "Minimal interval between advertisement and subsequent withdrawal of a route";
    }

    leaf soft-reset-with-stored-info {
      user-ext:CLI-comm-help "Enable BGP soft reset";
      user-ext:CLI-no-comm-help "Disable BGP soft reset";
      user-ext:CLI-param-help "Enable BGP soft reset";
      type empty;
      description
        "Configure soft reset with stored routing information.
         This option causes all routes learned from a peer to be
         stored so that the Adj-Rib-In can be recalculated without
         performing a route refresh or restarting the peer session.
         When not configured, BGP does not perform soft reset
         for any address family.";
    }

    container ebgp-multihop {
      user-ext:CLI-comm-help "Enable EBGP multihop for this neighbor";
      user-ext:CLI-no-comm-help "Disable EBGP multihop for this neighbor";
      presence "Enable EBGP-multihop on this neighbor";
      description
        "Enable EBGP-multihop on this neighbor";
      leaf ttl {
        user-ext:CLI-comm-help "Set neighbor's TTL for session";
        user-ext:CLI-no-comm-help "Remove neighbor's TTL for session";
        user-ext:CLI-param-help "Set TTL";
        type router-bgp-ttl;
      }
    }

    container enforce-first-as {
      user-ext:CLI-comm-help "Configure first AS number in AS PATH for EBGP nbrs";
      user-ext:CLI-no-comm-help "Configure first AS number in AS PATH for EBGP nbrs";
      description
        "Configure first AS in path and neighbor AS equal proof";
      leaf disable {
        user-ext:CLI-comm-help "Disable first AS number in AS PATH for EBGP neighbors";
        user-ext:CLI-no-comm-help "Enable first AS number in AS PATH for EBGP neighbors";
        type empty;
        description
          "Disable first AS in path and neighbor AS equal proof";
      }
    }

    leaf local-as {
      user-ext:CLI-comm-help "Set alternative AS number for peer session";
      user-ext:CLI-no-comm-help "Remove alternative AS number for peer session";
      user-ext:CLI-param-help "Set alternative AS number for peer session";
      type router-bgp-as;
      description
        "Local AS number for this session";
    }

    leaf password {
      user-ext:CLI-comm-help "Set password for BGP session";
      user-ext:CLI-no-comm-help "Remove password for BGP session";
      user-ext:CLI-param-help "Set password";
      type router-bgp-password-string;
      description
        "Password for BGP session";
    }

    leaf remote-as {
      user-ext:CLI-comm-help "Set remote AS number for this session";
      user-ext:CLI-no-comm-help "Remove remote AS number for this session";
      user-ext:CLI-param-help "Set AS number";
      type router-bgp-as;
      description
        "Remote AS number for this session";
    }

    container timers {
      user-ext:CLI-comm-help "Configure BGP session timers";
      user-ext:CLI-no-comm-help "Configure BGP session timers";
      description
        "BGP session timers";
      leaf keepalive {
        user-ext:CLI-comm-help "Set BGP session keepalive timer";
        user-ext:CLI-no-comm-help "Set default BGP session keepalive timer";
        user-ext:CLI-param-help "Set keepalive time";
        type router-bgp-ses-timer-keepalive;
      }

      leaf holdtime {
        user-ext:CLI-comm-help "Set BGP session holdtime timer";
        user-ext:CLI-no-comm-help "Set default BGP session holdtime timer";
        user-ext:CLI-param-help "Set hold time";
        type router-bgp-ses-timer-holdtime;
      }

      leaf connect-retry {
        user-ext:CLI-comm-help "Set BGP connect retry timer";
        user-ext:CLI-no-comm-help "Set default BGP connect retry timer";
        user-ext:CLI-param-help "Set connect retry time";
        type router-bgp-ses-timer-connect-retry;
      }
    }

    leaf send-community {
      user-ext:CLI-comm-help "Enable sending BGP community to peer";
      user-ext:CLI-no-comm-help "Disable sending BGP community to peer";
      type empty;
      description
        "Enable/disable sending BGP community attributes to the peer";
    }

    leaf send-community-ext {
      user-ext:CLI-comm-help "Enable sending BGP extended community to peer";
      user-ext:CLI-no-comm-help "Disable sending BGP extended community to peer";
      type empty;
      description
        "Enable/disable sending BGP extended community attributes
         to the peer";
    }

    leaf allow-local-as {
      user-ext:CLI-comm-help "Set local AS id count for sent route AS_PATH attribute";
      user-ext:CLI-no-comm-help "Set default local AS id count for sent route AS_PATH";
      user-ext:CLI-param-help "Set local AS id count for sent route AS_PATH attribute";
      type router-bgp-allow-local-as;
      description
        "The number of instances of the local AS identifier";
    }

    leaf confederation-member {
      user-ext:CLI-comm-help "Configure peer to be in same confederation as router";
      user-ext:CLI-no-comm-help "Configure to not be in same confederation as router";
      type empty;
      must "(../../../confederation-identifier) and  (../../../confederation-identifier != 0)" {
        error-message
          "BGP confederation-identifier must be configured to enable neighbor confederation-member";
      }
      description
        "Whether the peer is a member of the same confederation that this router is in";
    }

    leaf route-reflector-client {
      user-ext:CLI-comm-help "Set route-reflector characteristics";
      user-ext:CLI-no-comm-help "Set default route-reflector characteristics";
      user-ext:CLI-param-help "Configure route-reflector characteristics";
      type bgp-peer-reflector-client;
      description
        "Whether the given peer is a reflector client of this router";
    }

    container bfd {
      user-ext:CLI-comm-help "Configure BFD parameters for peer";
      user-ext:CLI-no-comm-help "Configure BFD parameters for peer";
      description
        "BFD parameters.";
      leaf fast-detect {
        user-ext:CLI-comm-help "Enable BFD for this peer";
        user-ext:CLI-no-comm-help "Disable BFD for this peer";
        type empty;
        description
          "Indicates whether Bidirectional Forwarding Detection (BFD)
           is desired for this peer.

           This leaf can be changed at any time.  However, if the
           leaf is changed while the peer is up, the
           change will only take effect after the peer has been
           cycled down and then up, thus forcing the
           peer session to be restarted.  In this case, until the
           peer is set down, the peer will be marked as
           out of date (as reported by the config_state field in the
           bgp-peer-config-states leaf for the peer).";
      }
    }

    leaf max-prefixes {
      user-ext:CLI-comm-help "Set maximum number of prefixes from peer";
      user-ext:CLI-no-comm-help "Set maximum number of prefixes from peer to default";
      user-ext:CLI-param-help "Set maximum number of prefixes";
      type router-bgp-max-prefixes;
      description
        "This is used to limit the number
         of prefixes that can be accepted from this peer.

         Setting router-bgp-max-prefixes to a non-zero value sets the
         maximum number of prefixes (totalled across all supported
         address families) that can be accepted from this peer.";
    }

    leaf prefix-threshold {
      user-ext:CLI-comm-help "Set percentage of maximum number of prefixes from peer at which to send prefix-threshold notification";
      user-ext:CLI-no-comm-help "Set percentage of maximum number of prefixes from peer at which to send prefix-threshold notification to default";
      user-ext:CLI-param-help "Set percentage of maximum number of prefixes";
      type router-bgp-prefix-threshold;
      default "75";
      description
        "Set percentage of maximum number of prefixes from peer at
         which to send prefix-threshold notification.";
    }

    leaf max-prefixes-clear {
      user-ext:CLI-comm-help "Set number of prefixes from peer at which to send max-prefix-clear notification";
      user-ext:CLI-no-comm-help "Set number of prefixes from peer at which to send max-prefix-clear notification to default";
      user-ext:CLI-param-help "Set number of prefixes to send prefix-clear notification";
      type router-bgp-max-prefixes;
      description
        "Set number of prefixes from peer at which to send
         max-prefix-clear notification.";
    }

    leaf prefix-threshold-clear {
      user-ext:CLI-comm-help "Set percentage of maximum number of prefixes from peer at which to issue prefix-threshold-clear notification";
      user-ext:CLI-no-comm-help "Set percentage of maximum number of prefixes from peer at which to issue prefix-threshold-clear notification to default";
      user-ext:CLI-param-help "Set percentage of maximum number of prefixes";
      type router-bgp-prefix-threshold;
      description
        "Set percentage of maximum number of prefixes from peer at
         which to issue prefix-threshold-clear notification.";
    }

    leaf session-drop-warning {
      user-ext:CLI-comm-help "Drop or warn session when max prefixes is exceeded";
      user-ext:CLI-no-comm-help "Generate warning when max prefixes is exceeded";
      user-ext:CLI-param-help "Whether the session is dropped or a warning is generated";
      type router-bgp-sess-drop-warning;
      description
        "This is used to determine whether
         the session is dropped or a warning is generated when the
         maximum number of prefixes set is exceeded.";
    }

    leaf max-prefix-hold {
      user-ext:CLI-comm-help "Set maximum prefix hold time interval";
      user-ext:CLI-no-comm-help "Set maximum prefix hold time interval to default";
      user-ext:CLI-param-help "Set interval in seconds";
      type router-bgp-max-prefix-hold;
      units "seconds";
      description
        "The time interval in seconds between when this BGP session
         is torn down due to the number of prefixes received from
         this peer exceeding the maximum in router-bgp-max-prefixes
         and when BGP attempts to reestablish the session.";
    }

    leaf slow-peer {
      user-ext:CLI-comm-help "Mark the peer as slow";
      user-ext:CLI-no-comm-help "Mark the peer as not slow";
      type empty;
      description
        "Marks the peer as a slow peer.

         When update groups are in use, slow peers are kept
         separate from other peers to prevent backpressure from the
         slow peers slowing down updates sent to the other peers.";
    }

    leaf ttl-security-min-ttl {
      user-ext:CLI-comm-help "Set minimum allowed TTL for received packets from peer";
      user-ext:CLI-no-comm-help "Do not specify minimum allowed TTL for received packets from peer";
      user-ext:CLI-param-help "Set minimum allowed TTL for received packets";
      type router-bgp-ttl-sec-min-ttl;
      description
        "The minimum TTL (for IPv4) or Hop Limit (for IPv6) that
         must be set in BGP packets received from this peer.  Packets
         received with a lower TTL are dropped.

         This field is used to enable the Generalized TTL Security
         Mechanism (GTSM), as defined in RFC 5082.

         Changes to this field will not take affect until the peer
         next activates.";
    }

    container remove-private-as {
      user-ext:CLI-comm-help "Remove private AS numbers";
      user-ext:CLI-no-comm-help "Do not remove private AS numbers";
      presence "Whether private AS numbers are removed from the AS path
       before sending an update to this peer.  This is only
       relevant for an EBGP peer.";
      description
        "The list of remove private AS number parameters.";
      leaf all {
        user-ext:CLI-comm-help "Remove private AS numbers from AS-paths with public and private AS numbers";
        user-ext:CLI-no-comm-help "Do not remove private AS numbers from AS-paths with public and private AS numbers";
        type boolean;
        default "false";
      }

      leaf replace-as {
        user-ext:CLI-comm-help "Replace private AS numbers with local AS number";
        user-ext:CLI-no-comm-help "Do not replace private AS numbers with local AS number";
        type boolean;
        default "false";
      }
    }
  }

  grouping neighbor-only-config {
    leaf update-source {
      user-ext:CLI-comm-help "Update source address for peering";
      user-ext:CLI-no-comm-help "Remove source address for peering";
      user-ext:CLI-param-help "Update source address";
      type interfaces:iface-ip-address-t;
      description
        "Source address for peering";
    }

    leaf shutdown {
      user-ext:CLI-comm-help "Administratively shut down this neighbor";
      user-ext:CLI-no-comm-help "Re-enable the session to this neighbor";
      type empty;
      description
        "Administratively shut down this neighbor";
    }

    leaf peer-group-name {
      user-ext:CLI-comm-help "Configure the peer group";
      user-ext:CLI-no-comm-help "Remove the configured peer group";
      user-ext:CLI-param-help "Configure the peer group";
      type bgp-peer-group-name;
      description
        "The name of the peer group this neighbor belongs to.";
    }
  }

  grouping neighbor-address-family-config {
    container address-family {
      user-ext:CLI-comm-help "Configure address-family for BGP neighbor";
      user-ext:CLI-no-comm-help "Configure address-family for BGP neighbor";
      description
        "Configure address-family for BGP neighbor";
      container ipv4 {
        user-ext:CLI-comm-help "Configure IPv4 address-family for BGP neighbor";
        user-ext:CLI-no-comm-help "Configure IPv4 address-family for BGP neighbor";
        description
          "Configure IPv4 address-family for BGP neighbor";
        leaf disable {
          user-ext:CLI-comm-help "Disable IPv4 address-family for BGP neighbor";
          user-ext:CLI-no-comm-help "Enable IPv4 address-family for BGP neighbor";
          type empty;
        }

        container unicast {
          user-ext:CLI-comm-help "Configure unicast IPv4 address-family for BGP neighbor";
          user-ext:CLI-no-comm-help "Configure unicast IPv4 address-family for BGP neighbor";
          description
            "Configure unicast IPv4 address-family for BGP neighbor";
          uses router-bgp-neighbor-af-v4v6-parameters;

          uses router-bgp-neighbor-af-unicast-parameters;
        }
      }

      container ipv6 {
        user-ext:CLI-comm-help "Configure IPv6 address-family for BGP neighbor";
        user-ext:CLI-no-comm-help "Configure IPv6 address-family for BGP neighbor";
        description
          "Configure IPv6 address-family for BGP neighbor";
        leaf disable {
          user-ext:CLI-comm-help "Disable IPv6 address-family for BGP neighbor";
          user-ext:CLI-no-comm-help "Enable IPv6 address-family for BGP neighbor";
          type empty;
        }

        container unicast {
          user-ext:CLI-comm-help "Configure unicast IPv6 address-family for BGP neighbor";
          user-ext:CLI-no-comm-help "Configure unicast IPv6 address-family for BGP neighbor";
          description
            "Configure unicast IPv6 address-family for BGP neighbor";
          uses router-bgp-neighbor-af-v4v6-parameters;

          uses router-bgp-neighbor-af-unicast-parameters;
        }
      }
    }
  }

  grouping neighbor-address-family-vpn-config {
    container l2vpn {
      user-ext:CLI-comm-help "Configure L2VPN address-family for BGP neighbor";
      user-ext:CLI-no-comm-help "Configure L2VPN address-family for BGP neighbor";
      description
        "Configure L2VPN address-family for BGP neighbor";
      container vpls {
        user-ext:CLI-comm-help "Configure unicast L2VPN address-family for BGP neighbor";
        user-ext:CLI-no-comm-help "Configure unicast L2VPN address-family for BGP neighbor";
        description
          "Configure unicast L2VPN address-family for BGP neighbor";
        uses router-bgp-neighbor-af-l2vpn-parameters;
      }

      container evpn {
        user-ext:CLI-comm-help "Configure EVPN address-family for BGP neighbor";
        user-ext:CLI-no-comm-help "Configure EVPN address-family for BGP neighbor";
        description
          "Configure EVPN address-family for BGP neighbor";
        uses router-bgp-neighbor-af-l2vpn-parameters;
      }
    }

    container vpnv4 {
      user-ext:CLI-comm-help "Configure VPNv4 address-family for BGP neighbor";
      user-ext:CLI-no-comm-help "Configure VPNv4 address-family for BGP neighbor";
      description
        "Configure VPNv4 address-family for BGP neighbor";
      leaf enable {
        user-ext:CLI-comm-help "Enable VPNv4 address-family for BGP neighbor";
        user-ext:CLI-no-comm-help "Disable VPNv4 address-family for BGP neighbor";
        type empty;
      }

      container unicast {
        user-ext:CLI-comm-help "Configure unicast VPNv4 address-family for BGP neighbor";
        user-ext:CLI-no-comm-help "Configure unicast VPNv4 address-family for BGP neighbor";
        description
          "Configure unicast VPNv4 address-family for BGP neighbor";
        uses router-bgp-neighbor-af-v4v6-parameters;
      }
    }

    container vpnv6 {
      user-ext:CLI-comm-help "Configure VPNv6 address-family for BGP neighbor";
      user-ext:CLI-no-comm-help "Configure VPNv6 address-family for BGP neighbor";
      description
        "Configure VPNv6 address-family for BGP neighbor";
      leaf enable {
        user-ext:CLI-comm-help "Enable VPNv6 address-family for BGP neighbor";
        user-ext:CLI-no-comm-help "Disable VPNv6 address-family for BGP neighbor";
        type empty;
      }

      container unicast {
        user-ext:CLI-comm-help "Configure unicast VPNv6 address-family for BGP neighbor";
        user-ext:CLI-no-comm-help "Configure unicast VPNv6 address-family for BGP neighbor";
        description
          "Configure unicast VPNv6 address-family for BGP neighbor";
        uses router-bgp-neighbor-af-v4v6-parameters;
      }
    }
  }

  grouping peer-group-only-config {
    leaf reset-peer-on-cfg-change {
      user-ext:CLI-comm-help "Peer-group config changes reset peer sessions when required";
      user-ext:CLI-no-comm-help "Peer-group config changes do not automatically reset peer sessions";
      type empty;
      description
        "Changes to peer-group configuration that require a peer session
         to be reset to take effect will cause affected peer sessions to be
         reset.";
    }
  }

  grouping neighbor-config {
    uses neighbor-group-config;

    uses neighbor-only-config;

    uses neighbor-address-family-config;
  }

  grouping peer-group-config {
    uses neighbor-group-config;

    uses peer-group-only-config;
  }

  grouping nlri-state {
    description
      "BGP NLRI state.";
    leaf peer-or-afm {
      type bgp-peer-or-afm;
      config false;
      description
        "Whether this route was learned from a BGP peer or an AFM.";
    }

    leaf peer-afm-index {
      type uint32;
      config false;
      description
        "The index of either the BGP peer or AFM this route was
         learned from.";
    }

    leaf afi {
      type bgp-afi;
      config false;
      description
        "The address family of the prefix for this NLRI.";
    }

    leaf safi {
      type bgp-safi;
      config false;
      description
        "The subsequent address family of the prefix for this NLRI.";
    }

    leaf prefix {
      type interfaces:iface-ip-prefix-t;
      config false;
      description
        "An address prefix in the Network Layer Reachability
         Information field.

         This field contains the full line format BGP NLRI omitting
         any NLRI length field.

         For SAFI 128 the NLRI includes the MPLS label and Route
         Distinguisher as well as the IPv4 or IPv6 address prefix.";
    }

    uses nlri-common-state;
  }

  grouping nlri-l2vpn-vpls-state {
    description
      "BGP NLRI state for L2VPN VPLS afi/safi.";
    leaf peer-or-afm {
      type bgp-peer-or-afm;
      config false;
      description
        "Whether this route was learned from a BGP peer or an AFM.";
    }

    leaf peer-afm-index {
      type uint32;
      config false;
      description
        "The index of either the BGP peer or AFM this route was
         learned from.";
    }

    leaf afi {
      type bgp-afi;
      config false;
      description
        "The address family of the prefix for this NLRI.";
    }

    leaf safi {
      type bgp-safi;
      config false;
      description
        "The subsequent address family of the prefix for this NLRI.";
    }

    leaf rd {
      type meta:bgp-route-distinguisher;
      config false;
      description
        "The local VPLS route distinguisher";
    }

    leaf ve-id {
      type l2vpn-ve-id-t;
      config false;
      description
        "The local VPLS VE ID";
    }

    leaf ve-blk {
      type uint32;
      config false;
      description
        "The local VPLS VE block offset";
    }

    leaf ve-blk-size {
      type uint32;
      config false;
      description
        "The local VPLS VE block size";
    }

    leaf label-base {
      type uint32;
      config false;
      description
        "The local VPLS label base";
    }

    uses nlri-common-state;
  }

  grouping nlri-l2vpn-evpn-state {
    description
      "BGP NLRI state for L2VPN EVPN afi/safi.";
    leaf peer-or-afm {
      type bgp-peer-or-afm;
      config false;
      description
        "Whether this route was learned from a BGP peer or an AFM.";
    }

    leaf peer-afm-index {
      type uint32;
      config false;
      description
        "The index of either the BGP peer or AFM this route was
         learned from.";
    }

    leaf afi {
      type bgp-afi;
      config false;
      description
        "The address family of the prefix for this NLRI.";
    }

    leaf safi {
      type bgp-safi;
      config false;
      description
        "The subsequent address family of the prefix for this NLRI.";
    }

    uses l2vpn-evpn-common-state;

    uses nlri-common-state;
  }

  grouping nlri-l3vpn-state {
    description
      "BGP NLRI state for l3vpn address family.";
    leaf peer-or-afm {
      type bgp-peer-or-afm;
      config false;
      description
        "Whether this route was learned from a BGP peer or an AFM.";
    }

    leaf peer-afm-index {
      type uint32;
      config false;
      description
        "The index of either the BGP peer or AFM this route was
         learned from.";
    }

    leaf afi {
      type bgp-afi;
      config false;
      description
        "The address family of the prefix for this NLRI.";
    }

    leaf safi {
      type bgp-safi;
      config false;
      description
        "The subsequent address family of the prefix for this NLRI.";
    }

    leaf label {
      type uint32;
      config false;
      description
        "The local l3vpn label";
    }

    leaf rd {
      type meta:bgp-route-distinguisher;
      config false;
      description
        "The local l3vpn route distinguisher";
    }

    leaf ip-prefix {
      type interfaces:iface-ip-prefix-t;
      config false;
      description
        "The local l3vpn ip prefix address";
    }

    uses nlri-common-state;
  }

  grouping adj-rib-out-common-indices {
    description
      "BGP Adj-RIB-Out common indices.";
    leaf peer-index {
      type uint32;
      description
        "The peer index.";
    }

    leaf afi {
      type bgp-afi;
      description
        "The address family of the prefix for this Adj-RIB Out
         route.";
    }

    leaf safi {
      type bgp-safi;
      description
        "The subsequent address family of the prefix for
         this Adj-RIB Out route.";
    }

    leaf path-id {
      type uint32;
      description
        "The path ID for this Adj-RIB Out route.

         If BGP additional path send capability was negotiated with
         the peer for this AFI/SAFI then this is the path ID sent for
         this Adj-RIB Out route, otherwise it is zero.";
    }
  }

  grouping community-lists {
    list community {
      config false;
      description
        "BGP communities advertised on a route";
      leaf community {
        type binary;
        config false;
        description
          "BGP community in line format (4 bytes).";
      }
    }

    list extended-community {
      config false;
      description
        "BGP extended communities advertised on a route";
      leaf extended-community {
        type binary;
        config false;
        description
          "BGP extended community in line format (8 bytes).";
      }
    }
  }

  grouping adj-rib-out-common-state {
    description
      "BGP Adj-RIB-Out common state.";
    leaf advertisement-status {
      type bgp-aro-advert-status-t;
      config false;
      description
        "This object indicates the current state of
         advertisement of the route to the peer.

         A value of advertised indicates that the route has
         been advertised to the peer.

         A value of suppressed indicates that the route is
         not currently advertised to the peer, but will be
         advertised when a minimum advertisement interval timer
         expires.

         A value of pendingWithdrawal indicates that the
         route is currently advertised to the peer, but will be
         withdrawn when the timer expires.

         A value of withdrawn indicates that the route has
         been withdrawn from the peer, and this entry will be
         removed from the Adj-RIB-Out on the expiry of the
         timer.";
    }

    leaf local-aggregation-type {
      type bgp-aro-aggr-status-t;
      config false;
      description
        "This object indicates any aggregation processing that
         has been applied to this Adj-RIB-Out route.

         A value of no-aggregation indicates that this route
         does not aggregate any other routes, and is not
         aggregated by any route.

         A value of aggregate-route indicates that this route
         is a locally configured aggregating route.

         A value of unsuppressed-aggregated-route indicates that this
         route has been aggregated by a locally configured
         aggregate route and is not suppressed - the route is
         still explicitly advertised to the peer.

         A value of suppressed-aggregated-route indicates that
         this route has been aggregated by a locally configured
         aggregate route and is flagged such that it should not be
         advertised along with the aggregate route.  Typically such
         routes are not installed on an Adj-RIB-Out.  If however
         the aggregate route itself is not permitted to be added to
         the Adj-RIB-Out then suppressed routes are advertised if
         they themselves are permitted by policy.";
    }

    leaf as-size {
      type bgp-as-size-t;
      config false;
      description
        "Whether the as-path-string object contains
         two or four byte AS numbers.";
    }

    leaf as-path-string {
      type string;
      config false;
      description
        "This is a string containing the autonomous system path
         sent to this peer in the AS_PATH attribute for this
         Adj-RIB-Out route.  If this path contains four-octet AS
         numbers and the peer does not support these a two-octet
         AS_PATH attribute and associated AS4_PATH attribute will be
         advertised to the peer instead as detailed in RFC 4893.
         However, this field will report the four-octet AS_PATH that
         would  have been advertised to the peer if it had supported
         four-byte AS numbers.  Two-octet AS numbers appear as
         four-octet numbers by adding two bytes of zero padding.  The
         format of the string is simply the AS_PATH attribute.  This
         can be converted to a more readable format by the management
         agent.";
    }

    leaf origin {
      type bgp-origin-codes;
      config false;
      description
        "The ultimate origin of the path information.";
    }

    leaf next-hop {
      type interfaces:iface-ip-address-t;
      config false;
      description
        "The next hop address transmitted in the UPDATE packet.

         Note that for RFC 2545 style double nexthops, this object
         will always contain the global scope nexthop.
         link-local-next-hop will contain the link local
         scope nexthop, if it is present.";
    }

    leaf multi-exit-discrminator {
      type uint32;
      config false;
      description
        "This metric is used to discriminate between multiple
         exit points to an adjacent autonomous system.";
    }

    leaf local-preference {
      type uint32;
      config false;
      description
        "The local preference for this Adj-RIB-Out route, as
         transmitted in the UPDATE message sent to the peer.";
    }

    leaf atomic-aggregate {
      type bgp-path-attr-atomic-agg;
      config false;
      description
        "When this object is set to present, the
         ATOMIC_AGGREGATE Path Attribute was included in the
         UPDATE sent to the peer for this Adj-RIB-Out route.";
    }

    leaf aggregator-as {
      type uint32;
      config false;
      description
        "The AS number of the last BGP speaker that performed
         route aggregation.";
    }

    leaf aggregator-address {
      type interfaces:iface-ipv4-address-allow-zero-t;
      config false;
      description
        "The IP address of the last BGP speaker that performed
         route aggregation.  A value of 0.0.0.0 indicates that
         this attribute was not included in the UPDATE message
         sent to the peer.";
    }

    leaf originator-id {
      type meta:router-id;
      config false;
      description
        "The Originator-ID identifying the router that initially
         advertised this destination to a Route Reflector.  A
         value of 0.0.0.0 indicates the absence of this
         attribute.";
    }

    leaf as-path-limit-as {
      type uint32;
      config false;
      description
        "If non-zero this is the number of the AS that attached the
         AS_PATHLIMIT attribute.";
    }

    leaf as-path-limit-upper {
      type uint32;
      config false;
      description
        "The upper bound on the number of ASes in the AS_PATH
         attribute after which the route will be filtered.  Only
         valid if as-path-limit-as is non-zero.";
    }

    leaf user-data {
      type bgp-user-data-t;
      config false;
      description
        "User data for this BGP ARO entry.";
    }

    leaf ecmp {
      type boolean;
      config false;
      description
        "Whether or not this route was installed into the
         Forwarding Table as an ECMP route.";
    }

    leaf stale {
      type boolean;
      config false;
      description
        "Whether or not this route was last sent by the peer before
         BGP detected that the peer was restarting.  If the route is
         not re-advertised by the peer before the restart completes,
         BGP will remove the route from its database.  This flag is
         set to 'false' if the peer is not restarting, or if the
         route has been advertised by the peer since the restart.";
    }

    leaf link-local-next-hop {
      type interfaces:iface-ip-address-t;
      config false;
      description
        "The IPv6 link-local address sent in the UPDATE message.
         This object is only valid if an RFC 2545 style double
         nexthop was sent in the UPDATE.";
    }

    leaf multi-exit-discriminator-set {
      type boolean;
      config false;
      description
        "If true, then the route has an associated MED attribute,
         whose value is given in multi-exit-discriminator.  If false,
         the route has no MED attribute.";
    }

    leaf peer-address {
      type interfaces:iface-ip-address-t;
      config false;
      description
        "The address of the BGP peer.";
    }

    leaf peer-scope-id {
      type uint32;
      config false;
      description
        "The scope ID of the BGP peer address.

         The scope ID is required if the address is an IPv6
         link-local address.  Otherwise, this field will be zero.";
    }

    leaf peer-interface {
      type interfaces:iface-name;
      config false;
      description
        "The local interface used to reach the BGP peer.";
    }

    uses community-lists;
  }

  grouping adj-rib-out-ip-state {
    description
      "BGP Adj-RIB-Out state for IP address family.";
    uses adj-rib-out-common-indices;

    leaf prefix {
      type interfaces:iface-ip-prefix-t;
      config false;
      description
        "An address prefix in the Network Layer Reachability
         Information field for this Adj-RIB Out route.

         This field contains the full line format BGP NLRI omitting
         any NLRI length field.

         For SAFI 128 the NLRI includes the MPLS label and Route
         Distinguisher as well as the IPv4 or IPv6 address prefix.";
    }

    uses adj-rib-out-common-state;
  }

  grouping adj-rib-out-l2vpn-vpls-state {
    description
      "BGP Adj-RIB-Out state for L2VPN VPLS afi/safi.";
    uses adj-rib-out-common-indices;

    leaf rd {
      type meta:bgp-route-distinguisher;
      config false;
      description
        "The local VPLS route distinguisher";
    }

    leaf ve-id {
      type l2vpn-ve-id-t;
      config false;
      description
        "The local VPLS VE ID";
    }

    leaf ve-blk {
      type uint32;
      config false;
      description
        "The local VPLS VE block offset";
    }

    leaf ve-blk-size {
      type uint32;
      config false;
      description
        "The local VPLS VE block size";
    }

    leaf label-base {
      type uint32;
      config false;
      description
        "The local VPLS label base";
    }

    uses adj-rib-out-common-state;
  }

  grouping adj-rib-out-l2vpn-evpn-state {
    description
      "BGP Adj-RIB-Out state for L2VPN EVPN afi/safi.";
    uses adj-rib-out-common-indices;

    uses l2vpn-evpn-common-state;

    uses adj-rib-out-common-state;
  }

  grouping adj-rib-out-l3vpn-state {
    description
      "BGP Adj-RIB-Out state for L3VPN address family.";
    uses adj-rib-out-common-indices;

    leaf label {
      type uint32;
      config false;
      description
        "The local l3vpn label";
    }

    leaf rd {
      type meta:bgp-route-distinguisher;
      config false;
      description
        "The local l3vpn route distinguisher";
    }

    leaf ip-prefix {
      type interfaces:iface-ip-prefix-t;
      config false;
      description
        "The local l3vpn ip prefix address";
    }

    uses adj-rib-out-common-state;
  }

  grouping router-bgp-advertise {
    container advertise {
      user-ext:CLI-comm-help "Configure BGP routing advertise";
      user-ext:CLI-no-comm-help "Configure BGP routing advertise";
      description
        "Configure BGP routing advertise";
      leaf inactive {
        user-ext:CLI-comm-help "Enable BGP advertise inactive";
        user-ext:CLI-no-comm-help "Disable BGP advertise inactive";
        type empty;
        description
          "Enable BGP advertise inactive";
      }
    }
  }

  grouping router-bgp-additional-paths {
    leaf maximum-paths {
      user-ext:CLI-comm-help "Set limit of best paths to calculate ";
      user-ext:CLI-no-comm-help "Set limit of best paths to calculate to the default";
      user-ext:CLI-param-help "Set calculation limit";
      type router-bgp-maximum-paths;
      default "1";
      description
        "Limit of best paths to calculate";
    }

    leaf additional-paths {
      user-ext:CLI-comm-help "Set additional path support";
      user-ext:CLI-no-comm-help "Disable additional path support";
      user-ext:CLI-param-help "Set additional path support";
      type bgp-add-path-caps-router;
      default "disable";
      description
        "The default BGP additional path capability for I-BGP
         sessions.

         This can be overridden at the BGP peer AFI/SAFI or peer
         group AFI/SAFI level.

         BGP additional path capability is never enabled by default
         for E-BGP sessions - instead it should be configured for
         specific E-BGP peers at the peer AFI/SAFI or peer group
         AFI/SAFI level.

         This field applies to all configured I-BGP peers including
         confederation peers in different member ASs.

         Valid values are:
         -  disable
         Disable sending and receiving additional BGP paths
         -  receive
         Receive but do not send additional BGP paths
         -  send
         Send but do not receive additional BGP paths
         -  both
         Send and receive additional BGP paths.

         Any update to this leaf will take effect the next time
         that the peer session reactivates.";
    }

    leaf best-n-paths {
      user-ext:CLI-comm-help "Set limit of best paths to install";
      user-ext:CLI-no-comm-help "Set limit of best paths to install to the default";
      user-ext:CLI-param-help "Set install limit";
      type router-bgp-best-n-paths;
      default "1";
      description
        "Number of paths to install for BGP Prefix Independent
         Convergence.";
    }
  }

  grouping router-bgp-martian-check {
    container martian-check {
      user-ext:CLI-comm-help "Configure martian check";
      user-ext:CLI-no-comm-help "Configure martian check";
      description
        "Martian-check switch";
      leaf disable {
        user-ext:CLI-comm-help "Disable martian check";
        user-ext:CLI-no-comm-help "Enable martian check";
        type empty;
      }
    }
  }

  grouping router-bgp-max-ecmp-paths {
    leaf max-ibgp-ecmp-paths {
      user-ext:CLI-comm-help "Configure max number of ECMP paths for IBGP routes";
      user-ext:CLI-no-comm-help "Configure max number of ECMP paths for IBGP routes";
      user-ext:CLI-param-help "Configure max number of ECMP paths for IBGP routes";
      type router-bgp-max-ecmp-paths;
      default "32";
      description
        "Maximum number of ECMP next hops for IBGP routes";
    }

    leaf max-ebgp-ecmp-paths {
      user-ext:CLI-comm-help "Configure max number of ECMP paths for EBGP routes";
      user-ext:CLI-no-comm-help "Configure max number of ECMP paths for EBGP routes";
      user-ext:CLI-param-help "Configure max number of ECMP paths for EBGP routes";
      type router-bgp-max-ecmp-paths;
      default "32";
      description
        "Maximum number of ECMP next hops for EBGP routes";
    }
  }

  grouping router-bgp-max-afi-safi-ecmp-paths {
    leaf max-ibgp-ecmp-paths {
      user-ext:CLI-comm-help "Configure max number of ECMP paths for IBGP routes";
      user-ext:CLI-no-comm-help "Configure max number of ECMP paths for IBGP routes";
      user-ext:CLI-param-help "Configure max number of ECMP paths for IBGP routes";
      type router-bgp-max-afi-safi-ecmp-paths;
      default "0";
      description
        "Maximum number of ECMP next hops for IBGP routes";
    }

    leaf max-ebgp-ecmp-paths {
      user-ext:CLI-comm-help "Configure max number of ECMP paths for EBGP routes";
      user-ext:CLI-no-comm-help "Configure max number of ECMP paths for EBGP routes";
      user-ext:CLI-param-help "Configure max number of ECMP paths for EBGP routes";
      type router-bgp-max-afi-safi-ecmp-paths;
      default "0";
      description
        "Maximum number of ECMP next hops for EBGP routes";
    }
  }

  grouping router-bgp-dampening {
    container dampening {
      user-ext:CLI-comm-help "Enable route flap dampening";
      user-ext:CLI-no-comm-help "Disable route flap dampening";
      must "((not(suppress)) and (not(reuse))) or ((not(suppress)) and (2000 >= reuse)) or ((not(reuse)) and (suppress >= 750)) or (number(suppress) >= number(reuse))" {
        error-message
          "BGP dampening suppress value must be at least reuse value";
      }
      presence "Enable route flap dampening";
      description
        "The list of Route Flap Dampening configuration parameters.";
      leaf route-map {
        user-ext:CLI-comm-help "Apply route map to route flap configuration";
        user-ext:CLI-no-comm-help "Remove route flap route map";
        user-ext:CLI-param-help "Apply route map to route flap configuration";
        type meta:route-map-name;
        description
          "The name of the route map to use for route flap
           configuration for this AFI/SAFI.";
      }

      leaf half-life {
        user-ext:CLI-comm-help "Dampening penalty half-life";
        user-ext:CLI-no-comm-help "Dampening penalty half-life";
        user-ext:CLI-param-help "Time in minutes after which a penalty is decreased";
        type bgp-half-life-t;
        units "minutes";
        default "15";
        description
          "The decay half life of the stability figure.";
      }

      leaf reuse {
        user-ext:CLI-comm-help "Penalty before reusing suppressed route";
        user-ext:CLI-no-comm-help "Penalty before reusing suppressed route";
        user-ext:CLI-param-help "Reuse threshold as a number of route withdrawals";
        type bgp-flap-threshold-t;
        default "750";
        description
          "The reuse threshold expressed as a number of route
           withdrawals.  Below this level the route will be reused.
           The scale used is 100 times that used in RFC2439 so the
           suggested value is 50, not 0.5 as suggested in the RFC.";
      }

      leaf suppress {
        user-ext:CLI-comm-help "Dampening penalty to start suppressing a route";
        user-ext:CLI-no-comm-help "Dampening penalty to start suppressing a route";
        user-ext:CLI-param-help "Suppress threshold as a number of route withdrawals";
        type bgp-flap-threshold-t;
        default "2000";
        description
          "The cutoff threshold expressed as a number of route
           withdrawals.  Above this level, the route will be
           suppressed.  This value must be greater than or equal to
           reuse.  The scale used is 100 times that used in
           RFC2439 so the suggested value is 125, not 1.25 as
           suggested in the RFC.";
      }

      leaf max-suppress-time {
        user-ext:CLI-comm-help "Maximum dampening penalty";
        user-ext:CLI-no-comm-help "Maximum dampening penalty";
        user-ext:CLI-param-help "Maximum time in minutes that a route can be suppressed";
        type bgp-max-suppress-time-t;
        units "minutes";
        default "60";
        description
          "The maximum time a route can be suppressed for (held).";
      }
    }
  }

  grouping router-bgp-af-vpn-common-parameters;

  grouping router-bgp-af-l2vpn-common-parameters {
    uses router-bgp-af-vpn-common-parameters;
  }

  grouping router-bgp-af-common-parameters {
    uses router-bgp-af-l2vpn-common-parameters;

    uses router-bgp-additional-paths;

    uses router-bgp-dampening;
  }

  grouping router-bgp-af-aggr-addr-parameters {
    leaf as-set {
      user-ext:CLI-comm-help "Enable AS-SET";
      user-ext:CLI-no-comm-help "Disable AS-SET";
      type empty;
      description
        "AS-SET flag";
    }

    leaf summary-only {
      user-ext:CLI-comm-help "Enable summary only mode (suppress inner path routes)";
      user-ext:CLI-no-comm-help "Disable summary only mode";
      type empty;
      description
        "Enable summary-only mode";
    }

    leaf suppress-map {
      user-ext:CLI-comm-help "Add route map to suppress routes";
      user-ext:CLI-no-comm-help "Do not use route map to suppress routes";
      when "not(../summary-only)";
      type meta:route-map-name;
      description
        "The Route Map used to suppress routes.  The
         match clauses of this route map are used to selectively
         suppress more specific routes from being advertised.";
    }

    leaf advertise-map {
      user-ext:CLI-comm-help "Add route map to advertise routes";
      user-ext:CLI-no-comm-help "Do not use route map to advertise routes";
      type meta:route-map-name;
      description
        "The Route Map used to advertise routes.  The
         match clauses of this route map are used to select routes
         which, although they match the aggregate address, should
         not be aggregated.";
    }

    leaf attribute-map {
      user-ext:CLI-comm-help "Add route map to set route attributes";
      user-ext:CLI-no-comm-help "Do not use route map to set route attributes";
      type meta:route-map-name;
      description
        "The Route Map used to set aggregated routes attributes.
         The set clauses of this route map are used to set path
         attributes of the aggregated route.";
    }
  }

  grouping router-bgp-af-ipv4-parameters {
    list aggregate-address {
      user-ext:CLI-comm-help "Configure aggregate address";
      user-ext:CLI-no-comm-help "Remove aggregate address";
      key "aa-prefix";
      description
        "BGP IPv4 aggregate-address";
      leaf aa-prefix {
        user-ext:CLI-param-help "IPv4 prefix";
        type meta:ipv4-short-prefix;
        description
          "Aggregate address";
      }

      uses router-bgp-af-aggr-addr-parameters;
    }
  }

  grouping router-bgp-af-ipv6-parameters {
    list aggregate-address {
      user-ext:CLI-comm-help "Configure aggregate address";
      user-ext:CLI-no-comm-help "Remove aggregate address";
      key "aa-prefix";
      description
        "BGP IPv6 aggregate-address";
      leaf aa-prefix {
        user-ext:CLI-param-help "IPv6 prefix";
        type meta:ipv6-short-prefix;
        description
          "Aggregate address";
      }

      uses router-bgp-af-aggr-addr-parameters;
    }
  }

  grouping router-bgp-af-unicast-parameters {
    uses router-bgp-martian-check;

    uses router-bgp-max-afi-safi-ecmp-paths;

    uses router-bgp-advertise;
  }

  grouping router-bgp-neighbor-af-common-parameters {
    leaf allowas-in {
      user-ext:CLI-comm-help "Set count of local AS allowed in sent route AS_PATH";
      user-ext:CLI-no-comm-help "Set default count of local AS in sent route AS_PATH";
      user-ext:CLI-param-help "Set count of local AS allowed in sent route AS_PATH attr";
      type router-bgp-allow-local-as;
      description
        "Allow to receive announce from origin AS with next AS count";
    }

    leaf next-hop-self {
      user-ext:CLI-comm-help "Set the nexthop calculation action on this neighbor";
      user-ext:CLI-no-comm-help "Set the nexthop calculation action on this neighbor to default";
      user-ext:CLI-param-help "Set the nexthop calcuation on this neighbor";
      type router-bgp-next-hop-self;
      default "false";
      description
        "Set the nexthop calculation action on this neighbor";
    }

    container soft-reconfiguration {
      user-ext:CLI-comm-help "Enable soft-reconfiguration for this neighbor";
      user-ext:CLI-no-comm-help "Disable soft-reconfiguration for this neighbor";
      description
        "Enable soft-reconfiguration for this neighbor";
      leaf inbound {
        user-ext:CLI-comm-help "Enable inbound soft-reconfiguration for this neighbor";
        user-ext:CLI-no-comm-help "Disable inbound soft-reconfiguration for this neighbor";
        type empty;
        description
          "Enable inbound soft-reconfiguration for this neighbor";
      }
    }

    container route-map {
      user-ext:CLI-comm-help "Configure route maps";
      user-ext:CLI-no-comm-help "Configure route maps";
      description
        "Configure the route maps.";
      leaf in {
        user-ext:CLI-comm-help "Apply route map to inbound routes from peer";
        user-ext:CLI-no-comm-help "Remove inbound routes route map";
        user-ext:CLI-param-help "Apply route map to inbound routes from peer";
        type meta:route-map-name;
        description
          "The name of the route map to use for route imports from
           the peer for this AFI/SAFI.";
      }

      leaf out {
        user-ext:CLI-comm-help "Apply route map to outbound routes to peer";
        user-ext:CLI-no-comm-help "Remove outbound routes route map";
        user-ext:CLI-param-help "Apply route map to outbound routes to peer";
        type meta:route-map-name;
        description
          "The name of the route map to use for route exports to the
           peer for this AFI/SAFI.";
      }
    }

    leaf preserve-next-hop {
      user-ext:CLI-comm-help "Enable preserving next hop when sending routes to eBGP peers";
      user-ext:CLI-no-comm-help "Disable preserving next hop when sending routes to eBGP peers";
      type empty;
      description
        "This field is used to preserve the BGP next hop when
         forwarding routes to this eBGP peer.

         By default, the next hop of a route is preserved when
         advertising the route to an iBGP peer, but is updated when
         advertising the route to an eBGP peer.  Enabling this feature
         over-rides this behavior and preserves the next hop when routes
         are advertised to this eBGP peer.";
    }

    leaf accept-remote-next-hop {
      user-ext:CLI-comm-help "Allow routes from directly-connected eBGP peer to use a next-hop not in a shared subnet.";
      user-ext:CLI-no-comm-help "Do not Allow routes from directly-connected eBGP peer to use a next-hop not in a shared subnet.";
      type empty;
      description
        "Allow routes from directly-connected eBGP peer to use a next-hop not in a shared subnet.";
    }

    leaf advertise-peer-as {
      user-ext:CLI-comm-help "Disable sender-side loop detection for this session";
      user-ext:CLI-no-comm-help "Enable sender-side loop detection for this session";
      type empty;
      description
        "Disable sender-side detection of AS path loops when advertising routes to this peer";
    }
  }

  grouping router-bgp-neighbor-af-v4v6-parameters {
    uses router-bgp-neighbor-af-common-parameters;

    container capability {
      user-ext:CLI-comm-help "Configure advertised capabilities";
      user-ext:CLI-no-comm-help "Configure advertised capabilities";
      description
        "Configure capability announcement";
      container orf {
        user-ext:CLI-comm-help "Configure ORF capability announcement";
        user-ext:CLI-no-comm-help "Configure ORF capability announcement";
        description
          "Configure ORF capability announcement";
        leaf prefix {
          user-ext:CLI-comm-help "Set ORF capability prefix";
          user-ext:CLI-no-comm-help "Set ORF capability prefix to default";
          user-ext:CLI-param-help "Set ORF capability prefix";
          type router-bgp-orf-prefix;
          default "none";
          description
            "ORF capability";
        }
      }
    }
  }

  grouping router-bgp-neighbor-af-l2vpn-parameters {
    leaf enable {
      user-ext:CLI-comm-help "Enable address-family for BGP neighbor";
      user-ext:CLI-no-comm-help "Disable address-family for BGP neighbor";
      type empty;
    }

    uses router-bgp-neighbor-af-common-parameters;
  }

  grouping router-bgp-neighbor-af-unicast-parameters {
    container prefix-list {
      user-ext:CLI-comm-help "Configure prefix lists";
      user-ext:CLI-no-comm-help "Configure prefix lists";
      description
        "Configure the IP prefix lists.";
      leaf in {
        user-ext:CLI-comm-help "Apply prefix list to inbound routes from peer";
        user-ext:CLI-no-comm-help "Remove inbound routes prefix list";
        user-ext:CLI-param-help "Apply prefix list to inbound routes from peer";
        type meta:ip-prefix-name;
        description
          "The name of the IP prefix access list to use for
           route imports from the peer for this AFI/SAFI.

           Route import policy applies any import IP prefix access
           list before any import route map, and the route must be
           permitted by both to be imported.  The import route map
           can apply its own prefix lists in addition to any import
           IP prefix access list.

           If the peer is a member of a peer group then BGP uses
           peer import policy in preference to peer group policy.";
      }

      leaf out {
        user-ext:CLI-comm-help "Apply prefix list to outbound routes to peer";
        user-ext:CLI-no-comm-help "Remove outbound routes prefix list";
        user-ext:CLI-param-help "Apply prefix list to outbound routes to peer";
        type meta:ip-prefix-name;
        description
          "The name of the IP prefix access list to use for
           route exports from the peer for this AFI/SAFI.

           Route export policy applies any export IP prefix access
           list before any export route map, and the route must be
           permitted by both to be exported.  The export route map
           can apply its own prefix lists in addition to any export
           IP prefix access list.

           If the peer is a member of a peer group then BGP always
           uses peer group export policy in order to take advantage
           of the economies of using peer groups.";
      }
    }

    leaf max-advertised-paths {
      user-ext:CLI-comm-help "Set limit of best paths to advertise to peer ";
      user-ext:CLI-no-comm-help "Set limit of best paths to advertise to peer to the default";
      user-ext:CLI-param-help "Set advertise limit";
      type router-bgp-maximum-paths;
      description
        "The number of best paths to advertise to this peer as
         additional paths for this AFI/SAFI.

         The number of candidate paths available to advertise to
         the peer depends on the value of maximum-paths configured at
         the router level.  This field specifies how
         many of the candidate paths to advertise to this peer.

         For the default value of 1 only the best path for each
         destination is advertised.

         A value of 2 is sufficient to advertise the best path and
         2nd best path for each destination.

         Any additional paths are advertised to peers subject to
         split horizon rules, export policy, and BGP ADD-PATH
         capability negotiation.  These filters apply after
         selecting the best N paths to advertise, so the actual
         number of paths advertised may be smaller.

         Changing the value of this field while the peer is active
         triggers BGP to advertise additional paths according to
         the new configuration.

         If the peer belongs to a peer group, this field is
         overridden by the peer group AFI/SAFI configuration.";
    }

    leaf additional-paths {
      user-ext:CLI-comm-help "Set additional path support";
      user-ext:CLI-no-comm-help "Use global setting for additional path support";
      user-ext:CLI-param-help "Set additional path support";
      type bgp-add-path-capabilities;
      description
        "The configured BGP additional path capability for this
         peer and AFI/SAFI.

         Valid values are:
         -  inherit: Inherit configuration from
         the entity AFI/SAFI level
         -  disable: Disable sending and receiving additional BGP paths
         -  receive: Receive but do not send additional BGP paths
         -  send: Send but do not receive additional BGP paths
         -  both: Send and receive additional BGP paths.

         The effective BGP additional path capabilities for the
         session are negotiated with the peer and are reported by
         the caps-negotiated/add-paths leaf.

         If the peer belongs to a peer group then the peer group
         configuration overrides peer configuration.

         Any update to this will take effect the next time
         that the BGP peer is activated.";
    }

    container default-originate {
      user-ext:CLI-comm-help "Originate a default route to this neighbor";
      user-ext:CLI-no-comm-help "Do not originate a default route to this neighbor";
      presence "Originate a default route to this neighbor";
      description
        "Enable origination of a default route to this neighbor for this AFI/SAFI";
      leaf route-map {
        user-ext:CLI-comm-help "Apply route map to default route origination";
        user-ext:CLI-no-comm-help "Remove route map for default route origination";
        user-ext:CLI-param-help "Apply route map to default route origination";
        type meta:route-map-name;
        description
          "The name of the route map to use for default route
           origination.

           The match clauses in the route map are used for conditional
           advertisement of the default route.  A default route is
           only originated for an address family if there is at
           least one route in the loc-RIB matching the route map.

           The set clauses in the route map determine the
           attributes of the originated default route.";
      }
    }
  }

  grouping router-bgp-peer-group-af-v4v6-parms {
    uses router-bgp-neighbor-af-common-parameters;
  }

  grouping router-bgp-peer-group-af-l2vpn-parms {
    uses router-bgp-neighbor-af-common-parameters;
  }

  grouping router-bgp-peer-group-af-unicast-parms {
    uses router-bgp-neighbor-af-unicast-parameters;
  }

  grouping bgp-peer-state-nbr-group-config {
    leaf shutdown {
      type boolean;
      config false;
      description
        "The desired state of the BGP connection.  This is not configurable
         via the Peer Group for dynamic peers and so is always returned as
         false in that case.";
    }

    leaf peer-group-name {
      type bgp-peer-group-name;
      config false;
      description
        "The name of the peer group this neighbor belongs to, or
         zero if this neighbor does not belong to a peer group.";
    }

    leaf max-prefixes {
      type router-bgp-max-prefixes;
      config false;
      description
        "This object is used to limit the number
         of prefixes that can be accepted from this peer.";
    }

    leaf prefix-threshold {
      type router-bgp-prefix-threshold;
      config false;
      description
        "Percentage of maximum number of prefixes from peer at which to send
         prefix-threshold notification.";
    }

    leaf max-prefixes-clear {
      type router-bgp-max-prefixes;
      config false;
      description
        "Number of prefixes from peer at which to send max-prefix-clear
         notification.";
    }

    leaf prefix-threshold-clear {
      type router-bgp-prefix-threshold;
      config false;
      description
        "Percentage of maximum number of prefixes from peer at which to issue
         prefix-threshold-clear notification.";
    }

    leaf max-prefix-hold {
      type router-bgp-max-prefix-hold;
      units "seconds";
      config false;
      description
        "The time interval in seconds between when this BGP session
         is torn down due to the number of prefixes received from
         this peer exceeding the maximum configured (max-prefixes)
         and when BGP attempts to reestablish the session.";
    }
  }

  grouping bgp-peer-state-config {
    uses bgp-peer-state-nbr-group-config;
  }

  grouping bgp-peer-state-af-common-config {
    leaf allowas-in {
      type router-bgp-allow-local-as;
      config false;
      description
        "Allow to receive announce from origin AS with next AS count";
    }

    leaf next-hop-self {
      type router-bgp-next-hop-self;
      config false;
      description
        "The nexthop calculation action on this neighbor";
    }

    container soft-reconfiguration {
      config false;
      leaf inbound {
        type empty;
        config false;
        description
          "Enable inbound soft-reconfiguration for this neighbor";
      }
    }

    container route-map {
      config false;
      leaf in {
        type meta:route-map-name;
        config false;
        description
          "The name of the route map to use for route imports from
           the peer for this AFI/SAFI.";
      }

      leaf out {
        type meta:route-map-name;
        config false;
        description
          "The name of the route map to use for route exports to the
           peer for this AFI/SAFI.";
      }
    }
  }

  grouping bgp-peer-state-af-v4v6-config {
    uses bgp-peer-state-af-common-config;

    container capability {
      config false;
      container orf {
        config false;
        leaf prefix {
          type router-bgp-orf-prefix;
          config false;
          description
            "Indicates whether the sender is (a) willing to receive ORF
             entries from its peer, (b) would like to send ORF entries
             to its peer, or (c) both.  For a dynamic peer, this will
             always be both.";
        }
      }
    }
  }

  grouping bgp-peer-state-af-l2vpn-config {
    leaf enabled {
      type boolean;
      config false;
      description
        "Enable advertisement of Multiprotocol support to the peer for this
         address family.";
    }

    uses bgp-peer-state-af-common-config;
  }

  grouping bgp-peer-state-af-unicast-config {
    container prefix-list {
      config false;
      leaf in {
        type meta:ip-prefix-name;
        config false;
        description
          "The name of the IP prefix access list to use for
           route imports from the peer for this AFI/SAFI.";
      }

      leaf out {
        type meta:ip-prefix-name;
        config false;
        description
          "The name of the IP prefix access list to use for
           route exports from the peer for this AFI/SAFI.";
      }
    }

    leaf max-advertised-paths {
      type router-bgp-maximum-paths;
      config false;
      description
        "The number of best paths to advertise to this peer as
         additional paths for this AFI/SAFI.";
    }

    leaf additional-paths {
      type bgp-add-path-capabilities;
      config false;
      description
        "The configured BGP additional path capability for this
         peer and AFI/SAFI.";
    }
  }

  grouping neighbor-state-config {
    container config {
      config false;
      description
        "Peer configuration taken from either the Neighbor or Peer
         Group depending on whether this is a dynamic peer.";
      container address-family {
        description
          "BGP Peer address family configuration";
        container ipv4 {
          config false;
          description
            "BGP Peer IPv4 address family configuration";
          leaf enabled {
            type boolean;
            config false;
            description
              "Enable advertisement of Multiprotocol support to the peer for this
               address family.";
          }

          container unicast {
            config false;
            description
              "BGP Peer IPv4 unicast address family configuration";
            uses bgp-peer-state-af-v4v6-config;

            uses bgp-peer-state-af-unicast-config;
          }
        }

        container ipv6 {
          config false;
          description
            "BGP Peer IPv6 address family configuration";
          leaf enabled {
            type boolean;
            config false;
            description
              "Enable advertisement of Multiprotocol support to the peer for this
               address family.";
          }

          container unicast {
            config false;
            description
              "BGP Peer IPv6 unicast address family configuration";
            uses bgp-peer-state-af-v4v6-config;

            uses bgp-peer-state-af-unicast-config;
          }
        }
      }

      uses bgp-peer-state-config;
    }
  }

  grouping router-bgp-neighbor-af-common-state {
    leaf update-group {
      type uint32;
      config false;
      description
        "The index of the update group that the peer is a member of
         for this AFI/SAFI.

         Zero if the peer is not a member of an update group.";
    }
  }

  grouping router-bgp-network-ipv4 {
    list network {
      user-ext:CLI-comm-help "Configure BGP network information";
      user-ext:CLI-no-comm-help "Remove BGP network information";
      key "network-prefix";
      description
        "This list contains the set of network prefixes that should be advertised by
         BGP.";
      leaf network-prefix {
        user-ext:CLI-param-help "Network prefix";
        type interfaces:iface-ipv4-prefix-t;
        description
          "Destination IP address prefix filter.  Do not match the source
           routing information to this entry if one of these fails:

           -  the destination IP address in the source routing
           information, with the IP address filter prefix length
           applied, matches the IP address filter with the IP address
           filter prefix length applied

           -  the destination IP address prefix length is greater
           than or equal to the IP address filter prefix length.";
      }
    }
  }

  grouping router-bgp-network-ipv6 {
    list network {
      user-ext:CLI-comm-help "Configure BGP network information";
      user-ext:CLI-no-comm-help "Remove BGP network information";
      key "network-prefix";
      description
        "This list contains the set of network prefixes that should be advertised by
         BGP.";
      leaf network-prefix {
        user-ext:CLI-param-help "Network prefix";
        type interfaces:iface-ipv6-prefix-t;
        description
          "Destination IP address prefix filter.  Do not match the source
           routing information to this entry if one of these fails:

           -  the destination IP address in the source routing
           information, with the IP address filter prefix length
           applied, matches the IP address filter with the IP address
           filter prefix length applied

           -  the destination IP address prefix length is greater
           than or equal to the IP address filter prefix length.";
      }
    }
  }

  grouping listen-group-config {
    leaf peer-group-name {
      user-ext:CLI-comm-help "Configure the peer group";
      user-ext:CLI-no-comm-help "Remove the configured peer group";
      user-ext:CLI-param-help "Configure the peer group";
      type leafref {
        path "../../peer-group/name";
      }
      mandatory true;
      description
        "The name of the peer group that neighbors in this peer
         range belongs to.

         The peer range must be assigned to a peer group so this
         field cannot be set to zero.

         If this field is changed while active then all dynamic peers
         based on the peer range entry are immediately updated.";
    }

    leaf max-peers {
      user-ext:CLI-comm-help "Set the maximum number of dynamic peers";
      user-ext:CLI-no-comm-help "Don't limit the number of dynamic peers";
      user-ext:CLI-param-help "Set the maximum number of dynamic peers";
      type bgp-listen-range-max-peers-t;
      default "0";
      description
        "The maximum number of dynamic BGP peers for this peer
         range, or zero if there is no limit.

         If this limit is reached then BGP rejects incoming
         connections from new dynamic BGP peers until BGP session
         termination causes the number of dynamic BGP peers to fall
         back below the limit.

         If this limit is reduced below the current number of
         dynamic BGP peers then BGP will reject incoming
         connections from new dynamic BGP peers until the number
         of dynamic BGP peers falls below the new limit.  BGP
         does not terminate existing BGP sessions with dynamic BGP
         peers in this case.";
    }
  }

  grouping listen-group-state {
    leaf num-peers {
      type uint32;
      config false;
      description
        "The current number of dynamic BGP peers for this peer
         range.";
    }
  }

  grouping bgp-ipv4-unicast-config {
    container unicast {
      user-ext:CLI-comm-help "Configure IPv4 unicast BGP routing";
      user-ext:CLI-no-comm-help "Configure IPv4 unicast BGP routing";
      description
        "Configure IPv4 unicast BGP routing";
      leaf disable {
        type empty;
        description
          "Disable advertisement of this multiprotocol capability (enabled by default)";
      }

      uses router-bgp-af-common-parameters;

      uses router-bgp-af-ipv4-parameters;

      uses router-bgp-af-unicast-parameters;

      uses router-bgp-network-ipv4;

      container redistribution {
        user-ext:CLI-comm-help "Configure redistribution information";
        user-ext:CLI-no-comm-help "Remove redistribution information";
        description
          "Redistribution information entries.
           This list is used to determine how routing information is
           redistributed to routing protocol managers (RPMs).  The RPM to which
           the information may be redistributed is called the
           destination RPM.  Routing information is received from RPMs
           and from configuration (for static routes); these are referred to
           as the routing information source.";
        list isis {
          user-ext:CLI-comm-help "Configure IS-IS redistribution rule";
          user-ext:CLI-no-comm-help "Remove IS-IS redistribution rule";
          key "name";
          leaf name {
            user-ext:CLI-param-help "Rule name";
            type redist:redist-name-string;
            description
              "Redistribution rule name";
          }

          uses redist:common-redist-ipv4;

          leaf path-type-filter {
            user-ext:CLI-comm-help "Set path type filter";
            user-ext:CLI-no-comm-help "Set path type filter to default";
            user-ext:CLI-param-help "Set path type filter";
            type redist:isis-redist-path-types;
            default "none";
            description
              "Value of IS-IS path type filter, if in use.  If the filter is in
               use then do not match the source routing information to
               this entry if the path type in the source routing
               information does not match this filter value.";
          }

          uses bgp-redist;

          leaf admin-tag {
            user-ext:CLI-comm-help "Set IS-IS tag";
            user-ext:CLI-no-comm-help "Set IS-IS tag to default";
            user-ext:CLI-param-help "Set IS-IS tag";
            type uint32 {
              range "0..4294967295";
            }
            description
              "Value of IS-IS tag.";
          }
        }

        list ospf {
          user-ext:CLI-comm-help "Configure OSPF redistribution rule";
          user-ext:CLI-no-comm-help "Remove OSPF redistribution rule";
          key "name";
          leaf name {
            user-ext:CLI-param-help "Rule name";
            type redist:redist-name-string;
            description
              "Redistribution rule name";
          }

          uses redist:common-redist-ipv4;

          leaf path-type-filter {
            user-ext:CLI-comm-help "Set path type filter";
            user-ext:CLI-no-comm-help "Set path type filter to default";
            user-ext:CLI-param-help "Set path type filter";
            type redist:ospf-redist-path-types;
            default "none";
            description
              "Value of OSPF path type filter, if in use.  If the filter is in
               use then do not match the source routing information to
               this entry if the path type in the source routing
               information does not match this filter value.";
          }

          uses bgp-redist;
        }

        list rip {
          user-ext:CLI-comm-help "Configure RIP redistribution rule";
          user-ext:CLI-no-comm-help "Remove RIP redistribution rule";
          key "name";
          leaf name {
            user-ext:CLI-param-help "Rule name";
            type redist:redist-name-string;
            description
              "Redistribution rule name";
          }

          uses redist:common-redist-ipv4;

          uses bgp-redist;
        }

        list static {
          user-ext:CLI-comm-help "Configure static redistribution rule";
          user-ext:CLI-no-comm-help "Remove static redistribution rule";
          key "name";
          leaf name {
            user-ext:CLI-param-help "Rule name";
            type redist:redist-name-string;
            description
              "Redistribution rule name";
          }

          uses redist:common-redist-ipv4;

          uses bgp-redist;
        }

        list connected {
          user-ext:CLI-comm-help "Configure connected redistribution rule";
          user-ext:CLI-no-comm-help "Remove connected redistribution rule";
          key "name";
          leaf name {
            user-ext:CLI-param-help "Rule name";
            type redist:redist-name-string;
            description
              "Redistribution rule name";
          }

          uses redist:common-redist-ipv4;

          uses bgp-redist;
        }

        list local {
          user-ext:CLI-comm-help "Configure local redistribution rule";
          user-ext:CLI-no-comm-help "Remove local redistribution rule";
          key "name";
          leaf name {
            user-ext:CLI-param-help "Rule name";
            type redist:redist-name-string;
            description
              "Redistribution rule name";
          }

          uses redist:common-redist-ipv4;

          uses bgp-redist;

          uses redist:fully-specified;
        }
      }
    }
  }

  grouping bgp-ipv6-unicast-config {
    container unicast {
      user-ext:CLI-comm-help "Configure IPv6 unicast BGP routing";
      user-ext:CLI-no-comm-help "Configure IPv6 unicast BGP routing";
      description
        "Configure IPv6 unicast BGP routing";
      leaf enable {
        type empty;
        description
          "Enable advertisement of this multiprotocol capability (disabled by default)";
      }

      uses router-bgp-af-common-parameters;

      uses router-bgp-af-ipv6-parameters;

      uses router-bgp-af-unicast-parameters;

      uses router-bgp-network-ipv6;

      container redistribution {
        user-ext:CLI-comm-help "Configure redistribution information";
        user-ext:CLI-no-comm-help "Remove redistribution information";
        description
          "Redistribution information entries.
           This list is used to determine how routing information is
           redistributed to routing protocol managers (RPMs).  The RPM to which
           the information may be redistributed is called the
           destination RPM.  Routing information is received from RPMs
           and from configuration (for static routes); these are referred to
           as the routing information source.";
        list isis {
          user-ext:CLI-comm-help "Configure IS-IS redistribution rule";
          user-ext:CLI-no-comm-help "Configure IS-IS redistribution rule";
          key "name";
          leaf name {
            user-ext:CLI-param-help "Rule name";
            type redist:redist-name-string;
            description
              "Redistribution rule name";
          }

          uses redist:common-redist-ipv6;

          leaf path-type-filter {
            user-ext:CLI-comm-help "Set path type filter";
            user-ext:CLI-no-comm-help "Set path type filter to default";
            user-ext:CLI-param-help "Set path type filter";
            type redist:isis-redist-path-types;
            default "none";
            description
              "Value of IS-IS path type filter, if in use.  If the filter is in
               use then do not match the source routing information to
               this entry if the path type in the source routing
               information does not match this filter value.";
          }

          uses bgp-redist;

          leaf admin-tag {
            user-ext:CLI-comm-help "Set IS-IS tag";
            user-ext:CLI-no-comm-help "Set IS-IS tag to default";
            user-ext:CLI-param-help "Set IS-IS tag";
            type uint32 {
              range "0..4294967295";
            }
            description
              "Value of IS-IS tag.";
          }
        }

        list ospf {
          user-ext:CLI-comm-help "Configure OSPF redistribution rule";
          user-ext:CLI-no-comm-help "Remove OSPF redistribution rule";
          key "name";
          leaf name {
            user-ext:CLI-param-help "Rule name";
            type redist:redist-name-string;
            description
              "Redistribution rule name";
          }

          uses redist:common-redist-ipv6;

          leaf path-type-filter {
            user-ext:CLI-comm-help "Set path type filter";
            user-ext:CLI-no-comm-help "Set path type filter to default";
            user-ext:CLI-param-help "Set path type filter";
            type redist:ospf-redist-path-types;
            default "none";
            description
              "Value of OSPF path type filter, if in use.  If the filter is in
               use then do not match the source routing information to
               this entry if the path type in the source routing
               information does not match this filter value.";
          }

          uses bgp-redist;
        }

        list rip {
          user-ext:CLI-comm-help "Configure RIP redistribution rule";
          user-ext:CLI-no-comm-help "Remove RIP redistribution rule";
          key "name";
          leaf name {
            user-ext:CLI-param-help "Rule name";
            type redist:redist-name-string;
            description
              "Redistribution rule name";
          }

          uses redist:common-redist-ipv6;

          uses bgp-redist;
        }

        list static {
          user-ext:CLI-comm-help "Configure static redistribution rule";
          user-ext:CLI-no-comm-help "Remove static redistribution rule";
          key "name";
          leaf name {
            user-ext:CLI-param-help "Rule name";
            type redist:redist-name-string;
            description
              "Redistribution rule name";
          }

          uses redist:common-redist-ipv6;

          uses bgp-redist;
        }

        list connected {
          user-ext:CLI-comm-help "Configure connected redistribution rule";
          user-ext:CLI-no-comm-help "Remove connected redistribution rule";
          key "name";
          leaf name {
            user-ext:CLI-param-help "Rule name";
            type redist:redist-name-string;
            description
              "Redistribution rule name";
          }

          uses redist:common-redist-ipv6;

          uses bgp-redist;
        }

        list local {
          user-ext:CLI-comm-help "Configure local redistribution rule";
          user-ext:CLI-no-comm-help "Remove local redistribution rule";
          key "name";
          leaf name {
            user-ext:CLI-param-help "Rule name";
            type redist:redist-name-string;
            description
              "Redistribution rule name";
          }

          uses redist:common-redist-ipv6;

          uses bgp-redist;

          uses redist:fully-specified;
        }
      }
    }
  }

  grouping bgp-router-parameters {
    container bgp {
      user-ext:CLI-comm-help "Configure BGP global parameters";
      user-ext:CLI-no-comm-help "Configure BGP global parameters";
      description
        "Configure BGP global parameters";
      container bestpath {
        user-ext:CLI-comm-help "Configure BGP bestpath parameters";
        user-ext:CLI-no-comm-help "Configure BGP bestpath parameters";
        description
          "Configure BGP bestpath parameters";
        container as-path {
          user-ext:CLI-comm-help "Configure BGP AS-PATH";
          user-ext:CLI-no-comm-help "Configure BGP AS-PATH";
          description
            "Configure BGP AS-PATH";
          leaf ignore {
            user-ext:CLI-comm-help "Ignore as-path length for bestpath";
            user-ext:CLI-no-comm-help "Don't ignore as-path length for bestpath";
            type empty;
            description
              "AS-PATH ignore flag";
          }

          leaf multipath-relax {
            user-ext:CLI-comm-help "Disable as-path length proof for bestpath if multipath routes";
            user-ext:CLI-no-comm-help "Enable as-path length proof for bestpath if multipath routes";
            type empty;
            description
              "AS-PATH multipath-relax flag";
          }
        }

        container med {
          user-ext:CLI-comm-help "Configure BGP MED parameters";
          user-ext:CLI-no-comm-help "Configure BGP MED parameters";
          description
            "Configure BGP MED parameters";
          leaf always {
            user-ext:CLI-comm-help "Enable MED always compare equal routes";
            user-ext:CLI-no-comm-help "Disable MED always compare equal routes";
            type empty;
            description
              "MED always equal routes flag";
          }

          leaf confed {
            user-ext:CLI-comm-help "Enable MED equal between confederation paths";
            user-ext:CLI-no-comm-help "Disable MED equal between confederation paths";
            type empty;
            description
              "MED equal between confed path";
          }

          leaf non-deterministic {
            user-ext:CLI-comm-help "Enable non-deterministic MED comparison";
            user-ext:CLI-no-comm-help "Disable non-deterministic MED comparison";
            type empty;
            description
              "MED comparison is non-deterministic";
          }

          leaf missing-as-worst {
            user-ext:CLI-comm-help "Enable MED minimal if not set";
            user-ext:CLI-no-comm-help "Disable MED minimal if not set";
            type empty;
            description
              "MED minimal";
          }
        }
      }

      container default {
        user-ext:CLI-comm-help "Configure BGP default local preference";
        user-ext:CLI-no-comm-help "Configure BGP default local preference";
        description
          "Configure BGP default local-preference";
        leaf local-preference {
          user-ext:CLI-comm-help "Set BGP default local preference";
          user-ext:CLI-no-comm-help "Remove BGP default local preference";
          user-ext:CLI-param-help "Set preference";
          type router-bgp-local-preference;
          description
            "BGP default local-preference";
        }
      }

      container enforce-first-as {
        user-ext:CLI-comm-help "Configure first AS number in AS PATH for EBGP nbrs";
        user-ext:CLI-no-comm-help "Configure first AS number in AS PATH for EBGP nbrs";
        description
          "Configure first AS in path and peer AS equal proof";
        leaf disable {
          user-ext:CLI-comm-help "Disable first AS number in AS PATH for EBGP nbrs";
          user-ext:CLI-no-comm-help "Enable first AS number in AS PATH for EBGP nbrs";
          type empty;
          description
            "Disable first AS in path and peer AS equal proof";
        }
      }

      container fast-external-fallover {
        user-ext:CLI-comm-help "Configure fallover for EBGP session";
        user-ext:CLI-no-comm-help "Configure fallover for EBGP session";
        description
          "Configure fallover EBGP session";
        leaf disable {
          user-ext:CLI-comm-help "Disable immediate fallover if interface with direct-connect is down";
          user-ext:CLI-no-comm-help "Enable immediate fallover if interface with direct-connect is down";
          type empty;
          description
            "Disable immediate fallover EBGP session if iface with direct-connect is down";
        }
      }

      uses router-bgp-max-ecmp-paths;

      container compare-routerid {
        user-ext:CLI-comm-help "Configure compare router ID";
        user-ext:CLI-no-comm-help "Configure compare router ID";
        description
          "Configure whether to compare-routerid when comparing route with existing best";
        leaf enable {
          user-ext:CLI-comm-help "Enable router ID comparison (so do not prefer existing route)";
          user-ext:CLI-no-comm-help "Disable router ID comparison (so we prefer existing route)";
          type empty;
          description
            "Enable comparison of router IDs when comparing route to existing best";
        }
      }

      container graceful-restart {
        user-ext:CLI-comm-help "Configure BGP graceful restart";
        user-ext:CLI-no-comm-help "Configure BGP graceful restart";
        must "((not(enable)) or  ((not(stale-path-time)) and (not(restart-time))) or  ((not(stale-path-time)) and (150 >= restart-time)) or  ((not(restart-time)) and (stale-path-time >= 120)) or   (((stale-path-time) and (restart-time)) and    (number(stale-path-time) >= number(restart-time))))" {
          error-message
            "BGP stale-path-time must be greater than or equal to restart-time";
        }
        must "((not(enable)) or  ((not(select-defer-time)) and (not(restart-time))) or  ((not(select-defer-time)) and (150 >= restart-time)) or  ((not(restart-time)) and (select-defer-time >= 120)) or   (((select-defer-time) and (restart-time)) and    (number(select-defer-time) >= number(restart-time))))" {
          error-message
            "BGP select-defer-time must be greater than or equal to restart-time";
        }
        must "((not(enable)) or (not(restart-helper-mode)))" {
          error-message
            "BGP cannot have graceful restart enabled and be in restart helper mode at the same time";
        }
        description
          "Configure BGP graceful restart";
        leaf enable {
          user-ext:CLI-comm-help "Enable BGP graceful restart";
          user-ext:CLI-no-comm-help "Disable BGP graceful restart";
          type empty;
          description
            "Enable BGP graceful restart";
        }

        leaf restart-time {
          user-ext:CLI-comm-help "Set maximum time to wait for neighbor to come [back] online";
          user-ext:CLI-no-comm-help "Set default max time to wait for neighbor to come [back] online";
          user-ext:CLI-param-help "Set maximum time to wait for neighbor to come [back] online";
          type router-bgp-graceful-restart-restart-time;
          default "120";
          description
            "Restart time to announce to neighbors";
        }

        leaf stale-path-time {
          user-ext:CLI-comm-help "Set maximum time to wait before removing stale routes from neighbor";
          user-ext:CLI-no-comm-help "Set default max time to wait before removing stale routes from neighbor";
          user-ext:CLI-param-help "Set maximum time to wait before removing stale routes from neighbor";
          type router-bgp-graceful-restart-restart-time;
          default "150";
          description
            "The maximum time to wait for neighbor to restart before
             removing stale routes from that neighbor";
        }

        leaf select-defer-time {
          user-ext:CLI-comm-help "Set maximum time to wait before performing route selection";
          user-ext:CLI-no-comm-help "Set default max time to wait before performing route selection";
          user-ext:CLI-param-help "Set maximum time to wait before performing route selection";
          type router-bgp-graceful-restart-restart-time;
          default "150";
          description
            "The maximum time to wait following local restart before performing
             route selection";
        }

        leaf restart-helper-mode {
          user-ext:CLI-comm-help "Enable BGP graceful restart helper mode";
          user-ext:CLI-no-comm-help "Disable BGP graceful restart helper mode";
          type empty;
          description
            "Enable BGP graceful restart helper mode";
        }
      }

      container update-groups {
        user-ext:CLI-comm-help "Configure BGP update groups";
        user-ext:CLI-no-comm-help "Configure BGP update groups";
        description
          "Configure BGP update groups";
        leaf enable {
          user-ext:CLI-comm-help "Enable BGP update groups";
          user-ext:CLI-no-comm-help "Disable BGP update groups";
          type empty;
          description
            "Enable BGP update groups";
        }
      }

      leaf router-id {
        user-ext:CLI-comm-help "Set BGP router ID";
        user-ext:CLI-no-comm-help "Remove BGP router ID";
        user-ext:CLI-param-help "Set router ID";
        type meta:ipv4-unicast-address;
        mandatory true;
        description
          "BGP router-id";
      }

      leaf update-delay {
        user-ext:CLI-comm-help "Set BGP update delay";
        user-ext:CLI-no-comm-help "Set BGP update delay to default";
        user-ext:CLI-param-help "Set delay";
        type router-bgp-update-delay;
        default "120";
        description
          "BGP update delay";
      }

      leaf cluster-id {
        user-ext:CLI-comm-help "Set BGP cluster ID";
        user-ext:CLI-no-comm-help "Remove BGP cluster ID";
        user-ext:CLI-param-help "Set cluster ID";
        type interfaces:iface-ipv4-address-t;
        description
          "BGP cluster-id";
      }

      leaf rib-size-limit {
        user-ext:CLI-comm-help "Set RIB size limit";
        user-ext:CLI-no-comm-help "Remove RIB size limit";
        user-ext:CLI-param-help "Set RIB size limit";
        type uint32;
        description
          "Limit on the total number of BGP routes";
      }

      container state {
        config false;
        uses global-state-for-bgp;
      }
    }
  }

  grouping bgp-nlri-prefix-state {
    container nlri-prefix-state-list {
      config false;
      description
        "Container to hold NLRI Prefix state for the IP address family.";
      list nlri-prefix-state {
        config false;
        description
          "This table contains information about paths to destination
           networks received from all BGP peers.";
        uses nlri-state;
      }
    }
  }

  grouping bgp-adj-rib-ip-out {
    container adj-rib-out-list {
      config false;
      description
        "Container to hold BGP Adj-RIB-Out Table state for the IP address family.";
      list adj-rib-out {
        config false;
        description
          "The BGP Adj-RIB-Out Table contains the set of routes
           advertised to each peer.";
        uses adj-rib-out-ip-state;
      }
    }
  }

  grouping bgp-route-administrative-distance {
    container admin-distance {
      user-ext:CLI-comm-help "Configure administrative distances for BGP routes";
      user-ext:CLI-no-comm-help "Configure administrative distances for BGP routes";
      description
        "Configure administrative distances for BGP routes";
      leaf bgp-internal {
        user-ext:CLI-comm-help "Set administrative distance used for internal and VPN BGP routes";
        user-ext:CLI-no-comm-help "Set administrative distance used for internal and VPN BGP routes to default";
        user-ext:CLI-param-help "Set administrative distance used for internal and VPN BGP routes";
        type redist:rtm-admin-distance;
        default "200";
        description
          "The administrative distance to use for internal and VPN BGP routes.  The lower
           the administrative distance for a type of route, the more likely a route
           of this type will be used as the active route for the given destination.";
      }

      leaf bgp-external {
        user-ext:CLI-comm-help "Set administrative distance used for BGP external routes";
        user-ext:CLI-no-comm-help "Set administrative distance used for BGP external routes to default";
        user-ext:CLI-param-help "Set administrative distance used for BGP external routes";
        type redist:rtm-admin-distance;
        default "20";
        description
          "The administrative distance to use for BGP external routes.  The lower
           the administrative distance for a type of route, the more likely a route
           of this type will be used as the active route for the given destination.";
      }
    }
  }

  grouping bgp-base-router {
    container address-family {
      user-ext:CLI-comm-help "Configure BGP routing for address-family";
      user-ext:CLI-no-comm-help "Configure BGP routing for address-family";
      description
        "Configure BGP routing for address-family";
      container ipv4 {
        user-ext:CLI-comm-help "Configure IPv4 BGP routing";
        user-ext:CLI-no-comm-help "Configure IPv4 BGP routing";
        description
          "Configure IPv4 BGP routing";
        uses bgp-ipv4-unicast-config;

        uses bgp-route-administrative-distance;
      }

      container ipv6 {
        user-ext:CLI-comm-help "Configure IPv6 BGP routing";
        user-ext:CLI-no-comm-help "Configure IPv6 BGP routing";
        description
          "Configure IPv6 BGP routing";
        uses bgp-ipv6-unicast-config;

        uses bgp-route-administrative-distance;
      }
    }

    uses bgp-router-parameters;

    list neighbor {
      user-ext:CLI-comm-help "Configure a BGP neighbor";
      user-ext:CLI-no-comm-help "Remove a BGP neighbor";
      must "(not(update-source) or  ((substring-after(address, ':') = '') and   (substring-after(update-source, ':') = '')) or  ((substring-after(address, ':') != '') and   (substring-after(update-source, ':') != '')))" {
        error-message
          "BGP neighbor address and update-source must have the same IP address type";
      }
      must "(((not(advertisement-interval)) and (not(withdraw-interval))) or  ((not(advertisement-interval)) and (30 >= withdraw-interval)) or  ((not(withdraw-interval)) and (advertisement-interval >= 30)) or   (((advertisement-interval) and (withdraw-interval)) and    (number(advertisement-interval) >= number(withdraw-interval))))" {
        error-message
          "BGP neighbor advertisement-interval must be at least withdraw-interval";
      }
      must "(((((not(remote-as)) and (local-as)) and    (local-as != 0)) or   (((remote-as) and (not(local-as))) and    ((remote-as != 0) and (number(remote-as) != number(../../as-num)))) or   (((remote-as) and (local-as)) and    (((remote-as != 0) and (number(remote-as) != number(../../as-num))) or     ((local-as != 0) and (number(remote-as) != number(local-as)))))) or  (not(ebgp-multihop)))" {
        error-message
          "eBGP configuration fields should not be set if this is an iBGP neighbor";
      }
      key "address";
      leaf address {
        user-ext:CLI-param-help "Neighbor address";
        type interfaces:iface-ip-address-t;
        description
          "Neighbor address";
      }

      uses neighbor-config;
    }

    list neighbor-interface {
      user-ext:CLI-comm-help "Configure a BGP neighbor by interface name";
      user-ext:CLI-no-comm-help "Configure a BGP neighbor by interface name";
      must "(not(update-source))" {
        error-message
          "BGP update-source not supported for neighbors configured by interface";
      }
      must "(((not(advertisement-interval)) and (not(withdraw-interval))) or  ((not(advertisement-interval)) and (30 >= withdraw-interval)) or  ((not(withdraw-interval)) and (advertisement-interval >= 30)) or   (((advertisement-interval) and (withdraw-interval)) and    (number(advertisement-interval) >= number(withdraw-interval))))" {
        error-message
          "BGP neighbor advertisement-interval must be at least withdraw-interval";
      }
      must "(not(ebgp-multihop))" {
        error-message
          "ebgp-multihop must not be set for neighbors configured by interface";
      }
      key "interface";
      leaf interface {
        user-ext:CLI-param-help "Name of interface on which the neighbor is reachable";
        type custom:iface-name;
        description
          "Name of interface on which the neighbor is reachable";
      }

      uses neighbor-config;
    }

    container neighbor-state-list {
      config false;
      description
        "Container to hold state for configured and dynamic Neighbors.";
      list neighbor-state {
        key "remote-address";
        config false;
        description
          "Configured and dynamic state.";
        uses neighbor-state-actions;

        uses neighbor-state;

        uses neighbor-state-config;
      }
    }

    container neighbor-interface-state-list {
      config false;
      description
        "Container to hold state for configured unnumbered Neighbors.";
      list neighbor-interface-state {
        key "interface";
        config false;
        description
          "Configured and dynamic state.";
        uses neighbor-state-actions;

        uses neighbor-state;

        uses neighbor-state-config;
      }
    }

    list listen-range {
      user-ext:CLI-comm-help "Configure a BGP dynamic peer range";
      user-ext:CLI-no-comm-help "Remove a BGP dynamic peer range";
      key "prefix";
      description
        "Peer range table.

         This table allows a user to configure BGP dynamic neighbors.
         Instead of being configured individually in the BGP peer
         table, BGP dynamic neighbors are configured as ranges of
         remote addresses with associated peer groups.  Each range
         is configured as a remote address prefix.  Any BGP peer with
         a remote address that matches the remote address prefix
         becomes a member of the associated peer group.

         Each entry in this table configures a remote address prefix
         and specifies the associated peer group.

         BGP handles incoming connections from BGP peers as
         follows.
         -  If the connection matches a peer configured in the
         BGP peer table then the peer is a configured peer.
         -  Otherwise if the connection matches a remote address
         prefix in the BGP peer range table then the peer is
         a dynamic peer.
         -  Otherwise if the listen socket is configured to accept
         all incoming connections then the connection is accepted
         and uses the default peer configuration.
         -  Otherwise the connection is rejected.

         If an incoming connection matches multiple peer range
         entries then the entry with the longest remote address
         prefix is selected.

         Although it is possible to configure overlapping peer ranges
         with different remote address prefix lengths, this is not
         recommended - peer range configuration is simpler and
         clearer if peer ranges do not overlap.";
      leaf prefix {
        user-ext:CLI-param-help "Peer range prefix";
        type interfaces:iface-ip-prefix-t;
        description
          "The remote address prefix.";
      }

      uses listen-group-config;

      container state {
        config false;
        uses listen-group-state;
      }
    }

    list peer-group {
      user-ext:CLI-comm-help "Configure a BGP peer group";
      user-ext:CLI-no-comm-help "Remove a BGP peer group";
      must "(((not(advertisement-interval)) and (not(withdraw-interval))) or  ((not(advertisement-interval)) and (30 >= withdraw-interval)) or  ((not(withdraw-interval)) and (advertisement-interval >= 30)) or   (((advertisement-interval) and (withdraw-interval)) and    (number(advertisement-interval) >= number(withdraw-interval))))" {
        error-message
          "BGP peer group advertisement-interval must be at least withdraw-interval";
      }
      must "(((((not(remote-as)) and (local-as)) and    (local-as != 0)) or   (((remote-as) and (not(local-as))) and    ((remote-as != 0) and (number(remote-as) != number(../../as-num)))) or   (((remote-as) and (local-as)) and    (((remote-as != 0) and (number(remote-as) != number(../../as-num))) or     ((local-as != 0) and (number(remote-as) != number(local-as)))))) or  (not(ebgp-multihop)))" {
        error-message
          "eBGP configuration fields should not be set if this is an iBGP neighbor";
      }
      key "name";
      description
        "The list of peer groups.

         A peer group is a set of peers that share a common peer
         group configuration.

         Using peer groups simplifies peer configuration.  Instead of
         configuring many peers with the same set of configuration
         values, you can configure a single peer group and then
         assign peers to the peer group.

         The configuration fields for a peer group mirror
         configuration fields for individual peers.";
      leaf name {
        user-ext:CLI-param-help "Set peer group name";
        type bgp-peer-group-name;
        description
          "The name of this BGP Route Map.";
      }

      container address-family {
        user-ext:CLI-comm-help "Configure address family for BGP peer group";
        user-ext:CLI-no-comm-help "Configure address family for BGP peer group";
        description
          "Configure address family for BGP peer group";
        container ipv4 {
          user-ext:CLI-comm-help "Configure IPv4 address family for BGP peer group";
          user-ext:CLI-no-comm-help "Configure IPv4 address family for BGP peer group";
          description
            "Configure IPv4 address family for BGP peer group";
          container unicast {
            user-ext:CLI-comm-help "Configure unicast IPv4 address family for BGP peer group";
            user-ext:CLI-no-comm-help "Configure unicast IPv4 address family for BGP peer group";
            description
              "Configure unicast IPv4 address family for BGP peer group";
            uses router-bgp-peer-group-af-v4v6-parms;

            uses router-bgp-peer-group-af-unicast-parms;
          }
        }

        container ipv6 {
          user-ext:CLI-comm-help "Configure IPv6 address family for BGP peer group";
          user-ext:CLI-no-comm-help "Configure IPv6 address family for BGP peer group";
          description
            "Configure IPv6 address family for BGP peer group";
          container unicast {
            user-ext:CLI-comm-help "Configure unicast IPv6 address family for BGP peer group";
            user-ext:CLI-no-comm-help "Configure unicast IPv6 address family for BGP peer group";
            description
              "Configure unicast IPv6 address family for BGP peer group";
            uses router-bgp-peer-group-af-v4v6-parms;

            uses router-bgp-peer-group-af-unicast-parms;
          }
        }
      }

      uses peer-group-config;
    }

    container update-group-state-list {
      config false;
      description
        "Container to hold Update Group state.";
      list update-group-state {
        config false;
        description
          "Update group table.";
        leaf update-group-index {
          type uint32;
          config false;
          description
            "Identifies an update group.";
        }

        leaf member-count {
          type uint32;
          config false;
          description
            "The count of members in this update group.";
        }

        list member {
          config false;
          description
            "Update Group member";
          leaf address {
            type interfaces:iface-ip-address-t;
            config false;
            description
              "Neighbor address";
          }
        }

        leaf afi {
          type bgp-afi;
          config false;
          description
            "The address family for this update group.";
        }

        leaf safi {
          type bgp-safi;
          config false;
          description
            "The subsequent address family for this update group.";
        }

        leaf local-address-afi {
          type bgp-afi;
          config false;
          description
            "The AFI of the local address used if next-hop-self is in
             use.";
        }

        leaf local-address-safi {
          type bgp-safi;
          config false;
          description
            "The SAFI of the local address used if next-hop-self is in
             use.";
        }

        leaf local-address-length {
          type uint32;
          config false;
          description
            "The length, in bytes, of the local address used if
             next-hop-self is in use.";
        }

        leaf as-size {
          type uint32;
          config false;
          description
            "The number of bytes (agreed with the neighbor) that are
             used for AS numbers.";
        }

        leaf neighbor-in-same-as {
          type boolean;
          config false;
          description
            "Whether the neighbor is in the same AS as this router.";
        }

        leaf confederation-member {
          type boolean;
          config false;
          description
            "Whether the neighbor is in the same confederation as this
             router.";
        }

        leaf conf-alt-local-as {
          type uint32;
          config false;
          description
            "The configured alternative local AS number for the session
             to the peers.";
        }

        leaf selected-local-as {
          type uint32;
          config false;
          description
            "The local AS number for the session to the peers.";
        }

        leaf alt-local-as-mode {
          type bgp-alt-loc-as-mode;
          config false;
          description
            "The alternative local AS number mode.";
        }

        leaf aggregate-confed {
          type boolean;
          config false;
          description
            "Whether or not the neighbor understands aggregated
             confederation AS_PATH information.";
        }

        leaf reflector-client {
          type bgp-peer-reflector-client;
          config false;
          description
            "The peer's type of Route Reflector client.";
        }

        leaf next-hop-self {
          type router-bgp-next-hop-self;
          config false;
          description
            "Whether or not next-hop-self is configured.";
        }

        leaf third-party-nh-enabled {
          type boolean;
          config false;
          description
            "Whether or not third-party next hop is enabled.";
        }

        leaf third-party-nh-addr-prefix {
          type interfaces:iface-ip-prefix-t;
          config false;
          description
            "Prefix to match on for third-party next hop.

             If third-party next hop is disabled for this peer, this
             field is empty.";
        }

        leaf peering-type {
          type bgp-peering-type;
          config false;
          description
            "The type of peering relationship associated with the peer.";
        }

        leaf slow-peer {
          type boolean;
          config false;
          description
            "Whether the peer has been marked as slow.";
        }

        leaf remove-private-as-numbers {
          type boolean;
          config false;
          description
            "Whether private AS numbers are removed from the AS path
             before sending an update to the peer.";
        }

        leaf conditional-advertisement {
          type boolean;
          config false;
          description
            "Whether conditional advertisement is enabled.";
        }

        leaf ca-advertise-map-index {
          type uint32;
          config false;
          description
            "The index of the route map used as the advertise map for
             conditional advertisement.";
        }

        leaf ca-non-exist-map-index {
          type uint32;
          config false;
          description
            "The index of the route map used as the non-exist map for
             conditional advertisement.";
        }

        leaf config-export-map-index {
          type uint32;
          config false;
          description
            "The index of the route map used for filtering exported
             routes, specified in the peer's configuration.";
        }

        leaf send-community {
          type boolean;
          config false;
          description
            "Whether or not to send BGP community attributes.";
        }

        leaf send-extcommunity {
          type boolean;
          config false;
          description
            "Whether or not to send BGP extended community attributes.";
        }

        leaf originate-default {
          type boolean;
          config false;
          description
            "Whether BGP should originate a default route.";
        }

        leaf originate-default-route-map {
          type uint32;
          config false;
          description
            "The index of the route map that is used for default
             routes.  This is zero if originate_default is false.";
        }

        leaf add-path-send-capability {
          type boolean;
          config false;
          description
            "The negotiated BGP additional path (ADD-PATH) send
             capability.";
        }

        leaf add-path-best-n {
          type uint32;
          config false;
          description
            "The number of best paths to advertise to these peers as
             additional paths.";
        }

        leaf distribution-list-acl-out {
          type int32;
          config false;
          description
            "The Access List index identifying the Access List used
             to filter routes advertised.  Zero indicates no Access
             List.";
        }

        leaf distribution-list-pl-out {
          type int32;
          config false;
          description
            "The Prefix List index identifying the Prefix List used to
             filter routes advertised.  Zero indicates no Prefix List.";
        }

        leaf filter-list-out {
          type uint32;
          config false;
          description
            "The Filter List index identifying the Filter List used to
             filter routes advertised.  Zero indicates no Filter List.";
        }

        leaf export-map-index {
          type uint32;
          config false;
          description
            "The index of the route map used for filtering exported
             routes.";
        }

        leaf export-prefix-list-is-aall {
          type boolean;
          config false;
          description
            "Whether the export prefix list is an IP prefix access
             list.";
        }

        leaf export-prefix-list {
          type uint32;
          config false;
          description
            "The index of the prefix list used for route exports.";
        }

        leaf use-export-local-pref {
          type boolean;
          config false;
          description
            "Whether the peers in this update group have an override
             local preference value configured.";
        }

        leaf export-local-pref {
          type uint32;
          config false;
          description
            "The override local preference value used for updates sent
             to the peers in this group.  Zero if an override value is
             not in use.";
        }

        leaf min-as-origination-interval {
          type uint32;
          units "seconds";
          config false;
          description
            "Time interval in seconds for determining the minimum
             amount of time that must elapse between successive
             advertisements of UPDATE messages that report changes to a
             route within the advertising BGP speaker's own autonomous
             system.";
        }

        leaf min-route-advertise-interval {
          type uint32;
          units "seconds";
          config false;
          description
            "Time interval in seconds for the
             MinRouteAdvertisementInterval timer.  This determines the
             minimum time between a BGP UPDATE to a peer advertising or
             withdrawing a route and a subsequent BGP UPDATE to the
             peer advertising a route to the same destination.";
        }

        leaf min-route-withdraw-interval {
          type uint32;
          units "seconds";
          config false;
          description
            "Time interval in seconds for the MinRouteWithdrawInterval
             timer.  This is the interval which is enforced between
             advertisement and subsequent withdrawal of a route.";
        }

        leaf preserve-next-hop {
          type boolean;
          config false;
          description
            "Indicates whether the BGP next hop is preserved when
             forwarding routes to eBGP peers in this update group.";
        }
      }
    }

    uses bgp-nlri-prefix-state;

    uses bgp-adj-rib-ip-out;
  }

  grouping nlri-common-state {
    leaf path-id {
      type uint32;
      config false;
      description
        "The path ID for this NLRI.

         If BGP additional path receive capability was negotiated
         with the peer for this AFI/SAFI then this is the received
         path ID for this NLRI, otherwise it is zero.";
    }

    leaf best-route {
      type boolean;
      config false;
      description
        "An indication of whether or not this route was chosen as
         the best BGP route.";
    }

    leaf as-size {
      type bgp-as-size-t;
      config false;
      description
        "Whether the as-path-string contains two or four
         byte AS numbers.";
    }

    leaf as-path-string {
      type string;
      config false;
      description
        "This is a string depicting the autonomous system path to
         this network which was received from the peer which
         advertised it.  If as-size is four-octet and the peer
         does not support four octet AS numbers this string
         represents the AS_PATH formed by combining the AS_PATH and
         AS4_PATH attributes as detailed in RFC 4893.  Two-octet AS
         numbers appear as four-octet numbers by adding two bytes of
         zero padding.  The format of the string is simply the
         AS_PATH attribute.  It can be converted to a more readable
         format by the management agent.";
    }

    leaf origin {
      type bgp-origin-codes;
      config false;
      description
        "The ultimate origin of the path information.";
    }

    leaf next-hop {
      type interfaces:iface-ip-address-allow-zero-t;
      config false;
      description
        "The address of the border router that should be used to
         access the destination network.  This address is the nexthop
         address received in the UPDATE packet.  The address family
         of this object will be the same as that of the prefix in
         this row.

         Note that for RFC 2545 style double nexthops, this object
         will always contain the global scope nexthop.
         link-local-next-hop will contain the link local
         scope nexthop, if it is present.";
    }

    leaf multi-exit-discriminator {
      type uint32;
      config false;
      description
        "This metric is used to discriminate between multiple exit
         points to an adjacent autonomous system.";
    }

    leaf local-preference {
      type uint32;
      config false;
      description
        "The originating BGP speaker's degree of preference for an
         advertised route.";
    }

    leaf atomic-aggregate {
      type bgp-path-attr-atomic-agg;
      config false;
      description
        "When this object is set to present,
         the ATOMIC_AGGREGATE Path Attribute is present and indicates
         that the NLRI MUST NOT be made more specific.";
    }

    leaf aggregator-as {
      type uint32;
      config false;
      description
        "The AS number of the last BGP speaker that performed
         route aggregation.";
    }

    leaf aggregator-address {
      type interfaces:iface-ipv4-address-allow-zero-t;
      config false;
      description
        "The IP address of the last BGP speaker that performed
         route aggregation.  A value of zero indicates the absence of
         this attribute.  Note propagation of AS of zero is illegal
         in the Internet.";
    }

    leaf calculated-local-preference {
      type uint32;
      config false;
      description
        "The degree of preference calculated by the receiving BGP
         speaker for an advertised route.";
    }

    leaf originator-id {
      type meta:router-id;
      config false;
      description
        "The Originator-ID identifying the router that initially
         advertised this destination to a Route Reflector.  A value
         of 0.0.0.0 indicates the absence of this attribute.";
    }

    leaf weight {
      type uint32;
      config false;
      description
        "The local degree of preference assigned to this route.";
    }

    leaf route-flap-config-index {
      type uint32;
      config false;
      description
        "The index of the route flap configuration table entry
         containing the settings being applied to this route for
         dampening.";
    }

    leaf route-flap-penalty {
      type uint32;
      config false;
      description
        "The current penalty value of this route.  If it is greater
         than the cutoff threshold the route is suppressed.";
    }

    leaf route-flap-count {
      type uint32;
      config false;
      description
        "The number of times this route has flapped since
         statistics were last cleared.";
    }

    leaf route-flap-suppressed {
      type boolean;
      config false;
      description
        "Whether or not this route is suppressed.";
    }

    leaf route-flap-time-left {
      type uint32;
      units "seconds";
      config false;
      description
        "The time left until this route is no longer suppressed.
         Only valid if the route is suppressed.";
    }

    leaf ecmp {
      type boolean;
      config false;
      description
        "Whether or not this route was installed into the
         Forwarding Table as an ECMP route (it may or may not be the
         best BGP route advertised to BGP peers).";
    }

    leaf as-path-limit-as {
      type uint32;
      config false;
      description
        "The AS number of the speaker that attached the
         AS_PATHLIMIT attribute.  A value of 0 indicates the absence
         of this attribute.  Note that propagation of AS of zero is
         illegal in the Internet.";
    }

    leaf as-path-limit-upper {
      type uint32;
      config false;
      description
        "The upper bound on the number of ASes in the AS_PATH
         associated with this route before the route will be
         filtered.  Only valid if as-path-limit-as is non-zero.";
    }

    leaf is-active {
      type bgp-nlri-is-active;
      config false;
      description
        "An indication of whether or not this route is installed in
         the forwarding table.

         If advertise/inactive is set to 'false', then
         this is set to

         - 'active' if the route is installed in the forwarding
         table, or is a route redistributed from another routing
         protocol instance

         - 'inactive' otherwise.

         If advertise/inactive is set to 'true', BGP does
         not track active routes and this leaf set to 'not-tracked'.";
    }

    leaf user-data {
      type bgp-user-data-t;
      config false;
      description
        "User data for this BGP NLRI entry.";
    }

    leaf stale {
      type boolean;
      config false;
      description
        "Whether or not this route was last sent by the peer before
         BGP detected that the peer was restarting.  If the route is
         not re-advertised by the peer before the restart completes,
         BGP will remove the route from its database.  This flag is
         set to 'false' if the peer is not restarting, or if the
         route has been advertised by the peer since the restart.";
    }

    leaf flap-start-time {
      type uint32;
      config false;
      description
        "The value of sysUpTime when this route first flapped.
         This field is only valid if the route has flapped.";
    }

    leaf link-local-next-hop {
      type interfaces:iface-ip-address-t;
      config false;
      description
        "The IPv6 link-local address of the border router that
         should be used to access the destination network.  This
         object is only valid for a prefix with a received RFC 2545
         style double nexthop.";
    }

    leaf multi-exit-discriminator-set {
      type boolean;
      config false;
      description
        "If true, then the route has an associated MED attribute,
         whose value is given in multi-exit-discriminator.  If false,

         the route has no MED attribute, and the value of
         multi-exit-discriminator is undefined.";
    }

    leaf history {
      type boolean;
      config false;
      description
        "If true, then the route is a history route.  If false it
         is current.";
    }

    leaf peer-type {
      type bgp-nlri-peer-type;
      config false;
      description
        "The type of peer that a route was received from, if any.";
    }

    leaf peer-address {
      type interfaces:iface-ip-address-t;
      config false;
      description
        "The address of the BGP peer that a route was learned from, if any.";
    }

    leaf peer-scope-id {
      type uint32;
      config false;
      description
        "The scope ID of the BGP peer address.

         The scope ID is required if the address is an IPv6
         link-local address.  Otherwise, this field will be zero.";
    }

    leaf peer-interface {
      type interfaces:iface-name;
      config false;
      description
        "The local interface used to reach the BGP peer.";
    }

    uses community-lists;
  }

  grouping l2vpn-evpn-common-state {
    choice route-type {
      description
        "The Route Type field defines the encoding of the rest of the EVPN
         NLRI (Route Type specific EVPN NLRI).";
      case auto-discovery {
        container auto-discovery {
          description
            "Ethernet Auto-Discovery (A-D) route.";
          leaf rd {
            type meta:bgp-route-distinguisher;
            config false;
            description
              "The local EVPN route distinguisher.";
          }

          leaf esi {
            type es:esi-t;
            config false;
            description
              "Ethernet Segment Identifier (ESI).";
          }

          leaf ethernet-tag {
            type uint32;
            config false;
            description
              "Ethernet tag.";
          }

          leaf label {
            type uint32;
            config false;
            description
              "The label or VNI associated with the route.";
          }
        }
      }

      case mac-ip {
        container mac-ip {
          description
            "MAC/IP Advertisement route.";
          leaf rd {
            type meta:bgp-route-distinguisher;
            config false;
            description
              "The local EVPN route distinguisher.";
          }

          leaf esi {
            type es:esi-t;
            config false;
            description
              "Ethernet Segment Identifier (ESI).";
          }

          leaf ethernet-tag {
            type uint32;
            config false;
            description
              "Ethernet tag.";
          }

          leaf mac-address {
            type meta:mac-address;
            config false;
            description
              "MAC address.";
          }

          leaf ip-addr {
            type interfaces:iface-ip-address-t;
            config false;
            description
              "IP address.";
          }

          leaf label1 {
            type uint32;
            config false;
            description
              "The first label or VNI associated with the route.";
          }

          leaf label2 {
            type uint32;
            config false;
            description
              "The second label or VNI associated with the route.";
          }
        }
      }

      case inclusive-mcast {
        container inclusive-mcast {
          description
            "Inclusive Multicast Ethernet Tag route.";
          leaf rd {
            type meta:bgp-route-distinguisher;
            config false;
            description
              "The local EVPN route distinguisher.";
          }

          leaf ethernet-tag {
            type uint32;
            config false;
            description
              "Ethernet tag.";
          }

          leaf originating-router-addr {
            type interfaces:iface-ip-address-t;
            config false;
            description
              "The originating router address.";
          }
        }
      }

      case ethernet-segment {
        container ethernet-segment {
          description
            "Ethernet Segment route.";
          leaf rd {
            type meta:bgp-route-distinguisher;
            config false;
            description
              "The local EVPN route distinguisher.";
          }

          leaf esi {
            type es:esi-t;
            config false;
            description
              "Ethernet Segment Identifier (ESI).";
          }

          leaf originating-router-addr {
            type interfaces:iface-ip-address-t;
            config false;
            description
              "The originating router address.";
          }
        }
      }

      case ip-prefix {
        container ip-prefix {
          description
            "IP Prefix route.";
          leaf rd {
            type meta:bgp-route-distinguisher;
            config false;
            description
              "The local EVPN route distinguisher.";
          }

          leaf esi {
            type es:esi-t;
            config false;
            description
              "Ethernet Segment Identifier (ESI).";
          }

          leaf ethernet-tag {
            type uint32;
            config false;
            description
              "Ethernet tag.";
          }

          leaf ip-prefix {
            type interfaces:iface-ip-prefix-t;
            config false;
            description
              "IP prefix.";
          }

          leaf gw-ip-addr {
            type interfaces:iface-ip-address-t;
            config false;
            description
              "GW IP address.";
          }

          leaf label {
            type uint32;
            config false;
            description
              "The first label or VNI associated with the route.";
          }
        }
      }
    }
  }

  grouping peer-notification-id {
    leaf vrf-name {
      type meta:l3vpn-vrf-name;
      description
        "The name of the VRF associated with the peer session.  This leaf
         reports an empty string for the global VRF";
    }

    leaf peer-local-address {
      type interfaces:iface-ip-address-t;
      description
        "The local address in use for the Peer Session";
    }

    leaf peer-remote-address {
      type interfaces:iface-ip-address-t;
      description
        "The remote address in use for the Peer Session";
    }

    leaf local-interface {
      type custom:iface-name;
      description
        "Name of local interface on which the neighbor is reachable";
    }
  }

  grouping bgp-rm-config {
    leaf as-num {
      user-ext:CLI-param-help "Set AS number";
      type router-bgp-as;
      mandatory true;
      description
        "BGP AS number.";
    }

    leaf vrf-name {
      user-ext:CLI-comm-help "Set VRF name";
      type meta:l3vpn-vrf-name;
      description
        "The name of this VRF. This may be equivalent to the RFC2685 VPN-ID.";
    }
  }

  grouping peer-address-config {
    leaf peer-address {
      user-ext:CLI-param-help "Set peer address";
      type interfaces:iface-ip-address-t;
      mandatory true;
      description
        "Peer address";
    }
  }

  container router {
    user-ext:CLI-comm-help "Configure router";
    user-ext:CLI-no-comm-help "Configure router";
    description
      "Configure router";
    list bgp {
      user-ext:CLI-comm-help "Configure BGP AS";
      user-ext:CLI-no-comm-help "Remove BGP AS";
      user-ext:CLI-max-elements-errmsg "maximum elements for 'router bgp' exceeded";
      key "vrf-name";
      description
        "BGP AS configuration";
      leaf vrf-name {
        user-ext:CLI-comm-help "Associate configuration with VRF";
        user-ext:CLI-no-comm-help "Clear VRF association";
        type meta:l3vpn-vrf-name;
        must "(not(../global/bgp/router-id) or (../global/bgp/router-id != '0.0.0.0'))" {
          error-message
            "If configured, the BGP VRF router-id must be a non-zero unicast address";
        }
        description
          "The name of this VRF.  This MAY be equivalent to the RFC2685 VPN-ID.";
      }

      leaf as-num {
        user-ext:CLI-param-help "BGP AS number";
        type router-bgp-as;
        must "(not(../global/bgp/router-id) or (../global/bgp/router-id != '0.0.0.0'))" {
          error-message
            "If configured, the BGP router-id must be a non-zero unicast address";
        }
        mandatory true;
        description
          "BGP AS number.";
      }

      leaf confederation-identifier {
        user-ext:CLI-comm-help "Set the confederation identifier";
        user-ext:CLI-no-comm-help "Set the confederation identifier to default";
        user-ext:CLI-param-help "Set the confederation identifier";
        type router-bgp-as;
        default "0";
        description
          "The confederation idenifier";
      }

      container global {
        user-ext:CLI-not-command;
        must "((./bgp/router-id) and (./bgp/router-id != '0.0.0.0'))" {
          error-message
            "A valid router-id must be configured for BGP";
        }
        uses bgp-base-router;
      }

      list vrf {
        user-ext:CLI-comm-help "Configure BGP VRF";
        user-ext:CLI-no-comm-help "Configure or remove BGP VRF";
        key "vrf-name";
        description
          "BGP VRF configuration";
        leaf vrf-name {
          user-ext:CLI-comm-help "Associate configuration with VRF";
          user-ext:CLI-no-comm-help "Clear VRF association";
          type meta:l3vpn-vrf-name;
          must "(not(../bgp/router-id) or (../bgp/router-id != '0.0.0.0'))" {
            error-message
              "If configured, the BGP VRF router-id must be a non-zero unicast address";
          }
          description
            "The name of this VRF.  This MAY be equivalent to the RFC2685 VPN-ID.";
        }

        uses bgp-base-router;
      }
    }
  }

  augment "/bgp:router/bgp:bgp/bgp:global" {
    container nlri-l2vpn-vpls-prefix-state-list {
      config false;
      description
        "Container to hold NLRI Prefix state for the L2VPN VPLS afi/safi.";
      list nlri-l2vpn-vpls-prefix-state {
        config false;
        description
          "This table contains information about paths to destination
           networks received from all BGP peers.";
        uses nlri-l2vpn-vpls-state;
      }
    }

    container adj-rib-out-l2vpn-vpls-list {
      config false;
      description
        "Container to hold BGP Adj-RIB-Out Table state for the L2VPN VPLS afi/safi.";
      list adj-rib-out-l2vpn-vpls {
        config false;
        description
          "The BGP Adj-RIB-Out Table contains the set of routes
           advertised to each peer.";
        uses adj-rib-out-l2vpn-vpls-state;
      }
    }

    container nlri-l2vpn-evpn-prefix-state-list {
      config false;
      description
        "Container to hold NLRI Prefix state for the L2VPN EVPN afi/safi.";
      list nlri-l2vpn-evpn-prefix-state {
        config false;
        description
          "This table contains information about paths to destination
           networks received from all BGP peers.";
        uses nlri-l2vpn-evpn-state;
      }
    }

    container adj-rib-out-l2vpn-evpn-list {
      config false;
      description
        "Container to hold BGP Adj-RIB-Out Table state for the L2VPN EVPN afi/safi.";
      list adj-rib-out-l2vpn-evpn {
        config false;
        description
          "The BGP Adj-RIB-Out Table contains the set of routes
           advertised to each peer.";
        uses adj-rib-out-l2vpn-evpn-state;
      }
    }

    container nlri-l3vpn-prefix-state-list {
      config false;
      description
        "Container to hold NLRI Prefix state for the l3vpn address family.";
      list nlri-l3vpn-prefix-state {
        config false;
        description
          "This table contains information about paths to destination
           networks received from all BGP peers.";
        uses nlri-l3vpn-state;
      }
    }

    container adj-rib-out-l3vpn-list {
      config false;
      description
        "Container to hold BGP Adj-RIB-Out Table state for the l3vpn address family.";
      list adj-rib-out-l3vpn {
        config false;
        description
          "The BGP Adj-RIB-Out Table contains the set of routes
           advertised to each peer.";
        uses adj-rib-out-l3vpn-state;
      }
    }
  }

  augment "/bgp:router/bgp:bgp/bgp:global/bgp:address-family" {
    container l2vpn {
      user-ext:CLI-comm-help "Configure L2VPN VPLS or EVPN routing";
      user-ext:CLI-no-comm-help "Configure L2VPN VPLS or EVPN routing";
      description
        "Configure L2VPN VPLS or EVPN routing";
      container vpls {
        user-ext:CLI-comm-help "Configure L2VPN VPLS BGP routing";
        user-ext:CLI-no-comm-help "Configure L2VPN VPLS BGP routing";
        description
          "Configure L2VPN VPLS BGP routing";
        leaf enable {
          type empty;
          description
            "Enable advertisement of this multiprotocol capability (disabled by default)";
        }

        uses router-bgp-dampening;
      }

      container evpn {
        user-ext:CLI-comm-help "Configure L2VPN EVPN BGP routing";
        user-ext:CLI-no-comm-help "Configure L2VPN EVPN BGP routing";
        description
          "Configure L2VPN EVPN BGP routing";
        leaf enable {
          type empty;
          description
            "Enable advertisement of this multiprotocol capability (disabled by default)";
        }

        uses router-bgp-dampening;
      }
    }

    container vpnv4 {
      user-ext:CLI-comm-help "Configure VPNv4 BGP routing";
      user-ext:CLI-no-comm-help "Configure VPNv4 BGP routing";
      description
        "Configure VPNv4 BGP routing";
      container unicast {
        user-ext:CLI-comm-help "Configure VPNv4 unicast BGP routing";
        user-ext:CLI-no-comm-help "Configure VPNv4 unicast BGP routing";
        description
          "Configure VPNv4 unicast BGP routing";
        leaf enable {
          type empty;
          description
            "Enable advertisement of this multiprotocol capability (disabled by default)";
        }

        uses router-bgp-af-common-parameters;
      }
    }

    container vpnv6 {
      user-ext:CLI-comm-help "Configure VPNv6 BGP routing";
      user-ext:CLI-no-comm-help "Configure VPNv6 BGP routing";
      description
        "Configure VPNv6 BGP routing";
      container unicast {
        user-ext:CLI-comm-help "Configure VPNv6 unicast BGP routing";
        user-ext:CLI-no-comm-help "Configure VPNv6 unicast BGP routing";
        description
          "Configure VPNv6 unicast BGP routing";
        leaf enable {
          type empty;
          description
            "Enable advertisement of this multiprotocol capability (disabled by default)";
        }

        uses router-bgp-af-common-parameters;
      }
    }
  }

  augment "/bgp:router/bgp:bgp/bgp:global/bgp:neighbor/bgp:address-family" {
    uses neighbor-address-family-vpn-config;
  }

  augment "/bgp:router/bgp:bgp/bgp:global/bgp:neighbor-interface/bgp:address-family" {
    uses neighbor-address-family-vpn-config;
  }

  augment "/bgp:router/bgp:bgp/bgp:global/bgp:peer-group/bgp:address-family" {
    container l2vpn {
      user-ext:CLI-comm-help "Configure L2VPN address family for BGP peer group";
      user-ext:CLI-no-comm-help "Configure L2VPN address family for BGP peer group";
      description
        "Configure L2VPN address family for BGP peer group";
      container vpls {
        user-ext:CLI-comm-help "Configure unicast L2VPN address family for BGP peer group";
        user-ext:CLI-no-comm-help "Configure unicast L2VPN address family for BGP peer group";
        description
          "Configure unicast L2VPN address family for BGP peer group";
        uses router-bgp-peer-group-af-l2vpn-parms;
      }

      container evpn {
        user-ext:CLI-comm-help "Configure EVPN address family for BGP peer group";
        user-ext:CLI-no-comm-help "Configure EVPN address family for BGP peer group";
        description
          "Configure EPVN address family for BGP peer group";
        uses router-bgp-peer-group-af-l2vpn-parms;
      }
    }

    container vpnv4 {
      user-ext:CLI-comm-help "Configure VPNv4 address family for BGP peer group";
      user-ext:CLI-no-comm-help "Configure VPNv4 address family for BGP peer group";
      description
        "Configure VPNv4 address family for BGP peer group";
      container unicast {
        user-ext:CLI-comm-help "Configure unicast VPNv4 address family for BGP peer group";
        user-ext:CLI-no-comm-help "Configure unicast VPNv4 address family for BGP peer group";
        description
          "Configure unicast VPNv4 address family for BGP peer group";
        uses router-bgp-peer-group-af-v4v6-parms;
      }
    }

    container vpnv6 {
      user-ext:CLI-comm-help "Configure VPNv6 address family for BGP peer group";
      user-ext:CLI-no-comm-help "Configure VPNv6 address family for BGP peer group";
      description
        "Configure VPNv6 address family for BGP peer group";
      container unicast {
        user-ext:CLI-comm-help "Configure unicast VPNv6 address family for BGP peer group";
        user-ext:CLI-no-comm-help "Configure unicast VPNv6 address family for BGP peer group";
        description
          "Configure unicast VPNv6 address family for BGP peer group";
        uses router-bgp-peer-group-af-v4v6-parms;
      }
    }
  }

  augment "/bgp:router/bgp:bgp/bgp:global/bgp:neighbor-state-list/bgp:neighbor-state/bgp:address-family" {
    container l2vpn {
      description
        "State for L2VPN";
      container vpls {
        description
          "State for VPLS";
        uses router-bgp-neighbor-af-common-state;
      }

      container evpn {
        description
          "State for EVPN";
        uses router-bgp-neighbor-af-common-state;
      }
    }

    container vpnv4 {
      description
        "State for VPNv4";
      container unicast {
        description
          "State for unicast";
        uses router-bgp-neighbor-af-common-state;
      }
    }

    container vpnv6 {
      description
        "State for VPNv6";
      container unicast {
        description
          "State for unicast";
        uses router-bgp-neighbor-af-common-state;
      }
    }
  }

  augment "/bgp:router/bgp:bgp/bgp:global/bgp:neighbor-state-list/bgp:neighbor-state/bgp:config/bgp:address-family" {
    container l2vpn {
      config false;
      description
        "BGP Peer L2VPN address family configuration";
      container vpls {
        config false;
        description
          "BGP Peer L2VPN VPLS address-family configuration";
        uses bgp-peer-state-af-l2vpn-config;
      }

      container evpn {
        config false;
        description
          "BGP Peer EVPN address-family configuration";
        uses bgp-peer-state-af-l2vpn-config;
      }
    }

    container vpnv4 {
      config false;
      description
        "BGP Peer VPNv4 address family configuration";
      leaf enabled {
        type boolean;
        config false;
        description
          "Whether advertisement of Multiprotocol support to the peer is
           enabled for this address family.";
      }

      container unicast {
        config false;
        description
          "BGP Peer VPNv4 unicast address-family configuration";
        uses bgp-peer-state-af-v4v6-config;
      }
    }

    container vpnv6 {
      config false;
      description
        "BGP Peer VPNv6 address family configuration";
      leaf enabled {
        type boolean;
        config false;
        description
          "Whether advertisement of Multiprotocol support to the peer is
           enabled for this address family.";
      }

      container unicast {
        config false;
        description
          "BGP Peer VPNv6 unicast address-family configuration";
        uses bgp-peer-state-af-v4v6-config;
      }
    }
  }

  rpc bgp-peer-clear-counters {
    description
      "Clear the bgp counters associated with this peer";
    input {
      uses bgp-rm-config;

      uses peer-address-config;
    }
  }

  rpc bgp-peer-clear-flap-stats {
    description
      "Clear the bgp flap statistics counters associated with this peer";
    input {
      uses bgp-rm-config;

      uses peer-address-config;

      leaf flap-clear-map {
        type uint32;
        description
          "This field is an index to the table of BGP Route Maps. The
           number of times the route has flapped in all routes matching the
           Route Map are cleared. Entries in the Route Map may be set to permit
           (to cause a match) or to deny (to prevent a match).";
      }
    }
  }

  rpc bgp-rm-clear-stats {
    description
      "Reset the peak number of Adj-RIB-Out routes
       and clear the total number of memory allocations for prefixes,
       the total number of memory allocations for routes,
       the total number of memory frees for prefixes and
       the total number of memory frees for routes counters.";
    input {
      uses bgp-rm-config;
    }
  }

  notification session-established {
    description
      "BGP Peer Session has moved into Established state.";
    uses peer-notification-id;
  }

  notification session-backward {
    description
      "BGP Peer Session FSM state has undergone a backward transition.";
    uses peer-notification-id;

    leaf new-fsm-state {
      type bgp-peer-state;
      description
        "The BGP Peer's new FSM state";
    }

    leaf old-fsm-state {
      type bgp-peer-state;
      description
        "The BGP Peer's old FSM state";
    }

    leaf error-sent-received {
      type enumeration {
        enum "sent" {
          description
            "Error was caused by local node sending a Notification";
        }
        enum "received" {
          description
            "Error was caused by receiving a Notification from remote node";
        }
        enum "other" {
          description
            "Error was not due to a sent or received Notification";
        }
      }
      description
        "Whether the error was caused by sending or receiving a
         Notification message";
    }

    leaf error-code {
      type identityref {
        base bgp-error-code;
      }
      description
        "The error code reported in the Notification";
    }

    leaf error-subcode {
      type identityref {
        base bgp-error-subcode;
      }
      description
        "The error subcode reported in the Notification";
    }
  }

  notification peer-max-prefix {
    description
      "BGP Peer has sent more prefixes than the configured maximum.";
    uses peer-notification-id;
  }

  notification peer-max-prefix-clear {
    description
      "BGP Peer has no longer sent more prefixes than the configured
       maximum.";
    uses peer-notification-id;
  }

  notification peer-prefix-threshold {
    description
      "BGP Peer has sent more prefixes than the configured threshold.";
    uses peer-notification-id;
  }

  notification peer-prefix-threshold-clear {
    description
      "BGP Peer has no longer sent more prefixes than the configured
       threshold.";
    uses peer-notification-id;
  }

  notification peer-restart-helper-change {
    description
      "Restart helper status for a BGP Peer has changed.";
    leaf restart-status {
      type bgp-peer-restart-status;
      description
        "The current state of the peer's restart processing.";
    }

    uses peer-notification-id;
  }

  notification rib-size-warn {
    description
      "The total number of routes in BGP's Adj-RIBs-In has exceeded or
       dropped back below the configured limit.";
    leaf vrf-name {
      type meta:l3vpn-vrf-name;
      description
        "The name of the VRF associated with this BGP instance.  This leaf
         reports an empty string for the global VRF";
    }

    leaf over-limit {
      type boolean;
      description
        "Whether the total number of routes is over the limit or not.";
    }
  }
}
