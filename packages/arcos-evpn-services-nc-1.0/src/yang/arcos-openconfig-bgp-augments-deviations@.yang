module arcos-openconfig-bgp-augments-deviations {
  yang-version 1.1;
  namespace "http://yang.arrcus.com/arcos/openconfig/bgp/augments/deviations";
  prefix arc-oc-bgp-aug-dev;

  import openconfig-network-instance {
    prefix oc-ni;
  }

  import arcos-openconfig-bgp-augments {
    prefix arc-oc-bgp-aug;
  }

  import arcos-openconfig-bgp-types {
    prefix arc-oc-bgp-types;
  }

  deviation "/oc-ni:network-instances/oc-ni:network-instance" +
            "/oc-ni:protocols/oc-ni:protocol" +
            "/oc-ni:bgp" +
            "/oc-ni:global" +
            "/oc-ni:afi-safis/oc-ni:afi-safi" +
            "/arc-oc-bgp-aug:aggregate-addresses/arc-oc-bgp-aug:aggregate-address" +
            "/arc-oc-bgp-aug:config/arc-oc-bgp-aug:default-export-policy" {
    deviate not-supported;
    description "Not supported in this release";
  }

  deviation "/oc-ni:network-instances/oc-ni:network-instance" +
            "/oc-ni:protocols/oc-ni:protocol" +
            "/oc-ni:bgp" +
            "/oc-ni:global" +
            "/oc-ni:afi-safis/oc-ni:afi-safi" +
            "/arc-oc-bgp-aug:aggregate-addresses/arc-oc-bgp-aug:aggregate-address" +
            "/arc-oc-bgp-aug:config/arc-oc-bgp-aug:export-policy" {
    deviate add {
      max-elements 1;
    }
    description "Only support one policy in this release.";
  }

  deviation "/oc-ni:network-instances/oc-ni:network-instance" +
            "/oc-ni:protocols/oc-ni:protocol" +
            "/oc-ni:bgp" +
            "/oc-ni:global" +
            "/oc-ni:afi-safis/oc-ni:afi-safi" +
            "/oc-ni:ipv4-unicast" +
            "/arc-oc-bgp-aug:networks/arc-oc-bgp-aug:network" +
            "/arc-oc-bgp-aug:config/arc-oc-bgp-aug:default-export-policy" {
    deviate not-supported;
    description "Not supported in this release";
  }

  deviation "/oc-ni:network-instances/oc-ni:network-instance" +
            "/oc-ni:protocols/oc-ni:protocol" +
            "/oc-ni:bgp" +
            "/oc-ni:global" +
            "/oc-ni:afi-safis/oc-ni:afi-safi" +
            "/oc-ni:ipv4-unicast" +
            "/arc-oc-bgp-aug:networks/arc-oc-bgp-aug:network" +
            "/arc-oc-bgp-aug:config/arc-oc-bgp-aug:export-policy" {
    deviate add {
      max-elements 1;
    }
    description "Only support one policy in this release.";
  }

  deviation "/oc-ni:network-instances/oc-ni:network-instance" +
            "/oc-ni:protocols/oc-ni:protocol" +
            "/oc-ni:bgp" +
            "/oc-ni:global" +
            "/oc-ni:afi-safis/oc-ni:afi-safi" +
            "/oc-ni:ipv6-unicast" +
            "/arc-oc-bgp-aug:networks/arc-oc-bgp-aug:network" +
            "/arc-oc-bgp-aug:config/arc-oc-bgp-aug:default-export-policy" {
    deviate not-supported;
    description "Not supported in this release";
  }

  deviation "/oc-ni:network-instances/oc-ni:network-instance" +
            "/oc-ni:protocols/oc-ni:protocol" +
            "/oc-ni:bgp" +
            "/oc-ni:global" +
            "/oc-ni:afi-safis/oc-ni:afi-safi" +
            "/oc-ni:ipv6-unicast" +
            "/arc-oc-bgp-aug:networks/arc-oc-bgp-aug:network" +
            "/arc-oc-bgp-aug:config/arc-oc-bgp-aug:export-policy" {
    deviate add {
      max-elements 1;
    }
    description "Only support one policy in this release.";
  }

  deviation "/oc-ni:network-instances/oc-ni:network-instance" +
            "/oc-ni:protocols/oc-ni:protocol" +
            "/oc-ni:bgp" +
            "/oc-ni:neighbors/oc-ni:neighbor" +
            "/oc-ni:config/arc-oc-bgp-aug:ttl-security-hops" {
    deviate add {
      must ". > 0" {
        error-message "TTL cannot be set to 0";
      }
    }
  }

  deviation "/oc-ni:network-instances/oc-ni:network-instance" +
            "/oc-ni:protocols/oc-ni:protocol" +
            "/oc-ni:bgp" +
            "/oc-ni:neighbors/oc-ni:neighbor" +
            "/arc-oc-bgp-aug:ebgp-local-as/arc-oc-bgp-aug:config" {
    deviate add {
      must "boolean(arc-oc-bgp-aug:local-as) or " +
           "(boolean(arc-oc-bgp-aug:no-prepend) != 'true' and" +
           " boolean(arc-oc-bgp-aug:replace-as) != 'true' and" +
           " boolean(arc-oc-bgp-aug:dual-as) != 'true')" {
        error-message "'local-as' must be configured if 'no-prepend',
                      'replace-as' and/or 'dual-as' is set.";
      }
    }

    deviate add {
      must "boolean(arc-oc-bgp-aug:local-as) != 'true' or " +
           "(arc-oc-bgp-aug:local-as !=" +
           "/oc-ni:network-instances/oc-ni:network-instance" +
           "/oc-ni:protocols/oc-ni:protocol" +
           "/oc-ni:bgp/oc-ni:global/oc-ni:config/oc-ni:as)" {
        error-message "'local-as' must not be the same as global AS number.";
      }
    }
  }
  
  deviation "/oc-ni:network-instances/oc-ni:network-instance" +
            "/oc-ni:protocols/oc-ni:protocol" +
            "/oc-ni:bgp" +
            "/oc-ni:peer-groups/oc-ni:peer-group" +
            "/arc-oc-bgp-aug:ebgp-local-as/arc-oc-bgp-aug:config" {
    deviate add {
      must "boolean(arc-oc-bgp-aug:local-as) or " +
           "(boolean(arc-oc-bgp-aug:no-prepend) != 'true' and" +
           " boolean(arc-oc-bgp-aug:replace-as) != 'true' and" +
           " boolean(arc-oc-bgp-aug:dual-as) != 'true')" {
        error-message "'local-as' must be configured if 'no-prepend',
                      'replace-as' and/or 'dual-as' is set.";
      }
    }

    deviate add {
      must "boolean(arc-oc-bgp-aug:local-as) != 'true' or " +
           "(arc-oc-bgp-aug:local-as !=" +
           "/oc-ni:network-instances/oc-ni:network-instance" +
           "/oc-ni:protocols/oc-ni:protocol" +
           "/oc-ni:bgp/oc-ni:global/oc-ni:config/oc-ni:as)" {
        error-message "'local-as' must not be the same as global AS number.";
      }
    }
  }

  deviation "/oc-ni:network-instances/oc-ni:network-instance" +
            "/oc-ni:protocols/oc-ni:protocol" +
            "/oc-ni:bgp" +
            "/arc-oc-bgp-aug:all-neighbors/arc-oc-bgp-aug:all-neighbor" +
            "/arc-oc-bgp-aug:graceful-restart/arc-oc-bgp-aug:state/arc-oc-bgp-aug:stale-routes-time" {
    deviate replace {
      type uint16;
    }
    description "Neighbor graceful-restart stale-time type changed";
  }

  deviation "/oc-ni:network-instances/oc-ni:network-instance" +
            "/oc-ni:protocols/oc-ni:protocol" +
            "/oc-ni:bgp" +
            "/arc-oc-bgp-aug:all-neighbors/arc-oc-bgp-aug:all-neighbor" +
            "/arc-oc-bgp-aug:route-reflector/arc-oc-bgp-aug:state" +
            "/arc-oc-bgp-aug:route-reflector-cluster-id" {
    deviate not-supported;
    description "Not supported in this release";
  }

  deviation "/oc-ni:network-instances/oc-ni:network-instance" +
            "/oc-ni:protocols/oc-ni:protocol" +
            "/oc-ni:bgp" +
            "/arc-oc-bgp-aug:all-neighbors/arc-oc-bgp-aug:all-neighbor" +
            "/arc-oc-bgp-aug:state/arc-oc-bgp-aug:route-flap-damping" {
    deviate not-supported;
    description "Not supported in this release";
  }

  deviation "/oc-ni:network-instances/oc-ni:network-instance" +
            "/oc-ni:protocols/oc-ni:protocol" +
            "/oc-ni:bgp" +
            "/arc-oc-bgp-aug:all-neighbors/arc-oc-bgp-aug:all-neighbor" +
            "/arc-oc-bgp-aug:afi-safis/arc-oc-bgp-aug:afi-safi/arc-oc-bgp-aug:state" +
            "/arc-oc-bgp-aug:prefixes/arc-oc-bgp-aug:installed" {
    deviate not-supported;
    description "Not supported in this release";
  }

  deviation "/oc-ni:network-instances/oc-ni:network-instance" +
            "/oc-ni:protocols/oc-ni:protocol" +
            "/oc-ni:bgp" +
            "/arc-oc-bgp-aug:all-neighbors/arc-oc-bgp-aug:all-neighbor/arc-oc-bgp-aug:state" +
            "/arc-oc-bgp-aug:session-state" {
    deviate replace {
      type enumeration {
        enum IDLE {
          description
            "neighbor is down, and in the Idle state of the
            FSM";
        }
        enum CONNECT {
          description
            "neighbor is down, and the session is waiting for
            the underlying transport session to be established";
        }
        enum ACTIVE {
          description
            "neighbor is down, and the local system is awaiting
            a conncetion from the remote peer";
        }
        enum OPENSENT {
          description
            "neighbor is in the process of being established.
            The local system has sent an Open message";
        }
        enum OPENCONFIRM {
          description
            "neighbor is in the process of being established.
            The local system is awaiting a Notification or
            Keepalive message";
        }
        enum ESTABLISHED {
          description
            "neighbor is up - the BGP session with the peer is
            established";
        }
        enum CLOSING {
          description
            "neighbor is down - the BGP session with the peer is
            is in Closing state trying to free up resources";
        }
        enum DELETING {
          description
            "neighbor is down - the BGP session with the peer is
            is in Deleting state trying to delete session";
        }
        enum INCOMPLETE {
          description
            "neighbor is down - the BGP session with the peer is
            is in Incomplete mandatory config state";
        }
        enum SHUTDOWN {
          description
            "neighbor is down - the BGP session with the peer is
            in Shutdown state";
        }
      }
    }
    description "BGP session state with updated types";
  }
}
