module arcos-aft-types {
  yang-version 1.1;
  namespace "http://yang.arrcus.com/arcos/aft/types";
  prefix arc-aft-types;

  typedef dpal-nexthop-type {
    type enumeration {
      enum GLEAN {
        value 1;
      }
      enum DROP {
        value 2;
      }
      enum LOCAL {
        value 3;
      }
      enum CONNECTED {
        value 4;
      }
      enum MPLS_CONNECTED {
        value 5;
      }
      enum PUNT_TO_CPU {
        value 6;
      }
      enum VXLAN {
        value 7;
      }
    }
  }
}
