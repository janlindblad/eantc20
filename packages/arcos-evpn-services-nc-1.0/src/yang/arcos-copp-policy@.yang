module arcos-copp-policy {
  yang-version 1.1;
  namespace "http://yang.arrcus.com/arcos/copp/policy";
  prefix arc-copp-pol;

  import arcos-policy {
    prefix arc-pol;
  }
  import arcos-policy-action {
    prefix arc-pol-actn;
  }
  import arcos-policy-action-types {
    prefix arc-pol-actn-types;
  }
  import arcos-copp {
    prefix arc-copp;
  }
  import arcos-copp-classifier {
    prefix arc-copp-cfr;
  }

  organization
    "Arrcus, Inc.";
  contact
    "Arrcus, Inc.
     Customer Service
     Postal: 2077 Gateway Place
     San Jose, CA 95110
     Tel: +1 1XXX XXX-XXXX
     E-mail: xxx@arrcus.com";
  description
    "YANG data-model for COPP policy definitions.";

  /*
   * Following augment list is what copp policy container supports
   */

  augment "/arc-copp:copp/policies/policy/classifiers/classifier/actions"
        + "/action" {
    uses arc-pol-actn:mark-top {
      when "./type = 'arc-pol-actn-types:MARK'";
    }
  }

  augment "/arc-copp:copp/policies/policy/classifiers/classifier/actions"
        + "/action/mark" {
    uses arc-pol-actn:mark-config;
  }

  augment "/arc-copp:copp/policies/policy/classifiers/classifier/actions"
        + "/action/mark/config" {
    uses arc-pol-actn:mark-local-tc-top;
  }

  augment "/arc-copp:copp/policies/policy/classifiers/classifier/actions"
        + "/action/mark/state" {
    uses arc-pol-actn:mark-local-tc-top;
  }

  augment "/arc-copp:copp/policies/policy/classifiers/classifier/actions"
        + "/action" {
    uses arc-pol-actn:police-top {
      when "./type = 'arc-pol-actn-types:POLICE'";
    }
  }

  augment "/arc-copp:copp/policies/policy/classifiers/classifier/actions"
        + "/action/police" {
    uses arc-pol-actn:police-config {
      refine "config/committed/rate/value" {
        mandatory true;
        description
          "rate value in the unit of pps";
      }
      refine "config/committed/burst/value" {
        description
          "burst value in the unit of packets";
      }
      refine "config/conform/action-type" {
        must "current() = 'arc-pol-actn-types:TRANSMIT'" {
          error-message "action type not supported for copp policer";
        }
      }
      refine "config/exceed/action-type" {
        must "current() = 'arc-pol-actn-types:DROP'" {
          error-message "action type not supported for copp policer";
        }
      }
      refine "config/violate/action-type" {
        must "current() = 'arc-pol-actn-types:DROP'" {
          error-message "action type not supported for copp policer";
        }
      }
    }
  }

  grouping copp-policy-top {
    uses arc-pol:policies-top {
      refine "policies/policy/classifiers/classifier" {
        min-elements 1;
      }
      refine "policies/policy/classifiers/classifier/actions/action/type" {
        must "current() = 'arc-pol-actn-types:MARK' or "
           + "current() = 'arc-pol-actn-types:DROP' or "
           + "current() = 'arc-pol-actn-types:POLICE'" {
          error-message "action type not supported for copp";
        }
      }
    }
  }

  augment "/arc-copp:copp" {
    uses copp-policy-top;
  }
}
