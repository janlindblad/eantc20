module arcos-openconfig-if-ethernet-deviations {
  yang-version 1.1;
  namespace "http://yang.arrcus.com/arcos/openconfig/interfaces/ethernet/deviations";
  prefix arc-oc-eth-dev;

  import openconfig-if-ethernet {
    prefix oc-eth;
  }
  import openconfig-interfaces {
    prefix oc-if;
  }

  deviation "/oc-if:interfaces/oc-if:interface/oc-eth:ethernet" +
            "/oc-eth:config/oc-eth:mac-address"  {
    deviate not-supported;
    description "Not supported in this release";
  }
  deviation "/oc-if:interfaces/oc-if:interface/oc-eth:ethernet" +
            "/oc-eth:config/oc-eth:auto-negotiate"  {
    deviate not-supported;
    description "Not supported in this release";
  }
  deviation "/oc-if:interfaces/oc-if:interface/oc-eth:ethernet" +
            "/oc-eth:config/oc-eth:duplex-mode"  {
    deviate not-supported;
    description "Not supported in this release";
  }
  deviation "/oc-if:interfaces/oc-if:interface/oc-eth:ethernet" +
            "/oc-eth:config/oc-eth:enable-flow-control"  {
    deviate not-supported;
    description "Not supported in this release";
  }
}
