module arcos-openconfig-routing-policy-augments {
  yang-version 1.1;
  namespace "http://yang.arrcus.com/arcos/openconfig/routing-policy/augments";
  prefix arc-oc-rpol-aug;

  import openconfig-routing-policy {
    prefix oc-rpol;
  }

  grouping stmt-top {
    leaf auto-seq-num {
      type uint64;
      description
        "Auto generated sequence number";
    }
  }

  augment "/oc-rpol:routing-policy/oc-rpol:policy-definitions" +
          "/oc-rpol:policy-definition/oc-rpol:statements" +
          "/oc-rpol:statement/oc-rpol:state" {
    uses stmt-top;
  }

  grouping stmt-actions-top {
    leaf next-policy {
      type empty;
      description
        "skip to the next policy module";
    }
  }

  augment "/oc-rpol:routing-policy/oc-rpol:policy-definitions" +
          "/oc-rpol:policy-definition/oc-rpol:statements/oc-rpol:statement" +
          "/oc-rpol:actions/oc-rpol:config" {
    description "Policy action for skipping to next policy module";

    uses stmt-actions-top;
  }

  augment "/oc-rpol:routing-policy/oc-rpol:policy-definitions" +
          "/oc-rpol:policy-definition/oc-rpol:statements/oc-rpol:statement" +
          "/oc-rpol:actions/oc-rpol:state" {
    description "Policy action for skipping to next policy module";

    uses stmt-actions-top;
  }
}
