module arcos-classifier-filter-types {
  yang-version 1.1;
  namespace "http://yang.arrcus.com/arcos/classifier/filter/types";
  prefix arc-cfr-fltr-types;

  identity LOGICAL_OPERATION_TYPE {
    description
      "Across the filter logical operation types: match-any, match-all";
  }

  identity MATCH_ANY_FILTER {
    base LOGICAL_OPERATION_TYPE;
    description
      "Logical OR operation across filters in a given classifier";
  }

  identity MATCH_ALL_FILTER {
    base LOGICAL_OPERATION_TYPE;
    description
      "Logical AND operation across filters in a given classifier";
  }

  identity FILTER_TYPE {
    description
      "This is an identity of base filter-type";
  }

  identity COS {
    base FILTER_TYPE;
    description
      "Layer-2 802.1p Class of Service filter-type";
  }

  identity DSCP {
    base FILTER_TYPE;
    description
      "Layer-3 IP Differentiated Service filter-type";
  }

  identity LOCAL_TC {
    base FILTER_TYPE;
    description
      "Local Priority Traffic Class filter-type";
  }

  identity MPLS_TC {
    base FILTER_TYPE;
    description
      "MPLS Traffic Class code-point filter-type";
  }

  identity ACL_IPV4 {
    base FILTER_TYPE;
    description
      "V4 type Access Control List filter-type";
  }

  identity ACL_IPV6 {
    base FILTER_TYPE;
    description
      "V6 type Access Control List filter-type";
  }

  identity ACL_L2 {
    base FILTER_TYPE;
    description
      "Layer2 type Access Control List filter-type";
  }

  identity EXCEPTION {
    base FILTER_TYPE;
    description
      "A filter-type that captures certain exceptions";
  }

  identity EXCEPTION_TYPE {
    description
      "This is an identity of base exception-type";
  }

  identity L3DESTMISS {
    base EXCEPTION_TYPE;
    description "An exception-type that captures packets that fail "
              + "ip destination lookup in forwarding";
  }

  identity SELFIP {
    base EXCEPTION_TYPE;
    description "An exception-type that captures packets that match "
              + "router address";
  }

  identity GLEAN {
    base EXCEPTION_TYPE;
    description "An exception-type that captures packets which does "
              + "not have dest mac resolved";
  }
}
