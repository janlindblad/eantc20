module arcos-openconfig-platform-deviations {
  yang-version 1.1;
  namespace "http://yang.arrcus.com/arcos/openconfig/platform/deviations";
  prefix arc-oc-platform-dev;

  import openconfig-platform {
    prefix oc-platform;
  }

  organization
    "Arrcus, Inc.";

  contact
    "Email: eng@arrcus.com";

  description
    "This module defines deviation statements for Arrcus
     implemention of the openconfig platform module.";

  revision 2018-08-14 {
    description "ArcOS release 2.2.1";
  }

  revision 2017-07-10 {
    description
      "Initial Revision
       * xxx not supported.
      ";

    reference
      "RFC 6020: YANG - A Data Modeling Language for the
       Network Configuration Protocol (NETCONF)";
  }

  deviation "/oc-platform:components/oc-platform:component/oc-platform:state/" + 
            "oc-platform:type" {
    deviate not-supported;
    description "Not supported in this release";
  }
  deviation "/oc-platform:components/oc-platform:component/oc-platform:state/" + 
            "oc-platform:name" {
    deviate not-supported;
    description "Not supported in this release";
  }
  deviation "/oc-platform:components/oc-platform:component/oc-platform:state/" + 
            "oc-platform:temperature" {
    deviate not-supported;
    description "Not supported in this release";
  }
  deviation "/oc-platform:components/oc-platform:component/oc-platform:properties/oc-platform:property/oc-platform:state/" +
            "oc-platform:configurable" {
    deviate not-supported;
    description "Not supported in this release";
  }
  deviation "/oc-platform:components/oc-platform:component/oc-platform:properties/oc-platform:property/oc-platform:state/" +
            "oc-platform:name" {
    deviate not-supported;
    description "Not supported in this release";
  }
  deviation "/oc-platform:components/oc-platform:component/oc-platform:state/" + 
            "oc-platform:mfg-name" {
    deviate not-supported;
    description "Not supported in this release";
  }
  deviation "/oc-platform:components/oc-platform:component/oc-platform:state/" + 
            "oc-platform:version" {
    deviate not-supported;
    description "Not supported in this release";
  }
  deviation "/oc-platform:components/oc-platform:component/oc-platform:state/" + 
            "oc-platform:serial-no" {
    deviate not-supported;
    description "Not supported in this release";
  }
  deviation "/oc-platform:components/oc-platform:component/oc-platform:state/" + 
            "oc-platform:part-no" {
    deviate not-supported;
    description "Not supported in this release";
  }
  deviation "/oc-platform:components/oc-platform:component/oc-platform:properties/oc-platform:property/oc-platform:config" {
    deviate not-supported;
    description "Not supported in this release";
  }
  deviation "/oc-platform:components/oc-platform:component/oc-platform:config" {
    deviate not-supported;
    description "Not supported in this release";
  }
  deviation "/oc-platform:components/oc-platform:component/oc-platform:subcomponents/oc-platform:subcomponent/oc-platform:config" {
    deviate not-supported;
    description "Not supported in this release";
  }
  deviation "/oc-platform:components/oc-platform:component/oc-platform:name" {
    deviate replace {
        type string;
    }
  }
  deviation "/oc-platform:components/oc-platform:component/oc-platform:properties/oc-platform:property/oc-platform:name" {
    deviate replace {
        type string;
    }
  }
  deviation "/oc-platform:components/oc-platform:component/oc-platform:subcomponents/oc-platform:subcomponent/oc-platform:name" {
    deviate replace {
        type string;
    }
  }
  deviation "/oc-platform:components/oc-platform:component/oc-platform:subcomponents/oc-platform:subcomponent/oc-platform:config/oc-platform:name" {
    deviate replace {
        type string;
    }
  }
  deviation "/oc-platform:components/oc-platform:component/oc-platform:subcomponents/oc-platform:subcomponent/oc-platform:state/oc-platform:name" {
    deviate replace {
        type string;
    }
  }
  deviation "/oc-platform:components/oc-platform:component/oc-platform:subcomponents/oc-platform:subcomponent/oc-platform:name" {
    deviate replace {
        config false;
    }
  }
  deviation "/oc-platform:components/oc-platform:component/oc-platform:subcomponents/oc-platform:subcomponent" {
    deviate replace {
        config false;
    }
  }
  deviation "/oc-platform:components/oc-platform:component/oc-platform:subcomponents" {
    deviate replace {
        config false;
    }
  }
  deviation "/oc-platform:components/oc-platform:component/oc-platform:properties/oc-platform:property/oc-platform:name" {
    deviate replace {
        config false;
    }
  }
  deviation "/oc-platform:components/oc-platform:component/oc-platform:properties/oc-platform:property" {
    deviate replace {
        config false;
    }
  }
  deviation "/oc-platform:components/oc-platform:component/oc-platform:properties" {
    deviate replace {
        config false;
    }
  }
  deviation "/oc-platform:components/oc-platform:component/oc-platform:name" {
    deviate replace {
        config false;
    }
  }
  deviation "/oc-platform:components/oc-platform:component" {
    deviate replace {
        config false;
    }
  }
  deviation "/oc-platform:components" {
    deviate replace {
        config false;
    }
  }
}
