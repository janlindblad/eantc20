submodule arcos-hardware-platform {
  yang-version 1.1;

  belongs-to arcos-hardware {
    prefix arc-hw;
  }

  import arcos-platform {
    prefix arc-platform;
  }

  import arcos-hardware-platform-xgs {
    prefix arc-hw-platform-xgs;
  }

  import arcos-hardware-platform-types {
    prefix arc-hw-platform-types;
  }

  import arcos-features {
    prefix arc-features;
  }

  typedef hw-pltf-fwd-profile {
    type enumeration {
      enum P1 {
        value 1;
        description
          "Profile 1";
      }
      enum P2 {
        description
          "Profile 2";
      }
      enum P3 {
        description
          "Profile 3";
      }
      enum P4 {
        description
          "Profile 4";
      }
      enum P5 {
        description
          "Profile 5";
      }
    }
  }

  grouping hardware-platform {
    description "Platform specific configuration";

    container config {
      leaf forwarding-mode {
        description "Configuration of switch forwarding mode";
        when "/arc-platform:platform/arc-platform:asic != 'arc-platform:BROADCOM_HELIX4'";

        type identityref {
          base arc-hw-platform-types:SWITCH_FORWARDING_MODE;
        }

        must "current() = 'arc-hw-platform-types:STORE_AND_FORWARD' or " +
             "/arc-platform:platform/arc-platform:family = 'arc-platform:BROADCOM_XGS'" {
          error-message "Cut through mode not supported on this platform";
        }
      }

      container forwarding-scale {
        leaf fwd-profile {
          type hw-pltf-fwd-profile;
          description
            "HW Forwarding Scale profile";
        }
        leaf overlay-nexthop-profile {
          when "/arc-features:features/arc-features:feature[arc-features:name='arc-features:ARCOS_RIOT']" +
               "/arc-features:supported = 'true'" {
            description
              "HW overlay nexthop profile";
          }
          type hw-pltf-fwd-profile;
        }
      }
    }

    container state {
      config false;

      leaf forwarding-mode {
        description "Configuration of switch forwarding mode";
        type identityref {
          base arc-hw-platform-types:SWITCH_FORWARDING_MODE;
        }
      }
    }

    uses arc-hw-platform-xgs:xgs-queue-profile {
      when "(/arc-platform:platform/arc-platform:asic = 'arc-platform:BROADCOM_TRIDENT3') or " +
           "(/arc-platform:platform/arc-platform:asic = 'arc-platform:BROADCOM_TOMAHAWK')";
      description "Device specific queue profile configuration";
    }

    uses arc-hw-platform-xgs:xgs-load-balancing {
      when "/arc-platform:platform/arc-platform:asic = 'arc-platform:BROADCOM_TRIDENT3'";
      description "Device specific load balancing configuration";
    }
  }
}
