module arcos-policy-action {
  yang-version 1.1;
  namespace "http://yang.arrcus.com/arcos/policy/action";
  prefix arc-pol-actn;

  import arcos-policy-action-types {
    prefix arc-pol-actn-types;
  }
  import ietf-inet-types {
    prefix inet;
  }

  grouping mark-cos-top {
    description
      "Grouping for Layer-2 802.1p Class Of Service marking";
    leaf cos {
      type uint8 {
        range "0..7";
      }
      description
        "Layer-2 802.1p Class Of Service marking value";
    }
  }

  grouping mark-dscp-top {
    description
      "Grouping for Layer-3 IP Diffserv Code-Point marking";
    leaf dscp {
      type inet:dscp;
      description
        "Layer-3 IP Diffserv Code-Point marking value";
    }
  }

  grouping mark-local-tc-top {
    description
      "Grouping for local priority Traffic Class marking";
    leaf local-tc {
      type uint8 {
        range "0..7";
      }
      description
        "Local priority Traffic Class marking value";
    }
  }

  grouping mark-mpls-tc-top {
    description
      "Grouping for MPLS Traffic Class marking";
    leaf mpls-tc {
      type uint8 {
        range "0..7";
      }
      description
        "MPLS Traffic Class marking value";
    }
  }

  grouping mark-config {
    description
      "mark configuration parameters";
    container config {
      description
        "Configuration data";
    }
  }

  grouping mark-state {
    description
      "mark state information parameters";
    container state {
      config false;
      description
        "State Information.";
    }
  }

  grouping mark-top {
    description
      "Top level container for all types of marking configuration";
    container mark {
      description
        "Container holding grouping of different marking types";
      uses mark-state;
    }
  }

  grouping traffic-rate {
    description
      "Generic rate grouping, to be used consistently by any policy
       action that requires provisioning of traffic rate";
    container rate {
      description
        "traffic rate";
      leaf value {
        type uint32 {
          range "1..4294967295";
        }
        description
          "rate-value";
      }
      leaf unit {
        type enumeration {
          enum bps;
          enum kbps;
          enum mbps;
          enum gbps;
        }
        default "kbps";
        description
          "rate-unit";
      }
    }
  }

  grouping traffic-burst {
    description
      "Generic burst grouping, to be used consistently by any policy
       action that requires provisioning of a burst";
    container burst {
      description
        "traffic burst";
      leaf value {
        type uint32 {
          range "1..4294967295";
        }
        description
          "burst-value";
      }
      leaf unit {
        type enumeration {
          enum bytes;
          enum kbytes;
        }
        default "kbytes";
        description
          "burst-unit";
      }
    }
  }

  grouping police-stats-top {
    description
      "Grouping for police related statistics";
    leaf conform-packets {
      type uint64;
      description
        "Number of packets conformed to committed rate";
    }
    leaf conform-bytes {
      type uint64;
      description
        "Number of bytes conformed to committed rate";
    }
    leaf exceed-packets {
      type uint64;
      description
        "Number of packets exceeded committed rate but
         conformed to peak rate";
    }
    leaf exceed-bytes {
      type uint64;
      description
        "Number of bytes exceeded committed rate but
         conformed to peak rate";
    }
    leaf violate-packets {
      type uint64;
      description
        "Number of packets violated committed/peak rate";
    }
    leaf violate-bytes {
      type uint64;
      description
        "Number of bytes violated committed/peak rate";
    }
    leaf conform-rate {
      type uint64;
      description
        "Normalized traffic-rate conforming to committed rate";
    }
    leaf exceed-rate {
      type uint64;
      description
        "Normalized traffic-rate exceeding committed rate but
         conforming to peak rate";
    }
    leaf violate-rate {
      type uint64;
      description
        "Normalized traffic-rate violating committed/peak rate";
    }
  }

  grouping police-action-attributes {
    description
      "police action attributes like action type";
    leaf action-type {
      type identityref {
        base arc-pol-actn-types:ACTION_TYPE;
      }
      description
        "police action type";
    }
  }

  grouping police-parameters {
    description
      "police parameters";
    container committed {
      description
        "Container for policer's committed rate and burst";
      uses traffic-rate;
      uses traffic-burst;
    }
    container peak {
      description
        "Container for policer's peak rate and burst";
      uses traffic-rate;
      uses traffic-burst;
    }
    container conform {
      description
        "action for packets conforming to committed rate";
      uses police-action-attributes;
    }
    container exceed {
      description
        "action for packets exceeding to committed rate
         but conforming peak rate";
      uses police-action-attributes;
    }
    container violate {
      description
        "action for packets violating committed/peak rate";
      uses police-action-attributes;
    }
  }

  grouping police-config {
    description
      "police configuration parameters";
    container config {
      description
        "Configuration data";
      uses police-parameters;
    }
  }

  grouping police-state {
    description
      "police state information parameters";
    container state {
      config false;
      description
        "State Information.";
      uses police-parameters;
    }
  }

  grouping police-top {
    description
      "Top level container for fields in police configuration";
    container police {
      description
        "police related fields";
      uses police-state;
    }
  }
}
