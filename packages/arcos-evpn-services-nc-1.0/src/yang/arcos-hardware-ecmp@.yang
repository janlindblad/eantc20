submodule arcos-hardware-ecmp {
  yang-version 1.1;

  belongs-to arcos-hardware {
    prefix arc-hw;
  }

  import arcos-platform {
    prefix arc-platform;
  }

  grouping hardware-ecmp {
    description "Controls for tuning ECMP hashing behavior";
    leaf hash-seed-value {
      type uint32;
      description "ECMP hash seed value";
      must "current() >= 0 and current() <= 65535 or" +
           " /arc-platform:platform/arc-platform:family = 'arc-platform:BROADCOM_XGS'" {
        error-message "ECMP hash seed value should be in the range of 0..65535, for Broadcom DNX devices";
      }
    }

    leaf hash-offset {
      type uint8;
      description "ECMP Hash offset value";
      must "current() >= 0 and current() <= 15 or" +
           " /arc-platform:platform/arc-platform:family = 'arc-platform:BROADCOM_XGS'" {
        error-message "ECMP hash offset should be in the range of 0..15, for Broadcom DNX devices";
      }
      must "current() >= 0 and current() <= 199 or" +
           " /arc-platform:platform/arc-platform:family = 'arc-platform:BROADCOM_DNX'" {
        error-message "ECMP hash offset should be in the range of 0..199, for Broadcom XGS devices";
      }
    }

    leaf hash-function-polynomial {
      type uint8;
      description "ECMP hash polynomial";
      must "current() >= 1 and current() <= 13 or" +
           " /arc-platform:platform/arc-platform:family = 'arc-platform:BROADCOM_DNX'" {
        error-message "ECMP hash polynomial should be in the range of 1..13, for Broadcom XGS devices";
      }
      must "current() >= 22 and current() <= 27 or" +
           " /arc-platform:platform/arc-platform:family = 'arc-platform:BROADCOM_XGS'" {
        error-message "ECMP hash polynomial should be in the range of 22..27, for Broadcom DNX devices";
      }
    }

    container hash-fields-ipv4 {
      description "ECMP IPv4 header fields";
      leaf src-ip {
        type boolean;
        default true;
        description "Use source ip address for hash computation";
      }
      leaf dst-ip {
        type boolean;
        default true;
        description "Use destination ip address for hash computation";
      }
      leaf src-port {
        type boolean;
        default true;
        description "Use source L4 port for hash computation";
      }
      leaf dst-port {
        type boolean;
        default true;
        description "Use destination L4 port for hash computation";
      }
      leaf proto {
        type boolean;
        default true;
        description "Use IP protocol for hash computation";
      }
    }

    container hash-fields-ipv6 {
      description "ECMP IPv6 header fields";
        leaf src-ip {
          type boolean;
          default true;
          description "Use source ip address for hash computation";
        }
        leaf dst-ip {
          type boolean;
          default true;
          description "Use destination ip address for hash computation";
        }
        leaf src-port {
          type boolean;
          default true;
          description "Use source L4 port for hash computation";
        }
        leaf dst-port {
          type boolean;
          default true;
          description "Use destination L4 port for hash computation";
        }
    }

    container hash-fields-l2 {
      description "ECMP L2 header fields";
      leaf vlan {
        type boolean;
        default true;
        description "Use vlan ID for hash computation";
      }
      leaf eth-type {
        type boolean;
        default true;
        description "Use ethertype for hash computation";
      }
      leaf src-mac {
        type boolean;
        default true;
        description "Use source MAC address for hash computation";
      }
      leaf dst-mac {
        type boolean;
        default true;
        description "Use destination MAC address for hash computation";
      }
    }
  }
}
