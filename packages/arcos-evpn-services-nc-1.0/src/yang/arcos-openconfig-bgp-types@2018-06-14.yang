module arcos-openconfig-bgp-types {
  yang-version 1.1;
  namespace "http://yang.arrcus.com/arcos/openconfig/bgp/types";

  prefix arc-oc-bgp-types;

  import openconfig-types {
    prefix oc-types;
  }

  organization
    "Arrcus, Inc.";

  contact
    "Arrcus, Inc.
     Customer Service
     Postal: 2077 Gateway Place
     San Jose, CA 95110
     Tel: +1 1XXX XXX-XXXX
     E-mail: xxx@arrcus.com";

  description
    "This module defines augmentation for Arrcus
     implemention of the openconfig bgp-policy module.";

  revision 2018-06-14 {
    description
      "Initial Revision
       * Add bgp large community
      ";

    reference
      "RFC 6020: YANG - A Data Modeling Language for the
       Network Configuration Protocol (NETCONF)";
  }

  identity ADD_PATHS_OPTIONS {
    description
      "Base identity for add-paths options";
  }

  identity ALL {
    base ADD_PATHS_OPTIONS;
    description
      "Advertise all paths";
  }

  identity SECOND_BEST {
    base ADD_PATHS_OPTIONS;
    description
      "Advertise second-best path - may be a multipath";
  }

  identity BACKUP {
    base ADD_PATHS_OPTIONS;
    description
      "Advertise backup path - excluding multipaths";
  }

  identity MULTIPATHS {
    base ADD_PATHS_OPTIONS;
    description
      "Advertise paths that are selected by multipath selection algorithm";
  }

  typedef bgp-std-large-community-type {
    /*
     * rfc8092#section-5
     * (4 byte global):(4 byte local 1):(4 byte local 2)
     */
    type string {
      pattern '^(429496729[0-5]|42949672[0-8][0-9]|4294967[0-1][0-9]{2}'   +
              '|429496[0-6][0-9]{3}|42949[0-5][0-9]{4}|4294[0-8][0-9]{5}|' +
              '429[0-3][0-9]{6}|4[0-1][0-9]{7}|[1-3][0-9]{9}|'             +
              '[1-9][0-9]{1,8}|[0-9]):'                                    +
              '(429496729[0-5]|42949672[0-8][0-9]|4294967[0-1][0-9]{2}'    +
              '|429496[0-6][0-9]{3}|42949[0-5][0-9]{4}|4294[0-8][0-9]{5}|' +
              '429[0-3][0-9]{6}|4[0-1][0-9]{7}|[1-3][0-9]{9}|'             +
              '[1-9][0-9]{1,8}|[0-9]):'                                    +
              '(429496729[0-5]|42949672[0-8][0-9]|4294967[0-1][0-9]{2}'    +
              '|429496[0-6][0-9]{3}|42949[0-5][0-9]{4}|4294[0-8][0-9]{5}|' +
              '429[0-3][0-9]{6}|4[0-1][0-9]{7}|[1-3][0-9]{9}|'             +
              '[1-9][0-9]{1,8}|[0-9])$';
    }
    description
      "Type definition for standard large community attribute represented as
      string of the form X:Y:Z where
      X = Global Administrator:  A four-octet namespace identifier.
      Y = Local Data Part 1:  A four-octet operator-defined value.
      Z = Local Data Part 2:  A four-octet operator-defined value.";
    reference "RFC 8092 - BGP Large Communities Attribute";
  }

  typedef bgp-large-community-regexp-type {
    type oc-types:std-regexp;
    description
      "Type definition for communities specified as regular
      expression patterns";
  }

  typedef bgp-large-community-type {
    /*
     * rfc8092#section-5
     * (4 byte global):(4 byte local 1):(4 byte local 2)
     */
    type string {
      pattern '^(429496729[0-5]|42949672[0-8][0-9]|4294967[0-1][0-9]{2}'   +
              '|429496[0-6][0-9]{3}|42949[0-5][0-9]{4}|4294[0-8][0-9]{5}|' +
              '429[0-3][0-9]{6}|4[0-1][0-9]{7}|[1-3][0-9]{9}|'             +
              '[1-9][0-9]{1,8}|[0-9]):'                                    +
              '(429496729[0-5]|42949672[0-8][0-9]|4294967[0-1][0-9]{2}'    +
              '|429496[0-6][0-9]{3}|42949[0-5][0-9]{4}|4294[0-8][0-9]{5}|' +
              '429[0-3][0-9]{6}|4[0-1][0-9]{7}|[1-3][0-9]{9}|'             +
              '[1-9][0-9]{1,8}|[0-9]):'                                    +
              '(429496729[0-5]|42949672[0-8][0-9]|4294967[0-1][0-9]{2}'    +
              '|429496[0-6][0-9]{3}|42949[0-5][0-9]{4}|4294[0-8][0-9]{5}|' +
              '429[0-3][0-9]{6}|4[0-1][0-9]{7}|[1-3][0-9]{9}|'             +
              '[1-9][0-9]{1,8}|[0-9])$';
    }
    description
      "Type definition for standard large community attribute represented as
      string of the form X:Y:Z where
      X = Global Administrator:  A four-octet namespace identifier.
      Y = Local Data Part 1:  A four-octet operator-defined value.
      Z = Local Data Part 2:  A four-octet operator-defined value.";
    reference "RFC 8092 - BGP Large Communities Attribute";
  }

  typedef session-state-type {
    type enumeration {
      enum IDLE {
        description
          "neighbor is down, and in the Idle state of the
          FSM";
      }
      enum CONNECT {
        description
          "neighbor is down, and the session is waiting for
          the underlying transport session to be established";
      }
      enum ACTIVE {
        description
          "neighbor is down, and the local system is awaiting
          a conncetion from the remote peer";
      }
      enum OPENSENT {
        description
          "neighbor is in the process of being established.
          The local system has sent an Open message";
      }
      enum OPENCONFIRM {
        description
          "neighbor is in the process of being established.
          The local system is awaiting a Notification or
          Keepalive message";
      }
      enum ESTABLISHED {
        description
          "neighbor is up - the BGP session with the peer is
          established";
      }
      enum CLOSING {
        description
          "neighbor is down - the BGP session with the peer is
          is in Closing state trying to free up resources";
      }
      enum DELETING {
        description
          "neighbor is down - the BGP session with the peer is
          is in Deleting state trying to delete session";
      }
      enum INCOMPLETE {
        description
          "neighbor is down - the BGP session with the peer is
          is in Incomplete mandatory config state";
      }
      enum SHUTDOWN {
        description
          "neighbor is down - the BGP session with the peer is
          in Shutdown state";
      }
    }
  }
}
