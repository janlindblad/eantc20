module arcos-vxlan {
  yang-version 1.1;
  namespace "http://yang.arrcus.com/arcos/vxlan";
  prefix arc-overlay;

  import iana-if-type {
    prefix ianaift;
  }
  import ietf-yang-types {
    prefix yang;
  }
  import openconfig-interfaces {
    prefix oc-if;
  }
  import openconfig-network-instance {
    prefix oc-netinst;
  }
  import ietf-inet-types {
    prefix inet;
  }
  import openconfig-if-ip {
    prefix oc-ip;
  }

  grouping vni-state-group {
    container vni-state {
      config false;
      leaf vni-run-state {
        type enumeration {
            enum UP {
                description "VNI state id up";
            }
            enum DOWN {
                description "VNI state is down";
            }
        }
        description "VNI state";
      }
      leaf vni-type {
        type enumeration {
            enum ROUTED {
                description "routed VNI associated with an IP VRF";
            }
            enum BRIDGED {
                description "bridged VNI associated with a MAC VRF";
            }
        }
        description "VNI type";
      }
      leaf ltep-id {
        type uint32;
        description "Local tunnel endpoint associated with this VNI";
      }
      leaf vni-ifindex {
        type uint32;
        description "vni ifindex";
      }
      leaf ip-or-mac-vrf {
        type string;
        description "IP or MAC VRF associated with this VNI";
      }
      leaf vrf-id {
        type uint32;
        description "VRF ID for L3-VNI IP-VRF or L2-VNI MAC-VRF";
      }
      leaf vrf-ifindex {
        type uint32;
        description "ifindex for L3-VNI IP-VRF or L2-VNI bridge";
      }
      leaf vni-router-mac {
        type yang:mac-address;
        description "router MAC address for a routed VNI";
      }
      leaf ingress-unicast-packets {
        type uint64;
        description "VPN ingress unicast packet count";
      }
      leaf ingress-mcast-packets {
        type uint64;
        description "VPN ingress multicast packet count";
      }
      leaf ingress-bcast-packets {
        type uint64;
        description "VPN ingress broadcast packet count";
      }
      leaf egress-unicast-packets {
        type uint64;
        description "VPN egress unicast packet count";
      }
      leaf egress-mcast-packets {
        type uint64;
        description "VPN egress multicast packet count";
      }
      leaf egress-bcast-packets {
        type uint64;
        description "VPN egress broadcast packet count";
      }
      leaf ingress-unicast-bytes {
        type uint64;
        description "VPN egress unicast byte count";
      }
      leaf ingress-mcast-bytes {
        type uint64;
        description "VPN egress multicast byte count";
      }
      leaf ingress-bcast-bytes {
        type uint64;
        description "VPN egress broadcast byte count";
      }
      leaf egress-unicast-bytes {
        type uint64;
        description "VPN egress unicast byte count";
      }
      leaf egress-mcast-bytes {
        type uint64;
        description "VPN egress multicast byte count";
      }
      leaf egress-bcast-bytes {
        type uint64;
        description "VPN egress broadcast byte count";
      }
    }
  }

  container overlay {
    description "Network Overlays Manager CLI";
    list vni-all{
      config false;
      key "vnid";
      description "Virtual Network Instance Table";

      leaf vnid {
        type uint32;
        description "Virtual Network Instance ID";
      }
      uses vni-state-group; 
    }
 
    list local-tunnel-endpoint {
      key "ltep-id";
      description "IP Local Tunnel Endpoint configuration";
      max-elements 1;

      leaf ltep-id {
        type uint32;
        description "IP Local Tunnel Endpoint ID";
        mandatory true;
      }

      leaf source-interface {
        type oc-if:base-interface-ref;
        description "IP Local Tunnel Endpoint source loopback";
        must "/oc-if:interfaces/oc-if:interface[oc-if:name=current()]"
           + "/oc-if:config/oc-if:type = 'ianaift:softwareLoopback'" {
          error-message "ltep source interface must be of type loopback";
        }
        must "count(/overlay/local-tunnel-endpoint/source-interface[current()=.]) = 1" {
          error-message "Each source interface may only be used in one local-tunnel-endpoint";
        }
        must "count(/oc-netinst:network-instances/oc-netinst:network-instance/" +
             "oc-netinst:interfaces/oc-netinst:interface[oc-netinst:id=current()]) = 0" {
          error-message "ltep source interface must be in the default network-instance";
        }
      }

      container local-tunnel-endpoint-state {
        config false;
        leaf ltep-run-state {
          type enumeration {
            enum UP {
                description "local tunnel endpoint state is up";
            }
            enum DOWN {
                description "local tunnel endpoint state is down";
            }
          }
          description "local tunnel endpoint state";
        }
        leaf source-interface {
          type oc-if:base-interface-ref;
          description "IP Local Tunnel Endpoint source loopback";
        }
        leaf source-ip {
          type inet:ipv4-address-no-zone;
          description "tunnel source ipv4 address";
        }
        leaf encapsulation {
          type enumeration {
            enum VXLAN {
                description "VXLAN tunnel encapsulation";
            }
          }
          description "tunnel encapsulation";
        }
        leaf udp-port {
          type uint32;
          description "tunnel destination UDP port";
        }
      }
    }
  }

  grouping vni-top {

    description "VNI configuration for a network instance";

    list vni {
      key "vni-id";
      max-elements 1;
      description "Virtual Network Instance";

      leaf vni-id {
        type uint32;
        description "Virtual Network Instance ID";
        mandatory true;
        must "count(/oc-if:interfaces/oc-if:interface[oc-if:name=current()/../../oc-netinst:name]"
           + "/oc-if:subinterfaces/oc-if:subinterface/oc-ip:ipv4/oc-ip:addresses"
           + "/oc-ip:address/oc-ip:vrrp/oc-ip:vrrp-group) = 0" {
          error-message "VRRP may not be configured on VXLAN enabled VLANs";
        }
        must "count(/oc-if:interfaces/oc-if:interface[oc-if:name=current()/../../oc-netinst:name]"
           + "/oc-if:subinterfaces/oc-if:subinterface/oc-ip:ipv6/oc-ip:addresses"
           + "/oc-ip:address/oc-ip:vrrp/oc-ip:vrrp-group) = 0" {
          error-message "VRRP may not be configured on VXLAN enabled VLANs";
        }
      }

      leaf local-tunnel-endpoint-id {
        type uint32;
        description "Local tunnel endpoint ID associated with this VNI";
        mandatory true;
      }

      uses vni-state-group;
    }
  }
  augment "/oc-netinst:network-instances/oc-netinst:network-instance" {
    uses vni-top {
      when "(current()/oc-netinst:name != 'default')";
    }
  }
}
