module arcos-copp {
  yang-version 1.1;
  namespace "http://yang.arrcus.com/arcos/copp";
  prefix arc-copp;

  import arcos-platform {
    prefix arc-platform;
  }

  organization
    "Arrcus, Inc.";
  contact
    "Arrcus, Inc.
     Customer Service
     Postal: 2077 Gateway Place
     San Jose, CA 95110
     Tel: +1 1XXX XXX-XXXX
     E-mail: xxx@arrcus.com";
  description
    "YANG data-model for top-level CoPP";

  grouping copp-top {
    description
      "Top level grouping for CoPP";
    container copp {
      description
        "Control Plane Policer";
      action counters {
        description
          "Clear all CoPP statistics";
        output {
          leaf result {
            type string;
            description
              "The status of the clear operation";
          }
        }
      }
    }
  }

  uses copp-top {
    when "(/arc-platform:platform/arc-platform:asic != 'arc-platform:X86_64')";
  }
}
