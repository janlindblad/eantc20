module arcos-qos {
  yang-version 1.1;
  namespace "http://yang.arrcus.com/arcos/qos";
  prefix arc-qos;

  import arcos-platform {
    prefix arc-platform;
  }

  organization
    "Arrcus, Inc.";
  contact
    "Arrcus, Inc.
     Customer Service
     Postal: 2077 Gateway Place
     San Jose, CA 95110
     Tel: +1 1XXX XXX-XXXX
     E-mail: xxx@arrcus.com";
  description
    "YANG data-model for top-level QoS";

  grouping qos-top {
    description
      "Top level grouping for QoS";
    container qos {
      description
        "Quality of Service";
      action counters {
        description
          "Clear all QoS statistics";
        output {
          leaf result {
            type string;
            description
              "The status of the Clear operation";
          }
        }
      }
    }
  }

  uses qos-top {
    when "(/arc-platform:platform/arc-platform:asic != 'arc-platform:X86_64')";
  }
}
