module arcos-process {
  yang-version 1.1;
  namespace "http://yang.arrcus.com/arcos/process";
  prefix arc-process;

  list processes {
    key "name";

    description
      "Display Arrcus Process Details.";

    config false;

    leaf name {
      type string;
      description
        "Name of the process";
    }

    leaf status {
      type string;
      description
        "Process status";
    }
  }
}
