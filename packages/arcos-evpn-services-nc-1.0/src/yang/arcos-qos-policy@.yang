module arcos-qos-policy {
  yang-version 1.1;
  namespace "http://yang.arrcus.com/arcos/qos/policy";
  prefix arc-qos-pol;

  import arcos-policy {
    prefix arc-pol;
  }
  import arcos-policy-action {
    prefix arc-pol-actn;
  }
  import arcos-policy-action-types {
    prefix arc-pol-actn-types;
  }
  import arcos-qos-policy-action-types {
    prefix arc-qos-pol-actn-types;
  }
  import arcos-qos {
    prefix arc-qos;
  }
  import arcos-qos-classifier {
    prefix arc-qos-cfr;
  }

  organization
    "Arrcus, Inc.";
  contact
    "Arrcus, Inc.
     Customer Service
     Postal: 2077 Gateway Place
     San Jose, CA 95110
     Tel: +1 1XXX XXX-XXXX
     E-mail: xxx@arrcus.com";
  description
    "YANG data-model for qos policy definitions.
     Expanded from the generic policy data model (policy.yang)";


  grouping rate-max-parameters {
    description
      "maximum rate parameters";
    uses arc-pol-actn:traffic-rate;
  }

  grouping rate-max-config {
    description
      "maximum rate configuration parameters";
    container config {
      description
        "Configuration data";
      uses rate-max-parameters;
    }
  }

  grouping rate-max-state {
    description
      "maximum rate state information parameters";
    container state {
      config false;
      description
        "State Information.";
      uses rate-max-parameters;
    }
  }

  grouping rate-max-top {
    description
      "Top level container for fields in maximum rate configuration";
    container rate-max {
      description
        "maximum rate related fields";
      uses rate-max-state;
    }
  }


  grouping rate-min-parameters {
    description
      "minimum rate parameters";
    leaf percent {
      type uint8 {
        range "1..100";
      }
      description
        "bandwidth guarantee percent";
    }
    uses arc-pol-actn:traffic-rate;
  }

  grouping rate-min-config {
    description
      "minimum rate configuration parameters";
    container config {
      description
        "Configuration data";
      uses rate-min-parameters;
    }
  }

  grouping rate-min-state {
    description
      "minimum rate state information parameters";
    container state {
      config false;
      description
        "State Information.";
      uses rate-min-parameters;
    }
  }

  grouping rate-min-top {
    description
      "Top level container for fields in minimum rate configuration";
    container rate-min {
      description
        "minimum rate related fields";
      uses rate-min-state;
    }
  }


  grouping rate-excess-parameters {
    description
      "excess rate parameters";
    leaf ratio {
      type uint8 {
        range "1..100";
      }
      description
        "bandwidth remaining percent";
    }
  }

  grouping rate-excess-config {
    description
      "excess rate configuration parameters";
    container config {
      description
        "Configuration data";
      uses rate-excess-parameters;
    }
  }

  grouping rate-excess-state {
    description
      "excess rate state information parameters";
    container state {
      config false;
      description
        "State Information.";
      uses rate-excess-parameters;
    }
  }

  grouping rate-excess-top {
    description
      "excess rate configuration parameters";
    container rate-excess {
      description
        "excess rate related fields";
      uses rate-excess-state;
    }
  }


  grouping priority-parameters {
    description
      "priority parameters";
    leaf level {
      type uint8 {
        range "1..2";
      }
      description
        "priority level";
    }
  }

  grouping priority-config {
    description
      "priority configuration parameters";
    container config {
      description
        "Configuration data";
      uses priority-parameters;
    }
  }

  grouping priority-state {
    description
      "priority state information parameters";
    container state {
      config false;
      description
        "State Information.";
      uses priority-parameters;
    }
  }

  grouping priority-top {
    description
      "priority configuration parameters";
    container priority {
      description
        "priority related fields";
      uses priority-state;
    }
  }

  augment "/arc-qos:qos/policies/policy/classifiers/classifier/actions/action" {
    uses rate-min-top {
      when "./type = 'arc-qos-pol-actn-types:RATE_MIN'";
    }
  }

  augment "/arc-qos:qos/policies/policy/classifiers/classifier/actions/action/rate-min" {
    uses rate-min-config {
      refine "config/rate/value" {
        mandatory true;
      }
    }
  }

  augment "/arc-qos:qos/policies/policy/classifiers/classifier/actions/action" {
    uses rate-max-top {
      when "./type = 'arc-qos-pol-actn-types:RATE_MAX'";
    }
  }

  augment "/arc-qos:qos/policies/policy/classifiers/classifier/actions/action/rate-max" {
    uses rate-max-config {
      refine "config/rate/value" {
        mandatory true;
      }
    }
  }

  augment "/arc-qos:qos/policies/policy/classifiers/classifier/actions/action" {
    uses rate-excess-top {
      when "./type = 'arc-qos-pol-actn-types:RATE_EXCESS'";
    }
  }

  augment "/arc-qos:qos/policies/policy/classifiers/classifier/actions/action/rate-excess" {
    uses rate-excess-config;
  }

  augment "/arc-qos:qos/policies/policy/classifiers/classifier/actions/action" {
    uses priority-top {
      when "./type = 'arc-qos-pol-actn-types:PRIORITY'";
    }
  }

  augment "/arc-qos:qos/policies/policy/classifiers/classifier/actions/action/priority" {
    uses priority-config;
  }

  grouping qos-policy-top {
    description
      "Top-level container for QoS specific policy database";
    uses arc-pol:policies-top {
      refine "policies/policy/classifiers/classifier" {
        min-elements 1;
        max-elements 7;
      }
      refine "policies/policy/classifiers/classifier/actions/action/type" {
        must "current() = 'arc-pol-actn-types:MARK' or "
           + "current() = 'arc-pol-actn-types:POLICE' or "
           + "current() = 'arc-qos-pol-actn-types:PRIORITY' or "
           + "current() = 'arc-qos-pol-actn-types:RATE_MIN' or "
           + "current() = 'arc-qos-pol-actn-types:RATE_EXCESS' or "
           + "current() = 'arc-qos-pol-actn-types:RATE_MAX'" {
          error-message "action type not supported for qos";
        }
      }
    }
  }

  augment "/arc-qos:qos" {
    uses qos-policy-top;
  }
}
