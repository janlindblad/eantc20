module arcos-qos-classifier {
  yang-version 1.1;
  namespace "http://yang.arrcus.com/arcos/qos/classifier";
  prefix arc-qos-cfr;

  import arcos-classifier {
    prefix arc-cfr;
  }
  import arcos-classifier-filter {
    prefix arc-cfr-fltr;
  }
  import arcos-classifier-filter-types {
    prefix arc-cfr-fltr-types;
  }
  import arcos-qos {
    prefix arc-qos;
  }

  organization
    "Arrcus, Inc.";
  contact
    "Arrcus, Inc.
     Customer Service
     Postal: 2077 Gateway Place
     San Jose, CA 95110
     Tel: +1 1XXX XXX-XXXX
     E-mail: xxx@arrcus.com";
  description
    "YANG data-model for qos classifier definitions.
     Expanded from the generic classifier data model (classifier.yang)";


  augment "/arc-qos:qos/classifiers/classifier/filters/filter/config" {
    uses arc-cfr-fltr:local-tc-top {
      when "../type = 'arc-cfr-fltr-types:LOCAL_TC'";
      refine "local-tc-value" {
        min-elements 1;
        max-elements 1;
      }
    }
  }

  augment "/arc-qos:qos/classifiers/classifier/filters/filter/state" {
    uses arc-cfr-fltr:local-tc-top;
  }

  grouping qos-classifier-top {
    description
      "Top-level grouping for QoS specific classifier database";
    uses arc-cfr:classifiers-top {
      refine "classifiers/classifier/filters/filter" {
        min-elements 1;
        max-elements 1;
      }
      refine "classifiers/classifier/filters/filter/type" {
        must "current() = 'arc-cfr-fltr-types:LOCAL_TC' or "
           + "current() = 'arc-cfr-fltr-types:ACL_IPV4' or "
           + "current() = 'arc-cfr-fltr-types:ACL_IPV6' or "
           + "current() = 'arc-cfr-fltr-types:ACL_L2'" {
          error-message "filter type not supported for qos";
        }
      }
    }
  }

  augment "/arc-qos:qos" {
    uses qos-classifier-top;
  }
}
