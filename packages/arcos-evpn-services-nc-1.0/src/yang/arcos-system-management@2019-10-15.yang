module arcos-system-management {
  yang-version 1.1;
  namespace "http://yang.arrcus.com/arcos/system/management";
  prefix arc-sys-mgmt;

  organization
    "Arrcus, Inc.";

  contact
    "Arrcus, Inc.
     2077 Gateway Place
     Suite 400
     San Jose, CA 95110

     E-mail: yang-support@arrcus.com";

  description
    "This module contains definitions for the
     native ArcOS system management domain.

     Copyright (c) 2016-2019 by Arrcus, Inc.
     All rights reserved.";


  revision 2019-10-15 {
    description "Initial version";
  }

  grouping system-tls-config {
    description
      "";

    leaf certificate-file {
      type string {
        length "1..100";
      }
      default "/mnt/onl/config/pki/certificate";
      must 'boolean(../key-file)' {
        error-message
          "If certificate-file is configured, key-file must be configured";
      }
      description
        "Absolute file path of the server certificate";
    }

    leaf key-file {
      type string {
        length "1..100";
      }
      default "/mnt/onl/config/pki/key.pem";
      must 'boolean(../certificate-file)' {
        error-message
          "If key-file is configured, certificate-file must be configured";
      }
      description
        "Absolute file path to the corresponding private key file for the
         server certificate";
    }
  }

  grouping system-tls-top {
    description
      "Top-level grouping for system TLS attributes";

    container tls {
      description
        "Top-level container for TLS attributes";

      container config {
        description
          "Configuration data for TLS related attributes";

        uses system-tls-config;
      }

      container state {
        config false;

        description
          "Operational state data for TLS related attributes";

        uses system-tls-config;
      }
    }
  }

  grouping system-clients-state {
    description
      "Operational state data of connected clients";

    leaf-list paths {
      type string;
      description
        "Subscribed Paths";
    }
  }

  grouping system-clients-top {
    description
      "Top-level grouping for system client data";

    container clients {
      description
        "Top level container for connected clients";
      container state {
        config false;
        description
          "Operational state data for the clients";
        list client {
          leaf peer-address {
            type string;
            description
              "IP address and port of the connected client";
          }
          uses system-clients-state;
        }
      }
    }
  }

}
