module arcos-openconfig-routing-policy-deviations {
  yang-version 1.1;
  namespace "http://yang.arrcus.com/arcos/openconfig/routing-policy/deviations";
  prefix arc-oc-rpol-dev;

  import openconfig-routing-policy {
    prefix oc-rpol;
  }
  import openconfig-policy-types {
    prefix oc-pol-types;
  }

  deviation "/oc-rpol:routing-policy/oc-rpol:defined-sets" +
            "/oc-rpol:prefix-sets/oc-rpol:prefix-set" +
            "/oc-rpol:prefixes/oc-rpol:prefix" +
            "/oc-rpol:config/oc-rpol:masklength-range" {
    deviate replace {
      type string {
        pattern '(([0-9]|[1-9][0-9]|1[0-2][0-8])\.\.([0-9]|[1-9][0-9]' +
                '|1[0-2][0-8]))|exact';
      }
    }
    description "Fix bad pattern.";
  }

  deviation "/oc-rpol:routing-policy/oc-rpol:defined-sets" +
            "/oc-rpol:prefix-sets/oc-rpol:prefix-set/oc-rpol:config" +
            "/oc-rpol:prefix-set-name" {
    deviate replace {
      type string {
        length "1..79";
      }
    }
    description "Limit size to 79 characters.";
  }

  deviation "/oc-rpol:routing-policy/oc-rpol:defined-sets" +
            "/oc-rpol:neighbor-sets" {
    deviate not-supported;
    description "Not supported in this release.";
  }

  deviation "/oc-rpol:routing-policy/oc-rpol:defined-sets" +
            "/oc-rpol:tag-sets" {
    deviate not-supported;
    description "Not supported in this release.";
  }

  deviation "/oc-rpol:routing-policy/oc-rpol:policy-definitions" +
            "/oc-rpol:policy-definition/oc-rpol:config/oc-rpol:name" {
    deviate replace {
      type string {
        length "1..79";
      }
    }
    description "Limit size to 79 characters.";
  }

  deviation "/oc-rpol:routing-policy/oc-rpol:policy-definitions" +
            "/oc-rpol:policy-definition/oc-rpol:statements" +
            "/oc-rpol:statement/oc-rpol:config/oc-rpol:name" {
    deviate replace {
      type string {
        length "1..79";
      }
    }
    description "Limit size to 79 characters.";
  }

  deviation "/oc-rpol:routing-policy/oc-rpol:policy-definitions" +
            "/oc-rpol:policy-definition/oc-rpol:statements" +
            "/oc-rpol:statement/oc-rpol:conditions" +
            "/oc-rpol:config/oc-rpol:call-policy" {
    deviate not-supported;
    description "Not supported in this release.";
  }

  deviation "/oc-rpol:routing-policy/oc-rpol:policy-definitions" +
            "/oc-rpol:policy-definition/oc-rpol:statements" +
            "/oc-rpol:statement/oc-rpol:conditions" +
            "/oc-rpol:state/oc-rpol:call-policy" {
    deviate not-supported;
    description "Not supported in this release.";
  }

  deviation "/oc-rpol:routing-policy/oc-rpol:policy-definitions" +
            "/oc-rpol:policy-definition/oc-rpol:statements" +
            "/oc-rpol:statement/oc-rpol:conditions" +
            "/oc-rpol:config/oc-rpol:install-protocol-eq" {
    deviate add {
      must "current() = 'oc-pol-types:DIRECTLY_CONNECTED' or "
         + "current() = 'oc-pol-types:STATIC' or "
         + "current() = 'oc-pol-types:ISIS' or "
         + "current() = 'oc-pol-types:OSPF' or "
         + "current() = 'oc-pol-types:LOCAL_AGGREGATE' or "
         + "current() = 'oc-pol-types:BGP'" {
        error-message
          "src-protocol can be DIRECTLY_CONNECTED, LOCAL_AGGREGATE,
           STATIC, ISIS, OSPF, or BGP";
      }
    }
    description "Source protocol choices same as in table-connection,
                 except that LOCAL_AGGREGATE is for BGP neighbor
                 export policy only";
  }

  deviation "/oc-rpol:routing-policy/oc-rpol:policy-definitions" +
            "/oc-rpol:policy-definition/oc-rpol:statements" +
            "/oc-rpol:statement/oc-rpol:conditions" +
            "/oc-rpol:match-neighbor-set" {
    deviate not-supported;
    description "Not supported in this release.";
  }

  deviation "/oc-rpol:routing-policy/oc-rpol:policy-definitions" +
            "/oc-rpol:policy-definition/oc-rpol:statements" +
            "/oc-rpol:statement/oc-rpol:conditions" +
            "/oc-rpol:match-tag-set" {
    deviate not-supported;
    description "Not supported in this release.";
  }

  deviation "/oc-rpol:routing-policy/oc-rpol:policy-definitions" +
            "/oc-rpol:policy-definition/oc-rpol:statements" +
            "/oc-rpol:statement/oc-rpol:actions/oc-rpol:igp-actions" +
            "/oc-rpol:config/oc-rpol:set-tag" {
    deviate not-supported;
    description "Not supported in this release.";
  }
}
