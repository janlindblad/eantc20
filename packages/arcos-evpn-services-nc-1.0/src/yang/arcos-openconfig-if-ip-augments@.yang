module arcos-openconfig-if-ip-augments {
  yang-version 1.1;
  namespace "http://yang.arrcus.com/arcos/openconfig/interfaces/ip/augments";
  prefix arc-oc-ip-aug;

  import openconfig-if-ip {
    prefix oc-ip;
  }

  import openconfig-interfaces {
    prefix oc-if;
  }

  typedef vrrp-proto-version {
    type enumeration {
      enum VRRP_V2 {
        description "VRRP protocol version 2.";
      }
      enum VRRP_V3 {
        description "VRRP protocol version 3.";
      }
      enum VRRP_V2_V3 {
        description "VRRP protocol version 2 and 3.";
      }
    }
  }
  grouping ipv6-ra-config {
    description
      "Configuration parameters for IPv6 router advertisements.";

    leaf interval {
      type uint32 {
        range "4..1800";
      }
      default 600;
      units seconds;
      description
        "The interval between periodic router advertisement neighbor
        discovery messages sent on this interface expressed in
        seconds.";
    }

    leaf lifetime {
      type uint32 {
        range "0..9000";
      }
      units seconds;
      must 'current() = 0 or current() > ../interval' {
        error-message "If lifetime is not 0, it must be greater than interval";
      }
      description
        "The lifetime advertised in RA messages sent on this interface
         (in seconds), value 0 means don't use as default router.";
    }

    leaf suppress {
      type boolean;
      default false;
      description
        "When set to true, router advertisement neighbor discovery
        messages are not transmitted on this interface.";
    }

    leaf virtual-router-only {
      type boolean;
      default false;
      description
        "When set to true, router advertisement neighbor discovery
        messages are only sent for VRRP virtual-routers on this interface.";
    }
  }

  grouping ipv6-ra-top {
    description
      "Top-level grouping for IPv6 router advertisements ";

    container router-advertisement {
      description
        "Configuration and operational state parameters relating to
        router advertisements.";

      container config {
        description
          "Configuration parameters relating to router advertisements
          for IPv6.";
        uses ipv6-ra-config;
      }

      container state {
        config false;
        description
          "Operational state parameters relating to router
           advertisements for IPv6.";
        uses ipv6-ra-config;
      }
    }
  }

  grouping vrrp-group-ag-state-top {
    description
      "Additional leafs for VRRP Group State ";

    leaf virtual-router-mode {
      type enumeration {
        enum MASTER {
          description "Virtual Router is in MASTER mode.";
        }
        enum BACKUP {
          description "Virtual Router is in BACKUP mode.";
        }
      }
      description
        "The mode of this specific Virtual Group
         on the current Virtual Router";
    }

    leaf advertisement-sent {
      type uint64;
      description
        "Number of VRRP advertisements sent for this VRRP group";
    }

    leaf advertisement-received {
      type uint64;
      description
        "Number of VRRP advertisements received for this VRRP group";
    }

    leaf advertisement-dropped {
      type uint64;
      description
        "Number of VRRP advertisements dropped for this VRRP group";
    }
  }

  augment "/oc-if:interfaces/oc-if:interface/oc-if:subinterfaces" +
          "/oc-if:subinterface/oc-ip:ipv6" {
    uses ipv6-ra-top;
  }

  augment "/oc-if:interfaces/oc-if:interface/oc-if:subinterfaces" +
          "/oc-if:subinterface/oc-ip:ipv4/oc-ip:addresses/oc-ip:address" +
          "/oc-ip:vrrp/oc-ip:vrrp-group/oc-ip:config" {
    leaf vrrp-version {
      description
        "Version of VRRP version to be enabled for this VRRP group.";
      type vrrp-proto-version;
      default "VRRP_V3";
    }
  }

  augment "/oc-if:interfaces/oc-if:interface/oc-if:subinterfaces" +
          "/oc-if:subinterface/oc-ip:ipv4/oc-ip:addresses/oc-ip:address" +
          "/oc-ip:vrrp/oc-ip:vrrp-group/oc-ip:state" {
    leaf vrrp-version {
      description
        "Version of VRRP version to be enabled for this VRRP group.";
      type vrrp-proto-version;
    }
  }

  augment "/oc-if:interfaces/oc-if:interface/oc-if:subinterfaces" +
          "/oc-if:subinterface/oc-ip:ipv4/oc-ip:addresses/oc-ip:address" +
          "/oc-ip:vrrp/oc-ip:vrrp-group/oc-ip:state" {
    uses vrrp-group-ag-state-top;
  }

  augment "/oc-if:interfaces/oc-if:interface/oc-if:subinterfaces" +
          "/oc-if:subinterface/oc-ip:ipv6/oc-ip:addresses/oc-ip:address" +
          "/oc-ip:vrrp/oc-ip:vrrp-group/oc-ip:state" {
    uses vrrp-group-ag-state-top;
  }
}
