module arcos-openconfig-network-instance-deviations {
  yang-version 1.1;
  namespace "http://yang.arrcus.com/arcos/openconfig/network-instance/deviations";
  prefix arc-oc-netinst-dev;

  import openconfig-isis-types {
    prefix oc-isis-types;
  }
  import openconfig-local-routing {
    prefix oc-loc-rt;
  }
  import openconfig-network-instance {
    prefix oc-netinst;
  }
  import openconfig-network-instance-types {
    prefix oc-ni-types;
  }
  import openconfig-policy-types {
    prefix oc-pol-types;
  }
  import openconfig-types {
    prefix oc-types;
  }
  import arcos-isis-types {
    prefix arc-isis-types;
  }
  import arcos-openconfig-bgp-augments {
    prefix arc-oc-bgp-aug;
  }
  import arcos-openconfig-rib-bgp-augments {
    prefix arc-oc-rib-bgp-aug;
  }
  import arcos-openconfig-bgp-types {
    prefix arc-oc-bgp-types;
  }

  deviation "/oc-netinst:network-instances/oc-netinst:network-instance" +
            "/oc-netinst:config/oc-netinst:route-distinguisher" {
    deviate not-supported;
    description
      "Not supported in this release.";
  }

  deviation "/oc-netinst:network-instances/oc-netinst:network-instance" +
            "/oc-netinst:state/oc-netinst:route-distinguisher" {
    deviate not-supported;
    description
      "Not supported in this release.";
  }

  deviation "/oc-netinst:network-instances/oc-netinst:network-instance" +
            "/oc-netinst:config/oc-netinst:enabled" {
    deviate not-supported;
    description
      "Not supported in this release.";
  }

  deviation "/oc-netinst:network-instances/oc-netinst:network-instance" +
            "/oc-netinst:state/oc-netinst:enabled" {
    deviate not-supported;
    description
      "Not supported in this release.";
  }

  deviation "/oc-netinst:network-instances/oc-netinst:network-instance" +
            "/oc-netinst:protocols/oc-netinst:protocol" +
            "/oc-netinst:config/oc-netinst:enabled" {
    deviate not-supported;
    description
      "Not supported in this release.";
  }

  deviation "/oc-netinst:network-instances/oc-netinst:network-instance/oc-netinst:state" {
    deviate not-supported;
    description
      "Not supported in this release.";
  }

  deviation "/oc-netinst:network-instances/oc-netinst:network-instance/oc-netinst:protocols"
          + "/oc-netinst:protocol/oc-netinst:state/oc-netinst:enabled" {
    deviate not-supported;
    description
      "Not supported in this release.";
  }

  deviation "/oc-netinst:network-instances/oc-netinst:network-instance/oc-netinst:interfaces"
          + "/oc-netinst:interface/oc-netinst:state/oc-netinst:associated-address-families" {
    deviate not-supported;
    description
      "Not supported in this release.";
  }

  deviation "/oc-netinst:network-instances/oc-netinst:network-instance/oc-netinst:interfaces"
          + "/oc-netinst:interface/oc-netinst:config/oc-netinst:associated-address-families" {
    deviate not-supported;
    description
      "Not supported in this release.";
  }

  deviation "/oc-netinst:network-instances/oc-netinst:network-instance/oc-netinst:config/oc-netinst:router-id" {
    deviate not-supported;
    description
      "Not supported in this release.";
  }

  deviation "/oc-netinst:network-instances/oc-netinst:network-instance/oc-netinst:state/oc-netinst:router-id" {
    deviate not-supported;
    description
      "Not supported in this release.";
  }

  deviation "/oc-netinst:network-instances/oc-netinst:network-instance/oc-netinst:inter-instance-policies" {
    deviate not-supported;
    description
      "Not supported in this release.";
  }

  deviation "/oc-netinst:network-instances/oc-netinst:network-instance/oc-netinst:connection-points" {
    deviate not-supported;
    description
      "Not supported in this release.";
  }

  deviation "/oc-netinst:network-instances/oc-netinst:network-instance"
          + "/oc-netinst:table-connections/oc-netinst:table-connection"
          + "/oc-netinst:config/oc-netinst:src-protocol" {
    deviate replace {
      type identityref {
        base oc-pol-types:INSTALL_PROTOCOL_TYPE;
      }
    }
    deviate add {
      must "current() = 'oc-pol-types:DIRECTLY_CONNECTED' or "
         + "current() = 'oc-pol-types:STATIC' or "
         + "current() = 'oc-pol-types:ISIS' or "
         + "current() = 'oc-pol-types:BGP'" {
        error-message "src-protocol not supported yet";
      }
    }
    description
      "Do not go through network-instance/table.";
  }

  deviation "/oc-netinst:network-instances/oc-netinst:network-instance"
          + "/oc-netinst:table-connections/oc-netinst:table-connection"
          + "/oc-netinst:config/oc-netinst:address-family" {
    deviate replace {
      type identityref {
        base oc-types:ADDRESS_FAMILY;
      }
    }
    deviate add {
      must "current() = 'oc-types:IPV4' or "
         + "current() = 'oc-types:IPV6'" {
        error-message "address-family not supported yet";
      }
    }
    description
      "Do not go through network-instance/table.";
  }

  deviation "/oc-netinst:network-instances/oc-netinst:network-instance"
          + "/oc-netinst:table-connections/oc-netinst:table-connection"
          + "/oc-netinst:config/oc-netinst:dst-protocol" {
    deviate replace {
      type identityref {
        base oc-pol-types:INSTALL_PROTOCOL_TYPE;
      }
    }
    deviate add {
      must "current() = 'oc-pol-types:BGP' or "
         + "current() = 'oc-pol-types:ISIS'" {
        error-message "dest-protocol not supported yet";
      }
      must 'current() != ../oc-netinst:src-protocol' {
        error-message "dest-protocol must be different then src-protocol";
      }
    }
    description
      "Do not go through network-instance/table.";
  }

  deviation "/oc-netinst:network-instances/oc-netinst:network-instance"
          + "/oc-netinst:table-connections/oc-netinst:table-connection"
          + "/oc-netinst:config/oc-netinst:import-policy" {
    deviate add {
      max-elements 1;
    }
    description
      "Only support one policy in this release.";
  }

  deviation "/oc-netinst:network-instances/oc-netinst:network-instance"
          + "/oc-netinst:table-connections/oc-netinst:table-connection"
          + "/oc-netinst:config/oc-netinst:default-import-policy" {
    deviate not-supported;
    description
      "Not supported in this release.";
  }

  deviation "/oc-netinst:network-instances/oc-netinst:network-instance/oc-netinst:encapsulation" {
    deviate not-supported;
    description
      "Not supported in this release.";
  }

  deviation "/oc-netinst:network-instances/oc-netinst:network-instance/oc-netinst:config/oc-netinst:type" {
    deviate add {
      must "current() = 'oc-ni-types:L2VLAN' or current() = 'oc-ni-types:L3VRF'" {
        error-message "Only the L3VRF and L2VLAN ni-type are supported.";
      }
    }
    description
      "Only supporting L2VLAN configuration in this release";
  }

  /*
   * Deviations for static routes
   */

  deviation "/oc-netinst:network-instances/oc-netinst:network-instance"
          + "/oc-netinst:protocols/oc-netinst:protocol/oc-netinst:local-aggregates" {
    deviate not-supported;
    description
      "Not supported in this release";
  }

  deviation "/oc-netinst:network-instances/oc-netinst:network-instance"
          + "/oc-netinst:protocols/oc-netinst:protocol/oc-netinst:static-routes"
          + "/oc-netinst:static/oc-netinst:next-hops/oc-netinst:next-hop"
          + "/oc-netinst:config/oc-netinst:recurse" {
    deviate not-supported;
    description
      "Resursive next-hop not supported in this release";
  }

  deviation "/oc-netinst:network-instances/oc-netinst:network-instance"
          + "/oc-netinst:protocols/oc-netinst:protocol/oc-netinst:static-routes"
          + "/oc-netinst:static/oc-netinst:state" {
    deviate not-supported;
    description
      "Not supported in this release";
  }

  deviation "/oc-netinst:network-instances/oc-netinst:network-instance"
          + "/oc-netinst:protocols/oc-netinst:protocol/oc-netinst:static-routes"
          + "/oc-netinst:static/oc-netinst:next-hops/oc-netinst:next-hop/oc-netinst:state" {
    deviate not-supported;
    description
      "Not supported in this release";
  }

  deviation "/oc-netinst:network-instances/oc-netinst:network-instance"
          + "/oc-netinst:protocols/oc-netinst:protocol/oc-netinst:static-routes"
          + "/oc-netinst:static/oc-netinst:next-hops/oc-netinst:next-hop"
          + "/oc-netinst:interface-ref/oc-netinst:state" {
    deviate not-supported;
    description
      "Not supported in this release";
  }

  deviation "/oc-netinst:network-instances/oc-netinst:network-instance"
          + "/oc-netinst:protocols/oc-netinst:protocol/oc-netinst:static-routes"
          + "/oc-netinst:static/oc-netinst:next-hops/oc-netinst:next-hop" {
    deviate add {
      must "(boolean(oc-netinst:interface-ref/config/interface) and boolean(oc-netinst:config/oc-netinst:next-hop)) or (oc-netinst:config/oc-netinst:next-hop = 'oc-loc-rt:DROP')" {
        error-message "Either next-hop must be DROP or both interface and next-hop address must be specified.";
      }
      must "(boolean(oc-netinst:interface-ref/config/interface) != 'true') or (boolean(oc-netinst:config/oc-netinst:next-hop) != 'true') or (oc-netinst:config/oc-netinst:next-hop != 'oc-loc-rt:DROP')" {
        error-message "Next-hop must not be DROP if interface is specified.";
      }
    }
  }

  deviation "/oc-netinst:network-instances/oc-netinst:network-instance"
          + "/oc-netinst:protocols/oc-netinst:protocol/oc-netinst:static-routes"
          + "/oc-netinst:static/oc-netinst:next-hops" {
    deviate add {
      must "(boolean(oc-netinst:next-hop/oc-netinst:config/oc-netinst:next-hop = 'oc-loc-rt:DROP') != 'true') or (count(oc-netinst:next-hop) = 1)" {
        error-message "No next-hop DROP in multi-paths";
      }
    }
  }

  deviation "/oc-netinst:network-instances/oc-netinst:network-instance"
          + "/oc-netinst:protocols/oc-netinst:protocol/oc-netinst:static-routes"
          + "/oc-netinst:static/oc-netinst:next-hops" {
    deviate add {
      must 'boolean(oc-netinst:next-hop)' {
        error-message "Static route has no path/next-hop.";
      }
    }
  }

  /*
   * Add this deviation of "unique" statement to enfornce unique
   * protocol identifiers per network-instance. This is needed
   * for single-instance protocol components including STATIC and
   * BGP. A separate solution is under investigation in order to
   * allow multiple instances per network-instance for IGPs like
   * IS-IS and OSPF.
   */
  deviation "/oc-netinst:network-instances/oc-netinst:network-instance"
          + "/oc-netinst:protocols/oc-netinst:protocol" {
    deviate add {
      unique "oc-netinst:identifier";
    }
  }

  deviation "/oc-netinst:network-instances/oc-netinst:network-instance"
          + "/oc-netinst:afts/oc-netinst:ipv4-unicast/oc-netinst:ipv4-entry"
          + "/oc-netinst:state" {
    deviate not-supported;
    description
      "Not supported in this release";
  }

  deviation "/oc-netinst:network-instances/oc-netinst:network-instance"
          + "/oc-netinst:afts/oc-netinst:ipv6-unicast/oc-netinst:ipv6-entry"
          + "/oc-netinst:state" {
    deviate not-supported;
    description
      "Not supported in this release";
  }

  deviation "/oc-netinst:network-instances/oc-netinst:network-instance"
          + "/oc-netinst:afts/oc-netinst:mpls/oc-netinst:label-entry"
          + "/oc-netinst:state" {
    deviate not-supported;
    description
      "Not supported in this release";
  }

  deviation "/oc-netinst:network-instances/oc-netinst:network-instance"
          + "/oc-netinst:afts/oc-netinst:policy-forwarding" {
    deviate not-supported;
    description
      "Not supported in this release";
  }

  deviation "/oc-netinst:network-instances/oc-netinst:network-instance"
          + "/oc-netinst:afts/oc-netinst:ipv4-unicast/oc-netinst:ipv4-entry"
          + "/oc-netinst:next-hops/oc-netinst:next-hop/oc-netinst:state/oc-netinst:index" {
    deviate not-supported;
    description
      "Not supported in this release";
  }

  deviation "/oc-netinst:network-instances/oc-netinst:network-instance"
          + "/oc-netinst:afts/oc-netinst:ipv4-unicast/oc-netinst:ipv4-entry"
          + "/oc-netinst:next-hops/oc-netinst:next-hop/oc-netinst:state/oc-netinst:weight" {
    deviate not-supported;
    description
      "Not supported in this release";
  }

  deviation "/oc-netinst:network-instances/oc-netinst:network-instance"
          + "/oc-netinst:afts/oc-netinst:ipv4-unicast/oc-netinst:ipv4-entry"
          + "/oc-netinst:next-hops/oc-netinst:next-hop/oc-netinst:state/oc-netinst:decapsulate-header" {
    deviate not-supported;
    description
      "Not supported in this release";
  }

  deviation "/oc-netinst:network-instances/oc-netinst:network-instance"
          + "/oc-netinst:afts/oc-netinst:ipv4-unicast/oc-netinst:ipv4-entry"
          + "/oc-netinst:next-hops/oc-netinst:next-hop/oc-netinst:state/oc-netinst:encapsulate-header" {
    deviate not-supported;
    description
      "Not supported in this release";
  }

  deviation "/oc-netinst:network-instances/oc-netinst:network-instance"
          + "/oc-netinst:afts/oc-netinst:ipv4-unicast/oc-netinst:ipv4-entry"
          + "/oc-netinst:next-hops/oc-netinst:next-hop/oc-netinst:state/oc-netinst:popped-mpls-label-stack" {
    deviate not-supported;
    description
      "Not supported in this release";
  }

  deviation "/oc-netinst:network-instances/oc-netinst:network-instance"
          + "/oc-netinst:afts/oc-netinst:ipv4-unicast/oc-netinst:ipv4-entry"
          + "/oc-netinst:next-hops/oc-netinst:next-hop/oc-netinst:state/oc-netinst:origin-protocol" {
    deviate not-supported;
    description
      "Not supported in this release";
  }

  deviation "/oc-netinst:network-instances/oc-netinst:network-instance"
          + "/oc-netinst:afts/oc-netinst:ipv4-unicast/oc-netinst:ipv4-entry"
          + "/oc-netinst:next-hops/oc-netinst:next-hop/oc-netinst:interface-ref"
          + "/oc-netinst:config" {
    deviate not-supported;
    description
      "Not supported in this release";
  }

  deviation "/oc-netinst:network-instances/oc-netinst:network-instance"
          + "/oc-netinst:afts/oc-netinst:ipv6-unicast/oc-netinst:ipv6-entry"
          + "/oc-netinst:next-hops/oc-netinst:next-hop/oc-netinst:state/oc-netinst:index" {
    deviate not-supported;
    description
      "Not supported in this release";
  }

  deviation "/oc-netinst:network-instances/oc-netinst:network-instance"
          + "/oc-netinst:afts/oc-netinst:ipv6-unicast/oc-netinst:ipv6-entry"
          + "/oc-netinst:next-hops/oc-netinst:next-hop/oc-netinst:state/oc-netinst:weight" {
    deviate not-supported;
    description
      "Not supported in this release";
  }

  deviation "/oc-netinst:network-instances/oc-netinst:network-instance"
          + "/oc-netinst:afts/oc-netinst:ipv6-unicast/oc-netinst:ipv6-entry"
          + "/oc-netinst:next-hops/oc-netinst:next-hop/oc-netinst:state/oc-netinst:decapsulate-header" {
    deviate not-supported;
    description
      "Not supported in this release";
  }

  deviation "/oc-netinst:network-instances/oc-netinst:network-instance"
          + "/oc-netinst:afts/oc-netinst:ipv6-unicast/oc-netinst:ipv6-entry"
          + "/oc-netinst:next-hops/oc-netinst:next-hop/oc-netinst:state/oc-netinst:encapsulate-header" {
    deviate not-supported;
    description
      "Not supported in this release";
  }

  deviation "/oc-netinst:network-instances/oc-netinst:network-instance"
          + "/oc-netinst:afts/oc-netinst:ipv6-unicast/oc-netinst:ipv6-entry"
          + "/oc-netinst:next-hops/oc-netinst:next-hop/oc-netinst:state/oc-netinst:popped-mpls-label-stack" {
    deviate not-supported;
    description
      "Not supported in this release";
  }

  deviation "/oc-netinst:network-instances/oc-netinst:network-instance"
          + "/oc-netinst:afts/oc-netinst:ipv6-unicast/oc-netinst:ipv6-entry"
          + "/oc-netinst:next-hops/oc-netinst:next-hop/oc-netinst:state/oc-netinst:origin-protocol" {
    deviate not-supported;
    description
      "Not supported in this release";
  }

  deviation "/oc-netinst:network-instances/oc-netinst:network-instance"
          + "/oc-netinst:afts/oc-netinst:ipv6-unicast/oc-netinst:ipv6-entry"
          + "/oc-netinst:next-hops/oc-netinst:next-hop/oc-netinst:interface-ref"
          + "/oc-netinst:config" {
    deviate not-supported;
    description
      "Not supported in this release";
  }

  deviation "/oc-netinst:network-instances/oc-netinst:network-instance"
          + "/oc-netinst:afts/oc-netinst:mpls/oc-netinst:label-entry"
          + "/oc-netinst:next-hops/oc-netinst:next-hop/oc-netinst:state/oc-netinst:index" {
    deviate not-supported;
    description
      "Not supported in this release";
  }

  deviation "/oc-netinst:network-instances/oc-netinst:network-instance"
          + "/oc-netinst:afts/oc-netinst:mpls/oc-netinst:label-entry"
          + "/oc-netinst:next-hops/oc-netinst:next-hop/oc-netinst:state/oc-netinst:weight" {
    deviate not-supported;
    description
      "Not supported in this release";
  }

  deviation "/oc-netinst:network-instances/oc-netinst:network-instance"
          + "/oc-netinst:afts/oc-netinst:mpls/oc-netinst:label-entry"
          + "/oc-netinst:next-hops/oc-netinst:next-hop/oc-netinst:state/oc-netinst:decapsulate-header" {
    deviate not-supported;
    description
      "Not supported in this release";
  }

  deviation "/oc-netinst:network-instances/oc-netinst:network-instance"
          + "/oc-netinst:afts/oc-netinst:mpls/oc-netinst:label-entry"
          + "/oc-netinst:next-hops/oc-netinst:next-hop/oc-netinst:state/oc-netinst:encapsulate-header" {
    deviate not-supported;
    description
      "Not supported in this release";
  }

  deviation "/oc-netinst:network-instances/oc-netinst:network-instance"
          + "/oc-netinst:afts/oc-netinst:mpls/oc-netinst:label-entry"
          + "/oc-netinst:next-hops/oc-netinst:next-hop/oc-netinst:state/oc-netinst:origin-protocol" {
    deviate not-supported;
    description
      "Not supported in this release";
  }

  deviation "/oc-netinst:network-instances/oc-netinst:network-instance"
          + "/oc-netinst:afts/oc-netinst:mpls/oc-netinst:label-entry"
          + "/oc-netinst:next-hops/oc-netinst:next-hop/oc-netinst:interface-ref"
          + "/oc-netinst:config" {
    deviate not-supported;
    description
      "Not supported in this release";
  }

  deviation "/oc-netinst:network-instances/oc-netinst:network-instance"
          + "/oc-netinst:afts-units/oc-netinst:aft-unit-entry"
          + "/oc-netinst:afts/oc-netinst:ipv4-unicast/oc-netinst:ipv4-entry"
          + "/oc-netinst:state" {
    deviate not-supported;
    description
      "Not supported in this release";
  }

  deviation "/oc-netinst:network-instances/oc-netinst:network-instance"
          + "/oc-netinst:afts-units/oc-netinst:aft-unit-entry"
          + "/oc-netinst:afts/oc-netinst:ipv6-unicast/oc-netinst:ipv6-entry"
          + "/oc-netinst:state" {
    deviate not-supported;
    description
      "Not supported in this release";
  }

  deviation "/oc-netinst:network-instances/oc-netinst:network-instance"
          + "/oc-netinst:afts-units/oc-netinst:aft-unit-entry"
          + "/oc-netinst:afts/oc-netinst:mpls/oc-netinst:label-entry"
          + "/oc-netinst:state" {
    deviate not-supported;
    description
      "Not supported in this release";
  }

  deviation "/oc-netinst:network-instances/oc-netinst:network-instance"
          + "/oc-netinst:afts-units/oc-netinst:aft-unit-entry"
          + "/oc-netinst:afts/oc-netinst:policy-forwarding" {
    deviate not-supported;
    description
      "Not supported in this release";
  }

  deviation "/oc-netinst:network-instances/oc-netinst:network-instance"
          + "/oc-netinst:afts-units/oc-netinst:aft-unit-entry"
          + "/oc-netinst:afts/oc-netinst:ipv4-unicast/oc-netinst:ipv4-entry"
          + "/oc-netinst:next-hops/oc-netinst:next-hop/oc-netinst:state/oc-netinst:index" {
    deviate not-supported;
    description
      "Not supported in this release";
  }

  deviation "/oc-netinst:network-instances/oc-netinst:network-instance"
          + "/oc-netinst:afts-units/oc-netinst:aft-unit-entry"
          + "/oc-netinst:afts/oc-netinst:ipv4-unicast/oc-netinst:ipv4-entry"
          + "/oc-netinst:next-hops/oc-netinst:next-hop/oc-netinst:state/oc-netinst:weight" {
    deviate not-supported;
    description
      "Not supported in this release";
  }

  deviation "/oc-netinst:network-instances/oc-netinst:network-instance"
          + "/oc-netinst:afts-units/oc-netinst:aft-unit-entry"
          + "/oc-netinst:afts/oc-netinst:ipv4-unicast/oc-netinst:ipv4-entry"
          + "/oc-netinst:next-hops/oc-netinst:next-hop/oc-netinst:state/oc-netinst:decapsulate-header" {
    deviate not-supported;
    description
      "Not supported in this release";
  }

  deviation "/oc-netinst:network-instances/oc-netinst:network-instance"
          + "/oc-netinst:afts-units/oc-netinst:aft-unit-entry"
          + "/oc-netinst:afts/oc-netinst:ipv4-unicast/oc-netinst:ipv4-entry"
          + "/oc-netinst:next-hops/oc-netinst:next-hop/oc-netinst:state/oc-netinst:encapsulate-header" {
    deviate not-supported;
    description
      "Not supported in this release";
  }

  deviation "/oc-netinst:network-instances/oc-netinst:network-instance"
          + "/oc-netinst:afts-units/oc-netinst:aft-unit-entry"
          + "/oc-netinst:afts/oc-netinst:ipv4-unicast/oc-netinst:ipv4-entry"
          + "/oc-netinst:next-hops/oc-netinst:next-hop/oc-netinst:state/oc-netinst:popped-mpls-label-stack" {
    deviate not-supported;
    description
      "Not supported in this release";
  }

  deviation "/oc-netinst:network-instances/oc-netinst:network-instance"
          + "/oc-netinst:afts-units/oc-netinst:aft-unit-entry"
          + "/oc-netinst:afts/oc-netinst:ipv4-unicast/oc-netinst:ipv4-entry"
          + "/oc-netinst:next-hops/oc-netinst:next-hop/oc-netinst:state/oc-netinst:origin-protocol" {
    deviate not-supported;
    description
      "Not supported in this release";
  }

  deviation "/oc-netinst:network-instances/oc-netinst:network-instance"
          + "/oc-netinst:afts-units/oc-netinst:aft-unit-entry"
          + "/oc-netinst:afts/oc-netinst:ipv4-unicast/oc-netinst:ipv4-entry"
          + "/oc-netinst:next-hops/oc-netinst:next-hop/oc-netinst:interface-ref"
          + "/oc-netinst:config" {
    deviate not-supported;
    description
      "Not supported in this release";
  }

  deviation "/oc-netinst:network-instances/oc-netinst:network-instance"
          + "/oc-netinst:afts-units/oc-netinst:aft-unit-entry"
          + "/oc-netinst:afts/oc-netinst:ipv6-unicast/oc-netinst:ipv6-entry"
          + "/oc-netinst:next-hops/oc-netinst:next-hop/oc-netinst:state/oc-netinst:index" {
    deviate not-supported;
    description
      "Not supported in this release";
  }

  deviation "/oc-netinst:network-instances/oc-netinst:network-instance"
          + "/oc-netinst:afts-units/oc-netinst:aft-unit-entry"
          + "/oc-netinst:afts/oc-netinst:ipv6-unicast/oc-netinst:ipv6-entry"
          + "/oc-netinst:next-hops/oc-netinst:next-hop/oc-netinst:state/oc-netinst:weight" {
    deviate not-supported;
    description
      "Not supported in this release";
  }

  deviation "/oc-netinst:network-instances/oc-netinst:network-instance"
          + "/oc-netinst:afts-units/oc-netinst:aft-unit-entry"
          + "/oc-netinst:afts/oc-netinst:ipv6-unicast/oc-netinst:ipv6-entry"
          + "/oc-netinst:next-hops/oc-netinst:next-hop/oc-netinst:state/oc-netinst:decapsulate-header" {
    deviate not-supported;
    description
      "Not supported in this release";
  }

  deviation "/oc-netinst:network-instances/oc-netinst:network-instance"
          + "/oc-netinst:afts-units/oc-netinst:aft-unit-entry"
          + "/oc-netinst:afts/oc-netinst:ipv6-unicast/oc-netinst:ipv6-entry"
          + "/oc-netinst:next-hops/oc-netinst:next-hop/oc-netinst:state/oc-netinst:encapsulate-header" {
    deviate not-supported;
    description
      "Not supported in this release";
  }

  deviation "/oc-netinst:network-instances/oc-netinst:network-instance"
          + "/oc-netinst:afts-units/oc-netinst:aft-unit-entry"
          + "/oc-netinst:afts/oc-netinst:ipv6-unicast/oc-netinst:ipv6-entry"
          + "/oc-netinst:next-hops/oc-netinst:next-hop/oc-netinst:state/oc-netinst:popped-mpls-label-stack" {
    deviate not-supported;
    description
      "Not supported in this release";
  }

  deviation "/oc-netinst:network-instances/oc-netinst:network-instance"
          + "/oc-netinst:afts-units/oc-netinst:aft-unit-entry"
          + "/oc-netinst:afts/oc-netinst:ipv6-unicast/oc-netinst:ipv6-entry"
          + "/oc-netinst:next-hops/oc-netinst:next-hop/oc-netinst:state/oc-netinst:origin-protocol" {
    deviate not-supported;
    description
      "Not supported in this release";
  }

  deviation "/oc-netinst:network-instances/oc-netinst:network-instance"
          + "/oc-netinst:afts-units/oc-netinst:aft-unit-entry"
          + "/oc-netinst:afts/oc-netinst:ipv6-unicast/oc-netinst:ipv6-entry"
          + "/oc-netinst:next-hops/oc-netinst:next-hop/oc-netinst:interface-ref"
          + "/oc-netinst:config" {
    deviate not-supported;
    description
      "Not supported in this release";
  }

  deviation "/oc-netinst:network-instances/oc-netinst:network-instance"
          + "/oc-netinst:afts-units/oc-netinst:aft-unit-entry"
          + "/oc-netinst:afts/oc-netinst:mpls/oc-netinst:label-entry"
          + "/oc-netinst:next-hops/oc-netinst:next-hop/oc-netinst:state/oc-netinst:index" {
    deviate not-supported;
    description
      "Not supported in this release";
  }

  deviation "/oc-netinst:network-instances/oc-netinst:network-instance"
          + "/oc-netinst:afts-units/oc-netinst:aft-unit-entry"
          + "/oc-netinst:afts/oc-netinst:mpls/oc-netinst:label-entry"
          + "/oc-netinst:next-hops/oc-netinst:next-hop/oc-netinst:state/oc-netinst:weight" {
    deviate not-supported;
    description
      "Not supported in this release";
  }

  deviation "/oc-netinst:network-instances/oc-netinst:network-instance"
          + "/oc-netinst:afts-units/oc-netinst:aft-unit-entry"
          + "/oc-netinst:afts/oc-netinst:mpls/oc-netinst:label-entry"
          + "/oc-netinst:next-hops/oc-netinst:next-hop/oc-netinst:state/oc-netinst:decapsulate-header" {
    deviate not-supported;
    description
      "Not supported in this release";
  }

  deviation "/oc-netinst:network-instances/oc-netinst:network-instance"
          + "/oc-netinst:afts-units/oc-netinst:aft-unit-entry"
          + "/oc-netinst:afts/oc-netinst:mpls/oc-netinst:label-entry"
          + "/oc-netinst:next-hops/oc-netinst:next-hop/oc-netinst:state/oc-netinst:encapsulate-header" {
    deviate not-supported;
    description
      "Not supported in this release";
  }

  deviation "/oc-netinst:network-instances/oc-netinst:network-instance"
          + "/oc-netinst:afts-units/oc-netinst:aft-unit-entry"
          + "/oc-netinst:afts/oc-netinst:mpls/oc-netinst:label-entry"
          + "/oc-netinst:next-hops/oc-netinst:next-hop/oc-netinst:state/oc-netinst:origin-protocol" {
    deviate not-supported;
    description
      "Not supported in this release";
  }

  deviation "/oc-netinst:network-instances/oc-netinst:network-instance"
          + "/oc-netinst:afts-units/oc-netinst:aft-unit-entry"
          + "/oc-netinst:afts/oc-netinst:mpls/oc-netinst:label-entry"
          + "/oc-netinst:next-hops/oc-netinst:next-hop/oc-netinst:interface-ref"
          + "/oc-netinst:config" {
    deviate not-supported;
    description
      "Not supported in this release";
  }

  /*
   * Deviation for ISIS.
   */

  deviation "/oc-netinst:network-instances/oc-netinst:network-instance"
          + "/oc-netinst:protocols/oc-netinst:protocol/oc-netinst:isis/oc-netinst:global"
          + "/oc-netinst:config/oc-netinst:authentication-check" {
    deviate not-supported;
    description
      "Not supported in this release";
  }

  deviation "/oc-netinst:network-instances/oc-netinst:network-instance"
          + "/oc-netinst:protocols/oc-netinst:protocol/oc-netinst:isis/oc-netinst:global"
          + "/oc-netinst:state/oc-netinst:authentication-check" {
    deviate not-supported;
    description
      "Not supported in this release";
  }

  deviation "/oc-netinst:network-instances/oc-netinst:network-instance"
          + "/oc-netinst:protocols/oc-netinst:protocol/oc-netinst:isis/oc-netinst:global"
          + "/oc-netinst:config/oc-netinst:instance" {
    deviate not-supported;
    description
      "Not supported in this release";
  }

  deviation "/oc-netinst:network-instances/oc-netinst:network-instance"
          + "/oc-netinst:protocols/oc-netinst:protocol/oc-netinst:isis/oc-netinst:global"
          + "/oc-netinst:config/oc-netinst:net" {
    deviate add {
      max-elements 3;
    }
    description
      "Only suppport three area-address in this release";
  }

  deviation "/oc-netinst:network-instances/oc-netinst:network-instance"
          + "/oc-netinst:protocols/oc-netinst:protocol/oc-netinst:isis/oc-netinst:global"
          + "/oc-netinst:config/oc-netinst:maximum-area-addresses" {
    deviate not-supported;
    description
      "Not supported in this release";
  }

  deviation "/oc-netinst:network-instances/oc-netinst:network-instance"
          + "/oc-netinst:protocols/oc-netinst:protocol/oc-netinst:isis/oc-netinst:global"
          + "/oc-netinst:config/oc-netinst:poi-tlv" {
    deviate not-supported;
    description
      "Not supported in this release";
  }

  deviation "/oc-netinst:network-instances/oc-netinst:network-instance"
          + "/oc-netinst:protocols/oc-netinst:protocol/oc-netinst:isis/oc-netinst:global"
          + "/oc-netinst:config/oc-netinst:iid-tlv" {
    deviate not-supported;
    description
      "Not supported in this release";
  }

  deviation "/oc-netinst:network-instances/oc-netinst:network-instance"
          + "/oc-netinst:protocols/oc-netinst:protocol/oc-netinst:isis/oc-netinst:global"
          + "/oc-netinst:config/oc-netinst:fast-flooding" {
    deviate not-supported;
    description
      "Not supported in this release";
  }

  deviation "/oc-netinst:network-instances/oc-netinst:network-instance"
          + "/oc-netinst:protocols/oc-netinst:protocol/oc-netinst:isis/oc-netinst:global"
          + "/oc-netinst:lsp-bit/oc-netinst:overload-bit/oc-netinst:config"
          + "/oc-netinst:advertise-high-metric" {
    deviate not-supported;
    description
      "Not supported in this release";
  }

  deviation "/oc-netinst:network-instances/oc-netinst:network-instance"
          + "/oc-netinst:protocols/oc-netinst:protocol/oc-netinst:isis/oc-netinst:global"
          + "/oc-netinst:lsp-bit/oc-netinst:overload-bit/oc-netinst:reset-triggers"
          + "/oc-netinst:reset-trigger/oc-netinst:config/oc-netinst:reset-trigger" {
    deviate add {
      must "(not (current() = 'oc-isis-types:WAIT_FOR_SYSTEM'))" {
        error-message "WAIT_FOR_SYSTEM not supported yet";
      }
    }
    description
      "Not supported in this release";
  }

  deviation "/oc-netinst:network-instances/oc-netinst:network-instance"
          + "/oc-netinst:protocols/oc-netinst:protocol/oc-netinst:isis/oc-netinst:global"
          + "/oc-netinst:reference-bandwidth" {
    deviate not-supported;
    description
      "Not supported in this release";
  }

  deviation "/oc-netinst:network-instances/oc-netinst:network-instance"
          + "/oc-netinst:protocols/oc-netinst:protocol/oc-netinst:isis/oc-netinst:global"
          + "/oc-netinst:timers/oc-netinst:lsp-generation" {
    deviate not-supported;
    description
      "Not supported in this release";
  }

  deviation "/oc-netinst:network-instances/oc-netinst:network-instance"
          + "/oc-netinst:protocols/oc-netinst:protocol/oc-netinst:isis/oc-netinst:global"
          + "/oc-netinst:inter-level-propagation-policies" {
    deviate not-supported;
    description
      "Not supported in this release";
  }

  deviation "/oc-netinst:network-instances/oc-netinst:network-instance"
          + "/oc-netinst:protocols/oc-netinst:protocol/oc-netinst:isis/oc-netinst:global"
          + "/oc-netinst:nsr" {
    deviate not-supported;
    description
      "Not supported in this release";
  }

  deviation "/oc-netinst:network-instances/oc-netinst:network-instance"
          + "/oc-netinst:protocols/oc-netinst:protocol/oc-netinst:isis/oc-netinst:global"
          + "/oc-netinst:mpls" {
    deviate not-supported;
    description
      "Not supported in this release";
  }

  deviation "/oc-netinst:network-instances/oc-netinst:network-instance"
          + "/oc-netinst:protocols/oc-netinst:protocol/oc-netinst:isis/oc-netinst:global"
          + "/oc-netinst:igp-shortcuts" {
    deviate not-supported;
    description
      "Not supported in this release";
  }

  deviation "/oc-netinst:network-instances/oc-netinst:network-instance"
          + "/oc-netinst:protocols/oc-netinst:protocol/oc-netinst:isis/oc-netinst:global"
          + "/oc-netinst:afi-safi/oc-netinst:af/oc-netinst:config/oc-netinst:metric" {
    deviate not-supported;
    description
      "Not supported in this release";
  }

  deviation "/oc-netinst:network-instances/oc-netinst:network-instance"
          + "/oc-netinst:protocols/oc-netinst:protocol/oc-netinst:isis/oc-netinst:global"
          + "/oc-netinst:afi-safi/oc-netinst:af/oc-netinst:state/oc-netinst:metric" {
    deviate not-supported;
    description
      "Not supported in this release";
  }

  deviation "/oc-netinst:network-instances/oc-netinst:network-instance"
          + "/oc-netinst:protocols/oc-netinst:protocol/oc-netinst:isis/oc-netinst:global"
          + "/oc-netinst:afi-safi/oc-netinst:af/oc-netinst:config/oc-netinst:safi-name" {
    deviate add {
      must "current() = 'oc-isis-types:UNICAST'" {
        error-message "SAFI not supported yet";
      }
    }
    description
      "Do not support multicast SAFI in this release";
  }

  deviation "/oc-netinst:network-instances/oc-netinst:network-instance"
          + "/oc-netinst:protocols/oc-netinst:protocol/oc-netinst:isis/oc-netinst:global"
          + "/oc-netinst:afi-safi/oc-netinst:af/oc-netinst:multi-topology" {
    deviate not-supported;
    description
      "Not supported in this release";
  }

  deviation "/oc-netinst:network-instances/oc-netinst:network-instance"
          + "/oc-netinst:protocols/oc-netinst:protocol/oc-netinst:isis/oc-netinst:global"
          + "/oc-netinst:timers/oc-netinst:spf/oc-netinst:config"
          + "/oc-netinst:spf-hold-interval" {
    deviate replace {
      type uint64 {
        range "1..120000";
      }
    }
    description
      "Add range for spf-hold-interval limit";
  }

  deviation "/oc-netinst:network-instances/oc-netinst:network-instance"
          + "/oc-netinst:protocols/oc-netinst:protocol/oc-netinst:isis/oc-netinst:global"
          + "/oc-netinst:timers/oc-netinst:spf/oc-netinst:config"
          + "/oc-netinst:spf-first-interval" {
    deviate replace {
      type uint64 {
        range "1..120000";
      }
    }
    description
      "Add range and default for spf-first-interval limit";
  }

  deviation "/oc-netinst:network-instances/oc-netinst:network-instance"
          + "/oc-netinst:protocols/oc-netinst:protocol/oc-netinst:isis/oc-netinst:global"
          + "/oc-netinst:transport/oc-netinst:config/oc-netinst:lsp-mtu-size" {
    deviate replace {
      type uint16 {
        range "128..65535";
      }
    }
    description
      "Add range for lsp-mtu-size";
  }

  deviation "/oc-netinst:network-instances/oc-netinst:network-instance"
          + "/oc-netinst:protocols/oc-netinst:protocol/oc-netinst:isis/oc-netinst:global"
          + "/oc-netinst:timers/oc-netinst:spf/oc-netinst:config"
          + "/oc-netinst:spf-second-interval" {
    deviate replace {
      type uint64 {
        range "1..120000";
      }
    }
    description
      "Add range and default for spf-second-interval limit";
  }

  deviation "/oc-netinst:network-instances/oc-netinst:network-instance"
          + "/oc-netinst:protocols/oc-netinst:protocol/oc-netinst:isis/oc-netinst:levels"
          + "/oc-netinst:level/oc-netinst:config/oc-netinst:authentication-check" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:state/oc-netinst:authentication-check" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:config/oc-netinst:metric-style" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:ipv4-te-router-id" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:ipv6-te-router-id" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:instance-id" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:ipv4-srlg" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:ipv6-srlg" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:purge-oi" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:router-capabilities" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:is-reachability" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-is-reachability"
          + "/oc-netinst:neighbors/oc-netinst:neighbor/oc-netinst:state/oc-netinst:system-id" {
    deviate replace {
      type arc-isis-types:node-id;
    }
    description
      "Fix incorrect use of System-Id as the key.";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:ipv4-internal-reachability" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:ipv4-external-reachability" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-is-reachability"
          + "/oc-netinst:neighbors/oc-netinst:neighbor/oc-netinst:subTLVs" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-ipv4-reachability"
          + "/oc-netinst:prefixes/oc-netinst:prefix/oc-netinst:subTLVs/oc-netinst:subTLVs"
          + "/oc-netinst:ipv4-source-router-id" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-ipv4-reachability"
          + "/oc-netinst:prefixes/oc-netinst:prefix/oc-netinst:subTLVs/oc-netinst:subTLVs"
          + "/oc-netinst:ipv6-source-router-id" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:extended-ipv4-reachability"
          + "/oc-netinst:prefixes/oc-netinst:prefix/oc-netinst:subTLVs/oc-netinst:subTLVs"
          + "/oc-netinst:prefix-sid" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:ipv6-reachability"
          + "/oc-netinst:prefixes/oc-netinst:prefix/oc-netinst:subTLVs/oc-netinst:subTLVs"
          + "/oc-netinst:ipv4-source-router-id" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:ipv6-reachability"
          + "/oc-netinst:prefixes/oc-netinst:prefix/oc-netinst:subTLVs/oc-netinst:subTLVs"
          + "/oc-netinst:ipv6-source-router-id" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:ipv6-reachability"
          + "/oc-netinst:prefixes/oc-netinst:prefix/oc-netinst:subTLVs/oc-netinst:subTLVs"
          + "/oc-netinst:prefix-sid" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-ipv4-reachability" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-ipv6-reachability" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:isis-neighbor-attribute" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:isis-alias-id" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-isn" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:mt-isis-neighbor-attribute" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:link-state-database/oc-netinst:lsp"
          + "/oc-netinst:tlvs/oc-netinst:tlv/oc-netinst:multi-topology" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:traffic-engineering" {
    deviate not-supported;
    description
      "Not supported in this release";
  }

  deviation "/oc-netinst:network-instances/oc-netinst:network-instance"
          + "/oc-netinst:protocols/oc-netinst:protocol/oc-netinst:isis/oc-netinst:levels"
          + "/oc-netinst:level/oc-netinst:route-preference" {
    deviate not-supported;
    description
      "Not supported in this release";
  }

  deviation "/oc-netinst:network-instances/oc-netinst:network-instance"
          + "/oc-netinst:protocols/oc-netinst:protocol/oc-netinst:isis/oc-netinst:interfaces"
          + "/oc-netinst:interface/oc-netinst:afi-safi/oc-netinst:af/oc-netinst:safi-name" {
    deviate add {
      must "current() = 'oc-isis-types:UNICAST'" {
        error-message "SAFI not supported yet";
      }
    }
    description
      "Do not support multicast SAFI in this release";
  }

  deviation "/oc-netinst:network-instances/oc-netinst:network-instance"
          + "/oc-netinst:protocols/oc-netinst:protocol/oc-netinst:isis/oc-netinst:interfaces"
          + "/oc-netinst:interface/oc-netinst:levels/oc-netinst:level"
          + "/oc-netinst:afi-safi/oc-netinst:af/oc-netinst:config/oc-netinst:metric" {
    deviate not-supported;
    description
      "Not supported in this release";
  }

  deviation "/oc-netinst:network-instances/oc-netinst:network-instance"
          + "/oc-netinst:protocols/oc-netinst:protocol/oc-netinst:isis/oc-netinst:interfaces"
          + "/oc-netinst:interface/oc-netinst:levels/oc-netinst:level"
          + "/oc-netinst:afi-safi/oc-netinst:af/oc-netinst:state/oc-netinst:metric" {
    deviate not-supported;
    description
      "Not supported in this release";
  }

  deviation "/oc-netinst:network-instances/oc-netinst:network-instance"
          + "/oc-netinst:protocols/oc-netinst:protocol/oc-netinst:isis/oc-netinst:interfaces"
          + "/oc-netinst:interface/oc-netinst:levels/oc-netinst:level"
          + "/oc-netinst:afi-safi/oc-netinst:af/oc-netinst:segment-routing" {
    deviate not-supported;
    description
      "Not supported in this release";
  }

  deviation "/oc-netinst:network-instances/oc-netinst:network-instance"
          + "/oc-netinst:protocols/oc-netinst:protocol/oc-netinst:isis/oc-netinst:interfaces"
          + "/oc-netinst:interface/oc-netinst:levels/oc-netinst:level"
          + "/oc-netinst:afi-safi" {
    deviate not-supported;
    description
      "Not supported in this release";
  }

  deviation "/oc-netinst:network-instances/oc-netinst:network-instance"
          + "/oc-netinst:protocols/oc-netinst:protocol/oc-netinst:isis/oc-netinst:interfaces"
          + "/oc-netinst:interface/oc-netinst:levels/oc-netinst:level"
          + "/oc-netinst:config/oc-netinst:passive" {
    deviate not-supported;
    description
      "Not supported in this release";
  }

  deviation "/oc-netinst:network-instances/oc-netinst:network-instance"
          + "/oc-netinst:protocols/oc-netinst:protocol/oc-netinst:isis/oc-netinst:interfaces"
          + "/oc-netinst:interface/oc-netinst:levels/oc-netinst:level"
          + "/oc-netinst:state/oc-netinst:passive" {
    deviate not-supported;
    description
      "Not supported in this release";
  }

  deviation "/oc-netinst:network-instances/oc-netinst:network-instance"
          + "/oc-netinst:protocols/oc-netinst:protocol/oc-netinst:isis/oc-netinst:interfaces"
          + "/oc-netinst:interface/oc-netinst:levels/oc-netinst:level"
          + "/oc-netinst:packet-counters/oc-netinst:esh" {
    deviate not-supported;
    description
      "Not supported in this release";
  }

  deviation "/oc-netinst:network-instances/oc-netinst:network-instance"
          + "/oc-netinst:protocols/oc-netinst:protocol/oc-netinst:isis/oc-netinst:interfaces"
          + "/oc-netinst:interface/oc-netinst:levels/oc-netinst:level"
          + "/oc-netinst:packet-counters/oc-netinst:ish" {
    deviate not-supported;
    description
      "Not supported in this release";
  }

  deviation "/oc-netinst:network-instances/oc-netinst:network-instance"
          + "/oc-netinst:protocols/oc-netinst:protocol/oc-netinst:isis/oc-netinst:interfaces"
          + "/oc-netinst:interface/oc-netinst:config/oc-netinst:hello-padding" {
    deviate not-supported;
    description
      "Not supported in this release";
  }

  /*
   * Make circuit-type to be operation state only and change the
   * type to the level-bits which is more accurate based on protocol
   * specificiation.
   */

  deviation "/oc-netinst:network-instances/oc-netinst:network-instance"
          + "/oc-netinst:protocols/oc-netinst:protocol/oc-netinst:isis/oc-netinst:interfaces"
          + "/oc-netinst:interface/oc-netinst:config/oc-netinst:circuit-type" {
    deviate not-supported;
    description
      "Not supported in this release";
  }

  deviation "/oc-netinst:network-instances/oc-netinst:network-instance"
          + "/oc-netinst:protocols/oc-netinst:protocol/oc-netinst:isis/oc-netinst:interfaces"
          + "/oc-netinst:interface/oc-netinst:state/oc-netinst:circuit-type" {
    deviate replace {
      type identityref {
        base arc-isis-types:level-bits;
      }
    }
    description
      "Fix incorrect use of the term circuit-type.";
  }

  deviation "/oc-netinst:network-instances/oc-netinst:network-instance"
          + "/oc-netinst:fdb/oc-netinst:config" {
    deviate not-supported;
    description
      "Not supported in this release";
  }

  deviation "/oc-netinst:network-instances/oc-netinst:network-instance" +
    "/oc-netinst:fdb/oc-netinst:state" {
    deviate not-supported;
    description "Not supported in this release";
  }

  /* no support for per-mac vlan or multiple vlans in an l2ni */

  deviation "/oc-netinst:network-instances/oc-netinst:network-instance"
          + "/oc-netinst:fdb/oc-netinst:mac-table/oc-netinst:entries/oc-netinst:entry/oc-netinst:config"
          + "/oc-netinst:vlan" {
    deviate not-supported;
    description
      "Not supported in this release";
  }

  deviation "/oc-netinst:network-instances/oc-netinst:network-instance" +
    "/oc-netinst:fdb/oc-netinst:mac-table/oc-netinst:entries/oc-netinst:entry/oc-netinst:interface" +
    "/oc-netinst:interface-ref/oc-netinst:config/oc-netinst:subinterface" {
    deviate not-supported;
    description "Not supported in this release";
  }

  deviation "/oc-netinst:network-instances/oc-netinst:network-instance" +
    "/oc-netinst:fdb/oc-netinst:mac-table/oc-netinst:entries/oc-netinst:entry/oc-netinst:interface" +
    "/oc-netinst:interface-ref/oc-netinst:state/oc-netinst:subinterface" {
    deviate not-supported;
    description "Not supported in this release";
  }

  deviation "/oc-netinst:network-instances/oc-netinst:network-instance" +
    "/oc-netinst:fdb/oc-netinst:mac-table/oc-netinst:entries/oc-netinst:entry" +
    "/oc-netinst:state/oc-netinst:age" {
    deviate not-supported;
    description "Not supported in this release";
  }

  /* protocol and table-conn supported for L3VRF only */

  deviation "/oc-netinst:network-instances/oc-netinst:network-instance" +
            "/oc-netinst:protocols/oc-netinst:protocol" +
            "/oc-netinst:config/oc-netinst:identifier" {
    deviate add {
      must "(../../../../oc-netinst:config/oc-netinst:type = 'oc-ni-types:L3VRF') or " +
           "(../identifier = 'oc-pol-types:BGP' and ../../../../oc-netinst:config/oc-netinst:type = 'oc-ni-types:L2VLAN')" {
        error-message "Cannot configure protocol instance in this mode";
      }
    }
    description
      "protocol only supported on l3 network instance";
  }

  deviation "/oc-netinst:network-instances/oc-netinst:network-instance/oc-netinst:table-connections/oc-netinst:table-connection" {
    deviate add {
      must "../../oc-netinst:config/oc-netinst:type = 'oc-ni-types:L3VRF'" {
        error-message "table-connection may only be configured for default or mamagement L3VRF network instance type";
      }
    }
    description
      "table-connection only supported on l3 network instance";
  }

  deviation "/oc-netinst:network-instances/oc-netinst:network-instance"
          + "/oc-netinst:fdb/oc-netinst:mac-table/oc-netinst:entries/oc-netinst:entry" {
    deviate add {
      must "../../../../oc-netinst:config/oc-netinst:type = 'oc-ni-types:L2VLAN' and ../../../../oc-netinst:config/oc-netinst:vlan" {
        error-message "mac entry may only be configured in L2VLAN network instance with a valid vlan-id";
      }
    }
    description
      "mac entry may only be configured in L2VLAN network instance with a valid vlan-id";
  }

  deviation "/oc-netinst:network-instances/oc-netinst:network-instance/oc-netinst:config/oc-netinst:type" {
    deviate add {
      default "oc-ni-types:L3VRF";
    }
  }

  /**********************
   * Deviations for BGP *
   **********************/
  // Global BGP Commands modified.
  deviation "/oc-netinst:network-instances/oc-netinst:network-instance" +
            "/oc-netinst:protocols/oc-netinst:protocol" +
            "/oc-netinst:bgp" +
            "/oc-netinst:global/oc-netinst:config/oc-netinst:as" {
    deviate replace {
      mandatory false;
    }
    deviate add {
      must "../../../../../../oc-netinst:name = 'default'" {
        error-message "BGP global AS number must be configured in network-instance default only.";
      }
    }
  }

  deviation "/oc-netinst:network-instances/oc-netinst:network-instance" +
            "/oc-netinst:protocols/oc-netinst:protocol" +
            "/oc-netinst:bgp" +
            "/oc-netinst:global/oc-netinst:config/oc-netinst:router-id" {
    deviate add {
      must "../../../../../../oc-netinst:name = 'default'" {
        error-message "BGP router-id must be configured in network-instance default only.";
      }
    }
  }

  deviation "/oc-netinst:network-instances/oc-netinst:network-instance" +
            "/oc-netinst:protocols/oc-netinst:protocol" +
            "/oc-netinst:bgp" +
            "/oc-netinst:neighbors/oc-netinst:neighbor" +
            "/oc-netinst:ebgp-multihop/oc-netinst:config/oc-netinst:enabled" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:apply-policy" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:config/oc-netinst:local-as" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi" +
            "/oc-netinst:apply-policy/oc-netinst:config/oc-netinst:import-policy" {
    deviate add {
      max-elements 8;
    }
    description "Only support eight policies in this release.";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi" +
            "/oc-netinst:apply-policy/oc-netinst:config" +
            "/oc-netinst:default-import-policy" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi" +
            "/oc-netinst:apply-policy/oc-netinst:config/oc-netinst:export-policy" {
    deviate add {
      max-elements 8;
    }
    description "Only support eight policies in this release.";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi" +
            "/oc-netinst:apply-policy/oc-netinst:config" +
            "/oc-netinst:default-export-policy" {
    deviate not-supported;
    description "Not supported in this release";
  }


  deviation "/oc-netinst:network-instances/oc-netinst:network-instance" +
            "/oc-netinst:protocols/oc-netinst:protocol" +
            "/oc-netinst:bgp" +
            "/oc-netinst:neighbors/oc-netinst:neighbor" +
            "/oc-netinst:ebgp-multihop/oc-netinst:config/oc-netinst:multihop-ttl" {
    deviate add {
      must ". > 0" {
        error-message "TTL cannot be set to 0";
      }
    }
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:config/oc-netinst:afi-safi-name" {
    deviate add {
      must "(boolean(/oc-netinst:network-instances" +
                    "/oc-netinst:network-instance[name=current()/../../../../../../../../../config/name]" +
                    "/oc-netinst:protocols/oc-netinst:protocol" +
                    "/oc-netinst:bgp/oc-netinst:global/oc-netinst:afi-safis" +
                    "/oc-netinst:afi-safi[afi-safi-name=current()]/oc-netinst:config/oc-netinst:afi-safi-name))" {
        error-message "BGP global AF must be configured first.";
      }
    }
    description "Not supported in this release";
  }

  // Global BGP Commands not supported.
  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:add-paths" +
            "/oc-netinst:config/oc-netinst:receive" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:add-paths" +
            "/oc-netinst:config/oc-netinst:send" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:add-paths" +
            "/oc-netinst:config/oc-netinst:send-max" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:add-paths" +
            "/oc-netinst:state/oc-netinst:receive" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:add-paths" +
            "/oc-netinst:state/oc-netinst:send" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:add-paths" +
            "/oc-netinst:state/oc-netinst:send-max" {
    deviate not-supported;
    description "Not supported in this release";
  }

  deviation "/oc-netinst:network-instances/oc-netinst:network-instance" +
            "/oc-netinst:protocols/oc-netinst:protocol" +
            "/oc-netinst:bgp" +
            "/oc-netinst:global/oc-netinst:confederation" {
    deviate not-supported;
    description "Not supported in this release";
  }

  deviation "/oc-netinst:network-instances/oc-netinst:network-instance" +
            "/oc-netinst:protocols/oc-netinst:protocol" +
            "/oc-netinst:bgp" +
            "/oc-netinst:global/oc-netinst:use-multiple-paths" {
    deviate not-supported;
    description "Not supported in this release";
  }

  deviation "/oc-netinst:network-instances/oc-netinst:network-instance" +
            "/oc-netinst:protocols/oc-netinst:protocol" +
            "/oc-netinst:bgp" +
            "/oc-netinst:global/oc-netinst:default-route-distance" {
    deviate not-supported;
    description "Not supported in this release";
  }

  deviation "/oc-netinst:network-instances/oc-netinst:network-instance" +
            "/oc-netinst:protocols/oc-netinst:protocol" +
            "/oc-netinst:bgp" +
            "/oc-netinst:global/oc-netinst:dynamic-neighbor-prefixes" {
    deviate not-supported;
    description "Not supported in this release";
  }

  // Global route-selection knobs not supported
  deviation "/oc-netinst:network-instances/oc-netinst:network-instance" +
            "/oc-netinst:protocols/oc-netinst:protocol" +
            "/oc-netinst:bgp" +
            "/oc-netinst:global/oc-netinst:route-selection-options" +
            "/oc-netinst:config/oc-netinst:always-compare-med" {
    deviate not-supported;
    description "Not supported in this release";
  }

  deviation "/oc-netinst:network-instances/oc-netinst:network-instance" +
            "/oc-netinst:protocols/oc-netinst:protocol" +
            "/oc-netinst:bgp" +
            "/oc-netinst:global/oc-netinst:route-selection-options" +
            "/oc-netinst:state/oc-netinst:always-compare-med" {
    deviate not-supported;
    description "Not supported in this release";
  }

  deviation "/oc-netinst:network-instances/oc-netinst:network-instance" +
            "/oc-netinst:protocols/oc-netinst:protocol" +
            "/oc-netinst:bgp" +
            "/oc-netinst:global/oc-netinst:route-selection-options" +
            "/oc-netinst:config/oc-netinst:ignore-as-path-length" {
    deviate not-supported;
    description "Not supported in this release";
  }

  deviation "/oc-netinst:network-instances/oc-netinst:network-instance" +
            "/oc-netinst:protocols/oc-netinst:protocol" +
            "/oc-netinst:bgp" +
            "/oc-netinst:global/oc-netinst:route-selection-options" +
            "/oc-netinst:state/oc-netinst:ignore-as-path-length" {
    deviate not-supported;
    description "Not supported in this release";
  }

  deviation "/oc-netinst:network-instances/oc-netinst:network-instance" +
            "/oc-netinst:protocols/oc-netinst:protocol" +
            "/oc-netinst:bgp" +
            "/oc-netinst:global/oc-netinst:route-selection-options" +
            "/oc-netinst:config/oc-netinst:external-compare-router-id" {
    deviate not-supported;
    description "Not supported in this release";
  }

  deviation "/oc-netinst:network-instances/oc-netinst:network-instance" +
            "/oc-netinst:protocols/oc-netinst:protocol" +
            "/oc-netinst:bgp" +
            "/oc-netinst:global/oc-netinst:route-selection-options" +
            "/oc-netinst:state/oc-netinst:external-compare-router-id" {
    deviate not-supported;
    description "Not supported in this release";
  }

  deviation "/oc-netinst:network-instances/oc-netinst:network-instance" +
            "/oc-netinst:protocols/oc-netinst:protocol" +
            "/oc-netinst:bgp" +
            "/oc-netinst:global/oc-netinst:route-selection-options" +
            "/oc-netinst:config/oc-netinst:advertise-inactive-routes" {
    deviate not-supported;
    description "Not supported in this release";
  }

  deviation "/oc-netinst:network-instances/oc-netinst:network-instance" +
            "/oc-netinst:protocols/oc-netinst:protocol" +
            "/oc-netinst:bgp" +
            "/oc-netinst:global/oc-netinst:route-selection-options" +
            "/oc-netinst:state/oc-netinst:advertise-inactive-routes" {
    deviate not-supported;
    description "Not supported in this release";
  }

  deviation "/oc-netinst:network-instances/oc-netinst:network-instance" +
            "/oc-netinst:protocols/oc-netinst:protocol" +
            "/oc-netinst:bgp" +
            "/oc-netinst:global/oc-netinst:route-selection-options" +
            "/oc-netinst:config/oc-netinst:enable-aigp" {
    deviate not-supported;
    description "Not supported in this release";
  }

  deviation "/oc-netinst:network-instances/oc-netinst:network-instance" +
            "/oc-netinst:protocols/oc-netinst:protocol" +
            "/oc-netinst:bgp" +
            "/oc-netinst:global/oc-netinst:route-selection-options" +
            "/oc-netinst:state/oc-netinst:enable-aigp" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:route-selection-options" {
    deviate not-supported;
    description "Not supported in this release";
  }

  // Global BGP AF Commands not supported.
  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:config/oc-netinst:enabled" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:use-multiple-paths" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:ipv4-unicast/oc-netinst:prefix-limit" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:ipv4-unicast/oc-netinst:config/oc-netinst:send-default-route" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:ipv6-unicast/oc-netinst:prefix-limit" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:ipv6-unicast/oc-netinst:config/oc-netinst:send-default-route" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:ipv4-labeled-unicast/oc-netinst:prefix-limit" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:ipv6-labeled-unicast/oc-netinst:prefix-limit" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:l3vpn-ipv4-unicast/oc-netinst:prefix-limit" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:l3vpn-ipv6-unicast/oc-netinst:prefix-limit" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:l3vpn-ipv4-multicast/oc-netinst:prefix-limit" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:l3vpn-ipv6-multicast/oc-netinst:prefix-limit" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:l2vpn-vpls/oc-netinst:prefix-limit" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:l2vpn-evpn/oc-netinst:prefix-limit" {
    deviate not-supported;
    description "Not supported in this release";
  }

  // Global BGP Neighbor Commands not supported.
  deviation "/oc-netinst:network-instances/oc-netinst:network-instance" +
            "/oc-netinst:protocols/oc-netinst:protocol" +
            "/oc-netinst:bgp" +
            "/oc-netinst:neighbors/oc-netinst:neighbor/oc-netinst:config" +
            "/oc-netinst:enabled" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor/oc-netinst:state" +
            "/oc-netinst:session-state" {
    deviate replace {
      type arc-oc-bgp-types:session-state-type;
    }
    description "BGP session state with updated types";
  }

  deviation "/oc-netinst:network-instances/oc-netinst:network-instance" +
            "/oc-netinst:protocols/oc-netinst:protocol" +
            "/oc-netinst:bgp" +
            "/oc-netinst:neighbors/oc-netinst:neighbor/oc-netinst:config" +
            "/oc-netinst:peer-type" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor/oc-netinst:config" +
            "/oc-netinst:route-flap-damping" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor/oc-netinst:state" +
            "/oc-netinst:route-flap-damping" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor/oc-netinst:config" +
            "/oc-netinst:send-community" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor/oc-netinst:timers" +
            "/oc-netinst:config/oc-netinst:minimum-advertisement-interval" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor/oc-netinst:timers" +
            "/oc-netinst:config/oc-netinst:hold-time" {
    deviate replace { default 180; }
  }

  deviation "/oc-netinst:network-instances/oc-netinst:network-instance" +
            "/oc-netinst:protocols/oc-netinst:protocol" +
            "/oc-netinst:bgp" +
            "/oc-netinst:neighbors/oc-netinst:neighbor/oc-netinst:timers" +
            "/oc-netinst:config/oc-netinst:keepalive-interval" {
    deviate replace { default 60; }
  }

  deviation "/oc-netinst:network-instances/oc-netinst:network-instance" +
            "/oc-netinst:protocols/oc-netinst:protocol" +
            "/oc-netinst:bgp" +
            "/oc-netinst:neighbors/oc-netinst:neighbor/oc-netinst:transport" +
            "/oc-netinst:config/oc-netinst:tcp-mss" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor/oc-netinst:transport" +
            "/oc-netinst:config/oc-netinst:mtu-discovery" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:error-handling" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:graceful-restart/oc-netinst:config" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor/oc-netinst:logging-options" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:route-reflector/oc-netinst:state" +
            "/oc-netinst:route-reflector-cluster-id" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:route-reflector/oc-netinst:config" +
            "/oc-netinst:route-reflector-cluster-id" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:use-multiple-paths" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor/oc-netinst:afi-safis" +
            "/oc-netinst:afi-safi/oc-netinst:config/oc-netinst:enabled" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi" +
            "/oc-netinst:graceful-restart/oc-netinst:config" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor/oc-netinst:afi-safis" +
            "/oc-netinst:afi-safi/oc-netinst:ipv4-unicast/oc-netinst:config" +
            "/oc-netinst:send-default-route" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor/oc-netinst:afi-safis" +
            "/oc-netinst:afi-safi/oc-netinst:ipv6-unicast/oc-netinst:config" +
            "/oc-netinst:send-default-route" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:use-multiple-paths" {
    deviate not-supported;
    description "Not supported in this release";
  }

  // Global BGP Commands modified.
  deviation "/oc-netinst:network-instances/oc-netinst:network-instance" +
            "/oc-netinst:protocols/oc-netinst:protocol" +
            "/oc-netinst:bgp" +
            "/oc-netinst:global/oc-netinst:afi-safis/oc-netinst:afi-safi/oc-netinst:config/oc-netinst:afi-safi-name" {
    deviate add {
       must "boolean(/oc-netinst:network-instances/oc-netinst:network-instance[name='default']" +
                    "/oc-netinst:protocols/oc-netinst:protocol" +
                    "/oc-netinst:bgp/oc-netinst:global/oc-netinst:config/oc-netinst:as) and " +
            "boolean(/oc-netinst:network-instances/oc-netinst:network-instance[name='default']" +
                    "/oc-netinst:protocols/oc-netinst:protocol" +
                    "/oc-netinst:bgp/oc-netinst:global/oc-netinst:config/oc-netinst:router-id)" {
           error-message "Local-AS and Router-ID must be configured.";
       }
    }
    description "Confd workaround";
  }

  deviation "/oc-netinst:network-instances/oc-netinst:network-instance" +
            "/oc-netinst:protocols/oc-netinst:protocol" +
            "/oc-netinst:bgp" +
            "/oc-netinst:neighbors/oc-netinst:neighbor/oc-netinst:config/oc-netinst:neighbor-address" {
    deviate add {
       must "boolean(/oc-netinst:network-instances/oc-netinst:network-instance[name='default']" +
                    "/oc-netinst:protocols/oc-netinst:protocol" +
                    "/oc-netinst:bgp/oc-netinst:global/oc-netinst:config/oc-netinst:as) and " +
            "boolean(/oc-netinst:network-instances/oc-netinst:network-instance[name='default']" +
                    "/oc-netinst:protocols/oc-netinst:protocol" +
                    "/oc-netinst:bgp/oc-netinst:global/oc-netinst:config/oc-netinst:router-id)" {
           error-message "Local-AS and Router-ID must be configured.";
       }
    }
    description "Confd workaround";
  }

  // Graceful-restart related deviations
  deviation "/oc-netinst:network-instances/oc-netinst:network-instance" +
            "/oc-netinst:protocols/oc-netinst:protocol" +
            "/oc-netinst:bgp" +
            "/oc-netinst:global/oc-netinst:graceful-restart" +
            "/oc-netinst:config/oc-netinst:enabled" {
    deviate add {
      default true;
    }
    description "Global graceful-restart enabled default value added";
  }

  deviation "/oc-netinst:network-instances/oc-netinst:network-instance" +
            "/oc-netinst:protocols/oc-netinst:protocol" +
            "/oc-netinst:bgp" +
            "/oc-netinst:global/oc-netinst:graceful-restart" +
            "/oc-netinst:config/oc-netinst:stale-routes-time" {
    deviate replace {
      type uint16;
    }
    description "Global graceful-restart stale-time type changed";
  }

  deviation "/oc-netinst:network-instances/oc-netinst:network-instance" +
            "/oc-netinst:protocols/oc-netinst:protocol" +
            "/oc-netinst:bgp" +
            "/oc-netinst:global/oc-netinst:graceful-restart/oc-netinst:state" +
            "/oc-netinst:stale-routes-time" {
    deviate replace {
      type uint16;
    }
    description "Global graceful-restart stale-time type changed";
  }

  deviation "/oc-netinst:network-instances/oc-netinst:network-instance" +
            "/oc-netinst:protocols/oc-netinst:protocol" +
            "/oc-netinst:bgp" +
            "/oc-netinst:global/oc-netinst:graceful-restart" +
            "/oc-netinst:config/oc-netinst:stale-routes-time" {
    deviate add {
      default 300;
    }
    description "Global graceful-restart stale-time default value added";
  }

  deviation "/oc-netinst:network-instances/oc-netinst:network-instance" +
            "/oc-netinst:protocols/oc-netinst:protocol" +
            "/oc-netinst:bgp" +
            "/oc-netinst:global/oc-netinst:graceful-restart" +
            "/oc-netinst:config/oc-netinst:restart-time" {
    deviate add {
      default 120;
    }
    description "Global graceful-restart restart-time default value added";
  }

  deviation "/oc-netinst:network-instances/oc-netinst:network-instance" +
            "/oc-netinst:protocols/oc-netinst:protocol" +
            "/oc-netinst:bgp" +
            "/oc-netinst:neighbors/oc-netinst:neighbor" +
            "/oc-netinst:graceful-restart/oc-netinst:state/oc-netinst:stale-routes-time" {
    deviate replace {
      type uint16;
    }
    description "Neighbor graceful-restart stale-time type changed";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:graceful-restart/oc-netinst:config/oc-netinst:enabled" {
    deviate delete {
      default false;
    }
    description "Global AF graceful-restart enabled default value deleted";
  }

  // end graceful-restart related deviations

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:state" +
            "/oc-netinst:prefixes/oc-netinst:installed" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:state" +
            "/oc-netinst:prefixes/oc-netinst:received-pre-policy" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:ipv4-unicast" +
            "/oc-netinst:prefix-limit/oc-netinst:config/oc-netinst:max-prefixes" {
    deviate replace {
      type uint32 {
        range "1..max";
      }
    }
    description "Add range for neighbor AF max-prefixes limit";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:ipv4-labeled-unicast" +
            "/oc-netinst:prefix-limit/oc-netinst:config/oc-netinst:max-prefixes" {
    deviate replace {
      type uint32 {
        range "1..max";
      }
    }
    description "Add range for neighbor AF max-prefixes limit";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:ipv6-unicast" +
            "/oc-netinst:prefix-limit/oc-netinst:config/oc-netinst:max-prefixes" {
    deviate replace {
      type uint32 {
        range "1..max";
      }
    }
    description "Add range for neighbor AF max-prefixes limit";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:ipv6-labeled-unicast" +
            "/oc-netinst:prefix-limit/oc-netinst:config/oc-netinst:max-prefixes" {
    deviate replace {
      type uint32 {
        range "1..max";
      }
    }
    description "Add range for neighbor AF max-prefixes limit";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:l3vpn-ipv4-unicast" +
            "/oc-netinst:prefix-limit/oc-netinst:config/oc-netinst:max-prefixes" {
    deviate replace {
      type uint32 {
        range "1..max";
      }
    }
    description "Add range for neighbor AF max-prefixes limit";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:l3vpn-ipv6-unicast" +
            "/oc-netinst:prefix-limit/oc-netinst:config/oc-netinst:max-prefixes" {
    deviate replace {
      type uint32 {
        range "1..max";
      }
    }
    description "Add range for neighbor AF max-prefixes limit";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:l2vpn-evpn" +
            "/oc-netinst:prefix-limit/oc-netinst:config/oc-netinst:max-prefixes" {
    deviate replace {
      type uint32 {
        range "1..max";
      }
    }
    description "Add range for neighbor AF max-prefixes limit";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:ipv4-unicast" +
            "/oc-netinst:prefix-limit/oc-netinst:config/oc-netinst:prevent-teardown" {
    deviate delete {
      default false;
    }
    description "Remove the unnecessary default value";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:ipv6-unicast" +
            "/oc-netinst:prefix-limit/oc-netinst:config/oc-netinst:prevent-teardown" {
    deviate delete {
      default false;
    }
    description "Remove the unnecessary default value";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:ipv4-labeled-unicast" +
            "/oc-netinst:prefix-limit/oc-netinst:config/oc-netinst:prevent-teardown" {
    deviate delete {
      default false;
    }
    description "Remove the unnecessary default value";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:ipv6-labeled-unicast" +
            "/oc-netinst:prefix-limit/oc-netinst:config/oc-netinst:prevent-teardown" {
    deviate delete {
      default false;
    }
    description "Remove the unnecessary default value";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:l3vpn-ipv4-unicast" +
            "/oc-netinst:prefix-limit/oc-netinst:config/oc-netinst:prevent-teardown" {
    deviate delete {
      default false;
    }
    description "Remove the unnecessary default value";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:l3vpn-ipv6-unicast" +
            "/oc-netinst:prefix-limit/oc-netinst:config/oc-netinst:prevent-teardown" {
    deviate delete {
      default false;
    }
    description "Remove the unnecessary default value";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:l2vpn-evpn" +
            "/oc-netinst:prefix-limit/oc-netinst:config/oc-netinst:prevent-teardown" {
    deviate delete {
      default false;
    }
    description "Remove the unnecessary default value";
  }

  /*
   * Make "max-prefixes" mandatory for "prefix-limit" config.
   */
  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:ipv4-unicast" +
            "/oc-netinst:prefix-limit/oc-netinst:config" {
    deviate add {
      must "boolean(oc-netinst:max-prefixes) or " +
           "(boolean(oc-netinst:prevent-teardown) != 'true' and" +
           " boolean(oc-netinst:warning-threshold-pct) != 'true' and" +
           " boolean(oc-netinst:restart-timer) != 'true')" {
        error-message "'max-prefixes' must be configured for prefix-limit.";
      }
    }
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:ipv6-unicast" +
            "/oc-netinst:prefix-limit/oc-netinst:config" {
    deviate add {
      must "boolean(oc-netinst:max-prefixes) or " +
           "(boolean(oc-netinst:prevent-teardown) != 'true' and" +
           " boolean(oc-netinst:warning-threshold-pct) != 'true' and" +
           " boolean(oc-netinst:restart-timer) != 'true')" {
        error-message "'max-prefixes' must be configured for prefix-limit.";
      }
    }
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:ipv4-labeled-unicast" +
            "/oc-netinst:prefix-limit/oc-netinst:config" {
    deviate add {
      must "boolean(oc-netinst:max-prefixes) or " +
           "(boolean(oc-netinst:prevent-teardown) != 'true' and" +
           " boolean(oc-netinst:warning-threshold-pct) != 'true' and" +
           " boolean(oc-netinst:restart-timer) != 'true')" {
        error-message "'max-prefixes' must be configured for prefix-limit.";
      }
    }
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:ipv6-labeled-unicast" +
            "/oc-netinst:prefix-limit/oc-netinst:config" {
    deviate add {
      must "boolean(oc-netinst:max-prefixes) or " +
           "(boolean(oc-netinst:prevent-teardown) != 'true' and" +
           " boolean(oc-netinst:warning-threshold-pct) != 'true' and" +
           " boolean(oc-netinst:restart-timer) != 'true')" {
        error-message "'max-prefixes' must be configured for prefix-limit.";
      }
    }
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:l3vpn-ipv4-unicast" +
            "/oc-netinst:prefix-limit/oc-netinst:config" {
    deviate add {
      must "boolean(oc-netinst:max-prefixes) or " +
           "(boolean(oc-netinst:prevent-teardown) != 'true' and" +
           " boolean(oc-netinst:warning-threshold-pct) != 'true' and" +
           " boolean(oc-netinst:restart-timer) != 'true')" {
        error-message "'max-prefixes' must be configured for prefix-limit.";
      }
    }
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:l3vpn-ipv6-unicast" +
            "/oc-netinst:prefix-limit/oc-netinst:config" {
    deviate add {
      must "boolean(oc-netinst:max-prefixes) or " +
           "(boolean(oc-netinst:prevent-teardown) != 'true' and" +
           " boolean(oc-netinst:warning-threshold-pct) != 'true' and" +
           " boolean(oc-netinst:restart-timer) != 'true')" {
        error-message "'max-prefixes' must be configured for prefix-limit.";
      }
    }
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi/oc-netinst:l2vpn-evpn" +
            "/oc-netinst:prefix-limit/oc-netinst:config" {
    deviate add {
      must "boolean(oc-netinst:max-prefixes) or " +
           "(boolean(oc-netinst:prevent-teardown) != 'true' and" +
           " boolean(oc-netinst:warning-threshold-pct) != 'true' and" +
           " boolean(oc-netinst:restart-timer) != 'true')" {
        error-message "'max-prefixes' must be configured for prefix-limit.";
      }
    }
  }

  /*
   * Deviations for peer-group under BGP
   */
  // Global BGP Commands modified.
  deviation "/oc-netinst:network-instances/oc-netinst:network-instance" +
            "/oc-netinst:protocols/oc-netinst:protocol" +
            "/oc-netinst:bgp" +
            "/oc-netinst:peer-groups/oc-netinst:peer-group" +
            "/oc-netinst:apply-policy" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:config/oc-netinst:local-as" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi" +
            "/oc-netinst:apply-policy/oc-netinst:config/oc-netinst:import-policy" {
    deviate add {
      max-elements 1;
    }
    description "Only support one policy in this release.";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi" +
            "/oc-netinst:apply-policy/oc-netinst:config" +
            "/oc-netinst:default-import-policy" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi" +
            "/oc-netinst:apply-policy/oc-netinst:config/oc-netinst:export-policy" {
    deviate add {
      max-elements 8;
    }
    description "Only support eight policies in this release.";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi" +
            "/oc-netinst:apply-policy/oc-netinst:config" +
            "/oc-netinst:default-export-policy" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:config" +
            "/oc-netinst:afi-safi-name" {
    deviate add {
      must "(boolean(/oc-netinst:network-instances" +
           "/oc-netinst:network-instance[name=current()/../../../../../../../../../config/name]" +
           "/oc-netinst:protocols/oc-netinst:protocol" +
           "/oc-netinst:bgp" +
           "/oc-netinst:global/oc-netinst:afi-safis" +
           "/oc-netinst:afi-safi[afi-safi-name=current()/../afi-safi-name]))" {
        error-message "BGP global AF must be configured first.";
      }
    }
    description "Not supported in this release";
  }

  deviation "/oc-netinst:network-instances/oc-netinst:network-instance" +
            "/oc-netinst:protocols/oc-netinst:protocol" +
            "/oc-netinst:bgp" +
            "/oc-netinst:peer-groups/oc-netinst:peer-group/oc-netinst:config" +
            "/oc-netinst:peer-type" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group/oc-netinst:config" +
            "/oc-netinst:route-flap-damping" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group/oc-netinst:state" +
            "/oc-netinst:route-flap-damping" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group/oc-netinst:config" +
            "/oc-netinst:send-community" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group/oc-netinst:state" +
            "/oc-netinst:send-community" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group/oc-netinst:state" +
            "/oc-netinst:total-paths" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group/oc-netinst:state" +
            "/oc-netinst:total-prefixes" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group/oc-netinst:timers" +
            "/oc-netinst:config/oc-netinst:minimum-advertisement-interval" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group/oc-netinst:timers" +
            "/oc-netinst:config/oc-netinst:hold-time" {
    deviate replace { default 180; }
  }

  deviation "/oc-netinst:network-instances/oc-netinst:network-instance" +
            "/oc-netinst:protocols/oc-netinst:protocol" +
            "/oc-netinst:bgp" +
            "/oc-netinst:peer-groups/oc-netinst:peer-group/oc-netinst:timers" +
            "/oc-netinst:config/oc-netinst:keepalive-interval" {
    deviate replace { default 60; }
  }

  deviation "/oc-netinst:network-instances/oc-netinst:network-instance" +
            "/oc-netinst:protocols/oc-netinst:protocol" +
            "/oc-netinst:bgp" +
            "/oc-netinst:peer-groups/oc-netinst:peer-group" +
            "/oc-netinst:transport/oc-netinst:config/oc-netinst:tcp-mss" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:transport/oc-netinst:config/oc-netinst:mtu-discovery" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:error-handling" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:graceful-restart/oc-netinst:config" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:logging-options" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:route-reflector/oc-netinst:state" +
            "/oc-netinst:route-reflector-cluster-id" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:route-reflector/oc-netinst:config" +
            "/oc-netinst:route-reflector-cluster-id" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:use-multiple-paths" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:config/oc-netinst:enabled" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi" +
            "/oc-netinst:graceful-restart/oc-netinst:config" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:ipv4-unicast" +
            "/oc-netinst:config/oc-netinst:send-default-route" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:ipv6-unicast" +
            "/oc-netinst:config/oc-netinst:send-default-route" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:use-multiple-paths" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:graceful-restart/oc-netinst:config/oc-netinst:stale-routes-time" {
    deviate replace {
      type uint16;
    }
    description "Neighbor graceful-restart stale-time type changed";
  }

  deviation "/oc-netinst:network-instances/oc-netinst:network-instance" +
            "/oc-netinst:protocols/oc-netinst:protocol" +
            "/oc-netinst:bgp" +
            "/oc-netinst:peer-groups/oc-netinst:peer-group" +
            "/oc-netinst:graceful-restart/oc-netinst:state/oc-netinst:stale-routes-time" {
    deviate replace {
      type uint16;
    }
    description "Neighbor graceful-restart stale-time type changed";
  }

  deviation "/oc-netinst:network-instances/oc-netinst:network-instance" +
            "/oc-netinst:protocols/oc-netinst:protocol" +
            "/oc-netinst:bgp" +
            "/oc-netinst:peer-groups/oc-netinst:peer-group" +
            "/oc-netinst:graceful-restart/oc-netinst:config/oc-netinst:stale-routes-time" {
    deviate add {
      default 300;
    }
    description "Neighbor graceful-restart stale-time default value added";
  }

  deviation "/oc-netinst:network-instances/oc-netinst:network-instance" +
            "/oc-netinst:protocols/oc-netinst:protocol" +
            "/oc-netinst:bgp" +
            "/oc-netinst:peer-groups/oc-netinst:peer-group" +
            "/oc-netinst:graceful-restart/oc-netinst:config/oc-netinst:restart-time" {
    deviate add {
      default 120;
    }
    description "Neighbor graceful-restart stale-time default value added";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:ipv4-unicast" +
            "/oc-netinst:prefix-limit/oc-netinst:config/oc-netinst:max-prefixes" {
    deviate replace {
      type uint32 {
        range "1..max";
      }
    }
    description "Add range for neighbor AF max-prefixes limit";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:ipv4-labeled-unicast" +
            "/oc-netinst:prefix-limit/oc-netinst:config/oc-netinst:max-prefixes" {
    deviate replace {
      type uint32 {
        range "1..max";
      }
    }
    description "Add range for neighbor AF max-prefixes limit";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:ipv6-unicast" +
            "/oc-netinst:prefix-limit/oc-netinst:config/oc-netinst:max-prefixes" {
    deviate replace {
      type uint32 {
        range "1..max";
      }
    }
    description "Add range for neighbor AF max-prefixes limit";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:ipv6-labeled-unicast" +
            "/oc-netinst:prefix-limit/oc-netinst:config/oc-netinst:max-prefixes" {
    deviate replace {
      type uint32 {
        range "1..max";
      }
    }
    description "Add range for neighbor AF max-prefixes limit";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:l3vpn-ipv4-unicast" +
            "/oc-netinst:prefix-limit/oc-netinst:config/oc-netinst:max-prefixes" {
    deviate replace {
      type uint32 {
        range "1..max";
      }
    }
    description "Add range for neighbor AF max-prefixes limit";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:l3vpn-ipv6-unicast" +
            "/oc-netinst:prefix-limit/oc-netinst:config/oc-netinst:max-prefixes" {
    deviate replace {
      type uint32 {
        range "1..max";
      }
    }
    description "Add range for neighbor AF max-prefixes limit";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:l2vpn-evpn" +
            "/oc-netinst:prefix-limit/oc-netinst:config/oc-netinst:max-prefixes" {
    deviate replace {
      type uint32 {
        range "1..max";
      }
    }
    description "Add range for neighbor AF max-prefixes limit";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:ipv4-unicast" +
            "/oc-netinst:prefix-limit/oc-netinst:config/oc-netinst:prevent-teardown" {
    deviate delete {
      default false;
    }
    description "Remove the unnecessary default value";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:ipv6-unicast" +
            "/oc-netinst:prefix-limit/oc-netinst:config/oc-netinst:prevent-teardown" {
    deviate delete {
      default false;
    }
    description "Remove the unnecessary default value";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:ipv4-labeled-unicast" +
            "/oc-netinst:prefix-limit/oc-netinst:config/oc-netinst:prevent-teardown" {
    deviate delete {
      default false;
    }
    description "Remove the unnecessary default value";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:ipv6-labeled-unicast" +
            "/oc-netinst:prefix-limit/oc-netinst:config/oc-netinst:prevent-teardown" {
    deviate delete {
      default false;
    }
    description "Remove the unnecessary default value";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:l3vpn-ipv4-unicast" +
            "/oc-netinst:prefix-limit/oc-netinst:config/oc-netinst:prevent-teardown" {
    deviate delete {
      default false;
    }
    description "Remove the unnecessary default value";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:l3vpn-ipv6-unicast" +
            "/oc-netinst:prefix-limit/oc-netinst:config/oc-netinst:prevent-teardown" {
    deviate delete {
      default false;
    }
    description "Remove the unnecessary default value";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:l2vpn-evpn" +
            "/oc-netinst:prefix-limit/oc-netinst:config/oc-netinst:prevent-teardown" {
    deviate delete {
      default false;
    }
    description "Remove the unnecessary default value";
  }

  /*
   * Make "max-prefixes" mandatory for "prefix-limit" config.
   */
  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:ipv4-unicast" +
            "/oc-netinst:prefix-limit/oc-netinst:config" {
    deviate add {
      must "boolean(oc-netinst:max-prefixes) or " +
           "(boolean(oc-netinst:prevent-teardown) != 'true' and" +
           " boolean(oc-netinst:warning-threshold-pct) != 'true' and" +
           " boolean(oc-netinst:restart-timer) != 'true')" {
        error-message "'max-prefixes' must be configured for prefix-limit.";
      }
    }
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:ipv6-unicast" +
            "/oc-netinst:prefix-limit/oc-netinst:config" {
    deviate add {
      must "boolean(oc-netinst:max-prefixes) or " +
           "(boolean(oc-netinst:prevent-teardown) != 'true' and" +
           " boolean(oc-netinst:warning-threshold-pct) != 'true' and" +
           " boolean(oc-netinst:restart-timer) != 'true')" {
        error-message "'max-prefixes' must be configured for prefix-limit.";
      }
    }
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:ipv4-labeled-unicast" +
            "/oc-netinst:prefix-limit/oc-netinst:config" {
    deviate add {
      must "boolean(oc-netinst:max-prefixes) or " +
           "(boolean(oc-netinst:prevent-teardown) != 'true' and" +
           " boolean(oc-netinst:warning-threshold-pct) != 'true' and" +
           " boolean(oc-netinst:restart-timer) != 'true')" {
        error-message "'max-prefixes' must be configured for prefix-limit.";
      }
    }
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:ipv6-labeled-unicast" +
            "/oc-netinst:prefix-limit/oc-netinst:config" {
    deviate add {
      must "boolean(oc-netinst:max-prefixes) or " +
           "(boolean(oc-netinst:prevent-teardown) != 'true' and" +
           " boolean(oc-netinst:warning-threshold-pct) != 'true' and" +
           " boolean(oc-netinst:restart-timer) != 'true')" {
        error-message "'max-prefixes' must be configured for prefix-limit.";
      }
    }
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:l3vpn-ipv4-unicast" +
            "/oc-netinst:prefix-limit/oc-netinst:config" {
    deviate add {
      must "boolean(oc-netinst:max-prefixes) or " +
           "(boolean(oc-netinst:prevent-teardown) != 'true' and" +
           " boolean(oc-netinst:warning-threshold-pct) != 'true' and" +
           " boolean(oc-netinst:restart-timer) != 'true')" {
        error-message "'max-prefixes' must be configured for prefix-limit.";
      }
    }
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:l3vpn-ipv6-unicast" +
            "/oc-netinst:prefix-limit/oc-netinst:config" {
    deviate add {
      must "boolean(oc-netinst:max-prefixes) or " +
           "(boolean(oc-netinst:prevent-teardown) != 'true' and" +
           " boolean(oc-netinst:warning-threshold-pct) != 'true' and" +
           " boolean(oc-netinst:restart-timer) != 'true')" {
        error-message "'max-prefixes' must be configured for prefix-limit.";
      }
    }
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:l2vpn-evpn" +
            "/oc-netinst:prefix-limit/oc-netinst:config" {
    deviate add {
      must "boolean(oc-netinst:max-prefixes) or " +
           "(boolean(oc-netinst:prevent-teardown) != 'true' and" +
           " boolean(oc-netinst:warning-threshold-pct) != 'true' and" +
           " boolean(oc-netinst:restart-timer) != 'true')" {
        error-message "'max-prefixes' must be configured for prefix-limit.";
      }
    }
  }

  deviation "/oc-netinst:network-instances/oc-netinst:network-instance" +
            "/oc-netinst:protocols/oc-netinst:protocol" +
            "/oc-netinst:bgp" +
            "/oc-netinst:peer-groups/oc-netinst:peer-group/oc-netinst:config" {
    deviate add {
       must "boolean(/oc-netinst:network-instances/oc-netinst:network-instance" +
                    "/oc-netinst:protocols/oc-netinst:protocol" +
                    "/oc-netinst:bgp" +
                    "/oc-netinst:global/oc-netinst:config/oc-netinst:as) and " +
             "boolean(/oc-netinst:network-instances/oc-netinst:network-instance" +
                    "/oc-netinst:protocols/oc-netinst:protocol" +
                    "/oc-netinst:bgp" +
                    "/oc-netinst:global/oc-netinst:config/oc-netinst:router-id)" {
           error-message "Local-AS and Router-ID must be configured.";
       }
    }
    description "Confd workaround";
  }

  deviation "/oc-netinst:network-instances/oc-netinst:network-instance" +
            "/oc-netinst:protocols/oc-netinst:protocol" +
            "/oc-netinst:bgp" +
            "/oc-netinst:peer-groups/oc-netinst:peer-group" +
            "/oc-netinst:ebgp-multihop/oc-netinst:config/oc-netinst:enabled" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:ebgp-multihop/oc-netinst:state/oc-netinst:enabled" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:ebgp-multihop/oc-netinst:config/oc-netinst:multihop-ttl" {
    deviate add {
      must ". > 0" {
        error-message "TTL cannot be set to 0";
      }
    }
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:apply-policy" +
            "/oc-netinst:state/oc-netinst:default-import-policy" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi/oc-netinst:apply-policy" +
            "/oc-netinst:state/oc-netinst:default-export-policy" {
    deviate not-supported;
    description "Not supported in this release";
  }

  deviation "/oc-netinst:network-instances/oc-netinst:network-instance" +
            "/oc-netinst:protocols/oc-netinst:protocol" +
            "/oc-netinst:bgp" +
            "/oc-netinst:neighbors/oc-netinst:neighbor" +
            "/oc-netinst:afi-safis/oc-netinst:afi-safi" +
            "/oc-netinst:add-paths" {
    deviate not-supported;
    description "Not supported in this release";
  }

  deviation "/oc-netinst:network-instances/oc-netinst:network-instance" +
            "/oc-netinst:protocols/oc-netinst:protocol" +
            "/oc-netinst:bgp" +
            "/oc-netinst:peer-groups/oc-netinst:peer-group" +
            "/oc-netinst:afi-safis/oc-netinst:afi-safi" +
            "/oc-netinst:add-paths" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:add-paths" {
    deviate not-supported;
    description "Not supported in this release";
  }

  deviation "/oc-netinst:network-instances/oc-netinst:network-instance" +
            "/oc-netinst:protocols/oc-netinst:protocol" +
            "/oc-netinst:bgp" +
            "/oc-netinst:global/oc-netinst:afi-safis/oc-netinst:afi-safi" +
            "/oc-netinst:add-paths" {
    deviate not-supported;
    description "Not supported in this release";
  }

  /**************************
   * Deviations for BGP-RIB *
   **************************/
  deviation "/oc-netinst:network-instances/oc-netinst:network-instance" +
            "/oc-netinst:protocols/oc-netinst:protocol" +
            "/oc-netinst:bgp/oc-netinst:rib" +
            "/oc-netinst:attr-sets/oc-netinst:attr-set" +
            "/oc-netinst:state/oc-netinst:next-hop" {
    deviate not-supported;
    description "Not supported in this release";
  }

  deviation "/oc-netinst:network-instances/oc-netinst:network-instance" +
            "/oc-netinst:protocols/oc-netinst:protocol" +
            "/oc-netinst:bgp/oc-netinst:rib" +
            "/oc-netinst:afi-safis" +
            "/oc-netinst:afi-safi/oc-netinst:ipv4-unicast" +
            "/oc-netinst:neighbors/oc-netinst:neighbor" +
            "/oc-netinst:adj-rib-out-pre" {
    deviate not-supported;
    description "Not supported in this release";
  }

  deviation "/oc-netinst:network-instances/oc-netinst:network-instance" +
            "/oc-netinst:protocols/oc-netinst:protocol" +
            "/oc-netinst:bgp/oc-netinst:rib" +
            "/oc-netinst:afi-safis" +
            "/oc-netinst:afi-safi/oc-netinst:ipv4-unicast" +
            "/oc-netinst:neighbors/oc-netinst:neighbor" +
            "/oc-netinst:adj-rib-out-post" {
    deviate not-supported;
    description "Not supported in this release";
  }

  deviation "/oc-netinst:network-instances/oc-netinst:network-instance" +
            "/oc-netinst:protocols/oc-netinst:protocol" +
            "/oc-netinst:bgp/oc-netinst:rib" +
            "/oc-netinst:afi-safis" +
            "/oc-netinst:afi-safi/oc-netinst:ipv6-unicast" +
            "/oc-netinst:neighbors/oc-netinst:neighbor" +
            "/oc-netinst:adj-rib-out-pre" {
    deviate not-supported;
    description "Not supported in this release";
  }

  deviation "/oc-netinst:network-instances/oc-netinst:network-instance" +
            "/oc-netinst:protocols/oc-netinst:protocol" +
            "/oc-netinst:bgp/oc-netinst:rib" +
            "/oc-netinst:afi-safis" +
            "/oc-netinst:afi-safi/oc-netinst:ipv6-unicast" +
            "/oc-netinst:neighbors/oc-netinst:neighbor" +
            "/oc-netinst:adj-rib-out-post" {
    deviate not-supported;
    description "Not supported in this release";
  }

  deviation "/oc-netinst:network-instances/oc-netinst:network-instance" +
            "/oc-netinst:protocols/oc-netinst:protocol" +
            "/oc-netinst:bgp/oc-netinst:rib" +
            "/oc-netinst:afi-safis/oc-netinst:afi-safi" +
            "/oc-netinst:ipv4-unicast/oc-netinst:neighbors" +
            "/oc-netinst:neighbor/oc-netinst:state" +
            "/oc-netinst:neighbor-address" {
    deviate replace {
      type leafref {
        path "/oc-netinst:network-instances/oc-netinst:network-instance" +
             "/oc-netinst:protocols/oc-netinst:protocol" +
             "/oc-netinst:bgp/oc-netinst:neighbors/oc-netinst:neighbor" +
             "/oc-netinst:neighbor-address";
      }
    }
    description "Change neighbor-address type to leafref";
  }

  deviation "/oc-netinst:network-instances/oc-netinst:network-instance" +
            "/oc-netinst:protocols/oc-netinst:protocol" +
            "/oc-netinst:bgp/oc-netinst:rib" +
            "/oc-netinst:afi-safis/oc-netinst:afi-safi" +
            "/oc-netinst:ipv6-unicast/oc-netinst:neighbors" +
            "/oc-netinst:neighbor/oc-netinst:state" +
            "/oc-netinst:neighbor-address" {
    deviate replace {
      type leafref {
        path "/oc-netinst:network-instances/oc-netinst:network-instance" +
             "/oc-netinst:protocols/oc-netinst:protocol" +
             "/oc-netinst:bgp/oc-netinst:neighbors/oc-netinst:neighbor" +
             "/oc-netinst:neighbor-address";
      }
    }
    description "Change neighbor-address type to leafref";
  }

  deviation "/oc-netinst:network-instances/oc-netinst:network-instance" +
            "/oc-netinst:protocols/oc-netinst:protocol" +
            "/oc-netinst:bgp/oc-netinst:rib" +
            "/oc-netinst:attr-sets/oc-netinst:attr-set" +
            "/oc-netinst:tunnel-encapsulation" {
    deviate not-supported;
    description "Not supported in this release";
  }

  deviation "/oc-netinst:network-instances/oc-netinst:network-instance" +
            "/oc-netinst:protocols/oc-netinst:protocol" +
            "/oc-netinst:bgp/oc-netinst:rib" +
            "/oc-netinst:afi-safis" +
            "/oc-netinst:afi-safi/oc-netinst:ipv4-srte-policy" {
     deviate not-supported;
     description "Not supported in this release";
  }

  deviation "/oc-netinst:network-instances/oc-netinst:network-instance" +
            "/oc-netinst:protocols/oc-netinst:protocol" +
            "/oc-netinst:bgp/oc-netinst:rib" +
            "/oc-netinst:afi-safis" +
            "/oc-netinst:afi-safi/oc-netinst:ipv6-srte-policy" {
     deviate not-supported;
     description "Not supported in this release";
  }

  deviation "/oc-netinst:network-instances/oc-netinst:network-instance" +
            "/oc-netinst:protocols/oc-netinst:protocol" +
            "/oc-netinst:bgp/oc-netinst:rib" +
            "/oc-netinst:afi-safis" +
            "/oc-netinst:afi-safi/oc-netinst:ipv4-unicast" +
            "/oc-netinst:loc-rib/oc-netinst:routes/oc-netinst:route" +
            "/oc-netinst:state/oc-netinst:path-id" {
    deviate replace {
      type uint64;
    }
    description "Change path-id type to handle 64-bit internal ID";
  }

  deviation "/oc-netinst:network-instances/oc-netinst:network-instance" +
            "/oc-netinst:protocols/oc-netinst:protocol" +
            "/oc-netinst:bgp/oc-netinst:rib" +
            "/oc-netinst:afi-safis" +
            "/oc-netinst:afi-safi/oc-netinst:ipv4-unicast" +
            "/oc-netinst:neighbors/oc-netinst:neighbor" +
            "/oc-netinst:adj-rib-in-pre/oc-netinst:routes/oc-netinst:route" +
            "/oc-netinst:state/oc-netinst:path-id" {
    deviate replace {
      type uint64;
    }
    description "Change path-id type to handle 64-bit internal ID";
  }

  deviation "/oc-netinst:network-instances/oc-netinst:network-instance" +
            "/oc-netinst:protocols/oc-netinst:protocol" +
            "/oc-netinst:bgp/oc-netinst:rib" +
            "/oc-netinst:afi-safis" +
            "/oc-netinst:afi-safi/oc-netinst:ipv4-unicast" +
            "/oc-netinst:neighbors/oc-netinst:neighbor" +
            "/oc-netinst:adj-rib-in-post/oc-netinst:routes/oc-netinst:route" +
            "/oc-netinst:state/oc-netinst:path-id" {
    deviate replace {
      type uint64;
    }
    description "Change path-id type to handle 64-bit internal ID";
  }

  deviation "/oc-netinst:network-instances/oc-netinst:network-instance" +
            "/oc-netinst:protocols/oc-netinst:protocol" +
            "/oc-netinst:bgp/oc-netinst:rib" +
            "/oc-netinst:afi-safis" +
            "/oc-netinst:afi-safi/oc-netinst:ipv6-unicast" +
            "/oc-netinst:loc-rib/oc-netinst:routes/oc-netinst:route" +
            "/oc-netinst:state/oc-netinst:path-id" {
    deviate replace {
      type uint64;
    }
    description "Change path-id type to handle 64-bit internal path ID";
  }

  deviation "/oc-netinst:network-instances/oc-netinst:network-instance" +
            "/oc-netinst:protocols/oc-netinst:protocol" +
            "/oc-netinst:bgp/oc-netinst:rib" +
            "/oc-netinst:afi-safis" +
            "/oc-netinst:afi-safi/oc-netinst:ipv6-unicast" +
            "/oc-netinst:neighbors/oc-netinst:neighbor" +
            "/oc-netinst:adj-rib-in-pre/oc-netinst:routes/oc-netinst:route" +
            "/oc-netinst:state/oc-netinst:path-id" {
    deviate replace {
      type uint64;
    }
    description "Change path-id type to handle 64-bit internal ID";
  }

  deviation "/oc-netinst:network-instances/oc-netinst:network-instance" +
            "/oc-netinst:protocols/oc-netinst:protocol" +
            "/oc-netinst:bgp/oc-netinst:rib" +
            "/oc-netinst:afi-safis" +
            "/oc-netinst:afi-safi/oc-netinst:ipv6-unicast" +
            "/oc-netinst:neighbors/oc-netinst:neighbor" +
            "/oc-netinst:adj-rib-in-post/oc-netinst:routes/oc-netinst:route" +
            "/oc-netinst:state/oc-netinst:path-id" {
    deviate replace {
      type uint64;
    }
    description "Change path-id type to handle 64-bit internal ID";
  }
}
