module arcos-hardware-platform-interface {
  yang-version 1.1;
  namespace "http://yang.arrcus.com/arcos/hardware/platform/interface";
  prefix arc-hw-platform-if;

  import iana-if-type {
    prefix ianaift;
  }
  import openconfig-interfaces {
    prefix oc-if;
  }
  import arcos-platform {
    prefix arc-platform;
  }
  import arcos-hardware-platform-xgs-interface {
    prefix arc-hw-platform-xgs-if;
  }

  grouping platform-interface {
    container platform {
      uses arc-hw-platform-xgs-if:xgs-intf-mmu-profile;
    }
  }

  augment "/oc-if:interfaces/oc-if:interface" {
    uses platform-interface {
      when "(((current()/oc-if:name != 'ma1') and " +
           "(current()/oc-if:config/oc-if:type = 'ianaift:ethernetCsmacd')) and " +
           "((/arc-platform:platform/arc-platform:asic = 'arc-platform:BROADCOM_TRIDENT3') or " +
           "(/arc-platform:platform/arc-platform:asic = 'arc-platform:BROADCOM_TOMAHAWK')))";
    }
    description
      "Platform MMU queue profile";
  }
}
