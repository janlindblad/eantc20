module arcos-openconfig-system-deviations {
  yang-version 1.1;
  namespace "http://yang.arrcus.com/arcos/openconfig/system/deviations";
  prefix arc-oc-sys-dev;

  import openconfig-system {
    prefix oc-sys;
  }

  import openconfig-aaa-types {
    prefix oc-aaa-types;
  }

  import arcos-openconfig-aaa-types {
    prefix arc-oc-aaa-types;
  }

  import arcos-system-types {
    prefix arc-sys-types;
  }

  import openconfig-aaa {
    prefix oc-aaa;
  }

  import ietf-inet-types {
    prefix inet;
  }

  import ietf-yang-types {
    prefix yang;
  }

  organization
    "Arrcus, Inc.";

  contact
    "Arrcus, Inc.
     2077 Gateway Place
     Suite 400
     San Jose, CA 95110

     E-mail: yang-support@arrcus.com";

  description
    "This module defines ArcOS deviations to the
     OpenConfig system module.

     Copyright (c) 2016-2019 by Arrcus, Inc.
     All rights reserved.";


  deviation "/oc-sys:system/oc-sys:cpus" {
    deviate not-supported;
    description "Not Supported in this release";
  }

  deviation "/oc-sys:system/oc-sys:alarms" {
    deviate not-supported;
    description "Not Supported in this release";
  }

  deviation "/oc-sys:system/oc-sys:messages" {
    deviate not-supported;
    description "Not Supported in this release";
  }

  deviation "/oc-sys:system/oc-sys:state/oc-sys:current-datetime" {
    deviate replace {
      type yang:date-and-time;
    }
  }

  deviation "/oc-sys:system/oc-sys:dns/oc-sys:servers/oc-sys:server" {
    deviate add {
      max-elements 3;
    }
    description "Support only 3 DNS servers";
  }

  deviation "/oc-sys:system/oc-sys:dns/oc-sys:servers/oc-sys:server" +
            "/oc-sys:config/oc-sys:address" {
    deviate replace {
      type inet:ip-address;
    }
  }

  deviation "/oc-sys:system/oc-sys:dns/oc-sys:servers/oc-sys:server" +
            "/oc-sys:state/oc-sys:address" {
    deviate replace {
      type inet:ip-address;
    }
  }

  deviation "/oc-sys:system/oc-sys:dns/oc-sys:host-entries/oc-sys:host-entry" +
            "/oc-sys:config/oc-sys:ipv4-address" {
    deviate replace {
      type inet:ipv4-address;
    }
  }

  deviation "/oc-sys:system/oc-sys:dns/oc-sys:host-entries/oc-sys:host-entry" +
            "/oc-sys:state/oc-sys:ipv4-address" {
    deviate replace {
      type inet:ipv4-address;
    }
  }

  deviation "/oc-sys:system/oc-sys:dns/oc-sys:host-entries/oc-sys:host-entry" +
            "/oc-sys:config/oc-sys:ipv6-address" {
    deviate replace {
      type inet:ipv6-address;
    }
  }

  deviation "/oc-sys:system/oc-sys:dns/oc-sys:host-entries/oc-sys:host-entry" +
            "/oc-sys:state/oc-sys:ipv6-address" {
    deviate replace {
      type inet:ipv6-address;
    }
  }

  deviation "/oc-sys:system/oc-sys:dns/oc-sys:servers/oc-sys:server" +
            "/oc-sys:config/oc-sys:port" {
    deviate not-supported;
    description "Not Supported in this release";
  }

  deviation "/oc-sys:system/oc-sys:dns/oc-sys:servers/oc-sys:server" +
            "/oc-sys:state/oc-sys:port" {
    deviate not-supported;
    description "Not Supported in this release";
  }

  deviation "/oc-sys:system/oc-sys:ssh-server/oc-sys:config" +
            "/oc-sys:enable" {
    deviate replace {
      default false;
    }
  }

  deviation "/oc-sys:system/oc-sys:ssh-server/oc-sys:config" +
            "/oc-sys:protocol-version" {
    deviate add {
      must ". = 'V2'" {
        error-message "Only protocol-version V2 is supported";
      }
    }
  }

  deviation "/oc-sys:system/oc-sys:ssh-server/oc-sys:config" +
            "/oc-sys:rate-limit" {
    deviate not-supported;
    description "Not Supported in this release";
  }

  deviation "/oc-sys:system/oc-sys:ssh-server/oc-sys:state" +
            "/oc-sys:rate-limit" {
    deviate not-supported;
    description "Not Supported in this release";
  }

  deviation "/oc-sys:system/oc-sys:telnet-server" {
    deviate not-supported;
    description "Not Supported in this release";
  }

  deviation "/oc-sys:system/oc-sys:memory" {
    deviate not-supported;
    description "Not Supported in this release";
  }

  deviation "/oc-sys:system/oc-sys:processes" {
    deviate not-supported;
    description "Not Supported in this release";
  }

  deviation "/oc-sys:system/oc-sys:ntp/oc-sys:config/oc-sys:enabled" {
    deviate not-supported;
    description "Not Supported in this release";
  }

  deviation "/oc-sys:system/oc-sys:ntp/oc-sys:state/oc-sys:enabled" {
    deviate not-supported;
    description "Not Supported in this release";
  }

  deviation "/oc-sys:system/oc-sys:ntp/oc-sys:config/oc-sys:enable-ntp-auth" {
      deviate not-supported;
      description "Not Supported in this release";
  }

  deviation "/oc-sys:system/oc-sys:ntp/oc-sys:state/oc-sys:enable-ntp-auth" {
      deviate not-supported;
      description "Not Supported in this release";
  }

  deviation "/oc-sys:system/oc-sys:ntp/oc-sys:config" +
            "/oc-sys:ntp-source-address" {
       deviate not-supported;
       description "Not Supported in this release";
  }

  deviation "/oc-sys:system/oc-sys:ntp/oc-sys:state" +
            "/oc-sys:ntp-source-address" {
       deviate not-supported;
       description "Not Supported in this release";
  }

  deviation "/oc-sys:system/oc-sys:ntp/oc-sys:state" +
            "/oc-sys:auth-mismatch" {
       deviate not-supported;
       description "Not Supported in this release";
  }

  deviation "/oc-sys:system/oc-sys:ntp/oc-sys:ntp-keys" {
    deviate not-supported;
    description "Not Supported in this release";
  }

  deviation "/oc-sys:system/oc-sys:ntp/oc-sys:servers" +
    "/oc-sys:server/oc-sys:config/oc-sys:version" {
    deviate not-supported;
    description "Not Supported in this release";
  }

  deviation "/oc-sys:system/oc-sys:ntp/oc-sys:servers" +
    "/oc-sys:server/oc-sys:config/oc-sys:association-type" {
    deviate not-supported;
    description "Not Supported in this release";
  }

  deviation "/oc-sys:system/oc-sys:ntp/oc-sys:servers" +
    "/oc-sys:server/oc-sys:state/oc-sys:version" {
    deviate not-supported;
    description "Not Supported in this release";
  }

  deviation "/oc-sys:system/oc-sys:ntp/oc-sys:servers" +
    "/oc-sys:server/oc-sys:state/oc-sys:association-type" {
    deviate not-supported;
    description "Not Supported in this release";
  }

  deviation "/oc-sys:system/oc-sys:logging/oc-sys:remote-servers" +
            "/oc-sys:remote-server" {
    deviate add {
      must "(boolean(oc-sys:selectors/oc-sys:selector/oc-sys:facility) " +
	         "and boolean(oc-sys:selectors/oc-sys:selector/oc-sys:severity))" {
        error-message "Both facility and severity must be specified";
      }
    }
  }

  deviation "/oc-sys:system/oc-sys:logging/oc-sys:remote-servers" +
            "/oc-sys:remote-server/oc-sys:config/oc-sys:host" {
    deviate replace {
      type inet:host;
    }
    description
      "Replacement of type due to OpenConfig non-compliance with YANG 1.0/1.1 pattern statement";
  }

  deviation "/oc-sys:system/oc-sys:logging/oc-sys:remote-servers" +
            "/oc-sys:remote-server/oc-sys:state/oc-sys:host" {
    deviate replace {
      type inet:host;
    }
    description
      "Replacement of type due to OpenConfig non-compliance with YANG 1.0/1.1 pattern statement";
  }

  deviation "/oc-sys:system/oc-sys:logging/oc-sys:remote-servers" +
            "/oc-sys:remote-server/oc-sys:config/oc-sys:source-address" {
    deviate replace {
      type inet:ip-address;
    }
    description
      "Replacement of type due to OpenConfig non-compliance with YANG 1.0/1.1 pattern statement";
  }

  deviation "/oc-sys:system/oc-sys:logging/oc-sys:remote-servers" +
            "/oc-sys:remote-server/oc-sys:state/oc-sys:source-address" {
    deviate replace {
      type inet:ip-address;
    }
    description
      "Replacement of type due to OpenConfig non-compliance with YANG 1.0/1.1 pattern statement";
  }

  deviation "/oc-sys:system/oc-sys:logging/oc-sys:console" {
    deviate not-supported;
    description "Not Supported in this release";
  }

  deviation "/oc-sys:system/oc-sys:grpc-server" +
            "/oc-sys:config/oc-sys:enable" {
    deviate replace {
      default false;
    }
    description "The gRPC server is disabled by default";
  }

  deviation "/oc-sys:system/oc-sys:grpc-server" +
            "/oc-sys:config/oc-sys:listen-addresses" {
    deviate replace {
      type inet:ip-address;
    }
    deviate add {
      max-elements 1;
    }
    description
      "Replacement of type due to OpenConfig non-compliance with YANG 1.0/1.1 pattern statement";
  }

  deviation "/oc-sys:system/oc-sys:grpc-server" +
            "/oc-sys:config/oc-sys:metadata-authentication" {
    deviate replace {
      default true;
    }
    description "Metadata-authentication is enabled by default";
  }

  deviation "/oc-sys:system/oc-sys:grpc-server" +
            "/oc-sys:state/oc-sys:listen-addresses" {
    deviate replace {
      type inet:ip-address;
    }
    description "Replacement of type due to OpenConfig non-compliance with YANG 1.0/1.1 pattern statement";
  }

  deviation "/oc-sys:system/oc-sys:grpc-server" +
            "/oc-sys:config/oc-sys:certificate-id" {
    deviate not-supported;
    description "Not Supported in this release";
  }

  deviation "/oc-sys:system/oc-sys:aaa/oc-sys:authentication" +
    "/oc-sys:admin-user/oc-sys:config/oc-sys:admin-password-hashed" {
    deviate not-supported;
  }

  deviation "/oc-sys:system/oc-sys:aaa/oc-sys:authentication" +
            "/oc-sys:admin-user/oc-sys:state/oc-sys:admin-password-hashed" {
    deviate not-supported;
  }

  deviation "/oc-sys:system/oc-sys:aaa/oc-sys:authentication" +
            "/oc-sys:admin-user/oc-sys:config/oc-sys:admin-password" {
    deviate replace {
      type arc-sys-types:password-hash;
    }
  }

  deviation "/oc-sys:system/oc-sys:aaa/oc-sys:authentication" +
            "/oc-sys:admin-user/oc-sys:state/oc-sys:admin-password" {
    deviate replace {
      type arc-sys-types:password-hash;
    }
  }

  deviation "/oc-sys:system/oc-sys:aaa/oc-sys:authentication" +
            "/oc-sys:users/oc-sys:user/oc-sys:config/oc-sys:password" {
    deviate replace {
      type arc-sys-types:password-hash;
    }
  }

  deviation "/oc-sys:system/oc-sys:aaa/oc-sys:authentication" +
            "/oc-sys:users/oc-sys:user/oc-sys:config" {
    deviate add {
      must "(boolean(oc-sys:password) or boolean(oc-sys:ssh-key))" {
        error-message "Either password or ssh public key must be provided.";
      }
    }
  }

  deviation "/oc-sys:system/oc-sys:aaa/oc-sys:authentication" +
            "/oc-sys:users/oc-sys:user/oc-sys:state/oc-sys:password" {
    deviate replace {
      type arc-sys-types:password-hash;
    }
  }

  deviation "/oc-sys:system/oc-sys:aaa/oc-sys:authentication" +
            "/oc-sys:users/oc-sys:user/oc-sys:config/oc-sys:password-hashed" {
    deviate not-supported;
  }

  deviation "/oc-sys:system/oc-sys:aaa/oc-sys:authentication" +
            "/oc-sys:users/oc-sys:user/oc-sys:state/oc-sys:password-hashed" {
    deviate not-supported;
  }

  deviation "/oc-sys:system/oc-sys:aaa/oc-sys:server-groups" +
            "/oc-sys:server-group" {
    deviate add {
      max-elements 2;
    }
    description "Maximum 2 server groups supported - 1 for TACACS and 1 for RADIUS";
  }

  deviation "/oc-sys:system/oc-sys:aaa/oc-sys:server-groups" +
            "/oc-sys:server-group/oc-sys:servers/oc-sys:server" {
    deviate add {
      min-elements 1;
      max-elements 5;
    }
    description "Support maximum of 5 servers. Maintain order input by user";
  }

  deviation "/oc-sys:system/oc-sys:aaa/oc-sys:server-groups" +
            "/oc-sys:server-group/oc-sys:servers/oc-sys:server/oc-sys:config" +
            "/oc-sys:address" {
    deviate replace {
      type inet:ip-address;
    }
  }
  deviation "/oc-sys:system/oc-sys:aaa/oc-sys:server-groups" +
    "/oc-sys:server-group/oc-sys:servers/oc-sys:server/oc-sys:state" +
    "/oc-sys:address" {
    deviate replace {
      type inet:ip-address;
    }
  }

  deviation "/oc-sys:system/oc-sys:aaa/oc-sys:server-groups" +
    "/oc-sys:server-group/oc-sys:config/oc-sys:type" {
    deviate add {
      default oc-aaa:TACACS;
    }
  }

  deviation "/oc-sys:system/oc-sys:aaa/oc-sys:server-groups" +
    "/oc-sys:server-group/oc-sys:servers/oc-sys:server/oc-sys:tacacs" +
    "/oc-sys:config/oc-sys:secret-key" {
    deviate replace {
      type arc-sys-types:encrypted-string;
    }
  }

  deviation "/oc-sys:system/oc-sys:aaa/oc-sys:server-groups" +
    "/oc-sys:server-group/oc-sys:servers/oc-sys:server/oc-sys:tacacs" +
    "/oc-sys:state/oc-sys:secret-key" {
    deviate replace {
      type arc-sys-types:encrypted-string;
    }
  }

  deviation "/oc-sys:system/oc-sys:aaa/oc-sys:server-groups" +
    "/oc-sys:server-group/oc-sys:servers/oc-sys:server" {
    deviate add {
      must "((../../oc-sys:config/oc-sys:type = 'oc-aaa:TACACS') and
             boolean(./oc-sys:tacacs/oc-sys:config/oc-sys:secret-key)) or
             ((../../oc-sys:config/oc-sys:type = 'oc-aaa:RADIUS') and
             boolean(./oc-sys:radius/oc-sys:config/oc-sys:secret-key))" {
        error-message "Server secret-key configuration is mandatory" ;
      }
    }
  }

  deviation "/oc-sys:system/oc-sys:aaa/oc-sys:authentication/oc-sys:config" +
    "/oc-sys:authentication-method" {
    deviate add {
      max-elements 2;
    }
  }

  deviation "/oc-sys:system/oc-sys:aaa/oc-sys:authorization/oc-sys:config" +
    "/oc-sys:authorization-method" {
    deviate add {
      max-elements 2;
    }
  }
  deviation "/oc-sys:system/oc-sys:aaa/oc-sys:accounting/oc-sys:config" +
    "/oc-sys:accounting-method" {
    deviate add {
      max-elements 2;
    }
  }

  deviation "/oc-sys:system/oc-sys:aaa/oc-sys:server-groups" +
    "/oc-sys:server-group/oc-sys:servers/oc-sys:server/oc-sys:radius" +
    "/oc-sys:config/oc-sys:secret-key" {
    deviate replace {
      type arc-sys-types:encrypted-string;
    }
  }

  deviation "/oc-sys:system/oc-sys:aaa/oc-sys:server-groups" +
    "/oc-sys:server-group/oc-sys:servers/oc-sys:server/oc-sys:radius" +
    "/oc-sys:state/oc-sys:secret-key" {
    deviate replace {
      type arc-sys-types:encrypted-string;
    }
  }

  deviation "/oc-sys:system/oc-sys:aaa/oc-sys:config" {
    deviate not-supported;
    description "Empty node";
  }

  deviation "/oc-sys:system/oc-sys:aaa/oc-sys:state" {
    deviate not-supported;
    description "Empty node";
  }

  deviation "/oc-sys:system/oc-sys:aaa/oc-sys:authorization" +
    "/oc-sys:events" {
    deviate not-supported;
    description "Authorization Events not supported in this release";
  }

  deviation "/oc-sys:system/oc-sys:aaa/oc-sys:accounting" +
    "/oc-sys:events" {
    deviate not-supported;
    description "Accounting Events not supported in this release";
  }

  deviation "/oc-sys:system/oc-sys:aaa/oc-sys:server-groups" +
    "/oc-sys:server-group/oc-sys:servers/oc-sys:server/oc-sys:radius" +
    "/oc-sys:config/oc-sys:source-address" {
    deviate not-supported;
    description "Not supported in this release";
  }

  deviation "/oc-sys:system/oc-sys:aaa/oc-sys:server-groups" +
    "/oc-sys:server-group/oc-sys:servers/oc-sys:server/oc-sys:radius" +
    "/oc-sys:state/oc-sys:source-address" {
    deviate not-supported;
    description "Not supported in this release";
  }

  deviation "/oc-sys:system/oc-sys:aaa/oc-sys:server-groups" +
    "/oc-sys:server-group/oc-sys:servers/oc-sys:server" +
    "/oc-sys:config/oc-sys:name" {
    deviate not-supported;
    description "Not supported in this release";
  }

  deviation "/oc-sys:system/oc-sys:aaa/oc-sys:server-groups" +
    "/oc-sys:server-group/oc-sys:servers/oc-sys:server" +
    "/oc-sys:config/oc-sys:timeout" {
    deviate replace {
      type uint16 {
        range 1..60;
      }
    }
    deviate add {
      default 5;
    }
  }

  deviation "/oc-sys:system/oc-sys:aaa/oc-sys:server-groups" +
    "/oc-sys:server-group/oc-sys:servers/oc-sys:server" +
    "/oc-sys:state/oc-sys:name" {
    deviate not-supported;
    description "Not supported in this release";
  }

  deviation "/oc-sys:system/oc-sys:aaa/oc-sys:server-groups" +
    "/oc-sys:server-group/oc-sys:servers/oc-sys:server" +
    "/oc-sys:state/oc-sys:connection-opens" {
    deviate replace {
      type yang:counter64;
    }
  }
  deviation "/oc-sys:system/oc-sys:aaa/oc-sys:server-groups" +
    "/oc-sys:server-group/oc-sys:servers/oc-sys:server" +
    "/oc-sys:state/oc-sys:connection-failures" {
    deviate replace {
      type yang:counter64;
    }
  }
  deviation "/oc-sys:system/oc-sys:aaa/oc-sys:server-groups" +
    "/oc-sys:server-group/oc-sys:servers/oc-sys:server" +
    "/oc-sys:state/oc-sys:connection-timeouts" {
    deviate replace {
      type yang:counter64;
    }
  }
  deviation "/oc-sys:system/oc-sys:aaa/oc-sys:server-groups" +
    "/oc-sys:server-group/oc-sys:servers/oc-sys:server" +
    "/oc-sys:state/oc-sys:connection-closes" {
    deviate not-supported;
    description "Not supported in this release";
  }
  deviation "/oc-sys:system/oc-sys:aaa/oc-sys:server-groups" +
    "/oc-sys:server-group/oc-sys:servers/oc-sys:server" +
    "/oc-sys:state/oc-sys:connection-aborts" {
    deviate not-supported;
    description "Not supported in this release";
  }
  deviation "/oc-sys:system/oc-sys:aaa/oc-sys:server-groups" +
    "/oc-sys:server-group/oc-sys:servers/oc-sys:server" +
    "/oc-sys:state/oc-sys:messages-sent" {
    deviate not-supported;
    description "Not supported in this release";
  }
  deviation "/oc-sys:system/oc-sys:aaa/oc-sys:server-groups" +
    "/oc-sys:server-group/oc-sys:servers/oc-sys:server" +
    "/oc-sys:state/oc-sys:messages-received" {
    deviate not-supported;
    description "Not supported in this release";
  }
  deviation "/oc-sys:system/oc-sys:aaa/oc-sys:server-groups" +
    "/oc-sys:server-group/oc-sys:servers/oc-sys:server" +
    "/oc-sys:state/oc-sys:errors-received" {
    deviate not-supported;
    description "Not supported in this release";
  }

  deviation "/oc-sys:system/oc-sys:aaa/oc-sys:server-groups" +
    "/oc-sys:server-group/oc-sys:servers" +
    "/oc-sys:server/oc-sys:tacacs/oc-sys:config" +
    "/oc-sys:source-address" {
    deviate not-supported;
    description "Not supported in this release";
  }

  deviation "/oc-sys:system/oc-sys:aaa/oc-sys:server-groups" +
    "/oc-sys:server-group/oc-sys:servers" +
    "/oc-sys:server/oc-sys:tacacs/oc-sys:state" +
    "/oc-sys:source-address" {
    deviate not-supported;
    description "Not supported in this release";
  }

  deviation "/oc-sys:system/oc-sys:aaa/oc-sys:authentication" +
    "/oc-sys:users/oc-sys:user/oc-sys:config/oc-sys:role" {
    deviate replace {
      type identityref {
        base oc-aaa-types:SYSTEM_DEFINED_ROLES;
      }
    }

    deviate add {
      default arc-oc-aaa-types:SYSTEM_ROLE_OPERATOR;
    }
  }

  deviation "/oc-sys:system/oc-sys:aaa/oc-sys:authentication" +
    "/oc-sys:users/oc-sys:user/oc-sys:state/oc-sys:role" {
    deviate replace {
      type identityref {
        base oc-aaa-types:SYSTEM_DEFINED_ROLES;
      }
    }
  }

  deviation "/oc-sys:system/oc-sys:aaa/oc-sys:server-groups" +
    "/oc-sys:server-group/oc-sys:servers/oc-sys:server" +
    "/oc-sys:radius/oc-sys:config/oc-sys:retransmit-attempts" {
    deviate replace {
      type uint8 {
        range 1..10;
      }
    }
    deviate add {
      default 2;
    }
  }

}
