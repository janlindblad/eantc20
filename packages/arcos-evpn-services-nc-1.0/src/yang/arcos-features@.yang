module arcos-features {
  yang-version 1.1;
  namespace "http://yang.arrcus.com/arcos/features";
  prefix arc-features;

  identity ARCOS_FEATURE {
    description
      "Base type for ARCOS features";
  }

  identity ARCOS_MPLS {
    base ARCOS_FEATURE;
    description
      "ArcOS implementation of MPLS";
  }

  identity ARCOS_QoS {
    base ARCOS_FEATURE;
    description
      "ArcOS implementation of QoS";
  }

  identity ARCOS_SUBIF {
    base ARCOS_FEATURE;
    description
      "ArcOS implementation of Subinterfaces";
  }

  identity ARCOS_SFLOW {
    base ARCOS_FEATURE;
    description
      "ArcOS implementation of Sflow";
  }

  identity ARCOS_RIOT {
    base ARCOS_FEATURE;
    description
      "ArcOS implementation of RIOT";
  }

  identity ARCOS_ICMP_SRC_REWRITE {
    base ARCOS_FEATURE;
    description
      "ArcOS implementation of ICMP source address rewrite";
  }

  container features {
    list feature {
      key "name";
      description
        "List of features";

      leaf name {
        type identityref {
          base ARCOS_FEATURE;
        }
        description
          "Name of feature";
      }

      leaf supported {
        type boolean;
        description
          "Whether feature is supported or not";
      }
    }
  }
}
