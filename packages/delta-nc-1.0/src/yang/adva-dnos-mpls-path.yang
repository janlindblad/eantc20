module adva-dnos-mpls-path {

  namespace "http://www.advaoptical.com/cim/adva-dnos-mpls-path";

  prefix "mplsp";

  import adva-dnos-types    { prefix "adva-types"; }
  import adva-dnos-extensions { prefix adva-ext; }

  organization
    "Adva Optical Networking";

  contact
    "For technical support, please contact your service channel";

  description
    "Definitions for MPLS Path.";

  revision "2019-07-22" {
    description
      "Integrating to ADVA YANG models.";
  }

  revision "2015-03-09" {
    description
      "Third draft version.";
  }

  grouping mpls_hop_data {
    leaf name {
      type string {
        length "1..255";
      }
      description "The canonical name assigned to the path option";
    }

    leaf list-index {
      type uint32;
      description "Identifies particular explicit route object.";
    }

    leaf path-option-index {
      type uint32;
      description
        "Identifies a particular group of hops representing a
         particular configured path.";
    }

    leaf hop {
      type uint32;
      description "Identifies a particular hop.";
    }

    leaf address {
      mandatory true;
      type adva-types:mpls-lsr-id;
      description "The Tunnel Hop Address for this tunnel hop.";
    }

    leaf link-id {
      type uint32 {
        range "1..max";
      }
      description
        "Contains the interface identifier of the unnumbered
         interface for this hop.";
    }

    leaf include {
      type boolean;
      description
        "If this value is set to true, then this indicates
         that this hop must be included in the tunnel's
         path. If this value is set to 'false', then this hop
         must be avoided when calculating the path for this
         tunnel. The default value of this object is 'true',
         so that by default all indicated hops are included
         in the CSPF path computation. If this object is set
         to 'false' the value of strict field should be ignored.";
      default true;
      adva-ext:agema-default "true";
    }

    leaf strict {
      type boolean;
      description
        "Denotes whether this tunnel hop is routed in a
         strict or loose fashion. The value of this object
         has no meaning if the include field is set to 'false'.";
      default false;
      adva-ext:agema-default "false";
    }
  }

  grouping mpls_chop_data {
    leaf list-index {
      type uint32;
      config false;
      description "Identifies a particular hop list.";
    }

    leaf hop {
      type uint32;
      config false;
      description "Identifies a particular hop.";
    }

    leaf address {
      type adva-types:mpls-lsr-id;
      config false;
      description "The Tunnel Hop Address for this tunnel hop.";
    }

    leaf link-id {
      type uint32 {
        range "1..max";
      }
      config false;
      description
        "Contains the interface identifier of the unnumbered
         interface for this hop.";
    }

    leaf explicit-label {
      type string {
        length "1..255";
      }
      config false;
      description "Contains the label to use on this hop.";
    }

    leaf arhop-protection {
      type string {
        length "1..255";
      }
      config false;
      description "Availability and usage of protection on the reported link.";
    }
  }

  container mpls_hop_objects {

    container config-hops {
      list config-hop {
        key "name hop";

        description
          "An entry in this table represents the hops, strict or loose,
           for an MPLS tunnel, when it is established via signaling,
           for the outgoing direction of the tunnel.
           An entry can be created by a network administrator
           or by an SNMP agent as instructed by an MPLS
           signaling protocol.";

        uses mpls_hop_data;
      }
    }

    container runtime-hops {
      config false;

      list runtime-config-hop {
        key "name hop";

        description
          "An entry in this table represents the hops, strict or loose,
           for an MPLS tunnel, when it is established via signaling,
           for the outgoing direction of the tunnel.
           An entry can be created by a network administrator
           or by an SNMP agent as instructed by an MPLS
           signaling protocol.";

        uses mpls_hop_data;
      }

      list computed-hop {
        key "list-index hop";

        description
          "An entry in this table represents the hops, strict
           or loose, for an MPLS tunnel, as computed by a
           constraint-based routing protocol, based on the config-hop
           list for the outgoing direction of the tunnel.";

        uses mpls_chop_data;
      }

      list actual-hop {
        key "list-index hop";

        description
          "An entry in this table represents the hops, strict or loose,
           for an MPLS tunnel, as reported by the MPLS signaling protocol,
           for the outgoing direction of the tunnel.";

        uses mpls_chop_data;
      }

      list hop-index-next {
        leaf next-index {
          type uint32;
          config false;
          description
            "Contains an appropriate value to be used for
             list-index when creating entries in the
             mpls_hop_data.";
        }
        description
          "An entry in this table represents the next
           available values of hop index for all entities.";
      }
    }
  }
}
