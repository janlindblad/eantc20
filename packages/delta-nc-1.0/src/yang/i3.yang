module i3 {

  namespace "http://metaswitch.com/yang/nbu/i3";

  prefix i3;

  organization "Metaswitch Networks";

  contact "Postal: Metaswitch Networks
                   100 Church Street
                   Enfield
                   EN2 6BQ
                   United Kingdom
           Tel:    +44 20 8366 1177
           E-mail: info@metaswitch.com";

  description
    "args.owner";

  revision 2016-01-01 {
    description
      "Initial revision.";
  }

  feature emu {
    description
      "This feature means that the device supports emulated interfaces.";
  }

  typedef AMB_INETWK_ADDR_TYPE {
    description
      "";
    type enumeration {
      enum other                            { value 0; }
      enum ipv4                             { value 1; }
      enum ipv6                             { value 2; }
      enum nsap                             { value 3; }
      enum hldc                             { value 4; }
      enum bbn1822                          { value 5; }
      enum ieee802                          { value 6; }
      enum e163                             { value 7; }
      enum e164                             { value 8; }
      enum f69                              { value 9; }
      enum x121                             { value 10; }
      enum ipx                              { value 11; }
      enum apple-talk                       { value 12; }
      enum dec-net-IV                       { value 13; }
      enum banyan-vin                       { value 14; }
      enum e164-nsap                        { value 15; }
      enum ipv4-TNA                         { value 16; }
      enum ipv6-tna                         { value 17; }
      enum nsap-tna                         { value 18; }
      enum VPN-ipv4                         { value 19; }
      enum VPN-ipv6                         { value 20; }
      enum L2VPN                            { value 25; }
    }
  }

  typedef AMB_ROW_STATUS {
    description
      "";
    type enumeration {
      enum active                           { value 1; }
      enum not-in-service                   { value 2; }
      enum not-ready                        { value 3; }
      enum create-and-go                    { value 4; }
      enum create-and-wait                  { value 5; }
      enum destroy                          { value 6; }
    }
  }

  typedef AMB_TRUTH_VALUE {
    description
      "";
    type enumeration {
      enum true                             { value 1; }
      enum false                            { value 2; }
    }
  }

  typedef AMB_STUBS_I3_EA_FEC_TYPES {
    description
      "";
    type enumeration {
      enum none                             { value 0; }
      enum host                             { value 1; }
      enum prefix                           { value 2; }
      enum vc                               { value 3; }
    }
  }

  typedef AMB_STUBS_I3_EA_ASS_END_TYPES {
    description
      "";
    type enumeration {
      enum local                            { value 0; }
      enum remote                           { value 1; }
    }
  }

  typedef AMB_STUBS_I3_EA_ADDR_USE_FLAGS {
    description
      "";
    type bits {
      bit stable                           { position 0; }
      bit node                             { position 1; }
      bit sc-pc-scn                        { position 2; }
      bit sc-pc-scn-address                { position 3; }
    }
  }

  typedef AMB_I3_IF_TYPE {
    description
      "";
    type enumeration {
      enum i3-if-unknown                    { value 0; }
      enum i3-if-other                      { value 1; }
      enum i3-if-ethernet                   { value 6; }
      enum i3-if-ethernet-l2-vlan           { value 135; }
      enum i3-if-ethernet-bundle            { value 161; }
    }
  }

  typedef AMB_I3_IF_FLAGS {
    description
      "";
    type bits {
      bit mpls-tunnel                      { position 0; }
      bit loopback                         { position 1; }
      bit point-to-point                   { position 2; }
      bit broadcast                        { position 3; }
      bit multicast                        { position 4; }
      bit unnumbered                       { position 5; }
      bit nbma                             { position 6; }
      bit composite-bundle                 { position 7; }
      bit component-data-link              { position 8; }
      bit inter-domain-link                { position 9; }
      bit unidirectional-in                { position 10; }
      bit unidirectional-out               { position 11; }
      bit unnumbered-ipv6                  { position 12; }
      bit routing                          { position 13; }
      bit mpls-forwarding                  { position 14; }
      bit bypass-tunnel                    { position 15; }
      bit igp-shortcut                     { position 16; }
      bit l2-switching                     { position 17; }
      bit in-l2-bundle                     { position 18; }
      bit vlan-subinterface                { position 19; }
      bit management                       { position 20; }
      bit provider-edge-port               { position 21; }
      bit customer-edge-port               { position 22; }
      bit l2-bundle                        { position 23; }
    }
  }

  typedef AMB_OPER_STATUS {
    description
      "";
    type enumeration {
      enum up                               { value 1; }
      enum down                             { value 2; }
      enum going-up                         { value 3; }
      enum going-down                       { value 4; }
      enum activation-failed                { value 5; }
    }
  }

  typedef AMB_STUBS_I3_EI_SC_MET_TYPE {
    description
      "";
    type enumeration {
      enum shrtct-metric-absolute           { value 1; }
      enum shrtct-metric-relative           { value 2; }
    }
  }

  typedef AMB_I3_ETH_SPEEDS {
    description
      "";
    type enumeration {
      enum i3-eth-unknown                   { value 0; }
      enum i3-eth-100-kbs                   { value 1; }
      enum i3-eth-1-mbs                     { value 2; }
      enum i3-eth-10-mbs                    { value 3; }
      enum i3-eth-100-mbs                   { value 4; }
      enum i3-eth-1-gbs                     { value 5; }
      enum i3-eth-10-gbs                    { value 6; }
      enum i3-eth-100-gbs                   { value 7; }
      enum i3-eth-1-tbs                     { value 8; }
      enum i3-eth-10-tbs                    { value 9; }
      enum i3-eth-os-info                   { value 255; }
    }
  }

  typedef AMB_I3_FAULT {
    description
      "";
    type bits {
      bit i3-fault-no-comp-link            { position 0; }
      bit i3-fault-snd-fail                { position 1; }
      bit i3-fault-rcv-fail                { position 2; }
      bit i3-fault-os-info                 { position 28; }
    }
  }

  typedef AMB_I3_VLAN_TYPE {
    description
      "";
    type enumeration {
      enum i3-vlan-type-none                { value 0; }
      enum i3-vlan-c-vlan                   { value 1; }
      enum i3-vlan-s-vlan                   { value 2; }
      enum i3-vlan-b-vlan                   { value 3; }
      enum i3-vlan-os                       { value 65535; }
    }
  }

  typedef AMB_MAU_AUTO_NEG_CAP_BITS {
    description
      "";
    type bits {
      bit mau-auto-neg-cap-other           { position 0; }
      bit mau-auto-neg-cap-10b-t           { position 1; }
      bit mau-auto-neg-cap-10b-tfd         { position 2; }
      bit mau-auto-neg-cap-100b-t4         { position 3; }
      bit mau-auto-neg-cap-100b-tx         { position 4; }
      bit mau-auto-neg-cap-100b-txfd       { position 5; }
      bit mau-auto-neg-cap-100b-t2         { position 6; }
      bit mau-auto-neg-cap-100b-t2fd       { position 7; }
      bit mau-auto-neg-cap-fdx-pause       { position 8; }
      bit mau-auto-neg-cap-fdx-a-paus      { position 9; }
      bit mau-auto-neg-cap-fdx-s-paus      { position 10; }
      bit mau-auto-neg-cap-fdx-b-paus      { position 11; }
      bit mau-auto-neg-cap-1000b-x         { position 12; }
      bit mau-auto-neg-cap-1000b-xfd       { position 13; }
      bit mau-auto-neg-cap-1000b-t         { position 14; }
      bit mau-auto-neg-cap-1000b-tfd       { position 15; }
      bit mau-auto-neg-cap-10gb-t          { position 16; }
      bit mau-auto-neg-cap-1000b-kx        { position 17; }
      bit mau-auto-neg-cap-10gb-kx4        { position 18; }
      bit mau-auto-neg-cap-10gb-kr         { position 19; }
      bit mau-auto-neg-cap-40gb-kr4        { position 20; }
      bit mau-auto-neg-cap-40gb-cr4        { position 21; }
      bit mau-auto-neg-cap-100gb-cr10      { position 22; }
    }
  }

  typedef AMB_MAU_TYPES {
    description
      "";
    type enumeration {
      enum mau-type-other                   { value 0; }
      enum mau-type-aui                     { value 1; }
      enum mau-type-10-base-5               { value 2; }
      enum mau-type-foirl                   { value 3; }
      enum mau-type-10-base-2               { value 4; }
      enum mau-type-10-base-t               { value 5; }
      enum mau-type-10-base-fp              { value 6; }
      enum mau-type-10-base-fb              { value 7; }
      enum mau-type-10-base-fl              { value 8; }
      enum mau-type-10-broad-36             { value 9; }
      enum mau-type-10-base-thd             { value 10; }
      enum mau-type-10-base-tfd             { value 11; }
      enum mau-type-10-base-flhd            { value 12; }
      enum mau-type-10-base-flfd            { value 13; }
      enum mau-type-100-base-t4             { value 14; }
      enum mau-type-100-base-txhd           { value 15; }
      enum mau-type-100-base-txfd           { value 16; }
      enum mau-type-100-base-fxhd           { value 17; }
      enum mau-type-100-base-fxfd           { value 18; }
      enum mau-type-100-base-t2hd           { value 19; }
      enum mau-type-100-base-t2fd           { value 20; }
      enum mau-type-1000-base-xhd           { value 21; }
      enum mau-type-1000-base-xfd           { value 22; }
      enum mau-type-1000-base-lxhd          { value 23; }
      enum mau-type-1000-base-lxfd          { value 24; }
      enum mau-type-1000-base-sxhd          { value 25; }
      enum mau-type-1000-base-sxfd          { value 26; }
      enum mau-type-1000-base-cxhd          { value 27; }
      enum mau-type-1000-base-cxfd          { value 28; }
      enum mau-type-1000-base-thd           { value 29; }
      enum mau-type-1000-base-tfd           { value 30; }
      enum mau-type-10-gig-base-x           { value 31; }
      enum mau-type-10-gig-base-lx4         { value 32; }
      enum mau-type-10-gig-base-r           { value 33; }
      enum mau-type-10-gig-base-er          { value 34; }
      enum mau-type-10-gig-base-lr          { value 35; }
      enum mau-type-10-gig-base-sr          { value 36; }
      enum mau-type-10-gig-base-w           { value 37; }
      enum mau-type-10-gig-base-ew          { value 38; }
      enum mau-type-10-gig-base-lw          { value 39; }
      enum mau-type-10-gig-base-sw          { value 40; }
      enum mau-type-10-gig-base-cx4         { value 41; }
      enum mau-type-2-base-tl               { value 42; }
      enum mau-type-10-pass-ts              { value 43; }
      enum mau-type-100-base-bx10d          { value 44; }
      enum mau-type-100-base-bx10u          { value 45; }
      enum mau-type-100-base-lx10           { value 46; }
      enum mau-type-1000-base-bx10d         { value 47; }
      enum mau-type-1000-base-bx10u         { value 48; }
      enum mau-type-1000-base-lx10          { value 49; }
      enum mau-type-1000-base-px10d         { value 50; }
      enum mau-type-1000-base-px10u         { value 51; }
      enum mau-type-1000-base-px20d         { value 52; }
      enum mau-type-1000-base-px20u         { value 53; }
    }
  }

  typedef AMB_I3_AUTO_NEG_SUPP_ENAB_OS {
    description
      "";
    type enumeration {
      enum i3-auto-neg-os                   { value 0; }
      enum i3-auto-neg-not-supported        { value 1; }
      enum i3-auto-neg-supp-not-enab        { value 2; }
      enum i3-auto-neg-supp-and-enab        { value 3; }
    }
  }

  typedef AMB_ADMIN_STATUS {
    description
      "";
    type enumeration {
      enum up                               { value 1; }
      enum down                             { value 2; }
    }
  }

  typedef AMB_STUBS_I3_EM_REFR_OPTS {
    description
      "";
    type bits {
      bit srefresh-messages                { position 0; }
      bit bundle-send-messages             { position 1; }
      bit no-request-ack                   { position 2; }
    }
  }

  typedef AMB_STUBS_I3_EM_LBL_SPC_TYPES {
    description
      "";
    type enumeration {
      enum generic                          { value 1; }
      enum atm                              { value 2; }
      enum frame-relay                      { value 3; }
      enum lambda                           { value 4; }
    }
  }

  typedef AMB_STUBS_I3_EM_IF_SIGP_TYPES {
    description
      "";
    type bits {
      bit rsvp                             { position 0; }
      bit ldp                              { position 1; }
      bit cr-ldp                           { position 2; }
      bit component-interface              { position 5; }
      bit signaling-only-interface         { position 6; }
      bit data-only-if                     { position 7; }
      bit bundle                           { position 8; }
    }
  }

  typedef AMB_STUBS_I3_EM_ATM_VP_VC_CAPS {
    description
      "";
    type enumeration {
      enum vc                               { value 1; }
      enum vp                               { value 2; }
      enum vp-vc                            { value 3; }
    }
  }

  typedef AMB_STUBS_I3_EM_DIST_MODES {
    description
      "";
    type enumeration {
      enum on-demand                        { value 0; }
      enum unsolicited                      { value 1; }
    }
  }

  typedef AMB_STUBS_I3_EM_RETENTION_MODES {
    description
      "";
    type enumeration {
      enum conservative                     { value 0; }
      enum liberal                          { value 1; }
    }
  }

  typedef AMB_STUBS_I3_EM_FR_SESS_LEN {
    description
      "";
    type enumeration {
      enum 10-dlci-bits                     { value 1; }
      enum 23-dlci-bits                     { value 2; }
    }
  }

  typedef AMB_STUBS_I3_EM_IF_PR_FLAGS {
    description
      "";
    type bits {
      bit zero-implicit-null               { position 0; }
    }
  }

  typedef AMB_STUBS_I3_EM_EGL {
    description
      "";
    type bits {
      bit penultimate-hop-popping          { position 0; }
      bit explicit-null                    { position 1; }
    }
  }

  typedef AMB_STUBS_I3_EM_HELLO_FLAGS {
    description
      "";
    type bits {
      bit hello-global-label-space-address { position 0; }
    }
  }

  typedef AMB_I3_MPLS_UNI_VERSION {
    description
      "";
    type enumeration {
      enum none                             { value 0; }
      enum gmpls-uni                        { value 1; }
      enum uni-v1-r1                        { value 2; }
      enum uni-v1-r2                        { value 3; }
      enum uni-v2                           { value 4; }
    }
  }

  typedef AMB_STUBS_I3_BFD_FLAGS {
    description
      "";
    type bits {
      bit ldp-discovery-desired            { position 0; }
      bit rsvp-desired                     { position 1; }
    }
  }

  typedef AMB_I3_CRYPTO_AUTH_TYPES {
    description
      "";
    type enumeration {
      enum hmacmd5                          { value 0; }
      enum hmacsha1                         { value 1; }
      enum hmacsha256                       { value 2; }
      enum hmacsha384                       { value 3; }
      enum hmacsha512                       { value 4; }
    }
  }

  typedef AMB_STUBS_I3_CM_LNK_ST_ACT {
    description
      "";
    type enumeration {
      enum link-set-action-inc-list         { value 0; }
      enum link-set-action-inc-range        { value 1; }
    }
  }

  typedef AMB_STUBS_I3_CM_LNK_ST_FORMAT {
    description
      "";
    type enumeration {
      enum link-set-format-unnum            { value 0; }
      enum link-set-format-ipv4             { value 1; }
      enum link-set-format-ipv6             { value 2; }
    }
  }

  typedef AMB_STUBS_I3_SW_CAP_VALUE {
    description
      "";
    type enumeration {
      enum packet-switch-capable-1          { value 1; }
      enum packet-switch-capable-2          { value 2; }
      enum packet-switch-capable-3          { value 3; }
      enum packet-switch-capable-4          { value 4; }
      enum layer-2-switch-capable           { value 51; }
      enum tdm-capable                      { value 100; }
      enum otn-tdm-capable                  { value 110; }
      enum data-channel-switch-capable      { value 125; }
      enum lambda-switch-capable            { value 150; }
      enum fiber-switch-capable             { value 200; }
    }
  }

  typedef AMB_STUBS_I3_SW_ENCODE_VAL {
    description
      "";
    type enumeration {
      enum packet                           { value 1; }
      enum ethernet                         { value 2; }
      enum ansi-etsi-pdh                    { value 3; }
      enum sdh-sonet                        { value 5; }
      enum dig-wrapper                      { value 7; }
      enum lambda                           { value 8; }
      enum fiber                            { value 9; }
      enum fiber-channel                    { value 11; }
      enum g709-oduk                        { value 12; }
      enum g709-och                         { value 13; }
    }
  }

  typedef AMB_STUBS_I3_ET_SONET_SDH_VAL {
    description
      "";
    type enumeration {
      enum standard                         { value 0; }
      enum arb                              { value 1; }
    }
  }

  typedef AMB_STUBS_I3_SONET_SIG_TYPES {
    description
      "";
    type enumeration {
      enum vt15-spe                         { value 1; }
      enum vt2-spe                          { value 2; }
      enum vt3-spe                          { value 3; }
      enum vt6-spe                          { value 4; }
      enum sts1-spe                         { value 5; }
      enum sts3c-spe                        { value 6; }
      enum sts1                             { value 7; }
      enum sts3                             { value 8; }
      enum sts12                            { value 9; }
      enum sts48                            { value 10; }
      enum sts192                           { value 11; }
      enum sts768                           { value 12; }
    }
  }

  typedef AMB_STUBS_I3_G709_SIG_TYPES {
    description
      "";
    type enumeration {
      enum odu-1                            { value 1; }
      enum odu-2                            { value 2; }
      enum odu-3                            { value 3; }
      enum odu-4                            { value 4; }
      enum odu-0                            { value 10; }
      enum odu-2e                           { value 11; }
      enum odu-flex-cbr                     { value 20; }
      enum odu-flex-gfp-resizable           { value 21; }
      enum odu-flex-gfp-non-resizable       { value 22; }
    }
  }

  typedef AMB_I3_FAULT_STATUS {
    description
      "";
    type enumeration {
      enum fault-status-unknown             { value 0; }
      enum fault-status-none                { value 1; }
      enum fault-status-present             { value 2; }
      enum fault-status-unsupported         { value 3; }
      enum fault-status-degraded            { value 4; }
    }
  }

  typedef AMB_MDI_POWER_PORT_CLASSES {
    description
      "";
    type enumeration {
      enum mdi-power-port-class-none        { value 0; }
      enum mdi-power-port-class-pse         { value 1; }
      enum mdi-power-port-class-pd          { value 2; }
    }
  }

  typedef AMB_MDI_POWER_SYSTEM_TYPES {
    description
      "";
    type enumeration {
      enum mdi-power-system-type-none       { value 0; }
      enum mdi-power-system-type-1          { value 1; }
      enum mdi-power-system-type-2          { value 2; }
    }
  }

  typedef AMB_MDI_POWER_PRIORITIES {
    description
      "";
    type enumeration {
      enum mdi-power-priority-unknown       { value 0; }
      enum mdi-power-priority-critical      { value 1; }
      enum mdi-power-priority-high          { value 2; }
      enum mdi-power-priority-low           { value 3; }
    }
  }

  typedef AMB_MDI_POWER_PAIR_TYPES {
    description
      "";
    type enumeration {
      enum mdi-power-pair-type-none         { value 0; }
      enum mdi-power-pair-type-signal       { value 1; }
      enum mdi-power-pair-type-spare        { value 2; }
    }
  }

  typedef AMB_MDI_POWER_CLASSES {
    description
      "";
    type enumeration {
      enum mdi-power-class-none             { value 0; }
      enum mdi-power-class-0                { value 1; }
      enum mdi-power-class-1                { value 2; }
      enum mdi-power-class-2                { value 3; }
      enum mdi-power-class-3                { value 4; }
      enum mdi-power-class-4                { value 5; }
    }
  }

  typedef AMB_MDI_POWER_PSE_SRCS {
    description
      "";
    type enumeration {
      enum mdi-power-pse-src-unknown        { value 0; }
      enum mdi-power-pse-src-primary        { value 1; }
      enum mdi-power-pse-src-backup         { value 2; }
    }
  }

  typedef AMB_MDI_POWER_PD_SRCS {
    description
      "";
    type enumeration {
      enum mdi-power-pd-src-unknown         { value 0; }
      enum mdi-power-pd-src-pse             { value 1; }
      enum mdi-power-pd-src-local           { value 2; }
      enum mdi-power-pd-src-pse-an-lcl      { value 3; }
    }
  }
  container emu {
    if-feature i3:emu;
    list emu {

      description
        "Each table entry controls one I3 EMU stub instance.";

      key "index";

      leaf index {
        // Low-level model info: Corresponds to i3EmuIndex.
        type uint32;
        description
          "A value which uniquely identifies this instance of the I3
      stub.";
      } // index

      container entity {
        leaf index {
          // Low-level model info: Corresponds to i3EmuIndex.
          type uint32;
          description
            "A value which uniquely identifies this instance of the I3
      stub.";
        } // index

        leaf admin-status {
          // Low-level model info: Corresponds to i3EmuAdminStatus.
          type AMB_ADMIN_STATUS;
          default up;
          description
            "The administrative status of the I3 stub.";
        } // admin-status

        leaf oper-status {
          // Low-level model info: Corresponds to i3EmuOperStatus.
          type AMB_OPER_STATUS;
          description
            "Indicates whether a request to active this I3 stub is
      active, inactive, has failed or is changing states.";
          config false;
        } // oper-status

        leaf send-interface-data-lost {
          // Low-level model info: Corresponds to i3EmuEiDataLost.
          type boolean;
          default false;
          description
            "When an AMB_SET is received with this field set to
      AMB_TRUE, the stub will send an ATG_I3_INET_INTERFACE_IND
      signal with the data_lost flag set.  This field acts only
      as a trigger and so its value is not stored.  The value
      returned on an AMB_GET is AMB_FALSE.";
        } // send-interface-data-lost

        leaf send-address-data-lost {
          // Low-level model info: Corresponds to i3EmuEaDataLost.
          type boolean;
          default false;
          description
            "When an AMB_SET is received with this field set to
      AMB_TRUE, the stub will send an ATG_I3_INET_ADDR_IND
      signal with the data_lost flag set.  This field acts only
      as a trigger and so its value is not stored.  The value
      returned on an AMB_GET is AMB_FALSE.";
        } // send-address-data-lost

        leaf send-mpls-data-lost {
          // Low-level model info: Corresponds to i3EmuEmDataLost.
          type boolean;
          default false;
          description
            "When an AMB_SET is received with this field set to
      AMB_TRUE, the stub will send an ATG_I3_MPLS_INTERFACE_IND
      signal with the data_lost flag set.  This field acts only
      as a trigger and so its value is not stored.  The value
      returned on an AMB_GET is AMB_FALSE.";
        } // send-mpls-data-lost

        leaf send-te-data-lost {
          // Low-level model info: Corresponds to i3EmuEtDataLost.
          type boolean;
          default false;
          description
            "When an AMB_SET is received with this field set to
      AMB_TRUE, the stub will send an ATG_I3_TE_PARAMS_IND
      signal with the data_lost flag set.  This field acts only
      as a trigger and so its value is not stored.  The value
      returned on an AMB_GET is AMB_FALSE.";
        } // send-te-data-lost

        leaf send-nodal-data-lost {
          // Low-level model info: Corresponds to i3EmuEnDataLost.
          type boolean;
          default false;
          description
            "When an AMB_SET is received with this field set to
      AMB_TRUE, the stub will send an ATG_I3_NODAL_INFO_IND
      signal with the data_lost flag set.  This field acts only
      as a trigger and so its value is not stored.  The value
      returned on an AMB_GET is AMB_FALSE.";
        } // send-nodal-data-lost

        leaf use-os-config {
          // Low-level model info: Corresponds to i3EmuUseOsConfig.
          type boolean;
          default true;
          description
            "Indicates whether the I3 stub (emulated) should read
      configuration information from the OS.  When returning
      configuration data to an interface user the I3 stub will
      return all OS configuration and any emulated configuration
      for the user's profile index.

      Setting this field from true to false causes any stored OS
      configuration to be discarded.

      Note that this is test function and is not intended for
      use in real systems.

      OS configuration information is always required when
      running on a 6WINDGate operating system.  When running on
      6WINDGate, this field is ignored and cannot be set through
      the MIB.";
        } // use-os-config

        leaf update-config-now {
          // Low-level model info: Corresponds to i3EmuUpdateConfigNow.
          type boolean;
          default false;
          description
            "Indicates that the I3 stub should carry out a poll to
      refresh its stored interface and address configuration
      information.  This poll will only be carried out if
      i3UseOsConfig is set to true.

      This field acts only as a trigger and so its value is not
      stored.  The value returned on an AMB_GET is AMB_FALSE.";
        } // update-config-now

        leaf if-index-map {
          // Low-level model info: Corresponds to i3EmuIfIndexMap.
          type uint32;
          default "0";
          description
            "The I3 stub uses this value to map OS-allocated interface
      indices to system-wide unique interface indices, which are
      reported over all IPS interfaces.

      This feature allows the I3 stub to run in a distributed
      system across multiple hardware locations with each
      location reporting unique interface indices.

      Note that this is test function and must not be used in a
      real system.

      When this feature is enabled, all Metaswitch MIBs use the
      system-wide interface indices.

      The reference implementation of the I3 stub uses an XOR
      mapping to translate between the two numbering spaces.";
        } // if-index-map

        leaf assign-bundle-mac-addr {
          // Low-level model info: Corresponds to i3EmuAssignBundleMACAddr.
          type boolean;
          default false;
          description
            "If set to true, the I3 stub uses a hardcoded MAC address
      as the MAC address of any LACP/MC-LAG bundles it learns
      about and reports that value on all interface indications
      regarding the bundle.

      Note that this is test function and must not be used in a
      real system.

      Setting this field to false disables this feature.";
        } // assign-bundle-mac-addr

        leaf dynamic-if-updates {
          // Low-level model info: Corresponds to i3EmuDynamicIfUpdates.
          type boolean;
          default false;
          description
            "Indicates that the I3 stub should register with the OS for
      dynamic interface updates.  It is set on creation of the
      emulated I3 stub and cannot be changed once the stub is
      created.

      This field is for TEST PURPOSES ONLY.";
        } // dynamic-if-updates

        leaf use-idi {
          // Low-level model info: Corresponds to i3EmuUseIDI.
          type boolean;
          default false;
          description
            "Indicates whether this instance of the I3 stub should use
      the Interface Discovery Interface to provide interface
      information.

      This field is for TEST PURPOSES ONLY.";
        } // use-idi

            leaf use-global-label-space {
              // Low-level model info: Corresponds to i3EmuUseGlobalLabelSpace.
              type boolean;
              default false;
              description
                "Indicates whether this instance of the I3 stub should
      advertise the interface index of 0 on MPLS interface
      information indications.  In this simple stub, once set
      this value cannot be withdrawn, and will not cause a
      dynamic MPLS interface information indication to be
      generated.";
            } // use-global-label-space

      } // entity

      container subtables {
        container emulated-address {
          list emulated-address {

            description
              "Each entry in this table represents a Emulated Interface
    Address entity.

    The address may be an internetwork address or an OIF
    Transport Network Address (TNA).

    Normally the information configured in this MIB table
    describes an address associated with a network interface
    local to a node, and the <product_index, instance_index,
    if_index, inet_addr> combination uniquely identifies this
    address (and the remaining indices can keep default values).

    However, for E-NNI Routing level information, this structure
    may describe an address associated with a non-local network
    interface.  This is indicated by the local_endpoint_id being
    non-zero (and in this case the unique identifier for the
    interface is the <product_index, instance_index,
    local_endpoint_id, if_index, inet_addr> combination).

    If this table is used to configure Transport Network
    Addresses, it is additionally indexed by address_type.

    If a row is created which matches an address learned from
    the OS, then the information presented across the I3
    interface for the address is decided by a strict set of
    field-by-field rules, detailed below.";

            key "i3-index instance-index local-endpoint-id interface-index address-type inet-address";

            leaf i3-index {
              // Low-level model info: Corresponds to i3EaPrIx.
              type uint32;
              description
                "Index for the I3 stub.";
            } // i3-index

            leaf instance-index {
              // Low-level model info: Corresponds to i3EaInIx.
              type int32;
              description
                "Index of the node to which the internetwork address is
      assigned.";
            } // instance-index

            leaf local-endpoint-id {
              // Low-level model info: Corresponds to i3EaLocalEndId.
              type uint32;
              description
                "The Routing Controller ID of the local endpoint this
      address is attached to.

      If this MIB row matches an address learned from the OS,
      then this MIB-configured value takes precedence over any
      OS value when passed across the I3 interface.";
            } // local-endpoint-id

            leaf interface-index {
              // Low-level model info: Corresponds to i3EaIfIx.
              type uint32;
              description
                "Network interface index in the IF-MIB (RFC 2233) of the
      network interface which the internetwork address is
      assigned to.

      If this MIB row matches an address learned from the OS,
      then the OS-learned value takes precedence over this MIB
      configured value when passed across the I3 interface.";
            } // interface-index

            leaf address-type {
              // Low-level model info: Corresponds to i3EaAddressType.
              type AMB_INETWK_ADDR_TYPE;
              description
                "Address type.

      If this MIB row matches an address learned from the OS,
      then the OS-learned value takes precedence over this MIB
      configured value when passed across the I3 interface.";
            } // address-type

            leaf inet-address {
              // Low-level model info: Corresponds to i3EaInetAddr.
              type string {
                length "2..32";
              }
              description
                "Internetwork address or OIF Transport Network Address
      (TNA).

      If this MIB row matches an address learned from the OS,
      then the OS-learned value takes precedence over this MIB
      configured value when passed across the I3 interface.";
            } // inet-address

            leaf scope-id {
              // Low-level model info: Corresponds to i3EaAddressScopeId.
              type uint32;
              default "0";
              description
                "The Scope Id for the address stored in i3EaInetAddr.  This
      is only valid if i3EaInetAddr contains a scoped Ipv6
      address.

      If this MIB row matches an address learned from the OS,
      then the OS-learned value takes precedence over this MIB
      configured value when passed across the I3 interface.";
            } // scope-id

            leaf prefix-length {
              // Low-level model info: Corresponds to i3EaPrefixLen.
              type uint32;
              description
                "Prefix length (in bits) for this address.

      If this MIB row matches an address learned from the OS,
      then the OS-learned value takes precedence over this MIB
      configured value when passed across the I3 interface.";
            } // prefix-length

            leaf broadcast-destination-address-type {
              // Low-level model info: Corresponds to i3EaBcastDestAddrType.
              type AMB_INETWK_ADDR_TYPE;
              default ipv4;
              description
                "Type of the broadcast or destination address.

      If this MIB row matches an address learned from the OS,
      then if this MIB-configured value is defined, it takes
      precedence over any OS value when passed across the I3
      interface.";
            } // broadcast-destination-address-type

            leaf broadcast-destination-address {
              // Low-level model info: Corresponds to i3EaBcastDestAddr.
              type string {
                length "2..32";
              }
              description
                "Broadcast or destination address.

      If this MIB row matches an address learned from the OS,
      then if this MIB-configured value is defined, it takes
      precedence over any OS value when passed across the I3
      interface.";
            } // broadcast-destination-address

            leaf ldp-advertise {
              // Low-level model info: Corresponds to i3EaAddressAdvertise.
              type boolean;
              default false;
              description
                "Whether to advertise this address for LDP Signaling
      purposes.

      If this MIB row matches an address learned from the OS,
      then this MIB-configured value takes precedence over any
      OS value when passed across the I3 interface.";
            } // ldp-advertise

            leaf fec-type {
              // Low-level model info: Corresponds to i3EaFecType.
              type AMB_STUBS_I3_EA_FEC_TYPES;
              default none;
              description
                "The LDP FEC type of this address.

      If this MIB row matches an address learned from the OS,
      then this MIB-configured value takes precedence over any
      OS value when passed across the I3 interface.";
            } // fec-type

            leaf associated-endpoint {
              // Low-level model info: Corresponds to i3EaAssociatedEndpoint.
              type AMB_STUBS_I3_EA_ASS_END_TYPES;
              description
                "If this is an OIF Transport Network Address (TNA), this
      field indicates whether the TNA is associated with the
      local or remote end of the link.

      If this MIB row matches an address learned from the OS,
      then this MIB-configured value takes precedence over any
      OS value when passed across the I3 interface.";
            } // associated-endpoint

            leaf address-use {
              // Low-level model info: Corresponds to i3EaAddressUse.
              type AMB_STUBS_I3_EA_ADDR_USE_FLAGS;
              default "";
              description
                "Settings for the extended use of the interface address,
      such as whether the address can be used as an LSR ID,
      Transport Address, or SC PC SCN address.

      If this MIB row matches an address learned from the OS,
      then this MIB-configured value takes precedence over any
      OS value when passed across the I3 interface.";
            } // address-use

            leaf ipv6-anycast {
              // Low-level model info: Corresponds to i3EaIpv6Anycast.
              type boolean;
              default false;
              description
                "Whether this is an IPv6 anycast address.

      If this MIB row matches an address learned from the OS,
      then this MIB-configured value takes precedence over any
      OS value when passed across the I3 interface.";
            } // ipv6-anycast

          } // emulated-address

        } // emulated-address

        container emulated-interface {
          list emulated-interface {

            description
              "Each entry in this table represents an Emulated Interface
    entity.

    Normally the information configured in this MIB table
    describes a network interface local to a node, and the
    <product_index, instance_index, if_index> triple is a unique
    identifier for the interface (and the remaining indices can
    keep default values).

    However, for E-NNI Routing level information, this structure
    may describe a non-local network interface.  This is
    indicated by the local_endpoint_id being non-zero (and in
    this case the unique identifier for the interface is the
    <product_index, instance_index, local_endpoint_id, if_index>
    combination).  Furthermore, such remote links may be of the
    following types.

    -  intra-domain links: links contained entirely within the
    routing domain.
    -  inter-domain links: links which connect this routing
    domain with a neighboring routing domain.

    These two cases are distinguished with the is_inter_domain
    field.

    Note that the local_endpoint_id index is only valid when
    this table is being used to configure E-NNI Routing level
    links, which may have a local endpoint which is not equal to
    the advertising node ID.

    If a row is created which matches an interface learned from
    the OS, the OS-learned information takes precedence and the
    configuration specified in this MIB row is ignored, with the
    exception of the following fields:

    -  Interface Flags
    -  Ethernet Port Speed
    -  Ethernet Port Number
    -  Fault status
    -  VLAN type.

    By default, these fields take their value from OS, but can
    be set to override the OS-learned information.";

            key "i3-index instance-index local-endpoint-id interface-index";

            leaf i3-index {
              // Low-level model info: Corresponds to i3EiPrIx.
              type uint32;
              description
                "Index for the I3 stub.";
            } // i3-index

            leaf instance-index {
              // Low-level model info: Corresponds to i3EiInIx.
              type int32;
              description
                "Index of the node to which this interface is assigned.";
            } // instance-index

            leaf local-endpoint-id {
              // Low-level model info: Corresponds to i3EiLocalEndId.
              type uint32;
              description
                "For a E-NNI Routing level link, this field can be used to
      configure the Routing Controller ID of the local endpoint
      of a link when this router is not the local endpoint.";
            } // local-endpoint-id

            leaf interface-index {
              // Low-level model info: Corresponds to i3EiIfIx.
              type uint32;
              description
                "Network interface index in the IF-MIB (RFC 2233).  For a
      E-NNI Routing level inter-domain or intra-domain link,
      this is the interface index of the link at the local
      endpoint node.";
            } // interface-index

            leaf name {
              // Low-level model info: Corresponds to i3EiIfName.
              type string {
                length "512";
              }
              description
                "The interface name used for logging.";
            } // name

            leaf type {
              // Low-level model info: Corresponds to i3EiIfType.
              type AMB_I3_IF_TYPE;
              default i3-if-unknown;
              description
                "Network interface type.";
            } // type

            leaf flags {
              // Low-level model info: Corresponds to i3EiIfFlags.
              type AMB_I3_IF_FLAGS;
              description
                "Network interface flags.

      If there is a matching interface learned from the O/S with
      the same interface index, then the flags set in this field
      are set on the interface when the interface is advertised
      across the I3 in addition to the flags already present on
      the O/S learned interface.  Note that flags set in the
      i3EiIfUnsetFlags field are unset on the interface after
      the flags in this field are set (N.B.  If the same flag is
      set in both fields it will not be set on the interface
      when it is advertised across the I3).

      If there is not a matching interface learned from the O/S
      with the same interface index, then the flags set in this
      field that are not set in the i3EiIfUnsetFlags are
      advertised across the I3.

      Note that the flags AMB_I3_IF_ROUTING and
      AMB_I3_IF_MPLS_FORWARDING are always set in this field and
      will be advertised across the I3 unless explicitly unset
      in the i3EiIfUnsetFlags field.  The flags
      AMB_I3_IF_COMPOSITE_BUNDLE, AMB_I3_IF_COMPONENT_DATA_LINK,
      AMB_I3_IF_INTER_DOMAIN_LINK and AMB_I3_IF_IGP_SHORTCUT are
      enabled/disabled by the i3EiIsBundle, i3EiIsComponent,
      i3EiIsInterDomain and i3EiIgpShortcutIf fields
      respectively and the value of this field is updated when
      the value of one of those fields is changed.";
            } // flags

            leaf oper-status {
              // Low-level model info: Corresponds to i3EiOperStatus.
              type AMB_OPER_STATUS;
              default up;
              description
                "Operational status of the network interface.";
            } // oper-status

            leaf mtu {
              // Low-level model info: Corresponds to i3EiIfMtu.
              type uint32;
              description
                "Maximum transfer unit for this interface.";
            } // mtu

            leaf remote-router-id {
              // Low-level model info: Corresponds to i3EiRmRtrId.
              type uint32;
              description
                "The router ID of the remote peer, required for unnumbered
      point to point interfaces and for identifying MPLS-TP
      Sections.

      For a point to point interface, this specifies the IPv4
      router ID of the remote peer.

      For MPLS-TP Sections (as defined in RFC 5960) this is the
      unique 32-bit value within the remote_global_id assigned
      to the remote peer.";
            } // remote-router-id

            leaf remote-interface-index {
              // Low-level model info: Corresponds to i3EiRmIfId.
              type uint32;
              description
                "Remote interface index.

      This field is only used for unnumbered interfaces and data
      plane interfaces in a UNI network and for identifying
      MPLS-TP Sections (as defined in RFC 5960).

      For a point to point interface, this specifies the
      interface index assigned to this link by the remote peer,
      or for a E-NNI Routing level link, the remote endpoint
      node.  If the remote interface ID is not known, this field
      should be set to zero.

      It is not valid for non point to point interfaces and
      should be set to zero.

      For an MPLS Section, it must be set in order to run OAM on
      an MPLS-TP Section at layer zero for which this interface
      is one end.";
            } // remote-interface-index

            leaf resource-class {
              // Low-level model info: Corresponds to i3EiResCls.
              type uint32;
              description
                "Resource Class.";
            } // resource-class

            leaf ospf-router-id {
              // Low-level model info: Corresponds to i3EiOspfRtrId.
              type string {
                length "8";
              }
              description
                "OSPF Router ID for the remote router.

      This corresponds to the ospf_router_id field in the
      ATG_I3_INET_INTERFACE_ENTRY structure, see the comment in
      that structure for more details.  This field is only valid
      on point to point links.";
            } // ospf-router-id

            leaf isis-system-id {
              // Low-level model info: Corresponds to i3EiIsisSysId.
              type string {
                length "12";
              }
              description
                "IS-IS System ID for the remote router.

      This corresponds to the isis_system_id field in the
      ATG_I3_INET_INTERFACE_ENTRY structure, see the comment in
      that structure for more details.  This field is only valid
      on point to point links.";
            } // isis-system-id

            leaf use-physical-address {
              // Low-level model info: Corresponds to i3EiUsePhysAddr.
              type string {
                length "0..32";
              }
              description
                "Physical address.";
            } // use-physical-address

            leaf enclosing-bundle-interface {
              // Low-level model info: Corresponds to i3EiEnclosingBundleIf.
              type int32;
              description
                "The interface that identifies the enclosing bundle (TE)
      link.";
            } // enclosing-bundle-interface

            leaf is-bundle {
              // Low-level model info: Corresponds to i3EiIsBundle.
              type boolean;
              default false;
              description
                "Flag set to indicate whether this interface is a
      composite/bundled link or not.";
            } // is-bundle

            leaf is-component {
              // Low-level model info: Corresponds to i3EiIsComponent.
              type boolean;
              default false;
              description
                "Flag set to indicate whether this interface is a component
      data link of a composite link.";
            } // is-component

            leaf is-ENNI-level {
              // Low-level model info: Corresponds to i3EiIsENNILevel.
              type boolean;
              default false;
              description
                "Flag set to indicate whether this interface is a E-NNI
      Routing level non-local or abstract link.";
            } // is-ENNI-level

            leaf is-inter-domain {
              // Low-level model info: Corresponds to i3EiIsInterDomain.
              type boolean;
              default false;
              description
                "Flag set to indicate whether this interface is an
      inter-domain link.";
            } // is-inter-domain

            leaf ENNI-router-id {
              // Low-level model info: Corresponds to i3EiENNIRtrId.
              type string {
                length "8";
              }
              description
                "E-NNI Routing Remote Routing Controller ID / Remote
      Ancestor Routing Controller ID.

      For an intra-domain NNI link, this specifies the Routing
      Controller ID of the remote peer.  For an inter-domain NNI
      link, and the remote_endpoint_id is non-zero, this
      specifies the Routing Controller ID of the remote
      ancestor.  If the ID is not known, this field should be
      set to zero.";
            } // ENNI-router-id

            leaf remote-endpoint-id {
              // Low-level model info: Corresponds to i3EiRemoteEndId.
              type uint32;
              description
                "Valid only if _is_inter_domain_ is AMB_TRUE.  This is the
      Routing Controller ID of the remote endpoint of the link.";
            } // remote-endpoint-id

            leaf bgp-next-hop-address-type {
              // Low-level model info: Corresponds to i3EiBgpNhAddrType.
              type AMB_INETWK_ADDR_TYPE;
              default ipv4;
              description
                "The type of the address used to correlate the BGP next hop
      to the LSP this interface represents.  For IGPs, this
      field is used to specify the remote IP address type.  If
      the interface is an IGP shortcut, this field must be set
      to 'ipv4' or 'ipv6'.";
            } // bgp-next-hop-address-type

            leaf bgp-next-hop-address {
              // Low-level model info: Corresponds to i3EiBgpNhAddr.
              type string {
                length "2..32";
              }
              description
                "The address used to correlate the BGP next hop to the LSP
      this interface represents.  For IGPs, this field is used
      to specify the remote IP address.  If the interface is an
      IGP shorcut, this field must be set to the TE router ID of
      the egress node of the IGP shortcut interface.";
            } // bgp-next-hop-address

            leaf remote-signaling-address-type {
              // Low-level model info: Corresponds to i3EiRemoteSignalAddrType.
              type AMB_INETWK_ADDR_TYPE;
              default ipv4;
              description
                "The type of the IP address used to reach the remote end of
      this interface for signaling messages.";
            } // remote-signaling-address-type

            leaf remote-signaling-address {
              // Low-level model info: Corresponds to i3EiRemoteSignalAddr.
              type string {
                length "2..32";
              }
              description
                "The IP address used to reach the remote end of this
      interface for signaling messages.";
            } // remote-signaling-address

            leaf remote-signaling-address-scope-id {
              // Low-level model info: Corresponds to i3EiRemoteSignalAddrScopeId.
              type uint32;
              default "0";
              description
                "The associated Scope ID for the local address that the
      remote signalling address is at the other end of the link
      from.  This field is only valid if the remote signaling
      address is a scoped IPv6 address.";
            } // remote-signaling-address-scope-id

            leaf opaque-parameters {
              // Low-level model info: Corresponds to i3EiOpaParam.
              type string {
                length "0..512";
              }
              description
                "An Octet string containing Opaque Parameters for this
      network interface.";
            } // opaque-parameters

            leaf remote-ipv6-router-id {
              // Low-level model info: Corresponds to i3EiRmIpv6RtrId.
              type string {
                length "2..32";
              }
              description
                "The IPv6 router ID of the remote peer, required for
      unnumbered point to point interfaces in IPv6 signalling
      networks.";
            } // remote-ipv6-router-id

            leaf routing-adjacency {
              // Low-level model info: Corresponds to i3EiRoutingAdjacency.
              type boolean;
              default true;
              description
                "When set to AMB_TRUE, the interface may be used for
      routing.";
            } // routing-adjacency

            leaf forwarding-adjacency {
              // Low-level model info: Corresponds to i3EiForwardingAdjacency.
              type boolean;
              default true;
              description
                "When set to AMB_TRUE, the interface may be used to forward
      MPLS labeled packets.";
            } // forwarding-adjacency

            leaf transport-node-id {
              // Low-level model info: Corresponds to i3EiTportNodeId.
              type uint32;
              description
                "The ASON identifier for the local transport node that owns
      this interface.

      This identifier is meaningless for an interface that is
      not in the transport plane.  It is required for UNI and
      NNI transport plane interfaces.  If this identifier is
      zero, a UNI v2.0 interface may not be activated.";
            } // transport-node-id

            leaf remote-sc-pc-id {
              // Low-level model info: Corresponds to i3EiRmScPcId.
              type uint32;
              description
                "The ASON SC PC ID associated with the remote peer for this
      interface.  This is only valid for a point-to-point
      transport plane interface in a UNI v2.0 network.  If this
      identifier is zero, a UNI v2.0 interface may not be
      activated.";
            } // remote-sc-pc-id

            leaf remote-transport-node-id {
              // Low-level model info: Corresponds to i3EiRmTportNodeId.
              type uint32;
              description
                "The ASON transport plane node ID associated with the
      remote peer for this interface.  This is only valid for a
      point-to-point transport interface in a UNI v2.0 network.

      If this identifier is zero, a UNI v2.0 interface may not
      be activated.";
            } // remote-transport-node-id

            leaf bypass-protected-interface-index {
              // Low-level model info: Corresponds to i3EiBypassProtIfIx.
              type uint32;
              default "0";
              description
                "This field is only valid for MPLS tunnel interfaces that
      provide Fast Reroute bypass protection.

      If it is non-zero, this field contains the interface index
      of the interface protected by this bypass tunnel
      interface.

      If this field is zero, this bypass tunnel interface
      protects all interfaces.";
            } // bypass-protected-interface-index

            leaf igp-shortcut-interface {
              // Low-level model info: Corresponds to i3EiIgpShortcutIf.
              type boolean;
              default false;
              description
                "When set to true, the interface is specified to be an IGP
      shortcut.  That is, IGP protocols may specify the
      interface as the outgoing interface for next hops to
      destinations.";
            } // igp-shortcut-interface

            leaf igp-shortcut-metric-type {
              // Low-level model info: Corresponds to i3EiIgpShortcutMetricTyp.
              type AMB_STUBS_I3_EI_SC_MET_TYPE;
              default shrtct-metric-relative;
              description
                "The type of metric value assigned to this IGP shortcut.

      The type of metric value can be one of the following.
      -  'metricTypeAbsolute'; the metric defined by
      mplsTunnelIgpShortcutMetricVal is used as the cost of
      the IGP shortcut.
      -  'metricTypeRelative'; the metric value defined by
      mplsTunnelIgpShortcutMetricVal is added to the
      IGP-calculated cost of reaching the egress of the
      shortcut to determine the cost of the IGP shortcut.
      Note that, in this case, the metric value may be zero,
      positive or negative.  Note also that a minimum value
      of 1 is defined for the result of the sum of the
      IGP-calculated cost and a relative metric value.

      This field's value is only used if i3EiIgpShortcutIf is
      true.";
            } // igp-shortcut-metric-type

            leaf igp-shortcut-metric-value {
              // Low-level model info: Corresponds to i3EiIgpShortcutMetricVal.
              type int32 {
                range "-16777214..16777215";
              }
              default "0";
              description
                "The metric assigned to this IGP shortcut.

      This field's value is only used if i3EiIgpShortcutIf is
      true.  If i3EiIgpShortcutMetricTyp is set to
      'metricTypeAbsolute' then the value must be set to 1 or
      more.";
            } // igp-shortcut-metric-value

            leaf signaling-interface {
              // Low-level model info: Corresponds to i3EiSignalInterface.
              type int32;
              default "0";
              description
                "The signaling interface to use for control plane messages
      to the data-plane peer that can be reached on this
      interface.  Only applies to data-only interfaces.

      If this is not set then RSVP Hellos will only be sent to
      the data-plane peer when there are active LSPs that go
      through the peer.";
            } // signaling-interface

            leaf local-global-id {
              // Low-level model info: Corresponds to i3EiLocalGlobalId.
              type string {
                length "8";
              }
              description
                "The Global ID is defined in RFC 6370 and uniquely
      identifies an operator.  It is derived from a 4-octet AS
      number assigned to the operator and is used solely to
      provide a globally unique context for other MPLS-TP
      identifiers.

      It must be set to be able to run OAM on an MPLS-TP Section
      at layer zero (as defined in RFC 5960) for which this
      interface is one end in a scenario where the local scope
      is insufficient for uniquely identifying services.";
            } // local-global-id

            leaf remote-global-id {
              // Low-level model info: Corresponds to i3EiRemoteGlobalId.
              type string {
                length "8";
              }
              description
                "The Global ID is defined in RFC 6370 and uniquely
      identifies an operator.  It is derived from a 4-octet AS
      number assigned to the operator and is used solely to
      provide a globally unique context for other MPLS-TP
      identifiers.

      It must be set to be able to run OAM on an MPLS-TP Section
      at layer zero (as defined in RFC 5960) for which this
      interface is one end in a scenario where the local scope
      is insufficient for uniquely identifying services.";
            } // remote-global-id

            leaf local-node-id {
              // Low-level model info: Corresponds to i3EiLocalNodeId.
              type uint32;
              description
                "Local node ID.

      The Node ID is defined in RFC 6370 and is assigned by the
      operator within the scope of a Global ID.

      It must be set to be able to run OAM on an MPLS-TP Section
      at layer zero (as defined in RFC 5960) for which this
      interface is one end.";
            } // local-node-id

            leaf port-ethernet-speed {
              // Low-level model info: Corresponds to i3EiPortEthernetSpeed.
              type AMB_I3_ETH_SPEEDS;
              default i3-eth-os-info;
              description
                "For Ethernet interfaces (see if_type), this value
      represents the order of magnitude of the speed (bandwidth)
      of the interface.

      For any other interface, this value is ignored.

      By default, the Ethernet speed is taken from a matching
      real interface, if one exists.  If this field is set to a
      value other than the default (AMB_I3_ETH_OS_INFO), then
      this value overrides the value from the real interface.
      If there is no matching real interface and the field is
      set to to AMB_I3_ETH_OS_INFO, then the Ethernet speed will
      be reported across the I3 as 'Unknown'.";
            } // port-ethernet-speed

            leaf port-number {
              // Low-level model info: Corresponds to i3EiPortNumber.
              type uint32 {
                range "0..65536";
              }
              default "65536";
              description
                "Ethernet Port number, as defined in 17.3.2.2 of 802.1Q.

      In an Ethernet bridge, each Bridge Port is uniquely
      identified by a Port Number.  A Port Number has no
      mandatory relationship to the interface index, but in the
      simple case, a Port Number will have the same value as the
      corresponding interface's interface index.  As a result of
      limitations in the BPDU for STP, the maximum port number
      that can be advertised to STP is 4095.  However, in the
      absence of spanning tree there is no restriction.  As a
      result, Port Numbers are in the range (1..65535) to allow
      correspondence to interface numbers - but the STP
      restriction must be adhered to if the interface is to be
      used for spanning tree.

      Note that if the interface is not an Ethernet interface,
      this value is ignored.

      By default, the Port number is taken from a matching real
      interface, if one exists.  If this field is set to a value
      other than the default (65536), then this value overrides
      the value from the real interface.  If there is no
      matching real interface and the field is set to to 65536,
      then the Port number will be reported across the I3 as 0.";
            } // port-number

            leaf fault-status-vector {
              // Low-level model info: Corresponds to i3EiFaultStatusVector.
              type AMB_I3_FAULT;
              default i3-fault-os-info;
              description
                "The fault status of the interface.

      If this field is set to zero then the interface has no
      faults.

      If the interface has a fault, then this field contains
      information on the fault or faults.

      By default, the fault status is taken from a matching real
      interface, if one exists.  If this field does not contain
      the flag AMB_I3_FAULT_OS_INFO, then this value overrides
      the value from the real interface.  If there is no
      matching real interface and the AMB_I3_FAULT_OS_INFO flag
      is set, then no fault will be reported across the I3.";
            } // fault-status-vector

            leaf ipv6-header-size {
              // Low-level model info: Corresponds to i3EiIpv6HeaderSize.
              type uint32;
              default "0";
              description
                "The size of IPv6 headers for packets on this interface,
      including any subheaders required (such as for
      authentication), in bytes.

      This value is advertised to the I3 interface user in the
      ATG_I3_INET_INTERFACE_ENTRY structure.

      The I3 interface user may use a non-zero default value if
      it this field takes the default value (zero).";
            } // ipv6-header-size

            leaf unset-flags {
              // Low-level model info: Corresponds to i3EiIfUnsetFlags.
              type AMB_I3_IF_FLAGS;
              description
                "Network interface flags to remove from an O/S-learned
      interface.

      If there is a matching interface learned from the O/S with
      the same interface index, then the flags set in this field
      are unset on the interface when the interface is
      advertised across the I3.  Note that flags set in the
      i3EiIfFlags field are set on the interface before the
      flags in this field are unset (N.B.  If the same flag is
      set in both fields it will not be set on the interface
      when it is advertised across the I3).

      If there is not a matching interface learned from the O/S
      with the same interface index, then any flags specified in
      this field will not be advertised across the I3.

      Note that the flags AMB_I3_IF_ROUTING and
      AMB_I3_IF_MPLS_FORWARDING are always set unless explicitly
      unset in the i3EiIfUnsetFlags field.  The flags
      AMB_I3_IF_COMPOSITE_BUNDLE, AMB_I3_IF_COMPONENT_DATA_LINK,
      AMB_I3_IF_INTER_DOMAIN_LINK and ATG_I3_IF_IGP_SHORTCUT are
      enabled/disabled by the i3EiIsBundle, i3EiIsComponent,
      i3EiIsInterDomain and i3EiIgpShortcutIf fields
      respectively.";
            } // unset-flags

            leaf vlan-type {
              // Low-level model info: Corresponds to i3EiVlanType.
              type AMB_I3_VLAN_TYPE;
              default i3-vlan-os;
              description
                "The type of VLANs supported by this interface.

      By default, the VLAN type is taken from a matching real
      interface, if one exists.  If this field is set to a value
      other than the default (AMB_I3_VLAN_OS), then this value
      overrides the value from the real interface.  If there is
      no matching real interface and the field is set to
      AMB_I3_VLAN_OS, then the VLAN type will be reported across
      the I3 as AMB_I3_VLAN_C_VLAN.

      NOTE - SETTING THIS FIELD TO AMB_I3_VLAN_OS IS CURRENTLY
      UNSUPPORTED AND HAS THE SAME EFFECT AS SETTING THE FIELD
      TO AMB_I3_VLAN_C_VLAN.";
            } // vlan-type

            leaf override-phys-addr {
              // Low-level model info: Corresponds to i3EiOverridePhysAddr.
              type boolean;
              default false;
              description
                "Whether the physical address defined in i3EiUsePhysAddr
      should be advertised in place of the physical address
      learned from the O/S for a matching real interface, if one
      exists.  If no matching real interface is present, this
      field has no effect.";
            } // override-phys-addr

            leaf port-vlan-id {
              // Low-level model info: Corresponds to i3EiPortVlanId.
              type int32 {
                range "0..4094";
              }
              default "0";
              description
                "The Port VLAN ID (PVID) for the interface.

      The PVID is the VLAN ID that the local system assigns to
      untagged or priority tagged frames received on an
      interface that uses port-based VLAN classification, as
      defined by IEEE 802.1Q-2011 s6.9.d.  This is also known as
      the default or native VLAN ID.";
            } // port-vlan-id

            leaf auto-neg-cap {
              // Low-level model info: Corresponds to i3EiAutoNegCap.
              type AMB_MAU_AUTO_NEG_CAP_BITS;
              default "";
              description
                "The local system's interface auto-negotiation
      capabilities.

      Set this to a non-zero value to override the
      auto-negotiation capabilities advertized on the I3 for
      this interface.  Note that if auto-negotiation is not
      supported then no capabilities are advertized and the
      setting of this field has no effect.";
            } // auto-neg-cap

            leaf oper-mau-type {
              // Low-level model info: Corresponds to i3EiOperMauType.
              type AMB_MAU_TYPES;
              default mau-type-other;
              description
                "The operational MAU type of the interface.";
            } // oper-mau-type

            leaf override-if-mtu {
              // Low-level model info: Corresponds to i3EiOverrideIfMtu.
              type boolean;
              default false;
              description
                "Whether the interface MTU value defined in i3EiIfMtu
      should be advertised in place of the MTU learned from the
      O/S for a matching real interface, if one exists.  If no
      matching real interface is present, this field has no
      effect.";
            } // override-if-mtu

            leaf auto-neg-supported-enabled-os {
              // Low-level model info: Corresponds to i3EiAutoNegSupportedEnabledOs.
              type AMB_I3_AUTO_NEG_SUPP_ENAB_OS;
              default i3-auto-neg-os;
              description
                "Whether or not the interface has auto-negotiation
      supported or enabled.

      If no matching real interface is present, this field has
      no effect.

      Otherwise, if a matching real interface is present, the
      effect is as follows.

      'autoNegNotSupportedNotEnabled' - this field will override
      the values determined from the O/S to indicate that
      auto-negotiation is neither supported nor enabled.

      'autoNegSupportedNotEnabled' - this field will override
      the values determined from the O/S to indicate that
      auto-negotiation is supported but not enabled.

      'autoNegSupportedAndEnabled' - this field will override
      the values determined from the O/S to indicate that
      auto-negotiation is both supported and enabled.

      'autoNegOs' - this field has no effect.";
            } // auto-neg-supported-enabled-os

          } // emulated-interface

        } // emulated-interface

        container emulated-mpls {
          list emulated-mpls {

            description
              "Each entry in this table represents an Emulated Interface
    MPLS information entity.";

            key "i3-index instance-index interface-index";

            leaf i3-index {
              // Low-level model info: Corresponds to i3EmPrIx.
              type uint32;
              description
                "Index for the I3 stub.";
            } // i3-index

            leaf instance-index {
              // Low-level model info: Corresponds to i3EmInIx.
              type int32;
              description
                "Index of the node to which this interface is assigned.";
            } // instance-index

            leaf interface-index {
              // Low-level model info: Corresponds to i3EmIfIx.
              type uint32;
              description
                "Network interface index in the IF-MIB (RFC 2233).";
            } // interface-index

            leaf admin-status {
              // Low-level model info: Corresponds to i3EmAdminStatus.
              type AMB_ADMIN_STATUS;
              default down;
              description
                "Administrative status for this interface.  When
      i3EmRowStatus is set to 'active' and i3EmAdminStatus is
      'up' this interface is advertised into DC-MPLS.";
            } // admin-status

            leaf interface-oper-status {
              // Low-level model info: Corresponds to i3EmIfOperStatus.
              type AMB_OPER_STATUS;
              description
                "Current operational status of the interface.";
            } // interface-oper-status

            leaf interface-data-only {
              // Low-level model info: Corresponds to i3EmIfDataOnly.
              type boolean;
              default false;
              description
                "Whether the interface is a data-only interface.";
            } // interface-data-only

            leaf interface-use-refresh-messages {
              // Low-level model info: Corresponds to i3EmIfUseRefrMsgs.
              type AMB_STUBS_I3_EM_REFR_OPTS;
              default "";
              description
                "Indicates the level of refresh reduction support to be
      configured on this interface.";
            } // interface-use-refresh-messages

            leaf interface-use-message-ids {
              // Low-level model info: Corresponds to i3EmIfUseMessageIDs.
              type boolean;
              default false;
              description
                "Indicates whether Message ID support should be configured
      on this interface.  Note that Refresh Reduction measures
      cannot be used if Message ID support is not enabled for
      that interface.";
            } // interface-use-message-ids

            leaf interface-bundle-send-delay {
              // Low-level model info: Corresponds to i3EmIfBndlSndDelay.
              type uint32;
              default "400";
              description
                "Indicates the maximum time (in milliseconds) that a single
      message sent out of this interface should be delayed for
      in order to include it in a Bundle Message.";
            } // interface-bundle-send-delay

            leaf interface-rapid-retry-interval {
              // Low-level model info: Corresponds to i3EmIfRRInterval.
              type uint32;
              default "500";
              description
                "Indicates Rapid Retry Interval (in milliseconds) that
      should be used on all interfaces.";
            } // interface-rapid-retry-interval

            leaf interface-rapid-retry-decay {
              // Low-level model info: Corresponds to i3EmIfRRDecay.
              type int32;
              default "100";
              description
                "The percentage increase in the rapid retransmission
      interval for each consecutive unacknowledged RSVP message
      sent out of this interface.  A value of 0 indicates a
      constant retransmission rate.";
            } // interface-rapid-retry-decay

            leaf interface-rapid-retry-limit {
              // Low-level model info: Corresponds to i3EmIfRRLimit.
              type uint32;
              default "2";
              description
                "The maximum number of times a message is resent if no
      acknowledgement is received on this interface.";
            } // interface-rapid-retry-limit

            leaf interface-refresh-interval {
              // Low-level model info: Corresponds to i3EmIfRefreshInterval.
              type int32;
              default "0";
              description
                "The average interval, in milliseconds, between Path and
      Resv refresh messages for LSPs which use this interface
      for RSVP-signalled data.

      A value of 0 indicates that the globally configured value
      in the RSVP Product MIB table is used for this interface.
      A value of -1 indicates that Path and Resv refresh
      messages are not required on this interface.";
            } // interface-refresh-interval

            leaf label-space {
              // Low-level model info: Corresponds to i3EmLabelSpace.
              type AMB_STUBS_I3_EM_LBL_SPC_TYPES;
              default atm;
              description
                "Type of label space on this interface.";
            } // label-space

            leaf suggested-label {
              // Low-level model info: Corresponds to i3EmSuggLabel.
              type boolean;
              default false;
              description
                "Determines whether suggested labels will be used on this
      interface.  This may only be set if _label_space_type_ is
      AMB_STUBS_I3_EM_LBL_SPC_LAMBDA.";
            } // suggested-label

            leaf signalling-capabilities {
              // Low-level model info: Corresponds to i3EmSignallingCaps.
              type AMB_STUBS_I3_EM_IF_SIGP_TYPES;
              default "";
              description
                "Indicates the type(s) of MPLS signalling supported by this
      interface.";
            } // signalling-capabilities

            leaf atm-vp-vc-capabilities {
              // Low-level model info: Corresponds to i3EmAtmVpVcCaps.
              type AMB_STUBS_I3_EM_ATM_VP_VC_CAPS;
              default vc;
              description
                "For ATM network interfaces, this indicates whether the
      switch supports VC switching, VP switching, or both.";
            } // atm-vp-vc-capabilities

            leaf bidirectional-vc-capability {
              // Low-level model info: Corresponds to i3EmBidirVcCap.
              type boolean;
              default true;
              description
                "This indicates whether the network interface supports
      bi-directional VC Capability.";
            } // bidirectional-vc-capability

            leaf vc-merge {
              // Low-level model info: Corresponds to i3EmVcMerge.
              type boolean;
              default true;
              description
                "This indicates whether the network interface supports
      VC merge Capability.";
            } // vc-merge

            leaf vp-merge {
              // Low-level model info: Corresponds to i3EmVpMerge.
              type boolean;
              default false;
              description
                "This indicates whether the network interface supports
      VP merge Capability.";
            } // vp-merge

            leaf label-space-id {
              // Low-level model info: Corresponds to i3EmLabelSpaceId.
              type int32;
              default "0";
              description
                "Determines the label space identifier for this interface.";
            } // label-space-id

            leaf distribution-mode {
              // Low-level model info: Corresponds to i3EmDistMode.
              type AMB_STUBS_I3_EM_DIST_MODES;
              default on-demand;
              description
                "Determines the Label distribution mode for this interface.";
            } // distribution-mode

            leaf retention-mode {
              // Low-level model info: Corresponds to i3EmRetenMode.
              type AMB_STUBS_I3_EM_RETENTION_MODES;
              default conservative;
              description
                "Determines the Label retention mode for this interface.";
            } // retention-mode

            leaf path-vector-limit {
              // Low-level model info: Corresponds to i3EmPathVecLimit.
              type int32;
              default "0";
              description
                "Determines the Path vector limit for this interface.

      A value of zero indicates that loop detection based on
      path vectors is disabled for this interface.

      This field is only used by (CR-)LDP.  It can be updated
      while the interface is already enabled, but only takes
      effect for new sessions associated with the interface.";
            } // path-vector-limit

            leaf hop-count-limit {
              // Low-level model info: Corresponds to i3EmHopCountLimit.
              type int32;
              default "0";
              description
                "Hop count limit for this interface.

      A value of zero indicates that loop detection based on hop
      counts is disabled for this interface.

      This field is only used by (CR-)LDP.  It can be updated
      while the interface is already enabled, but only takes
      effect for new sessions associated with the interface.";
            } // hop-count-limit

            leaf frame-relay-dlci-length {
              // Low-level model info: Corresponds to i3EmFrDlciLen.
              type AMB_STUBS_I3_EM_FR_SESS_LEN;
              default 10-dlci-bits;
              description
                "Determines the number of bits in the DLCI (only available
      if the i3EmLabelSpace type is FR).";
            } // frame-relay-dlci-length

            leaf frame-relay-min-dlci {
              // Low-level model info: Corresponds to i3EmFrMinDlci.
              type int32;
              default "33";
              description
                "Determines the minimum DLCI supported.  (Only available
      if the i3EmLabelSpace type is FR).";
            } // frame-relay-min-dlci

            leaf frame-relay-max-dlci {
              // Low-level model info: Corresponds to i3EmFrMaxDlci.
              type int32;
              default "1023";
              description
                "Determines the maximum DLCI supported.  (Only available
      if the i3EmLabelSpace type is FR).";
            } // frame-relay-max-dlci

            leaf atm-min-vpi {
              // Low-level model info: Corresponds to i3EmAtmMinVpi.
              type int32;
              default "0";
              description
                "Determines the minimum VPI supported.  (Only available
      if the i3EmLabelSpace type is ATM).";
            } // atm-min-vpi

            leaf atm-max-vpi {
              // Low-level model info: Corresponds to i3EmAtmMaxVpi.
              type int32;
              default "0";
              description
                "Determines the maximum VPI supported.  (Only available
      if the i3EmLabelSpace type is ATM).";
            } // atm-max-vpi

            leaf atm-min-vci {
              // Low-level model info: Corresponds to i3EmAtmMinVci.
              type int32;
              default "33";
              description
                "Determines the minimum VCI supported.  (Only available
      if the i3EmLabelSpace type is ATM).";
            } // atm-min-vci

            leaf atm-max-vci {
              // Low-level model info: Corresponds to i3EmAtmMaxVci.
              type int32;
              default "1023";
              description
                "Determines the maximum VCI supported.  (Only available
      if the i3EmLabelSpace type is ATM).";
            } // atm-max-vci

            leaf generic-min-label {
              // Low-level model info: Corresponds to i3EmGenMinLabel.
              type string {
                length "0..32";
              }
              description
                "Determines the minimum label supported.  (Only available
      if the i3EmLabelSpace type is gen or lambda).";
            } // generic-min-label

            leaf generic-max-label {
              // Low-level model info: Corresponds to i3EmGenMaxLabel.
              type string {
                length "0..32";
              }
              description
                "Determines the maximum label supported.  (Only available
      if the i3EmLabelSpace type is gen or lambda).";
            } // generic-max-label

            leaf hello-period {
              // Low-level model info: Corresponds to i3EmHelloPeriod.
              type uint32;
              default "0";
              description
                "Default period in milliseconds between sending Hello
      messages to all neighbors on this interface.  If this is
      set to 0, no Hello messages are sent by this interface.";
            } // hello-period

            leaf hello-decay {
              // Low-level model info: Corresponds to i3EmHelloDecay.
              type uint32;
              default "0";
              description
                "Percentage increase in hello period after each Hello
      message sent when the hello session with the neighbor has
      timed out.";
            } // hello-decay

            leaf hello-tolerance {
              // Low-level model info: Corresponds to i3EmHelloTolerance.
              type uint32;
              default "3";
              description
                "Number of hello periods which may pass without receiving a
      successful Hello message from a partner before the Hello
      session times out.";
            } // hello-tolerance

            leaf hello-persist {
              // Low-level model info: Corresponds to i3EmHelloPersist.
              type uint32;
              description
                "Number of hello periods which may pass after the Hello
      session times out before Hello messages cease.";
            } // hello-persist

            leaf global-label-space {
              // Low-level model info: Corresponds to i3EmGlobalLabelSpace.
              type boolean;
              default false;
              description
                "This indicates whether the interface represents the global
      label space.";
            } // global-label-space

            leaf is-uni {
              // Low-level model info: Corresponds to i3EmIsUni.
              type boolean;
              default false;
              description
                "Whether this is a box being configured to support OIF UNI
      or NNI signalling.";
            } // is-uni

            leaf switch-managed-labels {
              // Low-level model info: Corresponds to i3EmSwitchManagedLabels.
              type boolean;
              default false;
              description
                "Indicates whether the label space on this interface are
      managed by the LDF rather than LMGR.";
            } // switch-managed-labels

            leaf php-supported {
              // Low-level model info: Corresponds to i3EmPhpSupported.
              type boolean;
              default false;
              description
                "Whether Penultimate Hop Popping is supported on this
      interface.";
            } // php-supported

            leaf use-cryptographic-authentication-send {
              // Low-level model info: Corresponds to i3EmSendCryptoAuthentication.
              type boolean;
              default false;
              description
                "Indicates if cryptographic authentication should be used
      for packets sent to the neighbor reached through this
      interface.

      Note the following.
      -  If this is set to AMB_TRUE then the type of
      authentication to use is given by
      i3EmSendCryptoAuthType.
      -  If non-associated signaling is used then the
      configuration setting is taken from the data
      interface(s).
      -  If non-associated signaling is in use or if multiple
      un-numbered links to the same neighbor are in use then
      all interfaces must have the same cryptographic
      authentication configuration.";
            } // use-cryptographic-authentication-send

            leaf use-cryptographic-authentication-receive {
              // Low-level model info: Corresponds to i3EmRcvCryptoAuthentication.
              type boolean;
              default false;
              description
                "Indicates if cryptographic authentication should be used
      for packets received from the neighbor reached through
      this interface.

      Note the following.
      -  If this is set to AMB_TRUE then the type of
      authentication to use is given by
      i3EmRcvCryptoAuthType.
      -  If non-associated signaling is used then the
      configuration setting is taken from the data
      interface(s).
      -  If non-associated signaling is in use or if multiple
      un-numbered links to the same neighbor are in use then
      all interfaces must have the same cryptographic
      authentication configuration.";
            } // use-cryptographic-authentication-receive

            leaf message-delivery-tolerance {
              // Low-level model info: Corresponds to i3EmMsgDeliveryTolerance.
              type int32 {
                range "0..65535";
              }
              default "0";
              description
                "Out-of-order message delivery tolerance for received
      packets using Integrity objects for cryptographic
      authentication.  The use of IP by RSVP implies that
      messages may be delivered out of order.  This configured
      value specifies the size of a window within which out of
      order messages are tolerated.  Messages received with an
      Integrity object sequence number lower than the bottom
      edge of the window are discarded.

      Note the following.

      -  Only valid if i3EmRcvCryptoAuthentication is set to
      AMB_TRUE.
      -  If valid and set to 0 then a default value is used for
      the out-of-order message delivery tolerance for this
      interface.
      -  If non-associated signaling is in use or if multiple
      un-numbered links to the same neighbor are in use then
      all interfaces must have the same cryptographic
      authentication configuration.";
            } // message-delivery-tolerance

            leaf interface-property-flags {
              // Low-level model info: Corresponds to i3EmRsvpIfPropFlags.
              type AMB_STUBS_I3_EM_IF_PR_FLAGS;
              default "";
              description
                "Interface property flags.";
            } // interface-property-flags

            leaf rsvp-egress-label-usage {
              // Low-level model info: Corresponds to i3EmRsvpEgressLabelUsage.
              type AMB_STUBS_I3_EM_EGL;
              default "";
              description
                "Specifies how labels are assigned at Egress nodes for
      RSVP, where DC-LMGR is assigning labels.  These fields are
      on a per protocol basis, allowing different egress label
      policies for each protocol.  These fields are ignored if
      the switch is allocating labels.

      Further the use of the EXPLICIT_NULL (zero) egress label
      for any protocol means that the
      AMB_STUBS_I3_EM_IF_PR_ZERO_IMP _if_prop_flags_ field must
      not be set for this interface.";
            } // rsvp-egress-label-usage

            leaf ldp-egress-label-usage {
              // Low-level model info: Corresponds to i3EmLdpEgressLabelUsage.
              type AMB_STUBS_I3_EM_EGL;
              default "";
              description
                "Specifies how labels are assigned at Egress nodes for LDP,
      where DC-LMGR is assigning labels.  These fields are on a
      per protocol basis, allowing different egress label
      policies for each protocol.  These fields are ignored if
      the switch is allocating labels.

      Further the use of the EXPLICIT_NULL (zero) egress label
      for any protocol means that the
      AMB_STUBS_I3_EM_IF_PR_ZERO_IMP _if_prop_flags_ field must
      not be set for this interface.";
            } // ldp-egress-label-usage

            leaf refresh-multiple {
              // Low-level model info: Corresponds to i3EmRefreshMultiple.
              type int32;
              description
                "The RSVP value, K, which is the number of unresponded Path
      or Resv refresh attempts which must be made, spaced by the
      refresh interval before the state is deemed to have timed
      out.

      A value of 0 indicates that the globally configured value
      in the RSVP Product MIB table is used for this interface.";
            } // refresh-multiple

            leaf refresh-slew-denominator {
              // Low-level model info: Corresponds to i3EmRefreshSlewDenominator.
              type int32;
              description
                "The denominator of the fraction, SlewMax, which is the
      maximum allowable increase in the refresh interval, R, to
      prevent state timeout while changing R.  R is increased by
      this fraction until it reaches the new desired value.

      A value of 0 indicates that the globally configured value
      in the RSVP Product MIB table is used for this interface.";
            } // refresh-slew-denominator

            leaf refresh-slew-numerator {
              // Low-level model info: Corresponds to i3EmRefreshSlewNumerator.
              type int32;
              description
                "The numerator of the fraction, SlewMax, which is the
      maximum allowable increase in the refresh interval, R, to
      prevent state timeout while changing R.  R is increased by
      this fraction until it reaches the new desired value.

      A value of 0 indicates that the globally configured value
      in the RSVP Product MIB table is used for this interface.";
            } // refresh-slew-numerator

            leaf blockade-multiple {
              // Low-level model info: Corresponds to i3EmBlockadeMultiple.
              type int32;
              description
                "The RSVP value, Kb, which is the number of refresh timeout
      periods after which blockade state is deleted.

      A value of 0 indicates that the globally configured value
      in the RSVP Product MIB table is used for this interface.";
            } // blockade-multiple

            leaf use-legacy-frr-object {
              // Low-level model info: Corresponds to i3EmUseLegacyFRRObj.
              type boolean;
              default false;
              description
                "Indicates the type of FRR object added to Path messages
      sent on this interface.";
            } // use-legacy-frr-object

            leaf hello-address-flags {
              // Low-level model info: Corresponds to i3EmHelloAddrFlags.
              type AMB_STUBS_I3_EM_HELLO_FLAGS;
              default "";
              description
                "Flags used to set the transport address sent in LDP Hello
      messages.

      For the default value of zero, if the interface represents
      the global label space, an interface addesss is used as
      the transport address; otherwise, the Router's transport
      address is used.";
            } // hello-address-flags

            leaf ldp-hello-hold-timer {
              // Low-level model info: Corresponds to i3EmLdpHelloHoldTimer.
              type int32 {
                range "0..65535";
              }
              default "0";
              description
                "LDP's HELLO Hold timer value in seconds.";
            } // ldp-hello-hold-timer

            leaf ldp-keepalive-hold-timer {
              // Low-level model info: Corresponds to i3EmLdpKeepaliveHoldTimer.
              type int32 {
                range "0..65535";
              }
              default "0";
              description
                "LDP's Keepalive Hold timer value in seconds.";
            } // ldp-keepalive-hold-timer

            leaf uni-version {
              // Low-level model info: Corresponds to i3EmUNIVersion.
              type AMB_I3_MPLS_UNI_VERSION;
              default none;
              description
                "The UNI version supported on this interface.";
            } // uni-version

            leaf interface-summary-refresh-interval {
              // Low-level model info: Corresponds to i3EmIfSummaryRefreshInterval.
              type int32;
              default "0";
              description
                "The average interval, in milliseconds, between Summary
      refresh messages for LSPs which use this interface for
      RSVP-signalled data.

      A value of 0 indicates that the i3EmIfRefreshInterval
      object should be used instead.";
            } // interface-summary-refresh-interval

            leaf use-rsvp-hellos-for-all-point-to-point {
              // Low-level model info: Corresponds to i3EmUseRsvpHellosForAllP2p.
              type boolean;
              default false;
              description
                "If this is a point-to-point interface, set to AMB_TRUE to
      enable RSVP continuous Hello support on this interface
      regardless of whether it supports data traffic.";
            } // use-rsvp-hellos-for-all-point-to-point

            leaf bfd-flags {
              // Low-level model info: Corresponds to i3EmIfBfdFlags.
              type AMB_STUBS_I3_BFD_FLAGS;
              default "";
              description
                "BFD support on this interface.";
            } // bfd-flags

            leaf use-cryptographic-auth-type-send {
              // Low-level model info: Corresponds to i3EmSendCryptoAuthType.
              type AMB_I3_CRYPTO_AUTH_TYPES;
              default hmacmd5;
              description
                "Indicates the type of authentication to be used for
      packets sent to the neighbor(s) reached through this
      interface.

      Note the following.
      -  Only valid if i3EmSendCryptoAuthentication is set to
      AMB_TRUE.
      -  If non-associated signaling is used then the
      configuration setting is taken from the data
      interface(s).
      -  If non-associated signaling is in use or if multiple
      un-numbered links to the same neighbor are in use then
      all interfaces must have the same cryptographic
      authentication configuration.";
            } // use-cryptographic-auth-type-send

            leaf use-cryptographic-auth-type-receive {
              // Low-level model info: Corresponds to i3EmRcvCryptoAuthType.
              type AMB_I3_CRYPTO_AUTH_TYPES;
              default hmacmd5;
              description
                "Indicates the type of authentication to be used for
      packets received from the neighbor(s) reached through this
      interface.

      Note the following.
      -  Only valid if i3EmRcvCryptoAuthentication is set to
      AMB_TRUE.
      -  If non-associated signaling is used then the
      configuration setting is taken from the data
      interface(s).
      -  If non-associated signaling is in use or if multiple
      un-numbered links to the same neighbor are in use then
      all interfaces must have the same cryptographic
      authentication configuration.";
            } // use-cryptographic-auth-type-receive

            leaf hello-ttl {
              // Low-level model info: Corresponds to i3EmHelloTtl.
              type uint32 {
                range "0..255";
              }
              default "0";
              description
                "The Time-To-Live that will be set in the IP header of all
      MPLS Hello packets sent to the neighbor associated with
      this interface.

      In the case of out-of-band signalling, this is the value
      to use on packets sent to the neighbor represented by this
      point-to-point data interface.

      The value of this field may be changed at any time.";
            } // hello-ttl

            leaf remote-ip-addr-type {
              // Low-level model info: Corresponds to i3EmRemoteIpAddrType.
              type AMB_INETWK_ADDR_TYPE;
              default ipv4;
              description
                "The address type of the i3EmRemoteIpAddress field.  This
      must be set to either 'IPv4' or 'IPv6'.";
            } // remote-ip-addr-type

            leaf remote-ip-address {
              // Low-level model info: Corresponds to i3EmRemoteIpAddress.
              type string {
                length "0..32";
              }
              description
                "The IP address of the remote device at the other end of
      this interface.  This field is only relevant for
      multipoint-to-point or point-to-point interfaces.  This
      field is used by the ICP to determine the interface over
      which the higher-layer LSPs or PWs should be tunnelled.
      This IP address must therefore match the configuration on
      those LSPs or PWs.";
            } // remote-ip-address

            leaf flags {
              // Low-level model info: Corresponds to i3EmIfFlags.
              type AMB_I3_IF_FLAGS;
              description
                "Network interface flags.";
            } // flags

          } // emulated-mpls

        } // emulated-mpls

        container emulated-conn-matrix {
          list emulated-conn-matrix {

            description
              "This table is used to configure a connectivity matrix on a
    given node.  Each entry in this table represents a single
    matrix with a distinct Matrix ID.

    This table allows a matrix to be defined containing up to
    three link set pairs, with each link set in each pair
    containing up to five links, as defined by the
    ATG_WSON_STRUCTURES in a0wson.h.

    This table implements a pre-standard version of Connectivity
    Matrices.  As such the contents of the table and their
    formats may change in a non-back-compatible way in future
    releases once the standards have solidified.

    All writable fields in this MIB table can be changed whilst
    active.";

            key "i3-index instance-index local-endpoint-id matrix-id";

            leaf i3-index {
              // Low-level model info: Corresponds to i3EnCmProductIndex.
              type uint32;
              description
                "This field identifies an instance of the I3 stub.";
            } // i3-index

            leaf instance-index {
              // Low-level model info: Corresponds to i3EnCmInstance.
              type int32;
              description
                "Index of the I3 user instance (virtual router or node) to
      which this connectivity matrix is assigned.";
            } // instance-index

            leaf local-endpoint-id {
              // Low-level model info: Corresponds to i3EnCmLocalEndId.
              type uint32;
              description
                "The Routing Controller ID of the local endpoint of the
      address or interface to which the connectivity matrix is
      assigned.

      If this matrix is assigned to a local address then this
      field is set to zero.";
            } // local-endpoint-id

            leaf matrix-id {
              // Low-level model info: Corresponds to i3EnCmMatrixId.
              type uint32;
              description
                "The Matrix ID of this matrix.  This uniquely identifies
      the matrix for the given node and local endpoint ID.";
            } // matrix-id

            leaf connectivity-type {
              // Low-level model info: Corresponds to i3EnCmConnType.
              type int32;
              mandatory true;
              description
                "The connectivity type to be advertised in the matrix.";
            } // connectivity-type

            leaf bidir-link-set-pair-1 {
              // Low-level model info: Corresponds to i3EnCmBidirLinkSetPair1.
              type boolean;
              default false;
              description
                "Flag to say whether the link sets in Link Set Pair 1 have
      a bidirectional relationship.  AMB_TRUE means that both
      sets in the pair will be advertised with
      ATG_WSON_LINK_DIR_BI, while AMB_FALSE means that set 1A
      will be advertised with DIR_INGRESS and 1B with
      DIR_EGRESS.";
            } // bidir-link-set-pair-1

            leaf action-link-set-1a {
              // Low-level model info: Corresponds to i3EnCmActionLinkSet1A.
              type AMB_STUBS_I3_CM_LNK_ST_ACT;
              default link-set-action-inc-list;
              description
                "The action to specify on Link Set 1A.";
            } // action-link-set-1a

            leaf format-link-set-1a {
              // Low-level model info: Corresponds to i3EnCmFormatLinkSet1A.
              type AMB_STUBS_I3_CM_LNK_ST_FORMAT;
              default link-set-format-unnum;
              description
                "The format of the links in Link Set 1A - IPv4, IPv6 or
      unnumbered.";
            } // format-link-set-1a

            leaf num-links-link-set-1A {
              // Low-level model info: Corresponds to i3EnCmNumLinksLinkSet1A.
              type int32;
              default "0";
              description
                "The number of links in Link Set 1A which are present.  The
      present links will be contiguous and start from link 1.";
            } // num-links-link-set-1A

            leaf link-set-1A-link-1-addr {
              // Low-level model info: Corresponds to i3EnCmLinkSet1ALink1Addr.
              type string {
                length "8..32";
              }
              description
                "The identifier for the first link in Link Set 1A.  This
      will be read as an IPv4 address or an IPv6 address as
      specified by format_link_set_1a, or ignored if
      format_link_set_1a indicates using the Link IDs (_UNNUM).";
            } // link-set-1A-link-1-addr

            leaf link-set-1A-link-1-id {
              // Low-level model info: Corresponds to i3EnCmLinkSet1ALink1ID.
              type uint32;
              default "0";
              description
                "The identifier for the first link in Link Set 1A.  This is
      only used if the format of Link Set 1A is specified to be
      unnumbered.";
            } // link-set-1A-link-1-id

            leaf link-set-1A-link-2-addr {
              // Low-level model info: Corresponds to i3EnCmLinkSet1ALink2Addr.
              type string {
                length "8..32";
              }
              description
                "The identifier for the second link in Link Set 1A.  This
      will be read as an IPv4 address or an IPv6 address as
      specified by format_link_set_1a, or ignored if
      format_link_set_1a indicates using the Link IDs (_UNNUM).";
            } // link-set-1A-link-2-addr

            leaf link-set-1A-link-2-id {
              // Low-level model info: Corresponds to i3EnCmLinkSet1ALink2ID.
              type uint32;
              default "0";
              description
                "The identifier for the second link in Link Set 1A.  This
      is only used if the format of Link Set 1A is specified to
      be unnumbered.";
            } // link-set-1A-link-2-id

            leaf link-set-1A-link-3-addr {
              // Low-level model info: Corresponds to i3EnCmLinkSet1ALink3Addr.
              type string {
                length "8..32";
              }
              description
                "The identifier for the third link in Link Set 1A.  This
      will be read as an IPv4 address or an IPv6 address as
      specified by format_link_set_1a, or ignored if
      format_link_set_1a indicates using the Link IDs (_UNNUM).";
            } // link-set-1A-link-3-addr

            leaf link-set-1A-link-3-id {
              // Low-level model info: Corresponds to i3EnCmLinkSet1ALink3ID.
              type uint32;
              default "0";
              description
                "The identifier for the third link in Link Set 1A.  This is
      only used if the format of Link Set 1A is specified to be
      unnumbered.";
            } // link-set-1A-link-3-id

            leaf link-set-1A-link-4-addr {
              // Low-level model info: Corresponds to i3EnCmLinkSet1ALink4Addr.
              type string {
                length "8..32";
              }
              description
                "The identifier for the fourth link in Link Set 1A.  This
      will be read as an IPv4 address or an IPv6 address as
      specified by format_link_set_1a, or ignored if
      format_link_set_1a indicates using the Link IDs (_UNNUM).";
            } // link-set-1A-link-4-addr

            leaf link-set-1A-link-4-id {
              // Low-level model info: Corresponds to i3EnCmLinkSet1ALink4ID.
              type uint32;
              default "0";
              description
                "The identifier for the fourth link in Link Set 1A.  This
      is only used if the format of Link Set 1A is specified to
      be unnumbered.";
            } // link-set-1A-link-4-id

            leaf link-set-1A-link-5-addr {
              // Low-level model info: Corresponds to i3EnCmLinkSet1ALink5Addr.
              type string {
                length "8..32";
              }
              description
                "The identifier for the fifth link in Link Set 1A.  This
      will be read as an IPv4 address or an IPv6 address as
      specified by format_link_set_1a, or ignored if
      format_link_set_1a indicates using the Link IDs (_UNNUM).";
            } // link-set-1A-link-5-addr

            leaf link-set-1A-link-5-id {
              // Low-level model info: Corresponds to i3EnCmLinkSet1ALink5ID.
              type uint32;
              default "0";
              description
                "The identifier for the fifth link in Link Set 1A.  This is
      only used if the format of Link Set 1A is specified to be
      unnumbered.";
            } // link-set-1A-link-5-id

            leaf action-link-set-1b {
              // Low-level model info: Corresponds to i3EnCmActionLinkSet1B.
              type AMB_STUBS_I3_CM_LNK_ST_ACT;
              default link-set-action-inc-list;
              description
                "The action to specify on Link Set 1B.";
            } // action-link-set-1b

            leaf format-link-set-1b {
              // Low-level model info: Corresponds to i3EnCmFormatLinkSet1B.
              type AMB_STUBS_I3_CM_LNK_ST_FORMAT;
              default link-set-format-unnum;
              description
                "The format of the links in Link Set 1B - IPv4, IPv6 or
      unnumbered.";
            } // format-link-set-1b

            leaf num-links-link-set-1B {
              // Low-level model info: Corresponds to i3EnCmNumLinksLinkSet1B.
              type int32;
              default "0";
              description
                "The number of links in Link Set 1B which are present.  The
      present links will be contiguous and start from link 1.";
            } // num-links-link-set-1B

            leaf link-set-1B-link-1-addr {
              // Low-level model info: Corresponds to i3EnCmLinkSet1BLink1Addr.
              type string {
                length "8..32";
              }
              description
                "The identifier for the first link in Link Set 1B.  This
      will be read as an IPv4 address or an IPv6 address as
      specified by format_link_set_1b, or ignored if
      format_link_set_1b indicates using the Link IDs (_UNNUM).";
            } // link-set-1B-link-1-addr

            leaf link-set-1B-link-1-id {
              // Low-level model info: Corresponds to i3EnCmLinkSet1BLink1ID.
              type uint32;
              default "0";
              description
                "The identifier for the first link in Link Set 1B.  This is
      only used if the format of Link Set 1B is specified to be
      unnumbered.";
            } // link-set-1B-link-1-id

            leaf link-set-1B-link-2-addr {
              // Low-level model info: Corresponds to i3EnCmLinkSet1BLink2Addr.
              type string {
                length "8..32";
              }
              description
                "The identifier for the second link in Link Set 1B.  This
      will be read as an IPv4 address or an IPv6 address as
      specified by format_link_set_1b, or ignored if
      format_link_set_1b indicates using the Link IDs (_UNNUM).";
            } // link-set-1B-link-2-addr

            leaf link-set-1B-link-2-id {
              // Low-level model info: Corresponds to i3EnCmLinkSet1BLink2ID.
              type uint32;
              default "0";
              description
                "The identifier for the second link in Link Set 1B.  This
      is only used if the format of Link Set 1B is specified to
      be unnumbered.";
            } // link-set-1B-link-2-id

            leaf link-set-1B-link-3-addr {
              // Low-level model info: Corresponds to i3EnCmLinkSet1BLink3Addr.
              type string {
                length "8..32";
              }
              description
                "The identifier for the third link in Link Set 1B.  This
      will be read as an IPv4 address or an IPv6 address as
      specified by format_link_set_1b, or ignored if
      format_link_set_1b indicates using the Link IDs (_UNNUM).";
            } // link-set-1B-link-3-addr

            leaf link-set-1B-link-3-id {
              // Low-level model info: Corresponds to i3EnCmLinkSet1BLink3ID.
              type uint32;
              default "0";
              description
                "The identifier for the third link in Link Set 1B.  This is
      only used if the format of Link Set 1B is specified to be
      unnumbered.";
            } // link-set-1B-link-3-id

            leaf link-set-1B-link-4-addr {
              // Low-level model info: Corresponds to i3EnCmLinkSet1BLink4Addr.
              type string {
                length "8..32";
              }
              description
                "The identifier for the fourth link in Link Set 1B.  This
      will be read as an IPv4 address or an IPv6 address as
      specified by format_link_set_1b, or ignored if
      format_link_set_1b indicates using the Link IDs (_UNNUM).";
            } // link-set-1B-link-4-addr

            leaf link-set-1B-link-4-id {
              // Low-level model info: Corresponds to i3EnCmLinkSet1BLink4ID.
              type uint32;
              default "0";
              description
                "The identifier for the fourth link in Link Set 1B.  This
      is only used if the format of Link Set 1B is specified to
      be unnumbered.";
            } // link-set-1B-link-4-id

            leaf link-set-1B-link-5-addr {
              // Low-level model info: Corresponds to i3EnCmLinkSet1BLink5Addr.
              type string {
                length "8..32";
              }
              description
                "The identifier for the fifth link in Link Set 1B.  This
      will be read as an IPv4 address or an IPv6 address as
      specified by format_link_set_1b, or ignored if
      format_link_set_1b indicates using the Link IDs (_UNNUM).";
            } // link-set-1B-link-5-addr

            leaf link-set-1B-link-5-id {
              // Low-level model info: Corresponds to i3EnCmLinkSet1BLink5ID.
              type uint32;
              default "0";
              description
                "The identifier for the fifth link in Link Set 1B.  This is
      only used if the format of Link Set 1B is specified to be
      unnumbered.";
            } // link-set-1B-link-5-id

            leaf bidir-link-set-pair-2 {
              // Low-level model info: Corresponds to i3EnCmBidirLinkSetPair2.
              type boolean;
              default false;
              description
                "Flag to say whether the link sets in Link Set Pair 2 have
      a bidirectional relationship.  AMB_TRUE means that both
      sets in the pair will be advertised with
      ATG_WSON_LINK_DIR_BI, while AMB_FALSE means that set 2A
      will be advertised with DIR_INGRESS and 2B with
      DIR_EGRESS.";
            } // bidir-link-set-pair-2

            leaf action-link-set-2a {
              // Low-level model info: Corresponds to i3EnCmActionLinkSet2A.
              type AMB_STUBS_I3_CM_LNK_ST_ACT;
              default link-set-action-inc-list;
              description
                "The action to specify on Link Set 2A.";
            } // action-link-set-2a

            leaf format-link-set-2a {
              // Low-level model info: Corresponds to i3EnCmFormatLinkSet2A.
              type AMB_STUBS_I3_CM_LNK_ST_FORMAT;
              default link-set-format-unnum;
              description
                "The format of the links in Link Set 2A - IPv4, IPv6 or
      unnumbered.";
            } // format-link-set-2a

            leaf num-links-link-set-2A {
              // Low-level model info: Corresponds to i3EnCmNumLinksLinkSet2A.
              type int32;
              default "0";
              description
                "The number of links in Link Set 2A which are present.  The
      present links will be contiguous and start from link 1.";
            } // num-links-link-set-2A

            leaf link-set-2A-link-1-addr {
              // Low-level model info: Corresponds to i3EnCmLinkSet2ALink1Addr.
              type string {
                length "8..32";
              }
              description
                "The identifier for the first link in Link Set 2A.  This
      will be read as an IPv4 address or an IPv6 address as
      specified by format_link_set_2a, or ignored if
      format_link_set_2a indicates using the Link IDs (_UNNUM).";
            } // link-set-2A-link-1-addr

            leaf link-set-2A-link-1-id {
              // Low-level model info: Corresponds to i3EnCmLinkSet2ALink1ID.
              type uint32;
              default "0";
              description
                "The identifier for the first link in Link Set 2A.  This is
      only used if the format of Link Set 2A is specified to be
      unnumbered.";
            } // link-set-2A-link-1-id

            leaf link-set-2A-link-2-addr {
              // Low-level model info: Corresponds to i3EnCmLinkSet2ALink2Addr.
              type string {
                length "8..32";
              }
              description
                "The identifier for the second link in Link Set 2A.  This
      will be read as an IPv4 address or an IPv6 address as
      specified by format_link_set_2a, or ignored if
      format_link_set_2a indicates using the Link IDs (_UNNUM).";
            } // link-set-2A-link-2-addr

            leaf link-set-2A-link-2-id {
              // Low-level model info: Corresponds to i3EnCmLinkSet2ALink2ID.
              type uint32;
              default "0";
              description
                "The identifier for the second link in Link Set 2A.  This
      is only used if the format of Link Set 2A is specified to
      be unnumbered.";
            } // link-set-2A-link-2-id

            leaf link-set-2A-link-3-addr {
              // Low-level model info: Corresponds to i3EnCmLinkSet2ALink3Addr.
              type string {
                length "8..32";
              }
              description
                "The identifier for the third link in Link Set 2A.  This
      will be read as an IPv4 address or an IPv6 address as
      specified by format_link_set_2a, or ignored if
      format_link_set_2a indicates using the Link IDs (_UNNUM).";
            } // link-set-2A-link-3-addr

            leaf link-set-2A-link-3-id {
              // Low-level model info: Corresponds to i3EnCmLinkSet2ALink3ID.
              type uint32;
              default "0";
              description
                "The identifier for the third link in Link Set 2A.  This is
      only used if the format of Link Set 2A is specified to be
      unnumbered.";
            } // link-set-2A-link-3-id

            leaf link-set-2A-link-4-addr {
              // Low-level model info: Corresponds to i3EnCmLinkSet2ALink4Addr.
              type string {
                length "8..32";
              }
              description
                "The identifier for the fourth link in Link Set 2A.  This
      will be read as an IPv4 address or an IPv6 address as
      specified by format_link_set_2a, or ignored if
      format_link_set_2a indicates using the Link IDs (_UNNUM).";
            } // link-set-2A-link-4-addr

            leaf link-set-2A-link-4-id {
              // Low-level model info: Corresponds to i3EnCmLinkSet2ALink4ID.
              type uint32;
              default "0";
              description
                "The identifier for the fourth link in Link Set 2A.  This
      is only used if the format of Link Set 2A is specified to
      be unnumbered.";
            } // link-set-2A-link-4-id

            leaf link-set-2A-link-5-addr {
              // Low-level model info: Corresponds to i3EnCmLinkSet2ALink5Addr.
              type string {
                length "8..32";
              }
              description
                "The identifier for the fifth link in Link Set 2A.  This
      will be read as an IPv4 address or an IPv6 address as
      specified by format_link_set_2a, or ignored if
      format_link_set_2a indicates using the Link IDs (_UNNUM).";
            } // link-set-2A-link-5-addr

            leaf link-set-2A-link-5-id {
              // Low-level model info: Corresponds to i3EnCmLinkSet2ALink5ID.
              type uint32;
              default "0";
              description
                "The identifier for the fifth link in Link Set 2A.  This is
      only used if the format of Link Set 2A is specified to be
      unnumbered.";
            } // link-set-2A-link-5-id

            leaf action-link-set-2b {
              // Low-level model info: Corresponds to i3EnCmActionLinkSet2B.
              type AMB_STUBS_I3_CM_LNK_ST_ACT;
              default link-set-action-inc-list;
              description
                "The action to specify on Link Set 2B.";
            } // action-link-set-2b

            leaf format-link-set-2b {
              // Low-level model info: Corresponds to i3EnCmFormatLinkSet2B.
              type AMB_STUBS_I3_CM_LNK_ST_FORMAT;
              default link-set-format-unnum;
              description
                "The format of the links in Link Set 2B - IPv4, IPv6 or
      unnumbered.";
            } // format-link-set-2b

            leaf num-links-link-set-2B {
              // Low-level model info: Corresponds to i3EnCmNumLinksLinkSet2B.
              type int32;
              default "0";
              description
                "The number of links in Link Set 2B which are present.  The
      present links will be contiguous and start from link 1.";
            } // num-links-link-set-2B

            leaf link-set-2B-link-1-addr {
              // Low-level model info: Corresponds to i3EnCmLinkSet2BLink1Addr.
              type string {
                length "8..32";
              }
              description
                "The identifier for the first link in Link Set 2B.  This
      will be read as an IPv4 address or an IPv6 address as
      specified by format_link_set_2b, or ignored if
      format_link_set_2b indicates using the Link IDs (_UNNUM).";
            } // link-set-2B-link-1-addr

            leaf link-set-2B-link-1-id {
              // Low-level model info: Corresponds to i3EnCmLinkSet2BLink1ID.
              type uint32;
              default "0";
              description
                "The identifier for the first link in Link Set 2B.  This is
      only used if the format of Link Set 2B is specified to be
      unnumbered.";
            } // link-set-2B-link-1-id

            leaf link-set-2B-link-2-addr {
              // Low-level model info: Corresponds to i3EnCmLinkSet2BLink2Addr.
              type string {
                length "8..32";
              }
              description
                "The identifier for the second link in Link Set 2B.  This
      will be read as an IPv4 address or an IPv6 address as
      specified by format_link_set_2b, or ignored if
      format_link_set_2b indicates using the Link IDs (_UNNUM).";
            } // link-set-2B-link-2-addr

            leaf link-set-2B-link-2-id {
              // Low-level model info: Corresponds to i3EnCmLinkSet2BLink2ID.
              type uint32;
              default "0";
              description
                "The identifier for the second link in Link Set 2B.  This
      is only used if the format of Link Set 2B is specified to
      be unnumbered.";
            } // link-set-2B-link-2-id

            leaf link-set-2B-link-3-addr {
              // Low-level model info: Corresponds to i3EnCmLinkSet2BLink3Addr.
              type string {
                length "8..32";
              }
              description
                "The identifier for the third link in Link Set 2B.  This
      will be read as an IPv4 address or an IPv6 address as
      specified by format_link_set_2b, or ignored if
      format_link_set_2b indicates using the Link IDs (_UNNUM).";
            } // link-set-2B-link-3-addr

            leaf link-set-2B-link-3-id {
              // Low-level model info: Corresponds to i3EnCmLinkSet2BLink3ID.
              type uint32;
              default "0";
              description
                "The identifier for the third link in Link Set 2B.  This is
      only used if the format of Link Set 2B is specified to be
      unnumbered.";
            } // link-set-2B-link-3-id

            leaf link-set-2B-link-4-addr {
              // Low-level model info: Corresponds to i3EnCmLinkSet2BLink4Addr.
              type string {
                length "8..32";
              }
              description
                "The identifier for the fourth link in Link Set 2B.  This
      will be read as an IPv4 address or an IPv6 address as
      specified by format_link_set_2b, or ignored if
      format_link_set_2b indicates using the Link IDs (_UNNUM).";
            } // link-set-2B-link-4-addr

            leaf link-set-2B-link-4-id {
              // Low-level model info: Corresponds to i3EnCmLinkSet2BLink4ID.
              type uint32;
              default "0";
              description
                "The identifier for the fourth link in Link Set 2B.  This
      is only used if the format of Link Set 2B is specified to
      be unnumbered.";
            } // link-set-2B-link-4-id

            leaf link-set-2B-link-5-addr {
              // Low-level model info: Corresponds to i3EnCmLinkSet2BLink5Addr.
              type string {
                length "8..32";
              }
              description
                "The identifier for the fifth link in Link Set 2B.  This
      will be read as an IPv4 address or an IPv6 address as
      specified by format_link_set_2b, or ignored if
      format_link_set_2b indicates using the Link IDs (_UNNUM).";
            } // link-set-2B-link-5-addr

            leaf link-set-2B-link-5-id {
              // Low-level model info: Corresponds to i3EnCmLinkSet2BLink5ID.
              type uint32;
              default "0";
              description
                "The identifier for the fifth link in Link Set 2B.  This is
      only used if the format of Link Set 2B is specified to be
      unnumbered.";
            } // link-set-2B-link-5-id

            leaf bidir-link-set-pair-3 {
              // Low-level model info: Corresponds to i3EnCmBidirLinkSetPair3.
              type boolean;
              default false;
              description
                "Flag to say whether the link sets in Link Set Pair 3 have
      a bidirectional relationship.  AMB_TRUE means that both
      sets in the pair will be advertised with
      ATG_WSON_LINK_DIR_BI, while AMB_FALSE means that set 3A
      will be advertised with DIR_INGRESS and 3B with
      DIR_EGRESS.";
            } // bidir-link-set-pair-3

            leaf action-link-set-3a {
              // Low-level model info: Corresponds to i3EnCmActionLinkSet3A.
              type AMB_STUBS_I3_CM_LNK_ST_ACT;
              default link-set-action-inc-list;
              description
                "The action to specify on Link Set 3A.";
            } // action-link-set-3a

            leaf format-link-set-3a {
              // Low-level model info: Corresponds to i3EnCmFormatLinkSet3A.
              type AMB_STUBS_I3_CM_LNK_ST_FORMAT;
              default link-set-format-unnum;
              description
                "The format of the links in Link Set 3A - IPv4, IPv6 or
      unnumbered.";
            } // format-link-set-3a

            leaf num-links-link-set-3A {
              // Low-level model info: Corresponds to i3EnCmNumLinksLinkSet3A.
              type int32;
              default "0";
              description
                "The number of links in Link Set 3A which are present.  The
      present links will be contiguous and start from link 1.";
            } // num-links-link-set-3A

            leaf link-set-3A-link-1-addr {
              // Low-level model info: Corresponds to i3EnCmLinkSet3ALink1Addr.
              type string {
                length "8..32";
              }
              description
                "The identifier for the first link in Link Set 3A.  This
      will be read as an IPv4 address or an IPv6 address as
      specified by format_link_set_3a, or ignored if
      format_link_set_3a indicates using the Link IDs (_UNNUM).";
            } // link-set-3A-link-1-addr

            leaf link-set-3A-link-1-id {
              // Low-level model info: Corresponds to i3EnCmLinkSet3ALink1ID.
              type uint32;
              default "0";
              description
                "The identifier for the first link in Link Set 3A.  This is
      only used if the format of Link Set 3A is specified to be
      unnumbered.";
            } // link-set-3A-link-1-id

            leaf link-set-3A-link-2-addr {
              // Low-level model info: Corresponds to i3EnCmLinkSet3ALink2Addr.
              type string {
                length "8..32";
              }
              description
                "The identifier for the second link in Link Set 3A.  This
      will be read as an IPv4 address or an IPv6 address as
      specified by format_link_set_3a, or ignored if
      format_link_set_3a indicates using the Link IDs (_UNNUM).";
            } // link-set-3A-link-2-addr

            leaf link-set-3A-link-2-id {
              // Low-level model info: Corresponds to i3EnCmLinkSet3ALink2ID.
              type uint32;
              default "0";
              description
                "The identifier for the second link in Link Set 3A.  This
      is only used if the format of Link Set 3A is specified to
      be unnumbered.";
            } // link-set-3A-link-2-id

            leaf link-set-3A-link-3-addr {
              // Low-level model info: Corresponds to i3EnCmLinkSet3ALink3Addr.
              type string {
                length "8..32";
              }
              description
                "The identifier for the third link in Link Set 3A.  This
      will be read as an IPv4 address or an IPv6 address as
      specified by format_link_set_3a, or ignored if
      format_link_set_3a indicates using the Link IDs (_UNNUM).";
            } // link-set-3A-link-3-addr

            leaf link-set-3A-link-3-id {
              // Low-level model info: Corresponds to i3EnCmLinkSet3ALink3ID.
              type uint32;
              default "0";
              description
                "The identifier for the third link in Link Set 3A.  This is
      only used if the format of Link Set 3A is specified to be
      unnumbered.";
            } // link-set-3A-link-3-id

            leaf link-set-3A-link-4-addr {
              // Low-level model info: Corresponds to i3EnCmLinkSet3ALink4Addr.
              type string {
                length "8..32";
              }
              description
                "The identifier for the fourth link in Link Set 3A.  This
      will be read as an IPv4 address or an IPv6 address as
      specified by format_link_set_3a, or ignored if
      format_link_set_3a indicates using the Link IDs (_UNNUM).";
            } // link-set-3A-link-4-addr

            leaf link-set-3A-link-4-id {
              // Low-level model info: Corresponds to i3EnCmLinkSet3ALink4ID.
              type uint32;
              default "0";
              description
                "The identifier for the fourth link in Link Set 3A.  This
      is only used if the format of Link Set 3A is specified to
      be unnumbered.";
            } // link-set-3A-link-4-id

            leaf link-set-3A-link-5-addr {
              // Low-level model info: Corresponds to i3EnCmLinkSet3ALink5Addr.
              type string {
                length "8..32";
              }
              description
                "The identifier for the fifth link in Link Set 3A.  This
      will be read as an IPv4 address or an IPv6 address as
      specified by format_link_set_3a, or ignored if
      format_link_set_3a indicates using the Link IDs (_UNNUM).";
            } // link-set-3A-link-5-addr

            leaf link-set-3A-link-5-id {
              // Low-level model info: Corresponds to i3EnCmLinkSet3ALink5ID.
              type uint32;
              default "0";
              description
                "The identifier for the fifth link in Link Set 3A.  This is
      only used if the format of Link Set 3A is specified to be
      unnumbered.";
            } // link-set-3A-link-5-id

            leaf action-link-set-3b {
              // Low-level model info: Corresponds to i3EnCmActionLinkSet3B.
              type AMB_STUBS_I3_CM_LNK_ST_ACT;
              default link-set-action-inc-list;
              description
                "The action to specify on Link Set 3B.";
            } // action-link-set-3b

            leaf format-link-set-3b {
              // Low-level model info: Corresponds to i3EnCmFormatLinkSet3B.
              type AMB_STUBS_I3_CM_LNK_ST_FORMAT;
              default link-set-format-unnum;
              description
                "The format of the links in Link Set 3B - IPv4, IPv6 or
      unnumbered.";
            } // format-link-set-3b

            leaf num-links-link-set-3B {
              // Low-level model info: Corresponds to i3EnCmNumLinksLinkSet3B.
              type int32;
              default "0";
              description
                "The number of links in Link Set 3B which are present.  The
      present links will be contiguous and start from link 1.";
            } // num-links-link-set-3B

            leaf link-set-3B-link-1-addr {
              // Low-level model info: Corresponds to i3EnCmLinkSet3BLink1Addr.
              type string {
                length "8..32";
              }
              description
                "The identifier for the first link in Link Set 3B.  This
      will be read as an IPv4 address or an IPv6 address as
      specified by format_link_set_3b, or ignored if
      format_link_set_3b indicates using the Link IDs (_UNNUM).";
            } // link-set-3B-link-1-addr

            leaf link-set-3B-link-1-id {
              // Low-level model info: Corresponds to i3EnCmLinkSet3BLink1ID.
              type uint32;
              default "0";
              description
                "The identifier for the first link in Link Set 3B.  This is
      only used if the format of Link Set 3B is specified to be
      unnumbered.";
            } // link-set-3B-link-1-id

            leaf link-set-3B-link-2-addr {
              // Low-level model info: Corresponds to i3EnCmLinkSet3BLink2Addr.
              type string {
                length "8..32";
              }
              description
                "The identifier for the second link in Link Set 3B.  This
      will be read as an IPv4 address or an IPv6 address as
      specified by format_link_set_3b, or ignored if
      format_link_set_3b indicates using the Link IDs (_UNNUM).";
            } // link-set-3B-link-2-addr

            leaf link-set-3B-link-2-id {
              // Low-level model info: Corresponds to i3EnCmLinkSet3BLink2ID.
              type uint32;
              default "0";
              description
                "The identifier for the second link in Link Set 3B.  This
      is only used if the format of Link Set 3B is specified to
      be unnumbered.";
            } // link-set-3B-link-2-id

            leaf link-set-3B-link-3-addr {
              // Low-level model info: Corresponds to i3EnCmLinkSet3BLink3Addr.
              type string {
                length "8..32";
              }
              description
                "The identifier for the third link in Link Set 3B.  This
      will be read as an IPv4 address or an IPv6 address as
      specified by format_link_set_3b, or ignored if
      format_link_set_3b indicates using the Link IDs (_UNNUM).";
            } // link-set-3B-link-3-addr

            leaf link-set-3B-link-3-id {
              // Low-level model info: Corresponds to i3EnCmLinkSet3BLink3ID.
              type uint32;
              default "0";
              description
                "The identifier for the third link in Link Set 3B.  This is
      only used if the format of Link Set 3B is specified to be
      unnumbered.";
            } // link-set-3B-link-3-id

            leaf link-set-3B-link-4-addr {
              // Low-level model info: Corresponds to i3EnCmLinkSet3BLink4Addr.
              type string {
                length "8..32";
              }
              description
                "The identifier for the fourth link in Link Set 3B.  This
      will be read as an IPv4 address or an IPv6 address as
      specified by format_link_set_3b, or ignored if
      format_link_set_3b indicates using the Link IDs (_UNNUM).";
            } // link-set-3B-link-4-addr

            leaf link-set-3B-link-4-id {
              // Low-level model info: Corresponds to i3EnCmLinkSet3BLink4ID.
              type uint32;
              default "0";
              description
                "The identifier for the fourth link in Link Set 3B.  This
      is only used if the format of Link Set 3B is specified to
      be unnumbered.";
            } // link-set-3B-link-4-id

            leaf link-set-3B-link-5-addr {
              // Low-level model info: Corresponds to i3EnCmLinkSet3BLink5Addr.
              type string {
                length "8..32";
              }
              description
                "The identifier for the fifth link in Link Set 3B.  This
      will be read as an IPv4 address or an IPv6 address as
      specified by format_link_set_3b, or ignored if
      format_link_set_3b indicates using the Link IDs (_UNNUM).";
            } // link-set-3B-link-5-addr

            leaf link-set-3B-link-5-id {
              // Low-level model info: Corresponds to i3EnCmLinkSet3BLink5ID.
              type uint32;
              default "0";
              description
                "The identifier for the fifth link in Link Set 3B.  This is
      only used if the format of Link Set 3B is specified to be
      unnumbered.";
            } // link-set-3B-link-5-id

          } // emulated-conn-matrix

        } // emulated-conn-matrix

        container emulated-traffic {
          list emulated-traffic {

            description
              "Each entry in this table represents an Emulated Interface
    Traffic Engineering entity.

    Normally the information configured in this MIB table
    describes TE parameters associated with a network interface
    local to a node, and the <product_index, instance_index,
    if_index, inet_addr> combination uniquely identifies these
    TE parameters (and the remaining indices can keep default
    values).

    However, for E-NNI Routing level information, this structure
    may describe TE parameters associated with a non-local
    network interface.  This is indicated by the
    local_endpoint_id being non-zero (and in this case the
    unique identifier for these TE parameters is the
    <product_index, instance_index, local_endpoint_id, if_index,
    inet_addr> combination).

    If this table is being used to configure TE parameters for
    interfaces with Transport Network Addresses, then this table
    is additionally indexed by address_type.

    Note that the meaning of the unreserved bandwidth fields
    depends on whether the router is operating in a Diffserv-TE
    environment as specified in RFC4124.  In a non-Diffserv-TE
    environment, the fields give the unreserved bandwidth for
    the eight priority levels.  In a Diffserv-TE environment,
    they give the unreserved bandwidth for the eight TE-Classes.

    Before performing Hot Software Downgrade (HSD) from a level
    of code which supports bandwidth configuration in IEEE
    floating point format to a level of code which does not, the
    user must ensure that the configured values are supported by
    the back level code (less than 2,147,483,647 Bps /
    0x4EFFFFFF).

    For G.709v3 interfaces, the information in this table is
    supplemented by the i3EtTempG709OduResTable.";

            key "i3-index instance-index local-endpoint-id interface-index address-type inet-address";

            leaf i3-index {
              // Low-level model info: Corresponds to i3EtPrIx.
              type uint32;
              description
                "Index for the I3 stub.";
            } // i3-index

            leaf instance-index {
              // Low-level model info: Corresponds to i3EtInIx.
              type int32;
              description
                "Index of the node to which these TE parameters are
      assigned.";
            } // instance-index

            leaf local-endpoint-id {
              // Low-level model info: Corresponds to i3EtLocalEndId.
              type uint32;
              description
                "The Routing Controller ID of the local endpoint of the
      address which the TE parameters are assigned to.";
            } // local-endpoint-id

            leaf interface-index {
              // Low-level model info: Corresponds to i3EtIfIx.
              type uint32;
              description
                "Network interface index in the IF-MIB (RFC 2233) of the
      network interface which the TE parameters are assigned to.";
            } // interface-index

            leaf address-type {
              // Low-level model info: Corresponds to i3EtAddressType.
              type AMB_INETWK_ADDR_TYPE;
              description
                "Address type.";
            } // address-type

            leaf inet-address {
              // Low-level model info: Corresponds to i3EtInetAddr.
              type string {
                length "0..32";
              }
              description
                "Internetwork address.";
            } // inet-address

            leaf te-metric {
              // Low-level model info: Corresponds to i3EtTeMetric.
              type uint32;
              mandatory true;
              description
                "The Traffic Engineering metric for this interface.  Used
      in CSPF calculations.";
            } // te-metric

            leaf max-bandwidth {
              // Low-level model info: Corresponds to i3EtMaxBw.
              type uint32;
              description
                "The maximum bandwidth that can be used on this link.
      This is the true link capacity.  The units are bytes per
      second.

      If _use_ieee_floating_point_ is set to AMB_FALSE, then
      this field is configured and reported in standard format,
      otherwise IEEE floating point format is used.";
            } // max-bandwidth

            leaf max-reservable-bandwidth {
              // Low-level model info: Corresponds to i3EtMaxResBw.
              type uint32;
              description
                "The maximum bandwidth that may be reserved on this link in
      this direction.  Note that this may be greater than the
      maximum bandwidth (in which case the link may be
      oversubscribed).  The units are bytes per second.

      If _use_ieee_floating_point_ is set to AMB_FALSE, then
      this field is configured and reported in standard format,
      otherwise IEEE floating point format is used.";
            } // max-reservable-bandwidth

            leaf unreserved-bandwidth-0 {
              // Low-level model info: Corresponds to i3EtUnresBwidth0.
              type uint32;
              description
                "The unreserved bandwidth on this interface, at the first
      priority level(non-Diffserv-TE) or TE-Class(Diffserv-TE).
      The value is used by CSPF to calculate constrained routes.
      Each value will be less than or equal to i3EtMaxResBw.
      The units are bytes per second.

      If _use_ieee_floating_point_ is set to AMB_FALSE, then
      this field is configured and reported in standard format,
      otherwise IEEE floating point format is used.";
            } // unreserved-bandwidth-0

            leaf unreserved-bandwidth-1 {
              // Low-level model info: Corresponds to i3EtUnresBwidth1.
              type uint32;
              description
                "The unreserved bandwidth on this interface, at the second
      priority level(non-Diffserv-TE) or TE-Class(Diffserv-TE).
      The value is used by CSPF to calculate constrained routes.
      Each value will be less than or equal to i3EtMaxResBw.
      The units are bytes per second.

      If _use_ieee_floating_point_ is set to AMB_FALSE, then
      this field is configured and reported in standard format,
      otherwise IEEE floating point format is used.";
            } // unreserved-bandwidth-1

            leaf unreserved-bandwidth-2 {
              // Low-level model info: Corresponds to i3EtUnresBwidth2.
              type uint32;
              description
                "The unreserved bandwidth on this interface, at the third
      priority level(non-Diffserv-TE) or TE-Class(Diffserv-TE).
      The value is used by CSPF to calculate constrained routes.
      Each value will be less than or equal to i3EtMaxResBw.
      The units are bytes per second.

      If _use_ieee_floating_point_ is set to AMB_FALSE, then
      this field is configured and reported in standard format,
      otherwise IEEE floating point format is used.";
            } // unreserved-bandwidth-2

            leaf unreserved-bandwidth-3 {
              // Low-level model info: Corresponds to i3EtUnresBwidth3.
              type uint32;
              description
                "The unreserved bandwidth on this interface, at the fourth
      priority level(non-Diffserv-TE) or TE-Class(Diffserv-TE).
      The value is used by CSPF to calculate constrained routes.
      Each value will be less than or equal to i3EtMaxResBw.
      The units are bytes per second.

      If _use_ieee_floating_point_ is set to AMB_FALSE, then
      this field is configured and reported in standard format,
      otherwise IEEE floating point format is used.";
            } // unreserved-bandwidth-3

            leaf unreserved-bandwidth-4 {
              // Low-level model info: Corresponds to i3EtUnresBwidth4.
              type uint32;
              description
                "The unreserved bandwidth on this interface, at the fifth
      priority level(non-Diffserv-TE) or TE-Class(Diffserv-TE).
      The value is used by CSPF to calculate constrained routes.
      Each value will be less than or equal to i3EtMaxResBw.
      The units are bytes per second.

      If _use_ieee_floating_point_ is set to AMB_FALSE, then
      this field is configured and reported in standard format,
      otherwise IEEE floating point format is used.";
            } // unreserved-bandwidth-4

            leaf unreserved-bandwidth-5 {
              // Low-level model info: Corresponds to i3EtUnresBwidth5.
              type uint32;
              description
                "The unreserved bandwidth on this interface, at the sixth
      priority level(non-Diffserv-TE) or TE-Class(Diffserv-TE).
      The value is used by CSPF to calculate constrained routes.
      Each value will be less than or equal to i3EtMaxResBw.
      The units are bytes per second.

      If _use_ieee_floating_point_ is set to AMB_FALSE, then
      this field is configured and reported in standard format,
      otherwise IEEE floating point format is used.";
            } // unreserved-bandwidth-5

            leaf unreserved-bandwidth-6 {
              // Low-level model info: Corresponds to i3EtUnresBwidth6.
              type uint32;
              description
                "The unreserved bandwidth on this interface, at the seventh
      priority level(non-Diffserv-TE) or TE-Class(Diffserv-TE).
      The value is used by CSPF to calculate constrained routes.
      Each value will be less than or equal to i3EtMaxResBw.
      The units are bytes per second.

      If _use_ieee_floating_point_ is set to AMB_FALSE, then
      this field is configured and reported in standard format,
      otherwise IEEE floating point format is used.";
            } // unreserved-bandwidth-6

            leaf unreserved-bandwidth-7 {
              // Low-level model info: Corresponds to i3EtUnresBwidth7.
              type uint32;
              description
                "The unreserved bandwidth on this interface, at the eighth
      priority level(non-Diffserv-TE) or TE-Class(Diffserv-TE).
      The value is used by CSPF to calculate constrained routes.
      Each value will be less than or equal to i3EtMaxResBw.
      The units are bytes per second.

      If _use_ieee_floating_point_ is set to AMB_FALSE, then
      this field is configured and reported in standard format,
      otherwise IEEE floating point format is used.";
            } // unreserved-bandwidth-7

            leaf link-protection-type {
              // Low-level model info: Corresponds to i3EtLpType.
              type uint32;
              description
                "Link Protection Type.  Note that the lower three bytes are
      currently undefined and should be set to zero - see
      _link_prot_type_ in ATG_I3_TE_PARAMETERS for a full
      description of the format of this field.";
            } // link-protection-type

            leaf number-switching-descriptors {
              // Low-level model info: Corresponds to i3EtNumSwDesc.
              type uint32;
              description
                "Number of Switching Descriptors.";
            } // number-switching-descriptors

            leaf switching-capability-1 {
              // Low-level model info: Corresponds to i3EtSwitchingCap1.
              type AMB_STUBS_I3_SW_CAP_VALUE;
              default packet-switch-capable-1;
              description
                "The switching capability of the interface.  Possible
      values are defined in
      http://www.iana.org/assignments/gmpls-sig-parameters.

      Value      Switching Capability type.

      1          Packet-Switch Capable-1.

      2          Packet-Switch Capable-2.

      3          Packet-Switch Capable-3.

      4          Packet-Switch Capable-4.

      51         Layer-2 Switch Capable.

      100        Time-Division-Multiplex Capable.

      125        Data Channel (Port) Switch Capable.

      150        Lambda-Switch Capable.

      200        Fiber-Switch Capable.";
            } // switching-capability-1

            leaf switch-encoding-1 {
              // Low-level model info: Corresponds to i3EtSwitchEncoding1.
              type AMB_STUBS_I3_SW_ENCODE_VAL;
              default packet;
              description
                "The type of encoding used on this interface.  Possible
      values are:

      Value      Encoding type.

      1          Packet.

      2          Ethernet.

      3          ANSI/ETSI-PDH.

      5          SDH/SONET.

      7          DIG-Wrapper.

      8          Lambda.

      9          Fiber.

      11         Fiber-Channel.";
            } // switch-encoding-1

            leaf max-lsp-bandwidth-1-0 {
              // Low-level model info: Corresponds to i3EtMaxLspBwidth10.
              type uint32;
              description
                "The MAX Lsp bandwidth on this interface, at the first
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-1-0

            leaf max-lsp-bandwidth-1-1 {
              // Low-level model info: Corresponds to i3EtMaxLspBwidth11.
              type uint32;
              description
                "The MAX Lsp bandwidth on this interface, at the second
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-1-1

            leaf max-lsp-bandwidth-1-2 {
              // Low-level model info: Corresponds to i3EtMaxLspBwidth12.
              type uint32;
              description
                "The MAX Lsp bandwidth on this interface, at the third
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-1-2

            leaf max-lsp-bandwidth-1-3 {
              // Low-level model info: Corresponds to i3EtMaxLspBwidth13.
              type uint32;
              description
                "The MAX Lsp bandwidth on this interface, at the fourth
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-1-3

            leaf max-lsp-bandwidth-1-4 {
              // Low-level model info: Corresponds to i3EtMaxLspBwidth14.
              type uint32;
              description
                "The MAX Lsp bandwidth on this interface, at the fifth
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-1-4

            leaf max-lsp-bandwidth-1-5 {
              // Low-level model info: Corresponds to i3EtMaxLspBwidth15.
              type uint32;
              description
                "The MAX Lsp bandwidth on this interface, at the sixth
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-1-5

            leaf max-lsp-bandwidth-1-6 {
              // Low-level model info: Corresponds to i3EtMaxLspBwidth16.
              type uint32;
              description
                "The MAX Lsp bandwidth on this interface, at the seventh
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-1-6

            leaf max-lsp-bandwidth-1-7 {
              // Low-level model info: Corresponds to i3EtMaxLspBwidth17.
              type uint32;
              description
                "The MAX Lsp bandwidth on this interface, at the eighth
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-1-7

            leaf min-lsp-bandwidth-1 {
              // Low-level model info: Corresponds to i3EtMinLspBwidth1.
              type uint32;
              description
                "Specific information about the switching capability for
      this interface.  This represents the Minimium Lsp
      bandwidth for this interface.

      If _use_ieee_floating_point_ is set to AMB_FALSE, then
      this field is configured and reported in standard format,
      otherwise IEEE floating point format is used.";
            } // min-lsp-bandwidth-1

            leaf mtu-size-1 {
              // Low-level model info: Corresponds to i3EtMtuSize1.
              type int32;
              description
                "Specific information about the switching capability for
      this interface.  This field reports the Maximum
      Transmission Unit size for this type of traffic.  Note
      that this can supersede the more generic MTU size
      specified on the interface MIB.";
            } // mtu-size-1

            leaf sonet-sdh-1 {
              // Low-level model info: Corresponds to i3EtSonetSdh1.
              type AMB_STUBS_I3_ET_SONET_SDH_VAL;
              default standard;
              description
                "SONET/SDH support for TDM.";
            } // sonet-sdh-1

            leaf switching-capability-2 {
              // Low-level model info: Corresponds to i3EtSwitchingCap2.
              type AMB_STUBS_I3_SW_CAP_VALUE;
              default packet-switch-capable-1;
              description
                "The switching capability of the interface.  Possible
      values are defined in
      http://www.iana.org/assignments/gmpls-sig-parameters.

      Value      Switching Capability type.

      1          Packet-Switch Capable-1.

      2          Packet-Switch Capable-2.

      3          Packet-Switch Capable-3.

      4          Packet-Switch Capable-4.

      51         Layer-2 Switch Capable.

      100        Time-Division-Multiplex Capable.

      125        Data Channel (Port) Switch Capable.

      150        Lambda-Switch Capable.

      200        Fiber-Switch Capable.";
            } // switching-capability-2

            leaf switch-encoding-2 {
              // Low-level model info: Corresponds to i3EtSwitchEncoding2.
              type AMB_STUBS_I3_SW_ENCODE_VAL;
              default packet;
              description
                "The type of encoding used on this interface.  Possible
      values are:

      Value      Encoding type.

      1          Packet.
      2          Ethernet-V2DIX.
      3          ANSI-PDH.
      4          ETSI-PDH.
      5          SDH_707_1996.
      6          SONET_105_1995.
      7          DIG-Wrapper.
      8          Lambda.
      9          Fiber.
      10         Ethernet_802_3.
      11         SDH_707_2000.
      12         SONET_105_2000.";
            } // switch-encoding-2

            leaf max-lsp-bandwidth-2-0 {
              // Low-level model info: Corresponds to i3EtMaxLspBwidth20.
              type uint32;
              description
                "The MAX Lsp bandwidth on this interface, at the first
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-2-0

            leaf max-lsp-bandwidth-2-1 {
              // Low-level model info: Corresponds to i3EtMaxLspBwidth21.
              type uint32;
              description
                "The MAX Lsp bandwidth on this interface, at the second
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-2-1

            leaf max-lsp-bandwidth-2-2 {
              // Low-level model info: Corresponds to i3EtMaxLspBwidth22.
              type uint32;
              description
                "The MAX Lsp bandwidth on this interface, at the third
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-2-2

            leaf max-lsp-bandwidth-2-3 {
              // Low-level model info: Corresponds to i3EtMaxLspBwidth23.
              type uint32;
              description
                "The MAX Lsp bandwidth on this interface, at the fourth
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-2-3

            leaf max-lsp-bandwidth-2-4 {
              // Low-level model info: Corresponds to i3EtMaxLspBwidth24.
              type uint32;
              description
                "The MAX Lsp bandwidth on this interface, at the fifth
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-2-4

            leaf max-lsp-bandwidth-2-5 {
              // Low-level model info: Corresponds to i3EtMaxLspBwidth25.
              type uint32;
              description
                "The MAX Lsp bandwidth on this interface, at the sixth
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-2-5

            leaf max-lsp-bandwidth-2-6 {
              // Low-level model info: Corresponds to i3EtMaxLspBwidth26.
              type uint32;
              description
                "The MAX Lsp bandwidth on this interface, at the seventh
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-2-6

            leaf max-lsp-bandwidth-2-7 {
              // Low-level model info: Corresponds to i3EtMaxLspBwidth27.
              type uint32;
              description
                "The MAX Lsp bandwidth on this interface, at the eighth
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-2-7

            leaf min-lsp-bandwidth-2 {
              // Low-level model info: Corresponds to i3EtMinLspBwidth2.
              type uint32;
              description
                "Specific information about the switching capability for
      this interface.  This represents the Minimium Lsp
      bandwidth for this interface.

      If _use_ieee_floating_point_ is set to AMB_FALSE, then
      this field is configured and reported in standard format,
      otherwise IEEE floating point format is used.";
            } // min-lsp-bandwidth-2

            leaf mtu-size-2 {
              // Low-level model info: Corresponds to i3EtMtuSize2.
              type int32;
              description
                "Specific information about the switching capability for
      this interface.  This field reports the Maximum
      Transmission Unit size for this type of traffic.  Note
      that this can supersede the more generic MTU size
      specified on the interface MIB.";
            } // mtu-size-2

            leaf sonet-sdh-2 {
              // Low-level model info: Corresponds to i3EtSonetSdh2.
              type AMB_STUBS_I3_ET_SONET_SDH_VAL;
              default standard;
              description
                "SONET/SDH support for TDM.";
            } // sonet-sdh-2

            leaf switching-capability-3 {
              // Low-level model info: Corresponds to i3EtSwitchingCap3.
              type AMB_STUBS_I3_SW_CAP_VALUE;
              default packet-switch-capable-1;
              description
                "The switching capability of the interface.  Possible
      values are defined in
      http://www.iana.org/assignments/gmpls-sig-parameters.

      Value      Switching Capability type.

      1          Packet-Switch Capable-1.

      2          Packet-Switch Capable-2.

      3          Packet-Switch Capable-3.

      4          Packet-Switch Capable-4.

      51         Layer-2 Switch Capable.

      100        Time-Division-Multiplex Capable.

      125        Data Channel (Port) Switch Capable.

      150        Lambda-Switch Capable.

      200        Fiber-Switch Capable.";
            } // switching-capability-3

            leaf switch-encoding-3 {
              // Low-level model info: Corresponds to i3EtSwitchEncoding3.
              type AMB_STUBS_I3_SW_ENCODE_VAL;
              default packet;
              description
                "The type of encoding used on this interface.  Possible
      values are:

      Value      Encoding type.

      1          Packet.
      2          Ethernet-V2DIX.
      3          ANSI-PDH.
      4          ETSI-PDH.
      5          SDH_707_1996.
      6          SONET_105_1995.
      7          DIG-Wrapper.
      8          Lambda.
      9          Fiber.
      10         Ethernet_802_3.
      11         SDH_707_2000.
      12         SONET_105_2000.";
            } // switch-encoding-3

            leaf max-lsp-bandwidth-3-0 {
              // Low-level model info: Corresponds to i3EtMaxLspBwidth30.
              type uint32;
              description
                "The MAX Lsp bandwidth on this interface, at the first
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-3-0

            leaf max-lsp-bandwidth-3-1 {
              // Low-level model info: Corresponds to i3EtMaxLspBwidth31.
              type uint32;
              description
                "The MAX Lsp bandwidth on this interface, at the second
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-3-1

            leaf max-lsp-bandwidth-3-2 {
              // Low-level model info: Corresponds to i3EtMaxLspBwidth32.
              type uint32;
              description
                "The MAX Lsp bandwidth on this interface, at the third
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-3-2

            leaf max-lsp-bandwidth-3-3 {
              // Low-level model info: Corresponds to i3EtMaxLspBwidth33.
              type uint32;
              description
                "The MAX Lsp bandwidth on this interface, at the fourth
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-3-3

            leaf max-lsp-bandwidth-3-4 {
              // Low-level model info: Corresponds to i3EtMaxLspBwidth34.
              type uint32;
              description
                "The MAX Lsp bandwidth on this interface, at the fifth
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-3-4

            leaf max-lsp-bandwidth-3-5 {
              // Low-level model info: Corresponds to i3EtMaxLspBwidth35.
              type uint32;
              description
                "The MAX Lsp bandwidth on this interface, at the sixth
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-3-5

            leaf max-lsp-bandwidth-3-6 {
              // Low-level model info: Corresponds to i3EtMaxLspBwidth36.
              type uint32;
              description
                "The MAX Lsp bandwidth on this interface, at the seventh
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-3-6

            leaf max-lsp-bandwidth-3-7 {
              // Low-level model info: Corresponds to i3EtMaxLspBwidth37.
              type uint32;
              description
                "The MAX Lsp bandwidth on this interface, at the eighth
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-3-7

            leaf min-lsp-bandwidth-3 {
              // Low-level model info: Corresponds to i3EtMinLspBwidth3.
              type uint32;
              description
                "Specific information about the switching capability for
      this interface.  This represents the Minimium Lsp
      bandwidth for this interface.

      If _use_ieee_floating_point_ is set to AMB_FALSE, then
      this field is configured and reported in standard format,
      otherwise IEEE floating point format is used.";
            } // min-lsp-bandwidth-3

            leaf mtu-size-3 {
              // Low-level model info: Corresponds to i3EtMtuSize3.
              type int32;
              description
                "Specific information about the switching capability for
      this interface.  This field reports the Maximum
      Transmission Unit size for this type of traffic.  Note
      that this can supersede the more generic MTU size
      specified on the interface MIB.";
            } // mtu-size-3

            leaf sonet-sdh-3 {
              // Low-level model info: Corresponds to i3EtSonetSdh3.
              type AMB_STUBS_I3_ET_SONET_SDH_VAL;
              default standard;
              description
                "SONET/SDH support for TDM.";
            } // sonet-sdh-3

            leaf switching-capability-4 {
              // Low-level model info: Corresponds to i3EtSwitchingCap4.
              type AMB_STUBS_I3_SW_CAP_VALUE;
              default packet-switch-capable-1;
              description
                "The switching capability of the interface.  Possible
      values are defined in
      http://www.iana.org/assignments/gmpls-sig-parameters.

      Value      Switching Capability type.

      1          Packet-Switch Capable-1.

      2          Packet-Switch Capable-2.

      3          Packet-Switch Capable-3.

      4          Packet-Switch Capable-4.

      51         Layer-2 Switch Capable.

      100        Time-Division-Multiplex Capable.

      125        Data Channel (Port) Switch Capable.

      150        Lambda-Switch Capable.

      200        Fiber-Switch Capable.";
            } // switching-capability-4

            leaf switch-encoding-4 {
              // Low-level model info: Corresponds to i3EtSwitchEncoding4.
              type AMB_STUBS_I3_SW_ENCODE_VAL;
              default packet;
              description
                "The type of encoding used on this interface.  Possible
      values are:

      Value      Encoding type.

      1          Packet.
      2          Ethernet-V2DIX.
      3          ANSI-PDH.
      4          ETSI-PDH.
      5          SDH_707_1996.
      6          SONET_105_1995.
      7          DIG-Wrapper.
      8          Lambda.
      9          Fiber.
      10         Ethernet_802_3.
      11         SDH_707_2000.
      12         SONET_105_2000.";
            } // switch-encoding-4

            leaf max-lsp-bandwidth-4-0 {
              // Low-level model info: Corresponds to i3EtMaxLspBwidth40.
              type uint32;
              description
                "The MAX Lsp bandwidth on this interface, at the first
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-4-0

            leaf max-lsp-bandwidth-4-1 {
              // Low-level model info: Corresponds to i3EtMaxLspBwidth41.
              type uint32;
              description
                "The MAX Lsp bandwidth on this interface, at the second
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-4-1

            leaf max-lsp-bandwidth-4-2 {
              // Low-level model info: Corresponds to i3EtMaxLspBwidth42.
              type uint32;
              description
                "The MAX Lsp bandwidth on this interface, at the third
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-4-2

            leaf max-lsp-bandwidth-4-3 {
              // Low-level model info: Corresponds to i3EtMaxLspBwidth43.
              type uint32;
              description
                "The MAX Lsp bandwidth on this interface, at the fourth
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-4-3

            leaf max-lsp-bandwidth-4-4 {
              // Low-level model info: Corresponds to i3EtMaxLspBwidth44.
              type uint32;
              description
                "The MAX Lsp bandwidth on this interface, at the fifth
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-4-4

            leaf max-lsp-bandwidth-4-5 {
              // Low-level model info: Corresponds to i3EtMaxLspBwidth45.
              type uint32;
              description
                "The MAX Lsp bandwidth on this interface, at the sixth
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-4-5

            leaf max-lsp-bandwidth-4-6 {
              // Low-level model info: Corresponds to i3EtMaxLspBwidth46.
              type uint32;
              description
                "The MAX Lsp bandwidth on this interface, at the seventh
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-4-6

            leaf max-lsp-bandwidth-4-7 {
              // Low-level model info: Corresponds to i3EtMaxLspBwidth47.
              type uint32;
              description
                "The MAX Lsp bandwidth on this interface, at the eighth
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-4-7

            leaf min-lsp-bandwidth-4 {
              // Low-level model info: Corresponds to i3EtMinLspBwidth4.
              type uint32;
              description
                "Specific information about the switching capability for
      this interface.  This represents the Minimium Lsp
      bandwidth for this interface.

      If _use_ieee_floating_point_ is set to AMB_FALSE, then
      this field is configured and reported in standard format,
      otherwise IEEE floating point format is used.";
            } // min-lsp-bandwidth-4

            leaf mtu-size-4 {
              // Low-level model info: Corresponds to i3EtMtuSize4.
              type int32;
              description
                "Specific information about the switching capability for
      this interface.  This field reports the Maximum
      Transmission Unit size for this type of traffic.  Note
      that this can supersede the more generic MTU size
      specified on the interface MIB.";
            } // mtu-size-4

            leaf sonet-sdh-4 {
              // Low-level model info: Corresponds to i3EtSonetSdh4.
              type AMB_STUBS_I3_ET_SONET_SDH_VAL;
              default standard;
              description
                "SONET/SDH support for TDM.";
            } // sonet-sdh-4

            leaf switching-capability-5 {
              // Low-level model info: Corresponds to i3EtSwitchingCap5.
              type AMB_STUBS_I3_SW_CAP_VALUE;
              default packet-switch-capable-1;
              description
                "The switching capability of the interface.  Possible
      values are defined in
      http://www.iana.org/assignments/gmpls-sig-parameters.

      Value      Switching Capability type.

      1          Packet-Switch Capable-1.

      2          Packet-Switch Capable-2.

      3          Packet-Switch Capable-3.

      4          Packet-Switch Capable-4.

      51         Layer-2 Switch Capable.

      100        Time-Division-Multiplex Capable.

      125        Data Channel (Port) Switch Capable.

      150        Lambda-Switch Capable.

      200        Fiber-Switch Capable.";
            } // switching-capability-5

            leaf switch-encoding-5 {
              // Low-level model info: Corresponds to i3EtSwitchEncoding5.
              type AMB_STUBS_I3_SW_ENCODE_VAL;
              default packet;
              description
                "The type of encoding used on this interface.  Possible
      values are:

      Value   Encoding type.
      1       Packet.
      2       Ethernet-V2DIX.
      3       ANSI-PDH.
      4       ETSI-PDH.
      5       SDH_707_1996.
      6       SONET_105_1995.
      7       DIG-Wrapper.
      8       Lambda.
      9       Fiber.
      10      Ethernet_802_3.
      11      SDH_707_2000.
      12      SONET_105_2000.";
            } // switch-encoding-5

            leaf max-lsp-bandwidth-5-0 {
              // Low-level model info: Corresponds to i3EtMaxLspBwidth50.
              type uint32;
              description
                "The MAX Lsp bandwidth on this interface, at the first
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-5-0

            leaf max-lsp-bandwidth-5-1 {
              // Low-level model info: Corresponds to i3EtMaxLspBwidth51.
              type uint32;
              description
                "The MAX Lsp bandwidth on this interface, at the second
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-5-1

            leaf max-lsp-bandwidth-5-2 {
              // Low-level model info: Corresponds to i3EtMaxLspBwidth52.
              type uint32;
              description
                "The MAX Lsp bandwidth on this interface, at the third
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-5-2

            leaf max-lsp-bandwidth-5-3 {
              // Low-level model info: Corresponds to i3EtMaxLspBwidth53.
              type uint32;
              description
                "The MAX Lsp bandwidth on this interface, at the fourth
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-5-3

            leaf max-lsp-bandwidth-5-4 {
              // Low-level model info: Corresponds to i3EtMaxLspBwidth54.
              type uint32;
              description
                "The MAX Lsp bandwidth on this interface, at the fifth
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-5-4

            leaf max-lsp-bandwidth-5-5 {
              // Low-level model info: Corresponds to i3EtMaxLspBwidth55.
              type uint32;
              description
                "The MAX Lsp bandwidth on this interface, at the sixth
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-5-5

            leaf max-lsp-bandwidth-5-6 {
              // Low-level model info: Corresponds to i3EtMaxLspBwidth56.
              type uint32;
              description
                "The MAX Lsp bandwidth on this interface, at the seventh
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-5-6

            leaf max-lsp-bandwidth-5-7 {
              // Low-level model info: Corresponds to i3EtMaxLspBwidth57.
              type uint32;
              description
                "The MAX Lsp bandwidth on this interface, at the eighth
      priority level(non-Diffserv-TE) or TE-Class(Diffserv-TE).
      The value is used by CSPF to calculate constrained routes.

      If _use_ieee_floating_point_ is set to AMB_FALSE, then
      this field is configured and reported in standard format,
      otherwise IEEE floating point format is used.";
            } // max-lsp-bandwidth-5-7

            leaf min-lsp-bandwidth-5 {
              // Low-level model info: Corresponds to i3EtMinLspBwidth5.
              type uint32;
              description
                "Specific information about the switching capability for
      this interface.  This represents the Minimium Lsp
      bandwidth for this interface.

      If _use_ieee_floating_point_ is set to AMB_FALSE, then
      this field is configured and reported in standard format,
      otherwise IEEE floating point format is used.";
            } // min-lsp-bandwidth-5

            leaf mtu-size-5 {
              // Low-level model info: Corresponds to i3EtMtuSize5.
              type int32;
              description
                "Specific information about the switching capability for
      this interface.  This field reports the Maximum
      Transmission Unit size for this type of traffic.  Note
      that this can supersede the more generic MTU size
      specified on the interface MIB.";
            } // mtu-size-5

            leaf sonet-sdh-5 {
              // Low-level model info: Corresponds to i3EtSonetSdh5.
              type AMB_STUBS_I3_ET_SONET_SDH_VAL;
              default standard;
              description
                "SONET/SDH support for TDM.";
            } // sonet-sdh-5

            leaf srlgs {
              // Low-level model info: Corresponds to i3EtSrlgs.
              type string {
                length "0..512";
              }
              description
                "An Octet String indicating the  Shared Risk Link Groups
      (SRLGs) that links on this interface belong to.  Links
      belong to the same SRLG if they share the same risk
      characteristics.  The SRLGs are 32-bit Integer values,
      concatenated to form the Octet String.  The length of the
      octet string limits the MIB to returning a maximum of 64
      32-bit SRLGs.  The I3 stub further limits this to
      I3_MAX_SRLGS 32-bit SRLGs.";
            } // srlgs

            leaf number-srlgs {
              // Low-level model info: Corresponds to i3EtNumSrlgs.
              type uint32;
              description
                "Number of Shared Risk Link Groups (SRLGs).  The maximum
      allowed value of this field is I3_MAX_SRLGS.";
            } // number-srlgs

            leaf opaque-parameters {
              // Low-level model info: Corresponds to i3EtOpaParam.
              type string {
                length "0..512";
              }
              description
                "An Octet string containing Opaque TE Parameters.";
            } // opaque-parameters

            leaf number-sonet-signal-types {
              // Low-level model info: Corresponds to i3EtNumSonetSignalTypes.
              type uint32;
              description
                "Number of SONET/SDH signal types that are supported on
      this interface.";
            } // number-sonet-signal-types

            leaf signal-type-1 {
              // Low-level model info: Corresponds to i3EtSignalType1.
              type AMB_STUBS_I3_SONET_SIG_TYPES;
              description
                "A SONET/SDH signal type that is supported on this
      interface.";
            } // signal-type-1

            leaf unallocated-timeslots-1 {
              // Low-level model info: Corresponds to i3EtUnallocatedTimeslots1.
              type uint32 {
                range "0..16777215";
              }
              description
                "The number of unallocated timeslots on this interface of
      signal type i3EtSignalType1.";
            } // unallocated-timeslots-1

            leaf signal-type-2 {
              // Low-level model info: Corresponds to i3EtSignalType2.
              type AMB_STUBS_I3_SONET_SIG_TYPES;
              description
                "A SONET/SDH signal type that is supported on this
      interface.";
            } // signal-type-2

            leaf unallocated-timeslots-2 {
              // Low-level model info: Corresponds to i3EtUnallocatedTimeslots2.
              type uint32 {
                range "0..16777215";
              }
              description
                "The number of unallocated timeslots on this interface of
      signal type i3EtSignalType2.";
            } // unallocated-timeslots-2

            leaf signal-type-3 {
              // Low-level model info: Corresponds to i3EtSignalType3.
              type AMB_STUBS_I3_SONET_SIG_TYPES;
              description
                "A SONET/SDH signal type that is supported on this
      interface.";
            } // signal-type-3

            leaf unallocated-timeslots-3 {
              // Low-level model info: Corresponds to i3EtUnallocatedTimeslots3.
              type uint32 {
                range "0..16777215";
              }
              description
                "The number of unallocated timeslots on this interface of
      signal type i3EtSignalType3.";
            } // unallocated-timeslots-3

            leaf signal-type-4 {
              // Low-level model info: Corresponds to i3EtSignalType4.
              type AMB_STUBS_I3_SONET_SIG_TYPES;
              description
                "A SONET/SDH signal type that is supported on this
      interface.";
            } // signal-type-4

            leaf unallocated-timeslots-4 {
              // Low-level model info: Corresponds to i3EtUnallocatedTimeslots4.
              type uint32 {
                range "0..16777215";
              }
              description
                "The number of unallocated timeslots on this interface of
      signal type i3EtSignalType4.";
            } // unallocated-timeslots-4

            leaf signal-type-5 {
              // Low-level model info: Corresponds to i3EtSignalType5.
              type AMB_STUBS_I3_SONET_SIG_TYPES;
              description
                "A SONET/SDH signal type that is supported on this
      interface.";
            } // signal-type-5

            leaf unallocated-timeslots-5 {
              // Low-level model info: Corresponds to i3EtUnallocatedTimeslots5.
              type uint32 {
                range "0..16777215";
              }
              description
                "The number of unallocated timeslots on this interface of
      signal type i3EtSignalType5.";
            } // unallocated-timeslots-5

            leaf number-bandwidth-constraints {
              // Low-level model info: Corresponds to i3EtNumBandwidthConstraints.
              type uint32 {
                range "0..8";
              }
              description
                "The number of valid bandwidth constraints, starting from
      BC0.  In a non Diffserv-TE environment, this object must be
      set to 0.  Setting this value to 0 means that no bandwidth
      constraints are specified for this interface.";
            } // number-bandwidth-constraints

            leaf bandwidth-constraint-model {
              // Low-level model info: Corresponds to i3EtBandwidthConstraintModel.
              type uint32 {
                range "0..255";
              }
              description
                "The Bandwidth Constraints Model Identifier, from the name
      space managed by IANA - see RFC 4124.  If the
      i3EtNumBandwidthConstraints object is non-zero, the number
      of constraints should be consistent with the bandwidth
      constraint model.  Also the relationships between the
      values of the bandwidth constraints and the maximum
      reservable bandwidth must be consistent with the bandwidth
      constraint model.  The emulated I3 stub does not enforce
      any consistency checks here.

      Examples for the Bandwidth Constraints Model Identifier
      are as follows.

      0 - Russian Dolls model (RFC 4127).
      1 - Maximum Allocation model (RFC 4125).
      2 - Max Allocation with Reservation model (RFC 4126).

      This object is ignored if i3EtNumBandwidthConstraints is
      set to 0.";
            } // bandwidth-constraint-model

            leaf bandwidth-constraint-0 {
              // Low-level model info: Corresponds to i3EtBandwidthConstraint0.
              type uint32;
              description
                "The first bandwidth constraint (BC0).  The value is used
      by CSPF to calculate constrained routes.  The units are
      bytes per second.

      This object is ignored if i3EtNumBandwidthConstraints is
      set to 0.

      If _use_ieee_floating_point_ is set to AMB_FALSE, then
      this field is configured and reported in standard format,
      otherwise IEEE floating point format is used.";
            } // bandwidth-constraint-0

            leaf bandwidth-constraint-1 {
              // Low-level model info: Corresponds to i3EtBandwidthConstraint1.
              type uint32;
              description
                "The second bandwidth constraint (BC1).  The value is used
      by CSPF to calculate constrained routes.  The units are
      bytes per second.

      This object is ignored if i3EtNumBandwidthConstraints is
      set to 0 or 1.

      If _use_ieee_floating_point_ is set to AMB_FALSE, then
      this field is configured and reported in standard format,
      otherwise IEEE floating point format is used.";
            } // bandwidth-constraint-1

            leaf bandwidth-constraint-2 {
              // Low-level model info: Corresponds to i3EtBandwidthConstraint2.
              type uint32;
              description
                "The third bandwidth constraint (BC2).  The value is used
      by CSPF to calculate constrained routes.  The units are
      bytes per second.

      This object is ignored if i3EtNumBandwidthConstraints is
      set to 2 or less.

      If _use_ieee_floating_point_ is set to AMB_FALSE, then
      this field is configured and reported in standard format,
      otherwise IEEE floating point format is used.";
            } // bandwidth-constraint-2

            leaf bandwidth-constraint-3 {
              // Low-level model info: Corresponds to i3EtBandwidthConstraint3.
              type uint32;
              description
                "The fourth bandwidth constraint (BC3).  The value is used
      by CSPF to calculate constrained routes.  The units are
      bytes per second.

      This object is ignored if i3EtNumBandwidthConstraints is
      set to 3 or less.

      If _use_ieee_floating_point_ is set to AMB_FALSE, then
      this field is configured and reported in standard format,
      otherwise IEEE floating point format is used.";
            } // bandwidth-constraint-3

            leaf bandwidth-constraint-4 {
              // Low-level model info: Corresponds to i3EtBandwidthConstraint4.
              type uint32;
              description
                "The fifth bandwidth constraint (BC4).  The value is used
      by CSPF to calculate constrained routes.  The units are
      bytes per second.

      This object is ignored if i3EtNumBandwidthConstraints is
      set to 4 or less.

      If _use_ieee_floating_point_ is set to AMB_FALSE, then
      this field is configured and reported in standard format,
      otherwise IEEE floating point format is used.";
            } // bandwidth-constraint-4

            leaf bandwidth-constraint-5 {
              // Low-level model info: Corresponds to i3EtBandwidthConstraint5.
              type uint32;
              description
                "The sixth bandwidth constraint (BC5).  The value is used
      by CSPF to calculate constrained routes.  The units are
      bytes per second.

      This object is ignored if i3EtNumBandwidthConstraints is
      set to 5 or less.

      If _use_ieee_floating_point_ is set to AMB_FALSE, then
      this field is configured and reported in standard format,
      otherwise IEEE floating point format is used.";
            } // bandwidth-constraint-5

            leaf bandwidth-constraint-6 {
              // Low-level model info: Corresponds to i3EtBandwidthConstraint6.
              type uint32;
              description
                "The seventh bandwidth constraint (BC6).  The value is used
      by CSPF to calculate constrained routes.  The units are
      bytes per second.

      This object is ignored if i3EtNumBandwidthConstraints is
      set to 6 or less.

      If _use_ieee_floating_point_ is set to AMB_FALSE, then
      this field is configured and reported in standard format,
      otherwise IEEE floating point format is used.";
            } // bandwidth-constraint-6

            leaf bandwidth-constraint-7 {
              // Low-level model info: Corresponds to i3EtBandwidthConstraint7.
              type uint32;
              description
                "The eighth bandwidth constraint (BC7).  The value is used
      by CSPF to calculate constrained routes.  The units are
      bytes per second.

      This object is ignored if i3EtNumBandwidthConstraints is
      set to 7 or less.

      If _use_ieee_floating_point_ is set to AMB_FALSE, then
      this field is configured and reported in standard format,
      otherwise IEEE floating point format is used.";
            } // bandwidth-constraint-7

            leaf use-ieee-floating-point {
              // Low-level model info: Corresponds to i3EtUseIeeeFloatingPoint.
              type boolean;
              default false;
              description
                "Indicates whether the bandwidth fields are entered and
      returned in IEEE floating point format.

      This field cannot be modified after creation.";
            } // use-ieee-floating-point

          } // emulated-traffic

        } // emulated-traffic

        container temp-g709-odu-resource {
          list temp-g709-odu-resource {

            description
              "This table is used to configure the available G.709v3
    parameters on a given network or virtual interface on a
    per-supported signal type basis.  Each entry in this table
    indicates a set of G.709v3 Traffic Engineering parameters
    for a given signal_type.  As such, if multiple signal types
    are supported on a given interface, multiple rows may be
    configured in this table for a given interface.

    This table supplements the information in the i3EtTable.  In
    addition to the TE Parameters configured in this table,
    management must also configure a row in the i3EtTable to
    describe the per-interface TE parameters.

    This table implements a pre-standard version of G.709v3.  As
    such the contents of the table and their formats is likely
    to change in a non-back-compatible way in future releases
    once the standards for G.709v3 have solidified.

    All writeable fields in this MIB table can be changed whilst
    the row is active.";

            key "i3-index instance-index local-endpoint-id interface-index address-type inet-address signal-type";

            leaf i3-index {
              // Low-level model info: Corresponds to i3EtTempG709OduPrIx.
              type uint32;
              description
                "This field identifies an instance of the I3 stub.";
            } // i3-index

            leaf instance-index {
              // Low-level model info: Corresponds to i3EtTempG709OduInstance.
              type int32;
              description
                "Index of the I3 user instance (virtual router or node) to
      which these G.709v3 TE parameters are assigned.";
            } // instance-index

            leaf local-endpoint-id {
              // Low-level model info: Corresponds to i3EtTempG709OduLocalEndId.
              type uint32;
              description
                "The Routing Controller ID of the local endpoint of the
      address or interface to which the TE parameters are
      assigned.

      If these TE parameters are assigned to a local address
      then this field is set to zero.";
            } // local-endpoint-id

            leaf interface-index {
              // Low-level model info: Corresponds to i3EtTempG709OduIfIx.
              type uint32;
              description
                "Network interface index in the IF-MIB (RFC 2233) of the
      network interface which the G.709v3 TE parameters are
      assigned to.  If the TE parameters are assigned to a
      particular network address rather than an interface, this
      field may be set to zero.";
            } // interface-index

            leaf address-type {
              // Low-level model info: Corresponds to i3EtTempG709OduAddressType.
              type AMB_INETWK_ADDR_TYPE;
              description
                "Address type of the address to which these TE parameters
      are assigned.  If these TE parameters are assigned to an
      unnumbered interface this field is set to 'other'.";
            } // address-type

            leaf inet-address {
              // Low-level model info: Corresponds to i3EtTempG709OduInetAddr.
              type string {
                length "0..32";
              }
              description
                "Network address to which these TE parameters are assigned.
      If these TE parameters are assigned to an unnumbered
      interface this field is set to have length 0.";
            } // inet-address

            leaf signal-type {
              // Low-level model info: Corresponds to i3EtTempG709OduSignalType.
              type AMB_STUBS_I3_G709_SIG_TYPES;
              description
                "Signal Type for which these TE parameters are defined.";
            } // signal-type

            leaf switching-capability {
              // Low-level model info: Corresponds to i3EtTempG709OduSwitchCap.
              type AMB_STUBS_I3_SW_CAP_VALUE;
              default otn-tdm-capable;
              description
                "The switching capability of this interface.  Currently,
      the only supported switching capability is
      'otnTdmCapable'.";
            } // switching-capability

            leaf encoding {
              // Low-level model info: Corresponds to i3EtTempG709OduEncoding.
              type AMB_STUBS_I3_SW_ENCODE_VAL;
              default g709-oduk;
              description
                "The encoding of this interface.  Currently, the only
      supported encoding type is 'G709 ODUk Digital Path'.";
            } // encoding

            leaf termination-capable {
              // Low-level model info: Corresponds to i3EtTempG709OduTermCapable.
              type boolean;
              default false;
              description
                "Boolean indicating whether the interface is capable of
      terminating data traffic for this signal_type.";
            } // termination-capable

            leaf switching-capable {
              // Low-level model info: Corresponds to i3EtTempG709OduSwitchCapable.
              type boolean;
              default false;
              description
                "Boolean indicating whether the interface is capable of
      switching data traffic for this signal_type.";
            } // switching-capable

            leaf max-lsp-bandwidth0 {
              // Low-level model info: Corresponds to i3EtTempG709OduMaxLspBwidth0.
              type uint32;
              default "4294967295";
              description
                "The maximum LSP bandwidth in bytes per second at priority
      0 (in standard, IEEE floating point format).

      This field must be set to a valid bandwidth value for an
      ODUFlex signal type, usually a multiple of an ODU0
      bandwidth.

      For fixed ODUj signal types, if this field is set to
      0xFFFFFFFF then the maximum LSP bandwidth value for this
      signal type is set to be the maximum bandwidth an ODUj
      link can carry, otherwise this value is used as the
      maximum LSP bandwidth for this signal type.";
            } // max-lsp-bandwidth0

            leaf max-lsp-bandwidth1 {
              // Low-level model info: Corresponds to i3EtTempG709OduMaxLspBwidth1.
              type uint32;
              default "4294967295";
              description
                "The maximum LSP bandwidth in bytes per second at priority
      1 (in standard, IEEE floating point format).

      This field must be set to a valid bandwidth value for an
      ODUFlex signal type, usually a multiple of an ODU0
      bandwidth.

      For fixed ODUj signal types, if this field is set to
      0xFFFFFFFF then the maximum LSP bandwidth value for this
      signal type is set to be the maximum bandwidth an ODUj
      link can carry, otherwise this value is used as the
      maximum LSP bandwidth for this signal type.";
            } // max-lsp-bandwidth1

            leaf max-lsp-bandwidth2 {
              // Low-level model info: Corresponds to i3EtTempG709OduMaxLspBwidth2.
              type uint32;
              default "4294967295";
              description
                "The maximum LSP bandwidth in bytes per second at priority
      2 (in standard, IEEE floating point format).

      This field must be set to a valid bandwidth value for an
      ODUFlex signal type, usually a multiple of an ODU0
      bandwidth.

      For fixed ODUj signal types, if this field is set to
      0xFFFFFFFF then the maximum LSP bandwidth value for this
      signal type is set to be the maximum bandwidth an ODUj
      link can carry, otherwise this value is used as the
      maximum LSP bandwidth for this signal type.";
            } // max-lsp-bandwidth2

            leaf max-lsp-bandwidth3 {
              // Low-level model info: Corresponds to i3EtTempG709OduMaxLspBwidth3.
              type uint32;
              default "4294967295";
              description
                "The maximum LSP bandwidth in bytes per second at priority
      3 (in standard, IEEE floating point format).

      This field must be set to a valid bandwidth value for an
      ODUFlex signal type, usually a multiple of an ODU0
      bandwidth.

      For fixed ODUj signal types, if this field is set to
      0xFFFFFFFF then the maximum LSP bandwidth value for this
      signal type is set to be the maximum bandwidth an ODUj
      link can carry, otherwise this value is used as the
      maximum LSP bandwidth for this signal type.";
            } // max-lsp-bandwidth3

            leaf max-lsp-bandwidth4 {
              // Low-level model info: Corresponds to i3EtTempG709OduMaxLspBwidth4.
              type uint32;
              default "4294967295";
              description
                "The maximum LSP bandwidth in bytes per second at priority
      4 (in standard, IEEE floating point format).

      This field must be set to a valid bandwidth value for an
      ODUFlex signal type, usually a multiple of an ODU0
      bandwidth.

      For fixed ODUj signal types, if this field is set to
      0xFFFFFFFF then the maximum LSP bandwidth value for this
      signal type is set to be the maximum bandwidth an ODUj
      link can carry, otherwise this value is used as the
      maximum LSP bandwidth for this signal type.";
            } // max-lsp-bandwidth4

            leaf max-lsp-bandwidth5 {
              // Low-level model info: Corresponds to i3EtTempG709OduMaxLspBwidth5.
              type uint32;
              default "4294967295";
              description
                "The maximum LSP bandwidth in bytes per second at priority
      5 (in standard, IEEE floating point format).

      This field must be set to a valid bandwidth value for an
      ODUFlex signal type, usually a multiple of an ODU0
      bandwidth.

      For fixed ODUj signal types, if this field is set to
      0xFFFFFFFF then the maximum LSP bandwidth value for this
      signal type is set to be the maximum bandwidth an ODUj
      link can carry, otherwise this value is used as the
      maximum LSP bandwidth for this signal type.";
            } // max-lsp-bandwidth5

            leaf max-lsp-bandwidth6 {
              // Low-level model info: Corresponds to i3EtTempG709OduMaxLspBwidth6.
              type uint32;
              default "4294967295";
              description
                "The maximum LSP bandwidth in bytes per second at priority
      6 (in standard, IEEE floating point format).

      This field must be set to a valid bandwidth value for an
      ODUFlex signal type, usually a multiple of an ODU0
      bandwidth.

      For fixed ODUj signal types, if this field is set to
      0xFFFFFFFF then the maximum LSP bandwidth value for this
      signal type is set to be the maximum bandwidth an ODUj
      link can carry, otherwise this value is used as the
      maximum LSP bandwidth for this signal type.";
            } // max-lsp-bandwidth6

            leaf max-lsp-bandwidth7 {
              // Low-level model info: Corresponds to i3EtTempG709OduMaxLspBwidth7.
              type uint32;
              default "4294967295";
              description
                "The maximum LSP bandwidth in bytes per second at priority
      7 (in standard, IEEE floating point format).

      This field must be set to a valid bandwidth value for an
      ODUFlex signal type, usually a multiple of an ODU0
      bandwidth.

      For fixed ODUj signal types, if this field is set to
      0xFFFFFFFF then the maximum LSP bandwidth value for this
      signal type is set to be the maximum bandwidth an ODUj
      link can carry, otherwise this value is used as the
      maximum LSP bandwidth for this signal type.";
            } // max-lsp-bandwidth7

            leaf unres-bandwidth0 {
              // Low-level model info: Corresponds to i3EtTempG709OduUnresBwidth0.
              type uint32;
              default "0";
              description
                "The unreserved bandwidth available at priority 0.  For
      Fixed ODUj signal types this is expressed as a number of
      containers.  For ODUFlex signal type this is a bitrate in
      bytes per second (in standard, IEEE floating point
      format).";
            } // unres-bandwidth0

            leaf unres-bandwidth1 {
              // Low-level model info: Corresponds to i3EtTempG709OduUnresBwidth1.
              type uint32;
              default "0";
              description
                "The unreserved bandwidth available at priority 1.  For
      Fixed ODUj signal types this is expressed as a number of
      containers.  For ODUFlex signal type this is a bitrate in
      bytes per second (in standard, IEEE floating point
      format).";
            } // unres-bandwidth1

            leaf unres-bandwidth2 {
              // Low-level model info: Corresponds to i3EtTempG709OduUnresBwidth2.
              type uint32;
              default "0";
              description
                "The unreserved bandwidth available at priority 2.  For
      Fixed ODUj signal types this is expressed as a number of
      containers.  For ODUFlex signal type this is a bitrate in
      bytes per second (in standard, IEEE floating point
      format).";
            } // unres-bandwidth2

            leaf unres-bandwidth3 {
              // Low-level model info: Corresponds to i3EtTempG709OduUnresBwidth3.
              type uint32;
              default "0";
              description
                "The unreserved bandwidth available at priority 3.  For
      Fixed ODUj signal types this is expressed as a number of
      containers.  For ODUFlex signal type this is a bitrate in
      bytes per second (in standard, IEEE floating point
      format).";
            } // unres-bandwidth3

            leaf unres-bandwidth4 {
              // Low-level model info: Corresponds to i3EtTempG709OduUnresBwidth4.
              type uint32;
              default "0";
              description
                "The unreserved bandwidth available at priority 4.  For
      Fixed ODUj signal types this is expressed as a number of
      containers.  For ODUFlex signal type this is a bitrate in
      bytes per second (in standard, IEEE floating point
      format).";
            } // unres-bandwidth4

            leaf unres-bandwidth5 {
              // Low-level model info: Corresponds to i3EtTempG709OduUnresBwidth5.
              type uint32;
              default "0";
              description
                "The unreserved bandwidth available at priority 5.  For
      Fixed ODUj signal types this is expressed as a number of
      containers.  For ODUFlex signal type this is a bitrate in
      bytes per second (in standard, IEEE floating point
      format).";
            } // unres-bandwidth5

            leaf unres-bandwidth6 {
              // Low-level model info: Corresponds to i3EtTempG709OduUnresBwidth6.
              type uint32;
              default "0";
              description
                "The unreserved bandwidth available at priority 6.  For
      Fixed ODUj signal types this is expressed as a number of
      containers.  For ODUFlex signal type this is a bitrate in
      bytes per second (in standard, IEEE floating point
      format).";
            } // unres-bandwidth6

            leaf unres-bandwidth7 {
              // Low-level model info: Corresponds to i3EtTempG709OduUnresBwidth7.
              type uint32;
              default "0";
              description
                "The unreserved bandwidth available at priority 7.  For
      Fixed ODUj signal types this is expressed as a number of
      containers.  For ODUFlex signal type this is a bitrate in
      bytes per second (in standard, IEEE floating point
      format).";
            } // unres-bandwidth7

          } // temp-g709-odu-resource

        } // temp-g709-odu-resource

        container interface-fault-reports {

          list interface-fault-reports {

            description
              "Each entry in this table represents Interface Fault Report
    information.

    This is a read-only MIB.  For details of how the indices are
    used, in particular the i3FrLocalEndId field, see the
    description of the i3EiTable.";

            key "i3-index local-endpoint-id interface-index";

            config false;

            leaf i3-index {
              // Low-level model info: Corresponds to i3FrPrIx.
              type uint32;
              description
                "Index for the I3 stub.";
            } // i3-index

            leaf local-endpoint-id {
              // Low-level model info: Corresponds to i3FrLocalEndId.
              type uint32;
              description
                "For a E-NNI Routing level link, this field is the Routing
      Controller ID of the local endpoint of a link when this
      router is not the local endpoint.";
            } // local-endpoint-id

            leaf interface-index {
              // Low-level model info: Corresponds to i3FrIfIx.
              type uint32;
              description
                "Network interface index in the IF-MIB (RFC 2233).  For a
      E-NNI Routing level inter-domain or intra-domain link,
      this is the interface index of the link at the local
      endpoint node.";
            } // interface-index

            leaf bfd-send-status {
              // Low-level model info: Corresponds to i3FrBfdSendStatus.
              type AMB_I3_FAULT_STATUS;
              description
                "The current BFD fault status for sending data over this
      interface.";
              config false;
            } // bfd-send-status

            leaf bfd-recv-status {
              // Low-level model info: Corresponds to i3FrBfdRecvStatus.
              type AMB_I3_FAULT_STATUS;
              description
                "The current BFD fault status for receiving data over this
      interface.";
              config false;
            } // bfd-recv-status

            leaf y1731-send-status {
              // Low-level model info: Corresponds to i3FrY1731SendStatus.
              type AMB_I3_FAULT_STATUS;
              description
                "The current Y.1731 Continuity Check fault status for
      sending data over this interface.";
              config false;
            } // y1731-send-status

            leaf y1731-recv-status {
              // Low-level model info: Corresponds to i3FrY1731RecvStatus.
              type AMB_I3_FAULT_STATUS;
              description
                "The current Y.1731 Continuity Check fault status for
      receiving data over this interface.";
              config false;
            } // y1731-recv-status

            leaf bpdu-guard-status {
              // Low-level model info: Corresponds to i3FrBpduGuardStatus.
              type AMB_I3_FAULT_STATUS;
              description
                "The current STP BPDU guard fault status for this
      interface.";
              config false;
            } // bpdu-guard-status

            leaf elmi-uni-c-status {
              // Low-level model info: Corresponds to i3FrElmiUniCStatus.
              type AMB_I3_FAULT_STATUS;
              description
                "The current E-LMI UNI-C fault status for this interface.";
              config false;
            } // elmi-uni-c-status

          } // interface-fault-reports

        } // interface-fault-reports

        container power-info {
          list power-info {

            description
              "Each entry in this table represents the Medium Dependent
    Interface (MDI) power info for an Interface entity.

    This power information is advertised over the I3 for the
    interface, unless the power information is inconsistent (see
    the comments for each field below for what is required to
    achieve consistency).  If there is no row in this table for
    the interface, or the information is inconsistent, then no
    power information is advertised over the I3.

    AMBL managed: True.";

            key "i3-index instance-index local-endpoint-id interface-index";

            leaf i3-index {
              // Low-level model info: Corresponds to i3PowerInfoPrIx.
              type uint32;
              description
                "Index for the I3 stub.";
            } // i3-index

            leaf instance-index {
              // Low-level model info: Corresponds to i3PowerInfoInIx.
              type int32;
              description
                "Index of the VRF or virtual bridge that the interface
      belongs to.";
            } // instance-index

            leaf local-endpoint-id {
              // Low-level model info: Corresponds to i3PowerInfoLocalEndId.
              type uint32;
              description
                "The Routing Controller ID of the local endpoint of the
      interface, if this is an E-NNI Routing level link.

      In general it does not make sense for an E-NNI Routing
      level link to supply power, so this field should normally
      be set to 0.";
            } // local-endpoint-id

            leaf interface-index {
              // Low-level model info: Corresponds to i3PowerInfoIfIx.
              type uint32;
              description
                "Network interface index in the IF-MIB (RFC 2233).";
            } // interface-index

            leaf port-class {
              // Low-level model info: Corresponds to i3PowerInfoPortClass.
              type AMB_MDI_POWER_PORT_CLASSES;
              default mdi-power-port-class-none;
              description
                "The MDI power port class of the interface.

      -  If the device is not an MDI power entity, this field is
      set to 'pClassNone'.  All further fields in this
      structure are not valid and should be ignored.

      -  If the device is a Power Sourcing Equipment (PSE)
      entity, this field is set to 'pClassPSE'.

      -  If the device is a Powered Device (PD) entity, this
      field is set to 'pClassPD'.";
            } // port-class

            leaf system-type {
              // Low-level model info: Corresponds to i3PowerInfoSystemType.
              type AMB_MDI_POWER_SYSTEM_TYPES;
              default mdi-power-system-type-none;
              description
                "The MDI power system type of the MDI power interface.

      -  If the local system is a PSE or PD
      (i3PowerInfoPortClass is'pClassPSE' or 'pClassPD'),
      this field must not be set to 'none'.

      -  Else, this field is ignored.";
            } // system-type

            leaf priority {
              // Low-level model info: Corresponds to i3PowerInfoPriority.
              type AMB_MDI_POWER_PRIORITIES;
              default mdi-power-priority-unknown;
              description
                "The power priority of the MDI power interface.

      -  If the device is a PSE (i3PowerInfoPortClass is
      'pClassPSE'), this field contains the priority that the
      PSE assigns to the PD.

      -  Else if the device is a PD (i3PowerInfoPortClass is
      'pClassPD'), this field contains the priority that the
      PD requests from the PSE.

      -  Else, this field is ignored.";
            } // priority

            leaf in-use {
              // Low-level model info: Corresponds to i3PowerInfoInUse.
              type boolean;
              default false;
              description
                "Whether the MDI power is being used.

      -  If the device is a PSE (i3PowerInfoPortClass is
      'pClassPSE'), this field indicates whether the PSE is
      currently supplying power to a PD.

      -  Else if the device is a PD (i3PowerInfoPortClass is
      'pClassPD'), this field indicates whether the PD is
      currently drawing power from the PSE.

      -  Else, this field is ignored.";
            } // in-use

            leaf value {
              // Low-level model info: Corresponds to i3PowerInfoValue.
              type uint32 {
                range "0..65535";
              }
              default "0";
              description
                "The MDI power entity's power value, in tenths of a watt.

      -  If the device is a PSE (i3PowerInfoPortClass is
      'pClassPSE'), this field contains the PSE's allocated
      power (the maximum input average power).

      -  Else if the device is a PD (i3PowerInfoPortClass is
      'pClassPD'), this field contains the power value that
      the PD requests from the PSE.

      -  Else, this field is ignored.";
            } // value

            leaf pse-mdi-supported {
              // Low-level model info: Corresponds to i3PowerInfoPseMdiSupported.
              type boolean;
              default false;
              description
                "Whether the interface supports Power Sourcing Equipment
      (PSE) MDI power.

      If the local system is not a PSE (i3PowerInfoPortClass is
      not 'pClassPSE'), this field is ignored.";
            } // pse-mdi-supported

            leaf pse-mdi-enabled {
              // Low-level model info: Corresponds to i3PowerInfoPseMdiEnabled.
              type boolean;
              default false;
              description
                "Whether PSE MDI power is administratively enabled on the
      interface.

      If the local system is not a PSE (i3PowerInfoPortClass is
      not 'pClassPSE'), this field is ignored.";
            } // pse-mdi-enabled

            leaf pse-pair-controlable {
              // Low-level model info: Corresponds to i3PowerInfoPsePairControlable.
              type boolean;
              default false;
              description
                "Whether the local system is capable of controlling the PSE
      pairs functionality to switch pins for sourcing power.

      If the local system is not a PSE (i3PowerInfoPortClass is
      not 'pClassPSE'), this field is ignored.";
            } // pse-pair-controlable

            leaf pse-pairs {
              // Low-level model info: Corresponds to i3PowerInfoPsePairs.
              type AMB_MDI_POWER_PAIR_TYPES;
              default mdi-power-pair-type-none;
              description
                "The PSE pair that is in use.

      -  If the local system is a PSE (i3PowerInfoPortClass is
      'pClassPSE'), this field must not be set to 'none'.

      -  Else, this field is ignored.";
            } // pse-pairs

            leaf pse-class {
              // Low-level model info: Corresponds to i3PowerInfoPseClass.
              type AMB_MDI_POWER_CLASSES;
              default mdi-power-class-none;
              description
                "The power class detected by a PSE for a Powered Device
      (PD) on the interface.

      -  If the local system is a PSE (i3PowerInfoPortClass is
      'pClassPSE'), and is in use (i3PowerInfoInUse is
      'true'), this field must not be set to 'none'.

      -  Else, this field is ignored, and the power class is
      reported as 'none' over the I3.";
            } // pse-class

            leaf pse-source {
              // Low-level model info: Corresponds to i3PowerInfoPseSource.
              type AMB_MDI_POWER_PSE_SRCS;
              default mdi-power-pse-src-unknown;
              description
                "The power source for a PSE.

      If the local system is not a PSE (i3PowerInfoPortClass is
      not 'pClassPSE'), this field is ignored.";
            } // pse-source

            leaf pd-source {
              // Low-level model info: Corresponds to i3PowerInfoPdSource.
              type AMB_MDI_POWER_PD_SRCS;
              default mdi-power-pd-src-unknown;
              description
                "The power source for a PD.

      If the local system is not a PD (i3PowerInfoPortClass is
      not 'pClassPD'), this field is ignored.";
            } // pd-source

          } // power-info

        } // power-info

        container ppvid {
          list ppvid {

            description
              "Each entry in this table represents the port-and-protocol
    VLAN classification information for a VLAN on an interface.
    This is a default VLAN ID that is assigned to all untagged
    packets for a given protocol received on a port.

    The information advertised over the I3 will include an entry
    for every VLAN ID for which a RowActive row in this table
    exists for the corresponding {interface, VLAN ID} pair.

    AMBL managed: True.";

            key "i3-index instance-index local-endpoint-id interface-index vlan-id";

            leaf i3-index {
              // Low-level model info: Corresponds to i3PpvidPrIx.
              type uint32;
              description
                "Index for the I3 stub.";
            } // i3-index

            leaf instance-index {
              // Low-level model info: Corresponds to i3PpvidInIx.
              type int32;
              description
                "Index of the VRF or virtual bridge that the interface
      belongs to.";
            } // instance-index

            leaf local-endpoint-id {
              // Low-level model info: Corresponds to i3PpvidLocalEndId.
              type uint32;
              description
                "The Routing Controller ID of the local endpoint of the
      interface, if this is an E-NNI Routing level link.

      In general it does not make sense for an E-NNI Routing
      level link to have PPVIDs configured, so this field should
      normally be set to 0.";
            } // local-endpoint-id

            leaf interface-index {
              // Low-level model info: Corresponds to i3PpvidIfIx.
              type uint32;
              description
                "Network interface index in the IF-MIB (RFC 2233).";
            } // interface-index

            leaf vlan-id {
              // Low-level model info: Corresponds to i3PpvidVlanId.
              type uint32 {
                range "1..4094";
              }
              description
                "The port-and-protocol VLAN ID (PPVID).";
            } // vlan-id

            leaf supported {
              // Low-level model info: Corresponds to i3PpvidSupported.
              type boolean;
              default true;
              description
                "Whether the interface supports port-and-protocol-based
      VLAN classification for this VLAN.";
            } // supported

            leaf enabled {
              // Low-level model info: Corresponds to i3PpvidEnabled.
              type boolean;
              default true;
              description
                "Whether port-and-protocol-based VLAN classification is
      enabled on the interface for this VLAN.  If
      i3PpvidSupported is set to 'False', this field is ignored
      and treated as being set to 'False'.";
            } // enabled

          } // ppvid

        } // ppvid

      } // subtables

    } // emu

  } // emu

} // i3
