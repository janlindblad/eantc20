module routing {

  namespace "http://metaswitch.com/yang/nbu/routing/201512140000Z";

  prefix routing;

  import user-extensions { prefix "user-ext"; }
  import interfaces { prefix "interfaces"; }
  import interface { prefix "interface"; }
  import metaswitch-yang-types { prefix meta; }
  import metaswitch-custom-yang-types { prefix "custom"; }

  organization "Metaswitch Networks";

  contact "Postal: Metaswitch Networks
                   100 Church Street
                   Enfield
                   EN2 6BQ
                   United Kingdom
           Tel:    +44 20 8366 1177
           E-mail: info@metaswitch.com";

  description
    "Routing Configuration and State";

  revision 2015-12-14 {
    description "Initial revision.";
  }


  typedef routing-route-actions {
      type enumeration {
          enum local                            { value 1; description "Handle locally packets sent to this destination"; }
          enum forward                          { value 2; description "Forward packet to address specified as next-hop address"; }
          enum reject                           { value 3; description "Reject packets (drop and return packet to sender)"; }
          enum discard                          { value 4; description "Discard packets (drop but do not return packet to sender)"; }
      }
      description
        "Route action";
  }

  typedef routing-route-type {
      type enumeration {
          enum other                            { value 1; }
          enum reject                           { value 2; }
          enum local                            { value 3; }
          enum remote                           { value 4; }
      }
      description
        "Route type";
  }

  typedef routing-route-info {
      type enumeration {
          enum none                             { value 0; }
          enum ospf-intra-area                  { value 1; }
          enum ospf-inter-area                  { value 2; }
          enum ospf-external-type1              { value 3; }
          enum ospf-external-type2              { value 4; }
          enum isis-l1-internal                 { value 5; }
          enum isis-l2-internal                 { value 6; }
          enum isis-l1-internal-down            { value 7; }
          enum isis-l1-external                 { value 8; }
          enum isis-l2-external                 { value 9; }
          enum isis-l1-external-down            { value 10; }
      }
      description
        "Route protocol";
//      "A Routing Protocol Information Type.
//
//      For OSPF, this is an integer representation of the OID which
//      is required by RFC 2096.  The RFCs which define the OIDs,
//      and the represented OIDs, are shown here.  OSPF - RFC 1850.
//
//      For IS-IS, this is an integer representation of the types of
//      route to IP reachable addresses.";
  }

  typedef routing-metric-t {
      type uint32 {
          range "1..254";
      }
      description
        "(1-254)";
  }

  typedef routing-next-hop-protect-t {
    type enumeration {
      enum none                             { value 1; }
      enum local-lfa                        { value 2; }
      enum ecmp                             { value 3; }
      enum remote-lfa                       { value 4; }
    }
    description
      "Primary next hop protection type";
  }

  grouping routing-administrative-distance {

      // Low-level model info: Corresponds to rtmStaticRtAdminDist.
      leaf metric {
          type routing-metric-t;

          description
              "Administrative distance for static route.
              The lower the administrative distance for a given route, the
              more likely that route is to be used as the active
              route for the given destination.";

          user-ext:CLI-comm-help "Set metric";
          user-ext:CLI-no-comm-help "Set default metric";
          user-ext:CLI-param-help "Set metric";
      }
  }

  grouping routing-route-entry-parameters {

      uses routing-administrative-distance;

      // Low-level model info: Corresponds to rtmStaticRtAction.
      leaf action {
          type routing-route-actions;
          default "forward";

          description
            "The action to perform on receipt of a packet to the
            specified destination.

            The action type cannot be set to 'tunnel' for a static
            route.";

          user-ext:CLI-comm-help "Set routing action";
          user-ext:CLI-no-comm-help "Set default routing action";
          user-ext:CLI-param-help "Set routing action";
      }

      // Low-level model info: Corresponds to rtmStaticRtPathType.
      leaf path-type {
          type  meta:route-path-types-cfg;
          default "static";

          description
            "Type of path associated with this route.";

          user-ext:CLI-comm-help "Set path type";
          user-ext:CLI-no-comm-help "Set default path type";
          user-ext:CLI-param-help "Set path type";
      }

      container bfd {

          description
              "BFD parameters";

          user-ext:CLI-comm-help "Configure BFD parameters for route";
          user-ext:CLI-no-comm-help "Configure BFD parameters for route";

          // Low-level model info: Corresponds to rtmStaticRtBfdSupport.  Note the difference in default values between yang and MIB.
          // Low-level model info: Use AMB_RTM_BFD_SUPPORT group - presence means "desired"; absence means "none".

          leaf fast-detect {

              type empty;

              description
                  "This object indicates whether RTM should use BFD to
                  check IP reachability to the static route's next hop.

                  RTM will only attempt to use BFD if the static route has
                  action set to 'forward' and nexthop set to a non-null IP
                  address.";

              user-ext:CLI-comm-help "Enable BFD for this static route";
              user-ext:CLI-no-comm-help "Disable BFD for this static route";

          } // fast-detect

      } // bfd

      container state {

          config false;

          // Low-level model info: Corresponds to rtmStaticRtLooseNextHop.
          leaf loose-next-hop {
              type boolean;
              description
                  "This object indicates whether this static route contains a
                  loose next hop.";
              config false;
          }

          // Low-level model info: Corresponds to rtmStaticRtBfdStatus.
          leaf bfd-status {
              type meta:bfd-sess-state;
              description
                  "The current BFD session state for this static route.";
              config false;
          }

      } // state

  } // routing-route-entry-parameters

  grouping ifaces-to-use-in-routing {

      container interfaces {

        if-feature interfaces:standard-interfaces;
        user-ext:CLI-not-command;

        list interface {

          description "Specify the attachment interface";
          user-ext:CLI-comm-help "Configure attachment interface";
          user-ext:CLI-no-comm-help "Remove attachment interface";

          key "if-name";

          leaf if-name {
            type custom:iface-name;
            description
              "A unique identifier identifying the interface.";

            user-ext:CLI-param-help "Set interface name";
          }

          uses routing-route-entry-parameters;

        } // interface

      } // interfaces

      container custom-interfaces {

          if-feature interfaces:custom-interfaces;
          user-ext:CLI-not-command;

          container interface {

            description "Specify the attachment interface";
            user-ext:CLI-comm-help "Configure attachment interface";
            user-ext:CLI-no-comm-help "Remove attachment interface";

            container oneGE {

                user-ext:CLI-not-command;
                user-ext:CLI-comm-switch "gigabitethernet/gigabitethernet-sub";

                list gigabitethernet {

                    description "Specify the attachment 1G interface";

                    user-ext:CLI-comm-help "Configure attachment 1G interface";
                    user-ext:CLI-no-comm-help "Remove attachment 1G interface";

                    key "if-num";

                    leaf if-num {
                        type interfaces:eth-iface-num-t;
                        description "<unit>/<dev>/<port>";
                        user-ext:CLI-param-help "1G interface";
                    }

                    uses routing-route-entry-parameters;
                }

                list gigabitethernet-sub {

                    description "Specify the attachment 1G sub-interface";

                    user-ext:CLI-comm-help "Configure attachment 1G sub-interface";
                    user-ext:CLI-no-comm-help "Remove attachment 1G sub-interface";

                    key "if-num";

                    leaf if-num {
                        type interfaces:eth-subiface-range-t;
                        description "<unit>/<dev>/<port>.<subid>";
                        user-ext:CLI-param-help "1G sub-interface";
                    }

                    uses routing-route-entry-parameters;
                }

            } // oneGE

            container tenGE {

                user-ext:CLI-not-command;
                user-ext:CLI-comm-switch "tengigabitethernet/tengigabitethernet-sub";

                list tengigabitethernet {

                    description "Specify the attachment 10G interface";

                    user-ext:CLI-comm-help "Configure attachment 10G interface";
                    user-ext:CLI-no-comm-help "Remove attachment 10G interface";

                    key "if-num";

                    leaf if-num {
                        type interfaces:eth-iface-num-t;
                        description "<unit>/<dev>/<port>";
                        user-ext:CLI-param-help "10G interface";
                    }

                    uses routing-route-entry-parameters;
                }

                list tengigabitethernet-sub {

                    description "Specify the attachment 10G sub-interface";

                    user-ext:CLI-comm-help "Configure attachment 10G sub-interface";
                    user-ext:CLI-no-comm-help "Remove attachment 10G sub-interface";

                    key "if-num";

                    leaf if-num{
                        type interfaces:eth-subiface-range-t;
                        description "<unit>/<dev>/<port>.<subid>";
                        user-ext:CLI-param-help "10G sub-interface";
                    }

                    uses routing-route-entry-parameters;
                }

            } // tenGE

            container fortyGE {

                user-ext:CLI-not-command;
                user-ext:CLI-comm-switch "fortygigabitethernet/fortygigabitethernet-sub";

                list fortygigabitethernet {

                    description "Specify the attachment 40G interface";

                    user-ext:CLI-comm-help "Configure attachment 40G interface";
                    user-ext:CLI-no-comm-help "Remove attachment 40G interface";

                    key "if-num";

                    leaf if-num {
                        type interfaces:eth-iface-num-t;
                        description "<unit>/<dev>/<port>";
                        user-ext:CLI-param-help "40G interface";
                    }

                    uses routing-route-entry-parameters;
                }

                list fortygigabitethernet-sub {

                    description "Specify the attachment 40G sub-interface";

                    user-ext:CLI-comm-help "Configure attachment 40G sub-interface";
                    user-ext:CLI-no-comm-help "Remove attachment 40G sub-interface";

                    key "if-num";

                    leaf if-num {
                        type interfaces:eth-subiface-range-t;
                        description "<unit>/<dev>/<port>.<subid>";
                        user-ext:CLI-param-help "40G sub-interface";
                    }

                    uses routing-route-entry-parameters;
                }

            } // fortyGE

            container hundredGE {

                user-ext:CLI-not-command;
                user-ext:CLI-comm-switch "hundredgigabitethernet/hundredgigabitethernet-sub";

                list hundredgigabitethernet {

                    description "Specify the attachment 100G interface";

                    user-ext:CLI-comm-help "Configure attachment 100G interface";
                    user-ext:CLI-no-comm-help "Remove attachment 100G interface";

                    key "if-num";

                    leaf if-num {
                        type interfaces:eth-iface-num-t;
                        description "<unit>/<dev>/<port>";
                        user-ext:CLI-param-help "100G interface";
                    }

                    uses routing-route-entry-parameters;
                }

                list hundredgigabitethernet-sub {

                    description "Specify the attachment 100G sub-interface";

                    user-ext:CLI-comm-help "Configure attachment 100G sub-interface";
                    user-ext:CLI-no-comm-help "Remove attachment 100G sub-interface";

                    key "if-num";

                    leaf if-num {
                        type interfaces:eth-subiface-range-t;
                        description "<unit>/<dev>/<port>.<subid>";
                        user-ext:CLI-param-help "100G sub-interface";
                    }

                    uses routing-route-entry-parameters;
                }

            } // hundredGE

            container bundle-ifaces {

                user-ext:CLI-not-command;
                user-ext:CLI-comm-switch "bundle-ether/bundle-ether-sub";

                list bundle-ether {

                    description "Specify the attachment bundle-ether interface";

                    user-ext:CLI-comm-help "Configure attachment bundle-ether interface";
                    user-ext:CLI-no-comm-help "Remove attachment bundle-ether interface";

                    key "bundle-id";

                    leaf bundle-id {
                        type interfaces:bundle-id-t;
                        description "Bundle-ether id";
                        user-ext:CLI-param-help "Bundle-ether interface";
                    }

                    uses routing-route-entry-parameters;
                }

                list bundle-ether-sub {

                    description "Specify the attachment bundle-ether sub-interface";

                    user-ext:CLI-comm-help "Configure attachment bundle-ether sub-interface";
                    user-ext:CLI-no-comm-help "Remove attachment bundle-ether sub-interface";

                    key "bundle-id";

                    leaf bundle-id {
                        type interfaces:bundle-sub-id-t;
                        description "Bundle-ether id";
                        user-ext:CLI-param-help "Attachment bundle-ether sub-interface";
                    }

                    uses routing-route-entry-parameters;
                }

            } // bundle-ifaces

            container ipip-ifaces {

                user-ext:CLI-not-command;

                list tunnel-gre {

                    description "Specify the attachment GRE tunnel";

                    user-ext:CLI-comm-help "Configure attachment GRE tunnel";
                    user-ext:CLI-no-comm-help "Remove attachment GRE tunnel";

                    key "gre-id";

                    leaf gre-id {
                        type interfaces:tunnel-gre-id-t;
                        description "GRE id";
                        user-ext:CLI-param-help "GRE tunnel id";
                    }

                    uses routing-route-entry-parameters;
                 }

            } // ipip-ifaces

          } // interface

      } // custom-interfaces

  } // ifaces-to-use-in-routing

  grouping route-common-state {

    uses interfaces:iface-id;

    // Low-level model info: Corresponds to rtmRouteNextHopLabel and rtmRibNextHopLabel.
    leaf next-hop-label {
      type meta:mpls-label-state-integer-t;
      description
        "The next hop (outer) MPLS label to be used for this route,
        if required for packets sent to the next hop.  If there is
        no next hop label for this route, then this field is empty.";
      config false;
    }

    // Low-level model info: Corresponds to rtmRouteProto and rtmRibProto.
    leaf protocol {
      type meta:route-protocols;
      description
        "The routing mechanism via which this route was learned.
        Inclusion of values for gateway routing protocols is not
        intended to imply that hosts should support those
        protocols.";
      config false;
    }

    // Low-level model info: Corresponds to rtmRouteMetric1 and rtmRibMetric1.
    leaf metric {
      type int32;
      description
        "The primary routing metric for this route.  The
        semantics of this metric are determined by the
        protocol specified.  If this metric is not used, its value should be
        set to -1.";
      config false;
    }

    // Low-level model info: Corresponds to rtmRouteAdminTag and rtmRibAdminTag.
    leaf admin-tag {
      type uint32;
      description
        "Protocol specific admin tag.  If this route was learned
        from OSPF or IS-IS, this is the admin tag assigned to the
        route.  Otherwise it is set to zero.";
      config false;
    }

    // Low-level model info: Corresponds to rtmRouteType and rtmRibType.
    leaf route-type {
      type routing-route-type;
      description
        "The type of route.

        local refers to a route for which the destination is a
        local IP address or for which the next hop is the final
        destination.  This includes routes to local IP addresses
        and routes to directly connected IP addresses or subnets.

        remote refers to a route for which the next hop is not
        the final destination.

        reject refers to a route which, if matched, discards
        the message as unreachable.  This is used in some
        protocols as a means of correctly aggregating routes.";
      config false;
    }

    // Low-level model info: Corresponds to rtmRouteAge and rtmRibAge.
    leaf age {
      type uint32 {
        range "0..2147483647";
      }
      description
        "The number of seconds since this route was last updated or
        otherwise determined to be correct.  Note that no
        semantics of 'too old' can be implied except through
        knowledge of the routing protocol by which the route was
        learned.  This age is only accurate for entries which are
        less that 49 days old.";
      config false;
    }

    // Low-level model info: Corresponds to rtmRouteConnecte and rtmRibConnecte.
    leaf connected {
      type boolean;
      description
        "Indicates whether the route destination is directly
        connected.

        A directly connected route can be reached without going
        through any IP routers.

        Route destinations that are local IP addresses
        are not considered to be directly connected.

        This field can only be true if route-type is set to 'local'.";
      config false;
    }

    // Low-level model info: Corresponds to rtmRouteAdminDistanc and rtmRibAdminDistanc.
    leaf admin-distance {
      type int32;
      description
        "Administrative distance for this route.

        The lower the administrative distance for a given route,
        the more likely that route is to be used by RTM as the
        active route for the route destination, and hence the more
        likely the route is to appear in this table.";
      config false;
    }

    // Low-level model info: Corresponds to rtmRoutePathType and rtmRibPathType.
    leaf path-type {
      type  meta:route-path-types-all;
      description
        "Protocol specific path type.  This field only has meaning
        if route-type is set to 'remote'.  Otherwise it is set
        to 'none'.";
      config false;
    }

    // Low-level model info: Corresponds to rtmRouteNextHopProtectionType and rtmRibNextHopProtectionType.
    leaf protection {
      type routing-next-hop-protect-t;
      description
        "This field indicates whether the next hop for this route
        is protected from failure, and if so, how it is protected.

        If this field is set to local-lfa or remote-lfa then the
        loop-free alternate can be located in the route table
        with the following index.
        -  destination equal to this route entry.
        -  nexthop equal to lfa/nexthop.
        -  interfacex equal to lfa/if-base-name.";
      config false;
    }

  } // route-common-state

  grouping route-only-state {

    // Low-level model info: Corresponds to rtmRouteInfo.
    leaf info {
      type routing-route-info;
      description
        "A reference to definitions specific to the particular
        routing protocol which is responsible for this route, as
        determined by the value specified in the route's
        protocol leaf.

        This returns the following.

        -  For OSPF, an integer representation of the OID which is
        required by RFC 2096.

        -  For IS-IS, an integer representation of the types of
        route to IP reachable addresses.";
      config false;
    }

    // Low-level model info: Corresponds to rtmRouteNextHopAS.
    leaf next-hop-as {
      type uint32;
      description
        "The Autonomous System Number of the Next Hop.  The
        semantics of this object are determined by the
        routing protocol specified in the route's protocol leaf.
        When this object is unknown or not relevant its
        value is set to zero.";
      config false;
    }

  } // route-only-state

  grouping rib-only-state {

    // Low-level model info: Corresponds to rtmRibLooseNextHop.
    leaf loose-next-hop {
      type boolean;
      description
        "This flag indicates whether RTM considers that the
        next-hop address for this route is a loose next hop.

        If RTM sets this object to 'true' then

        -  it must also have set route-type to 'remote'
        -  the next-hop address (nexthop) may not be on a
        directly connected device
        -  if RTM cannot find a route to the next-hop address,
        it does not return the route, it
        does not redistribute the route to routing protocol
        managers, and it does not program the route to a
        forwarding table (unless the forwarding table has
        registered to receive loose next hops) or to a partner
        that is querying route information (such as BGP or
        PIM).";
      config false;
    }

    // Low-level model info: Corresponds to rtmRibFibRoute.
    leaf fib-route {
      type boolean;
      description
        "Flag indicating whether or not this route has been
        programmed either to a forwarding table, or to a partner
        that queries route information (such as BGP or PIM).

        If there is no forwarding table and no partners are
        querying route information then this object is set to
        'false' for every route.

        If this route has loose-next=hop set to 'true', it is
        possible that RTM knows of more than one explicit next hop
        to the loose next hop address.  If so, RTM programs these
        explicit next hops separately to a forwarding table
        (unless the forwarding table registers to receive loose
        next hops) and to a partner that queries route
        information; in this case the fib-route flag is set
        to 'true' if and only if one or more of these explicit
        next hops has been programmed.";
      config false;
    }

  } // rib-only-state

  grouping route-common-lfa-state {

    // Low-level model info: Corresponds to rtmRouteLfaPriIfIndex and rtmRibLfaPriIfIndex.
    leaf if-index {
      type meta:ro-if-index-or-zero;
      description
        "If the next hop for this route has a loop-free alternate
        (protection is local-lfa or remote-lfa)
        then this field contains the value of the local interface
        index through which the loop-free alternate can be
        reached.

        If the next hop for this route is a loop-free alternate
        then this field contains the local interface index
        through which the primary next hop can be reached.

        Otherwise, this field is not used and is set to zero.";
      config false;
    }

    // Low-level model info: Corresponds to rtmRouteLfaPriIfIndex and rtmRibLfaPriIfIndex.
    leaf if-base-name {
      type interfaces:iface-base-name;
      description
        "If the next hop for this route has a loop-free alternate
        (protection is local-lfa or remote-lfa)
        then this field contains the value of the local interface
        base name through which the loop-free alternate can be
        reached.

        If the next hop for this route is a loop-free alternate
        then this field contains the local interface name through which
        the primary next hop can be reached.

        Otherwise, this field is not used and is set to zero.";
      config false;
    }

    // Low-level model info: Corresponds to rtmRouteLfaPriIfIndex and rtmRibLfaPriIfIndex.
    leaf if-ext-id {
      type interfaces:iface-ext-id;
      description
        "If the next hop for this route has a loop-free alternate
        (protection is local-lfa or remote-lfa)
        then this field contains the value of the local interface
        extended id through which the loop-free alternate can be
        reached.

        If the next hop for this route is a loop-free alternate
        then this field contains the local interface extended id through which
        the primary next hop can be reached.

        Otherwise, this field is not used and is set to zero.";
      config false;
    }

  } // route-common-lfa-state

  grouping route-ipv4-lfa-state {

    container lfa {

      // Low-level model info: Corresponds to rtmRouteLfaPriNextHop(Type) and rtmRibLfaPriNextHop(Type).
      leaf nexthop {
        type interfaces:iface-ipv4-address-allow-zero-t;
        description
          "If the next hop for this route has a loop-free alternate
          (protection is local-lfa or remote-lfa)
          then this field contains the loop-free alternate's
          address.

          If the next hop for this route is a loop-free alternate
          then this field contains the corresponding primary next hop's address.

          Otherwise, this field is not used and is set to zero.";
        config false;
      }

      uses route-common-lfa-state;

    } // lfa

  } // route-ipv4-lfa-state

  grouping route-ipv6-lfa-state {

    container lfa {

      // Low-level model info: Corresponds to rtmRouteLfaPriNextHop(Type) and rtmRibLfaPriNextHop(Type).
      leaf nexthop {
        type interfaces:iface-ipv6-address-t;
        description
          "If the next hop for this route has a loop-free alternate
          (protection is local-lfa or remote-lfa)
          then this field contains the loop-free alternate's
          address.

          If the next hop for this route is a loop-free alternate
          then this field contains the corresponding primary next hop's address.

          Otherwise, this field is not used and is set to zero.";
        config false;
      }

      uses route-common-lfa-state;

    } // lfa

  } // route-ipv6-lfa-state

  grouping route-state {

    uses route-common-state;
    uses route-only-state;

  } // route-state

  grouping rib-state {

    uses route-common-state;
    uses rib-only-state;

  } // rib-state

  grouping route-type-info {

    leaf route-count {
      type uint32;
      description
        "The number of routes of the given protocol type to which RTM
        currently has a route.";
      config false;
    }

  } // route-type-info

  grouping route-target-list {

    list route-target {

      // Low-level model info: Corresponds to AMB_BVM_VRF_RT (mplsVpnVrfRtTable).

      description
        "Route target configuration for the VRF.";

      user-ext:CLI-comm-help "Configure route target";
      user-ext:CLI-no-comm-help "Remove route target";

      key "rt";

      leaf rt {
        type meta:vpn-rt-value-t;
        description
          "BGP extended community route target value.";

        user-ext:CLI-param-help "Route target extended community value";
      }

    } // route-target

  } // route-target-list

  grouping route-count-state {

    container state {

      // Low-level model info: Corresponds to read-only fields in AMB_CIPR_RTM_ENTITY (rtmEntityTable).

      config false;

      leaf route-count {
        type uint32;
        description
          "The number of destination prefixes to which RTM
          currently has a route.  This is the same as the number of
          rows in the route list if the following are both true.

          -  RTM knows of at most one route to each destination prefix.  This
          means that there is at most one route in the route list for
          each destination prefix included in route-count.
          -  None of the routes which RTM has learned about are loose
          next hops that cannot be resolved.  This means that there
          is at least one route in the route list per destination
          prefix included in route-count.";
        config false;
      }

      container connected-route-info {
        description
          "Container to hold connected route information.";

        config false;

        uses route-type-info;
      }

      container local-route-info {
        description
          "Container to hold local route information.";

        config false;

        uses route-type-info;
      }

      container static-route-info {
        description
          "Container to hold static route information.";

        config false;

        uses route-type-info;
      }

      container rip-route-info {
        description
          "Container to hold RIP route information.";

        config false;

        uses route-type-info;
      }

      container isis-route-info {
        description
          "Container to hold ISIS route information.";

        config false;

        uses route-type-info;
      }

      container ospf-route-info {
        description
          "Container to hold OSPF route information.";

        config false;

        uses route-type-info;
      }

      container bgp-route-info {
        description
          "Container to hold BGP route information.";

        config false;

        uses route-type-info;
      }

      container lfa-route-info {
        description
          "Container to hold LFA route information.";

        config false;

        uses route-type-info;
      }

      container summ-addr-route-info {
        description
          "Container to hold summary address route information.";

        config false;

        uses route-type-info;
      }

      container default-route-info {
        description
          "Container to hold default route information.";

        config false;

        uses route-type-info;
      }

    } // state

  } // route-count-state

  grouping routing-loose-next-hop-config {

    container loose-next-hop {

      description
          "Configure static routing for loose next hop";

      user-ext:CLI-comm-help "Configure loose next hop static routing";
      user-ext:CLI-no-comm-help "Configure loose next hop static routing";

      uses routing-administrative-distance;

    }

  } // routing-loose-next-hop-config

  grouping router-config {

    // Low-level model info: Corresponds to AMB_CIPR_RTM_ENTITY (rtmEntityTable).

    description "Configure router";

    user-ext:CLI-comm-help "Configure router";
    user-ext:CLI-no-comm-help "Configure router";

    // Low-level model info: Corresponds to rtmEntityEqlCostOpt.  Presence maps to equalCostAll.
    // Low-level model info: Note the difference in default values between yang and MIB.
    leaf equal-cost {
        type empty;

        description
            "How to select which equal cost routes to give to an active
            routing information consumer, if there is more than one
            route to a given destination with the lowest
            administrative distance.

            If you want to use IGP shortcuts for any routes then this
            leaf must be defined.";

        user-ext:CLI-comm-help "Enable ECMP";
        user-ext:CLI-no-comm-help "Disable ECMP";
    }

    container static {

        // Low-level model info: Corresponds to AMB_CIPR_RTM_STATIC_RT (rtmStaticRtTable).

        description
            "Configuration for static routing";

        user-ext:CLI-comm-help "Configure static routing";
        user-ext:CLI-no-comm-help "Configure static routing";

        container address-family {

            description
                "Configuration static routing for address-family";

            user-ext:CLI-comm-help "Configure static routing for address-family";
            user-ext:CLI-no-comm-help "Configure static routing for address-family";

            container ipv4 {

                description
                    "IPv4 static routing";

                user-ext:CLI-comm-help "Configure IPv4 static routing";
                user-ext:CLI-no-comm-help "Configure IPv4 static routing";

                container unicast {

                    description
                        "Configure IPv4 unicast static routing";

                    user-ext:CLI-comm-help "Configure IPv4 unicast static routing";
                    user-ext:CLI-no-comm-help "Configure IPv4 unicast static routing";

                    list destination {

                        description
                            "Static route";

                        user-ext:CLI-comm-help "Configure destination prefix";
                        user-ext:CLI-no-comm-help "Remove destination prefix";

                        key "prefix nexthop";

                        must "(not(loose-next-hop/metric) or " +
                             " not(interfaces/interface))" {
                          error-message
                            "A loose-next-hop cannot be associated with an interface";
                        }

                        must "(not(loose-next-hop/metric) or " +
                             " (not(custom-interfaces/interface/oneGE/gigabitethernet) and" +
                             "  not(custom-interfaces/interface/oneGE/gigabitethernet-sub) and" +
                             "  not(custom-interfaces/interface/tenGE/tengigabitethernet) and" +
                             "  not(custom-interfaces/interface/tenGE/tengigabitethernet-sub) and" +
                             "  not(custom-interfaces/interface/fortyGE/fortygigabitethernet) and" +
                             "  not(custom-interfaces/interface/fortyGE/fortygigabitethernet-sub) and" +
                             "  not(custom-interfaces/interface/hundredGE/hundredgigabitethernet) and" +
                             "  not(custom-interfaces/interface/hundredGE/hundredgigabitethernet-sub) and" +
                             "  not(custom-interfaces/interface/bundle-ifaces/bundle-ether) and" +
                             "  not(custom-interfaces/interface/bundle-ifaces/bundle-ether-sub) and" +
                             "  not(custom-interfaces/interface/ipip-ifaces/tunnel-gre)))" {
                          error-message
                            "A loose-next-hop cannot be associated with an interface";
                        }

                        // Low-level model info: Corresponds to rtmStaticRtDestAddr.
                        leaf prefix {
                            type interfaces:iface-ipv4-prefix-allow-zero-t;

                            user-ext:CLI-param-help "IPv4 network prefix";

                            description
                                "Destination internetwork prefix or subnet prefix.";
                        }

                        // Low-level model info: Corresponds to rtmStaticRtNextHop.
                        leaf nexthop {
                            type interfaces:iface-ipv4-address-allow-zero-t;

                            user-ext:CLI-comm-help "Set nexthop IPv4 address";
                            user-ext:CLI-no-comm-help "Set nexthop IPv4 address";
                            user-ext:CLI-param-help "Set IPv4 nexthop address";

                            description
                                "The next-hop IP address, if any.

                                If action is 'forward', there may or may not be
                                a next-hop IP address.

                                A next-hop IP address is not required if an output
                                interface is specified.

                                It is possible to supply a next-hop IP address, but to set
                                the output interface to zero.
                                In this case

                                -  the next hop is referred to as a loose next hop
                                -  the next-hop address does not need to be on a directly
                                connected device
                                -  if RTM cannot find a route to the specified next-hop
                                address, it does not return the static route in the
                                route list, it does not redistribute the static
                                route to routing protocol managers, and it does not
                                program the static route to a forwarding table (unless
                                the forwarding table has registered to receive loose
                                next hops) or to a partner that is querying route
                                information (such as BGP or PIM).

                                If action is not 'forward', there is no next-hop IP address.

                                If there is no next-hop IP address, nexthop
                                is set to all zeroes.";
                        }

                        uses ifaces-to-use-in-routing;

                        uses routing-loose-next-hop-config;

                    } // destination

                } // unicast

                container multicast {

                    description
                        "Configure IPv4 multicast static routing";

                    user-ext:CLI-comm-help "Configure IPv4 multicast static routing";
                    user-ext:CLI-no-comm-help "Configure IPv4 multicast static routing";

                    list destination {

                        description
                            "Static route";

                        user-ext:CLI-comm-help "Configure destination prefix";
                        user-ext:CLI-no-comm-help "Remove destination prefix";

                        key "prefix nexthop";

                        must "(not(loose-next-hop/metric) or " +
                             " not(interfaces/interface))" {
                          error-message
                            "A loose-next-hop metric cannot be associated with an interface";
                        }

                        must "(not(loose-next-hop/metric) or " +
                             " (not(custom-interfaces/interface/oneGE/gigabitethernet) and" +
                             "  not(custom-interfaces/interface/oneGE/gigabitethernet-sub) and" +
                             "  not(custom-interfaces/interface/tenGE/tengigabitethernet) and" +
                             "  not(custom-interfaces/interface/tenGE/tengigabitethernet-sub) and" +
                             "  not(custom-interfaces/interface/fortyGE/fortygigabitethernet) and" +
                             "  not(custom-interfaces/interface/fortyGE/fortygigabitethernet-sub) and" +
                             "  not(custom-interfaces/interface/hundredGE/hundredgigabitethernet) and" +
                             "  not(custom-interfaces/interface/hundredGE/hundredgigabitethernet-sub) and" +
                             "  not(custom-interfaces/interface/bundle-ifaces/bundle-ether) and" +
                             "  not(custom-interfaces/interface/bundle-ifaces/bundle-ether-sub) and" +
                             "  not(custom-interfaces/interface/ipip-ifaces/tunnel-gre)))" {
                          error-message
                            "A loose-next-hop metric cannot be associated with an interface";
                        }

                        // Low-level model info: Corresponds to rtmStaticRtDestAddr.
                        leaf prefix {
                            type interfaces:iface-ipv4-prefix-allow-zero-t;

                            user-ext:CLI-param-help "IPv4 network prefix";

                            description
                                "Destination internetwork prefix or subnet prefix.";
                        }

                        // Low-level model info: Corresponds to rtmStaticRtNextHop.
                        leaf nexthop {
                            type interfaces:iface-ipv4-address-allow-zero-t;

                            user-ext:CLI-param-help "Set IPv4 nexthop address";

                            description
                                "The next-hop IP address, if any.

                                If action is 'forward', there may or may not be
                                a next-hop IP address.

                                A next-hop IP address is not required if an output
                                interface is specified.

                                It is possible to supply a next-hop IP address, but to set
                                the output interface to zero.
                                In this case

                                -  the next hop is referred to as a loose next hop
                                -  the next-hop address does not need to be on a directly
                                connected device
                                -  if RTM cannot find a route to the specified next-hop
                                address, it does not return the static route in the
                                route list, it does not redistribute the static
                                route to routing protocol managers, and it does not
                                program the static route to a forwarding table (unless
                                the forwarding table has registered to receive loose
                                next hops) or to a partner that is querying route
                                information (such as BGP or PIM).

                                If action is not 'forward', there is no next-hop IP address.

                                If there is no next-hop IP address, nexthop
                                is set to all zeroes.";
                        }

                        uses ifaces-to-use-in-routing;

                        uses routing-loose-next-hop-config;

                    } // destination

                } // multicast

            } // ipv4

            container ipv6 {

                description
                    "IPv6 static routing";

                user-ext:CLI-comm-help "Configure IPv6 static routing";
                user-ext:CLI-no-comm-help "Configure IPv6 static routing";

                container unicast {

                    description
                        "Configure IPv6 unicast static routing";

                    user-ext:CLI-comm-help "Configure IPv6 unicast static routing";
                    user-ext:CLI-no-comm-help "Configure IPv6 unicast static routing";

                    list destination {

                        description
                            "Static route";

                        user-ext:CLI-comm-help "Configure destination prefix";
                        user-ext:CLI-no-comm-help "Remove destination prefix";

                        key "prefix nexthop";

                        must "(not(loose-next-hop/metric) or " +
                             " not(interfaces/interface))" {
                          error-message
                            "A loose-next-hop cannot be associated with an interface";
                        }

                        must "(not(loose-next-hop/metric) or " +
                             " (not(custom-interfaces/interface/oneGE/gigabitethernet) and" +
                             "  not(custom-interfaces/interface/oneGE/gigabitethernet-sub) and" +
                             "  not(custom-interfaces/interface/tenGE/tengigabitethernet) and" +
                             "  not(custom-interfaces/interface/tenGE/tengigabitethernet-sub) and" +
                             "  not(custom-interfaces/interface/fortyGE/fortygigabitethernet) and" +
                             "  not(custom-interfaces/interface/fortyGE/fortygigabitethernet-sub) and" +
                             "  not(custom-interfaces/interface/hundredGE/hundredgigabitethernet) and" +
                             "  not(custom-interfaces/interface/hundredGE/hundredgigabitethernet-sub) and" +
                             "  not(custom-interfaces/interface/bundle-ifaces/bundle-ether) and" +
                             "  not(custom-interfaces/interface/bundle-ifaces/bundle-ether-sub) and" +
                             "  not(custom-interfaces/interface/ipip-ifaces/tunnel-gre)))" {
                          error-message
                            "A loose-next-hop cannot be associated with an interface";
                        }

                        // Low-level model info: Corresponds to rtmStaticRtDestAddr.
                        leaf prefix {
                            type interfaces:iface-ipv6-prefix-allow-zero-t;

                            user-ext:CLI-param-help "IPv6 network prefix";

                            description
                                "Destination internetwork prefix or subnet prefix.";
                        }

                        // Low-level model info: Corresponds to rtmStaticRtNextHop.
                        leaf nexthop {
                            type interfaces:iface-ipv6-address-t;

                            user-ext:CLI-param-help "Set IPv6 nexthop address";

                            description
                                "The next-hop IP address, if any.

                                If action is 'forward', there may or may not be
                                a next-hop IP address.

                                A next-hop IP address is not required if an output
                                interface is specified.

                                It is possible to supply a next-hop IP address, but to set
                                the output interface to zero.
                                In this case

                                -  the next hop is referred to as a loose next hop
                                -  the next-hop address does not need to be on a directly
                                connected device
                                -  if RTM cannot find a route to the specified next-hop
                                address, it does not return the static route in the
                                route list, it does not redistribute the static
                                route to routing protocol managers, and it does not
                                program the static route to a forwarding table (unless
                                the forwarding table has registered to receive loose
                                next hops) or to a partner that is querying route
                                information (such as BGP or PIM).

                                If action is not 'forward', there is no next-hop IP address.

                                If there is no next-hop IP address, nexthop
                                is set to all zeroes.";
                        }

                        uses ifaces-to-use-in-routing;

                        uses routing-loose-next-hop-config;

                    } // destination

                } // unicast

                container multicast {

                    description
                        "Configure IPv6 multicast static routing";

                    user-ext:CLI-comm-help "Configure IPv6 multicast static routing";
                    user-ext:CLI-no-comm-help "Configure IPv6 multicast static routing";

                    list destination {

                        description
                            "Static route";

                        user-ext:CLI-comm-help "Configure destination prefix";
                        user-ext:CLI-no-comm-help "Remove destination prefix";

                        must "(not(loose-next-hop/metric) or " +
                             " not(interfaces/interface))" {
                          error-message
                            "A loose-next-hop cannot be associated with an interface";
                        }

                        must "(not(loose-next-hop/metric) or " +
                             " (not(custom-interfaces/interface/oneGE/gigabitethernet) and" +
                             "  not(custom-interfaces/interface/oneGE/gigabitethernet-sub) and" +
                             "  not(custom-interfaces/interface/tenGE/tengigabitethernet) and" +
                             "  not(custom-interfaces/interface/tenGE/tengigabitethernet-sub) and" +
                             "  not(custom-interfaces/interface/fortyGE/fortygigabitethernet) and" +
                             "  not(custom-interfaces/interface/fortyGE/fortygigabitethernet-sub) and" +
                             "  not(custom-interfaces/interface/hundredGE/hundredgigabitethernet) and" +
                             "  not(custom-interfaces/interface/hundredGE/hundredgigabitethernet-sub) and" +
                             "  not(custom-interfaces/interface/bundle-ifaces/bundle-ether) and" +
                             "  not(custom-interfaces/interface/bundle-ifaces/bundle-ether-sub) and" +
                             "  not(custom-interfaces/interface/ipip-ifaces/tunnel-gre)))" {
                          error-message
                            "A loose-next-hop cannot be associated with an interface";
                        }

                        key "prefix nexthop";

                        // Low-level model info: Corresponds to rtmStaticRtDestAddr.
                        leaf prefix {
                            type interfaces:iface-ipv6-prefix-allow-zero-t;

                            user-ext:CLI-param-help "IPv6 network prefix";

                            description
                                "Destination internetwork prefix or subnet prefix.";
                        }

                        // Low-level model info: Corresponds to rtmStaticRtNextHop.
                        leaf nexthop {
                            type interfaces:iface-ipv6-address-t;

                            user-ext:CLI-comm-help "Set nexthop IPv6 address";
                            user-ext:CLI-no-comm-help "Set nexthop IPv6 address";
                            user-ext:CLI-param-help "Set IPv6 nexthop address";

                            description
                                "The next-hop IP address, if any.

                                If action is 'forward', there may or may not be
                                a next-hop IP address.

                                A next-hop IP address is not required if an output
                                interface is specified.

                                It is possible to supply a next-hop IP address, but to set
                                the output interface to zero.
                                In this case

                                -  the next hop is referred to as a loose next hop
                                -  the next-hop address does not need to be on a directly
                                connected device
                                -  if RTM cannot find a route to the specified next-hop
                                address, it does not return the static route in the
                                route list, it does not redistribute the static
                                route to routing protocol managers, and it does not
                                program the static route to a forwarding table (unless
                                the forwarding table has registered to receive loose
                                next hops) or to a partner that is querying route
                                information (such as BGP or PIM).

                                If action is not 'forward', there is no next-hop IP address.

                                If there is no next-hop IP address, nexthop
                                is set to all zeroes.";
                        }

                        uses ifaces-to-use-in-routing;

                        uses routing-loose-next-hop-config;

                    } // destination

                } // multicast

            } // ipv6

        } // address-family

    } // static

  } // router-config

  grouping ipv4-route-state-list {

    container route-state-list {

      description
        "Container to hold Route state.";

      config false;

      list route-state {

        // Low-level model info: Corresponds to AMB_CIPR_RTM_ROUTE (rtmRouteTable).

        description
          "This entity's IP Routing table.

          A route is present in this table if and only if it has been
          programmed to an Active Routes Interface consumer.  This may
          be a consumer that asks for all route updates (such as a
          forwarding table), or it may be a consumer that queries
          information about specific routes (such as BGP or PIM).";

        config false;

        // Low-level model info: Corresponds to rtmRouteDest.
        leaf prefix {
          type interfaces:iface-ipv4-prefix-allow-zero-t;
          description
            "Destination internetwork prefix or subnet prefix.  The
            destination prefix length is applied to this value, and to
            a particular destination address, to determine whether the
            route applies to the particular address.

            If the prefix length is L, then applying the length to an
            address means taking the first L bits of the address.";
          config false;
        }

        // Low-level model info: Corresponds to rtmRouteNextHop.
        leaf nexthop {
          type interfaces:iface-ipv4-address-allow-zero-t;
          description
            "On remote routes, the address of the next system en
            route; Otherwise, zero.";
          config false;
        }

        uses route-state;
        uses route-ipv4-lfa-state;

      } // route-state

    } // route-state-list

  } // ipv4-route-state-list

  grouping ipv4-rib-state-list {

    container rib-state-list {

      description
        "Container to hold RIB state.";

      config false;

      list rib-state {

        // Low-level model info: Corresponds to AMB_CIPR_RTM_RIB (rtmRibTable).

        description
          "Read-only copy of this entity's Routing Information Base.
          This is the complete set of routes known by RTM and is a
          superset of the routes accessible through the route list
          (which accesses only the active routes from the Forwarding
          Information Base).";

        config false;

        // Low-level model info: Corresponds to rtmRibDest.
        leaf prefix {
          type interfaces:iface-ipv4-prefix-allow-zero-t;
          description
            "Destination internetwork prefix or subnet prefix.  The
            destination prefix length is applied to this value, and to
            a particular destination address, to determine whether the
            route applies to the particular address.

            If the prefix length is L, then applying the length to an
            address means taking the first L bits of the address.";
          config false;
        }

        // Low-level model info: Corresponds to rtmRibNextHop.
        leaf nexthop {
          type interfaces:iface-ipv4-address-allow-zero-t;
          description
            "On remote routes, the address of the next system en
            route; Otherwise, zero.";
          config false;
        }

        uses rib-state;
        uses route-ipv4-lfa-state;

      } // rib-state

    } // rib-state-list

  } // ipv4-rib-state-list

  grouping ipv6-route-state-list {

    container route-state-list {

      description
        "Container to hold Route state.";

      config false;

      list route-state {

        // Low-level model info: Corresponds to AMB_CIPR_RTM_ROUTE (rtmRouteTable).

        description
          "This entity's IP Routing table.

          A route is present in this table if and only if it has been
          programmed to an Active Routes Interface consumer.  This may
          be a consumer that asks for all route updates (such as a
          forwarding table), or it may be a consumer that queries
          information about specific routes (such as BGP or PIM).";

        config false;

        // Low-level model info: Corresponds to rtmRouteDest.
        leaf prefix {
          type interfaces:iface-ipv6-prefix-allow-zero-t;
          description
            "Destination internetwork prefix or subnet prefix.  The
            destination prefix length is applied to this value, and to
            a particular destination address, to determine whether the
            route applies to the particular address.

            If the prefix length is L, then applying the length to an
            address means taking the first L bits of the address.";
        }

        // Low-level model info: Corresponds to rtmRouteNextHop.
        leaf nexthop {
          type interfaces:iface-ipv6-address-t;
          description
            "On remote routes, the address of the next system en
            route; Otherwise, zero.";
        }

        uses route-state;
        uses route-ipv6-lfa-state;

      } // route-state

    } // route-state-list

  } // ipv6-route-state-list

  grouping ipv6-rib-state-list {

    container rib-state-list {

      description
        "Container to hold RIB state.";

      config false;

      list rib-state {

        // Low-level model info: Corresponds to AMB_CIPR_RTM_RIB (rtmRibTable).

        description
          "Read-only copy of this entity's Routing Information Base.
          This is the complete set of routes known by RTM and is a
          superset of the routes accessible through the route list
          (which accesses only the active routes from the Forwarding
          Information Base).";

        config false;

        // Low-level model info: Corresponds to rtmRibDest.
        leaf prefix {
          type interfaces:iface-ipv6-prefix-allow-zero-t;
          description
            "Destination internetwork prefix or subnet prefix.  The
            destination prefix length is applied to this value, and to
            a particular destination address, to determine whether the
            route applies to the particular address.

            If the prefix length is L, then applying the length to an
            address means taking the first L bits of the address.";
        }

        // Low-level model info: Corresponds to rtmRibNextHop.
        leaf nexthop {
          type interfaces:iface-ipv6-address-t;
          description
            "On remote routes, the address of the next system en
            route; Otherwise, zero.";
        }

        uses rib-state;
        uses route-ipv6-lfa-state;

      } // rib-state

    } // rib-state-list

  } // ipv6-rib-state-list

  grouping route-rib-state {

    container ipv4-state {

      description
        "IPv4 Route / RIB state.";

      config false;

      uses route-count-state;
      uses ipv4-route-state-list;
      uses ipv4-rib-state-list;

    } // ipv4-state

    container ipv6-state {

      description
        "IPv6 Route / RIB state.";

      config false;

      uses route-count-state;
      uses ipv6-route-state-list;
      uses ipv6-rib-state-list;

    } // ipv6-state

  } // route-rib-state

  grouping vrf-bind-config {

    leaf bind-vrf-name {
      type leafref {
        path "/routing:router/routing:vrf/routing:vrf-name";
      }
      description
        "L3VPN VRF to which an interface is bound.";

      user-ext:CLI-comm-help "Set L3VPN VRF to which an interface is bound";
      user-ext:CLI-no-comm-help "Remove L3VPN VRF to which an interface is bound";
      user-ext:CLI-param-help "Set L3VPN VRF to which an interface is bound";
    }

  } // vrf-bind-config


  container router {

    uses router-config;
    uses route-rib-state;

    list vrf {

      description
          "VRF routing configuration";

      user-ext:CLI-comm-help "Configure routing in VRF";
      user-ext:CLI-no-comm-help "Configure or remove routing in VRF";

      key "vrf-name";

      leaf vrf-name {
        type meta:l3vpn-vrf-name;
        description
          "The name of this VRF.  This MAY be equivalent to the RFC2685 VPN-ID.";

        user-ext:CLI-comm-help "Associate configuration with VRF";
        user-ext:CLI-no-comm-help "Clear VRF association";
      }

      leaf description {
        type meta:l3vpn-vrf-description;
        description
          "The human-readable description of this VRF.";

        user-ext:CLI-comm-help "Set VRF description";
        user-ext:CLI-no-comm-help "Remove VRF description";
        user-ext:CLI-param-help "Set VRF description";
      }

      container import {

        description
          "Import route target configuration for the VRF.";

        user-ext:CLI-comm-help "Configure import route targets";
        user-ext:CLI-no-comm-help "Configure or remove import route targets";

        uses route-target-list;

      } // import

      container export {

        description
          "Export route target configuration for the VRF.";

        user-ext:CLI-comm-help "Configure export route targets";
        user-ext:CLI-no-comm-help "Configure or remove export route targets";

        uses route-target-list;

      } // export

      leaf import-vrf-default {
        type empty;
        description
          "Enables importing of routes from the default or global VRF.";

        user-ext:CLI-comm-help "Import routes from the default VRF";
        user-ext:CLI-no-comm-help "Disable importing of routes from the default VRF";
      }

      leaf export-vrf-default {
        type empty;
        description
            "Enables exporting of routes to the default or global VRF.";

        user-ext:CLI-comm-help "Export routes to the default VRF";
        user-ext:CLI-no-comm-help "Disable exporting of routes to the default VRF";
      }

      container advertise-l2vpn-evpn {

        presence "Advertise routes into EVPN";

        description
          "Enables the advertisement of routes within a tenant VRF into
          EVPN.";

        user-ext:CLI-comm-help "Advertise routes into EVPN";
        user-ext:CLI-no-comm-help "Disable advertisement of routes into EVPN";

        list summary-address {

          description
            "Summary address";

          user-ext:CLI-comm-help "Configure summary address";
          user-ext:CLI-no-comm-help "Remove summary address";

          key "prefix";

          leaf prefix {
            type interfaces:iface-ip-prefix-t;
            description
              "Summary prefix.";

            user-ext:CLI-param-help "Summary prefix";
          }

          leaf advertise {
            type boolean;
            default "true";
            description
              "Determines whether the summary address is advertised
              into EVPN.

              If set to true,the summary address is advertised and any
              routes matching the summary address are not advetised.

              If set to false, neither the summary address not any
              routes matching the summary address are advertised into
              EVPN.";

            user-ext:CLI-param-help "Configure whether to advertise summary address into EVPN";
            user-ext:CLI-comm-help "Configure whether to advertise summary address into EVPN";
            user-ext:CLI-no-comm-help "Advertise summary address into EVPN";
          }

        } // summary-address

      } // advertise-l2vpn-evpn

      uses router-config;
      uses route-rib-state;

    } // vrf

  } // router


  augment "/interface:interfaces/interface:interface" {

    if-feature interface:l3vpn-vrf-bind;
    description
      "Add a node for the identification of the VRF associated
      with the information configured on a interface.";

    uses vrf-bind-config;

  }

} // routing
