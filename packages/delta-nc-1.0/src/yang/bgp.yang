module bgp {

    // Actions require Yang version 1.1.
    // Start yang1.1-only
    yang-version 1.1;
    // End yang1.1-only

    namespace "http://metaswitch.com/yang/nbu/bgp/201512020000Z";

    prefix "bgp";

    import metaswitch-custom-yang-types { prefix "custom"; }
    import user-extensions { prefix "user-ext"; }
    import interfaces { prefix "interfaces"; }
    import metaswitch-yang-types { prefix meta; }
    import ethernet-segment { prefix es; }
    import redist { prefix redist; }

    organization "Metaswitch Networks";

    contact "Postal: Metaswitch Networks
                     100 Church Street
                     Enfield
                     EN2 6BQ
                     United Kingdom
             Tel:    +44 20 8366 1177
             E-mail: info@metaswitch.com";

    description
        "Border Gateway Protocol";

    revision 2015-12-02 {
        description "Initial revision.";
    }

    typedef router-bgp-ttl {
        type int32 {
            range "1..255";
        }

        description
            "TTL (1-255)";
    }

    typedef router-bgp-ttl-sec-min-ttl {
        type int32 {
            range "0..255";
        }

        description
            "MIN TTL (0-255)";
    }

    typedef router-bgp-as {
        type uint32 {
            range "0..4294967295";
        }

        description
            "INT (0-4294967295)";
    }

    typedef router-bgp-password-string {
        type string {
            length "1..128";
        }

        description
            "WORD (1-128)";
    }

    typedef router-bgp-maximum-paths {
        type int32 {
            range "1..32";
        }

        description
            "PATHS LIMIT (1-32)";
    }

    typedef router-bgp-best-n-paths {
        type int32 {
            range "1..255";
        }

        description
            "BEST N PATHS (1-255)";
    }

    typedef router-bgp-local-preference {
        type uint32 {
            range "0..4294967295";
        }

        description
            "INT (0-4294967295)";
    }

    typedef router-bgp-retain-local-label {
        type int32 {
            range "3..60";
        }

        description
            "DELAY (3-60 min)";
    }

    typedef router-bgp-graceful-restart-restart-time {
        type int32  {
            range "1..3600";
        }

        description
            "SEC (1-3600)";
    }

    typedef router-bgp-max-ecmp-paths {
        type int32 {
            range "1..255";
        }
    }

    typedef router-bgp-max-afi-safi-ecmp-paths {
        type int32 {
            range "0..255";
        }
    }

    typedef router-bgp-update-delay {
        type int32 {
            range "0..3600";
        }

        description
            "SEC (0-3600)";
    }

    typedef router-bgp-orf-prefix {
        type enumeration  {
            enum none                       { value 1; description "ORF entries not supported in either direction"; }
            enum both                       { value 2; description "Send and receive ORF entries"; }
            enum send                       { value 3; description "Would like to send ORF entries to peer"; }
            enum receive                    { value 4; description "Willing to receive ORF entries from peer"; }
        }

        description
            "ORF prefix";
    }

    typedef router-bgp-adv-interval {
        type int32 {
            range "0..600";
        }

        description
            "SEC (0-600)";
    }

    typedef router-bgp-wd-interval {
        type int32 {
            range "0..600";
        }

        description
            "SEC (0-600)";
    }

    typedef router-bgp-ses-timer-keepalive {
        type int32 {
            range "0..65535";
        }

        description
            "SEC (0-65535)";
    }

    typedef router-bgp-ses-timer-holdtime {
        type int32 {
            range "0 | 3..65535";
        }

        description
            "SEC (0 or 3-65535)";
    }

    typedef router-bgp-ses-timer-connect-retry {
        type int32 {
            range "1..65535";
        }

        description
            "SEC (1-65535)";
    }

    typedef router-bgp-max-prefixes {
      type uint32 {
        range "0..2147483647";
      }
      description
        "(0-2147483647)";
    }

    typedef router-bgp-prefix-threshold {
      type uint32 {
        range "0..100";
      }
      description
        "(0-100%)";
    }

    typedef router-bgp-sess-drop-warning {
      type enumeration {
        enum drop                             { value 1; description "The session is dropped"; }
        enum warn                             { value 2; description "A warning is produced"; }
      }
      description
        "Session action";
    }

    typedef router-bgp-max-prefix-hold {
        type int32 {
            range "0 | 30..86400";
        }

        description
            "SEC (0 or 30-86400)";
    }

    typedef bgp-restart-exit-reason {
      type enumeration {
        enum none                             { value 1; }
        enum in-progress                      { value 2; }
        enum completed                        { value 3; }
        enum timed-out                        { value 4; }
        enum failed                           { value 5; }
        enum completedPeerNoSupport           { value 6; }
      }
      description
        "BGP restart exit reason";
    }

    typedef bgp-last-error {
      type string {
        length 4;
      }
      description
        "BGP last error string";
    }

    typedef bgp-last-error-data {
      type string {
        length "0..256";
      }
      description
        "BGP last error data string";
    }

    typedef bgp-user-data-t {
      type string {
        length 8;
      }
      description
        "BGP user data";
    }

    typedef router-bgp-allow-local-as {
      type uint32 {
        range "0..10";
      }

      description
        "INT (0-10)";
    }

    typedef bgp-peer-events {
      type enumeration {
        enum no-event                         { value 0; }
        enum start                            { value 1; }
        enum stop                             { value 2; }
        enum transport-open                   { value 3; }
        enum transport-closed                 { value 4; }
        enum transport-open-failed            { value 5; }
        enum transport-fatal-error            { value 6; }
        enum connect-retry-timer              { value 7; }
        enum hold-retry-timer                 { value 8; }
        enum keepalive-timer                  { value 9; }
        enum recv-open                        { value 10; }
        enum recv-keepalive                   { value 11; }
        enum recv-update                      { value 12; }
        enum recv-notification                { value 13; }
      }
      description
        "BGP Peer events";
    }

    typedef bgp-peer-restart-support {
      type enumeration {
        enum none                             { value 1; }
        enum aware-only                       { value 2; }
        enum enabled                          { value 3; }
      }
      description
        "BGP Peer restart support types";
    }

    typedef bgp-peer-state {
      type enumeration {
        enum idle                             { value 1; }
        enum connect                          { value 2; }
        enum active                           { value 3; }
        enum open-sent                        { value 4; }
        enum open-confirm                     { value 5; }
        enum established                      { value 6; }
      }
      description
        "BGP Peer states";
    }

    typedef bgp-peer-restart-status {
      type enumeration {
        enum not-restarting                   { value 1; }
        enum restart-timer-running            { value 2; }
        enum stale-path-timer-running         { value 3; }
      }
      description
        "BGP Peer restart status values";
    }

    typedef bgp-peer-config-states {
      type enumeration {
        enum state-up-to-date                 { value 1; }
        enum state-out-of-date-admin-down     { value 2; }
        enum state-out-of-date-row-inactive   { value 3; }
      }
      description
        "BGP Peer config states";
    }

    typedef bgp-peer-reflector-client {
      type enumeration {
        enum non-client                       { value 1; description "Non client"; }
        enum client                           { value 2; description "Client"; }
        enum meshed-client                    { value 3; description "Meshed client"; }
      }
      description
        "BGP Reflector Client type";
    }

    typedef bgp-alt-loc-as-mode {
      type enumeration {
        enum mode1                            { value 1; }
        enum mode2                            { value 2; }
        enum mode3                            { value 3; }
      }
      description
        "BGP alternative local AS modes.";
    }

    typedef bgp-peer-or-afm {
      type enumeration {
        enum peer                             { value 1; }
        enum afm                              { value 2; }
      }
      description
        "BGP Peer or AFM type";
    }

    typedef bgp-afi {
      type enumeration {
        enum other                            { value 0; }
        enum ipv4                             { value 1; }
        enum ipv6                             { value 2; }
        enum l2vpn                            { value 25; }
      }
      description
        "BGP Afi types";
    }

    typedef bgp-safi {
      type enumeration {
        enum none                             { value 0; }
        enum unicast                          { value 1; }
        enum multicast                        { value 2; }
        enum unicast-multicast                { value 3; }
        enum labeled                          { value 4; }
        enum vpls                             { value 65; }
        enum evpn                             { value 70; }
        enum vpn                              { value 128; }
      }
      description
        "BGP Safi types";
    }

    typedef bgp-as-size-t {
      type enumeration {
        enum two-octet                        { value 1; }
        enum four-octet                       { value 2; }
      }
      description
        "BGP AS size values";
    }

    typedef bgp-origin-codes {
      type enumeration {
        enum igp                              { value 0; }
        enum egp                              { value 1; }
        enum incomplete                       { value 2; }
      }
      description
        "BGP origin codes";
    }

    typedef bgp-nlri-peer-type {
      type enumeration {
        enum none                             { value 0; }
        enum ibgp                             { value 1; }
        enum ebgp                             { value 2; }
      }
      description
        "Type of BGP peer";
    }

    typedef bgp-path-attr-atomic-agg {
      type enumeration {
        enum present                          { value 1; }
        enum absent                           { value 2; }
      }
      description
        "BGP Path attribute atomic aggregate types";
    }

    typedef bgp-nlri-is-active {
      type enumeration {
        enum not-tracked                      { value 1; }
        enum inactive                         { value 2; }
        enum active                           { value 3; }
      }
      description
        "BGP NLRI is active values";
    }

    typedef bgp-half-life-t {
        type uint32 {
            range "1..45";
        }
        description
          "MINS (1-45)";
    }

    typedef bgp-flap-threshold-t {
        type uint32 {
            range "1..20000";
        }
        description
          "(1-20000)";
    }

    typedef bgp-max-suppress-time-t {
        type uint32 {
            range "1..255";
        }
        description
          "MINS (1-255)";
    }

    typedef l2vpn-ve-id-t {
      type uint32 {
        range "1..65535";
      }
      description
        "(1-65535)";
    }

    typedef bgp-add-path-caps-router {
      type enumeration {
        enum disable                          { value 1; description "Neither send or receive"; }
        enum receive                          { value 2; description "Receive only"; }
        enum send                             { value 3; description "Send only"; }
        enum both                             { value 4; description "Both send and receive"; }
      }
      description
        "BGP Add Path Capabilities configurable at the router level";
    }

    typedef bgp-add-path-capabilities {
      type enumeration {
        enum disable                          { value 1; description "Neither send or receive"; }
        enum receive                          { value 2; description "Receive only"; }
        enum send                             { value 3; description "Send only"; }
        enum both                             { value 4; description "Both send and receive"; }
        enum inherit                          { value 5; description "Use BGP address-family value"; }
      }
      description
        "BGP Add Path Capabilities";
    }

    typedef bgp-peer-group-name {
      type meta:ascii-string {
        length "1..32";
      }
      description
        "WORD (1-32)";
    }

    typedef bgp-listen-range-max-peers-t {
      type uint32 {
        range "0..4294967295";
      }
      description
        "(0-4294967295)";
    }

    typedef bgp-peer-group-area-type {
      type enumeration {
        enum ibgp                             { value 1; description "Internal BGP"; }
        enum ebgp                             { value 2; description "External BGP"; }
        enum ebgp-confederation               { value 3; description "External BGP confederation"; }
      }
      description
        "BGP Peer Group Area type";
    }

    typedef bgp-peering-type {
      type enumeration {
        enum unspecified                      { value 1; description "Unspecified"; }
        enum provider                         { value 2; description "Provider"; }
        enum customer                         { value 3; description "Customer"; }
        enum bilateral                        { value 4; description "Bilateral"; }
      }
      description
        "BGP Peering Type";
    }

    typedef bgp-aro-advert-status-t {
      type enumeration {
        enum advertised                       { value 1; }
        enum suppressed                       { value 2; }
        enum pending-withdrawal               { value 3; }
        enum withdrawn                        { value 4; }
      }
      description
        "BGP ARO advertisement status";
    }

    typedef bgp-aro-aggr-status-t {
      type enumeration {
        enum no-aggregation                   { value 1; }
        enum aggregate-route                  { value 2; }
        enum unsuppressed-aggregated-route    { value 3; }
        enum suppressed-aggregated-route      { value 4; }
      }
      description
        "BGP ARO aggregation status";
    }

    typedef bgp-oper-status-t {
      type enumeration {
        enum up                               { value 1; description "Up"; }
        enum down                             { value 2; description "Down"; }
        enum going-up                         { value 3; description "Going up"; }
        enum going-down                       { value 4; description "Going down"; }
        enum activation-failed                { value 5; description "Activation failed"; }
      }
      description
        "BGP operational status";
    }

    typedef router-bgp-next-hop-self {
      type enumeration {
        enum true {
          value 1;
          description
            "Set self as next hop for advertised routes (except when
             reflecting routes)";
        }
        enum false {
          value 2;
          description
            "Do not set self as next hop for advertised routes";
        }
        enum all {
          value 3;
          description
            "Set self as next hop for both eBGP and iBGP advertised routes
             including when acting as a route reflector";
        }
      }
      description
        "BGP Next Hop Calculation Actions";
    }

    identity bgp-error-code {
      description
        "Indicates the error type in a BGP NOTIFICATION message";
      reference
        "RFC 4271 - A Border Gateway Protocol 4 (BGP-4)";
    }

    identity unspecific {
      base bgp-error-code;
      description
        "No specific error was indicated in the BGP Notification message";
    }

    identity message-header-error {
      base bgp-error-code;
      description
        "An error was detected while processing a BGP Message Header";
    }

    identity open-message-error {
      base bgp-error-code;
      description
        "An error was detected while processing a BGP OPEN message";
    }

    identity update-message-error {
      base bgp-error-code;
      description
        "An error was detected while processing a BGP UPDATE message";
    }

    identity hold-timer-expired {
      base bgp-error-code;
      description
        "Indicates that the system did not receive a KEEPALIVE, UPDATE, and/or
         NOTIFICATION message within the specified Hold Time";
    }

    identity fsm-error {
      base bgp-error-code;
      description
        "An error was detected by the BGP Finite State Machine (for example,
         receipt of an unexpected event)";
    }

    identity cease {
      base bgp-error-code;
      description
        "A BGP speaker has closed its BGP connection in the absence of any
         fatal errors";
    }

    identity route-refresh-message-error {
      base bgp-error-code;
      description
        "An error was detected while processing a BGP ROUTE-REFRESH message";
      reference
        "RFC 7313 - Enhanced Route Refresh Capability for BGP-4";
    }

    identity bgp-error-subcode {
      description
        "Provides more specific information about the error reported in a
         NOTIFICATION message.";
      reference
        "RFC 4271 - A Border Gateway Protocol 4 (BGP-4)";
    }

    identity no-subcode {
      base bgp-error-subcode;
      description
        "No specific error subcode was indicated in the BGP Notification
         message";
    }

    identity message-header-subcode {
      base bgp-error-subcode;
      description
        "Error subcode definitions for Message Header error notifications";
    }

    identity connection-not-synchronised {
      base message-header-subcode;
      description
        "Marker field of the message header is not all ones as expected";
    }

    identity bad-message-length {
      base message-header-subcode;
      description
        "Indicates the message has an erroneous length with one or more of the
         following:
         - the Length field of the message header is less than 19 or greater
           than 4096
         - the Length field of an OPEN message is less than the minimum length
           of the OPEN message
         - the Length field of an UPDATE message is less than the minimum
           length of the UPDATE message
         - the Length field of a KEEPALIVE message is not equal to 19
         - the Length field of a NOTIFICATION message is less than the minimum
           length of the NOTIFICATION message";
    }

    identity bad-message-type {
      base message-header-subcode;
      description
        "Message type is not recognised.";
    }

    identity open-message-subcode {
      base bgp-error-subcode;
      description
        "Error subcode definitions for OPEN message error notifications";
    }

    identity unsupported-version-number {
      base open-message-subcode;
      description
        "Version number of the received OPEN message is not supported";
    }

    identity bad-peer-as {
      base  open-message-subcode;
      description
        "Autonomous System field of the received OPEN message is unacceptable";
    }

    identity bad-bgp-identifier {
      base open-message-subcode;
      description
        "BGP Identifier field of the received OPEN message is syntactically
         incorrect";
    }

    identity unsupported-optional-parameter {
      base open-message-subcode;
      description
        "One or more of the Optional Parameters in the received OPEN message
         is not recognized";
    }

    identity authentication-failure {
      base open-message-subcode;
      description
        "Authentication procedure has failed";
    }

    identity unacceptable-hold-time {
      base open-message-subcode;
      description
        "Hold Time field of the received OPEN message is unacceptable";
    }

    identity unsupported-capability {
      base open-message-subcode;
      description
        "Indicates that the peer does not support capabilities
         advertisement.";
      reference
        "RFC 5492 - Capabilities Advertisement with BGP-4";
    }

    identity update-message-subcode {
      base bgp-error-subcode;
      description
        "Error subcode definitions for UPDATE message error notifications";
    }

    identity malformed-attribute-list {
      base update-message-subcode;
      description
        "Inidicates Withdrawn Routes Length or Total Attribute Length is too
         large, or an attribute appears more than once in the UPDATE message";
    }

    identity unrecognized-well-known-attribute {
      base update-message-subcode;
      description
        "One or more of the well-known mandatory attributes are not
         recognized";
    }

    identity missing-well-known-attribute {
      base update-message-subcode;
      description
        "One or more of the well-known mandatory attributes are not present";
    }

    identity attribute-flags-error {
      base update-message-subcode;
      description
        "Attribute has Attribute Flags that conflict with the Attribute Type
         Code";
    }

    identity attribute-length-error {
      base update-message-subcode;
      description
        "Attribute has an Attribute Length that conflicts with the expected
         length based on the attribute type code";
    }

    identity invalid-origin-attribute {
      base update-message-subcode;
      description
        "ORIGIN attribute has an undefined value";
    }

    identity invalid-next-hop-attribute {
      base update-message-subcode;
      description
        "The NEXT_HOP attribute field is syntactically incorrect";
    }

    identity optional-attribute-error {
      base update-message-subcode;
      description
        "An error is detected in the value of a recognized optional attribute";
    }

    identity invalid-network-field {
      base update-message-subcode;
      description
        "The NLRI field in the UPDATE message is syntactically incorrect";
    }

    identity malformed-as-path {
      base update-message-subcode;
      description
        "The AS_PATH attribute is syntactically incorrect";
    }

    identity finite-state-machine-subcode {
      base bgp-error-subcode;
      description
        "Error subcode definitions for BGP finite state machine errors.";
      reference
        "RFC 6608 - Subcodes for BGP Finite State Machine Error";
    }

    identity cease-subcode {
      base bgp-error-subcode;
      description
        "Error subcode definitions for Cease notification messages";
      reference
        "RFC 4486 - Subcodes for BGP Cease Notification Message";
    }

    identity max-num-prefixes-reached {
      base cease-subcode;
      description
        "The BGP speaker terminated its peering with the peer because the
         number of address prefixes received exceeds the configured upper
         bound";
    }

    identity administrative-shutdown {
      base cease-subcode;
      description
        "The BGP speaker administratively shut down the peer session";
    }

    identity peer-de-configured {
      base cease-subcode;
      description
        "The BGP speaker de-configured the peer session";
    }

    identity administrative-reset {
      base cease-subcode;
      description
        "The BGP speaker administratively reset the peer session";
    }

    identity connection-rejected {
      base cease-subcode;
      description
        "The BGP speaker disallowed the BGP peer session after the BGP speaker
         accepted a transport protocol connection";
    }

    identity other-config-change {
      base cease-subcode;
      description
        "The BGP speaker administratively reset the peer session due to a
         configuration change that is not covered by another subcode.";
    }

    identity conn-collision-resolution {
      base cease-subcode;
      description
        "The BGP speaker sent a CEASE NOTIFICATION as a result of the collision
         resolution procedure";
    }

    identity out-of-resources {
      base cease-subcode;
      description
        "The BGP speaker ran out of resources (for example, memory) and reset
         the peer session";
    }

    identity route-refresh-subcode {
      base bgp-error-subcode;
      description
        "Error subcode definitions for the ROUTE-REFRESH message error";
    }

    identity invalid-message-length {
      base route-refresh-subcode;
      description
        "The length, excluding the fixed-size message header, of the received
         ROUTE-REFRESH message with Message Subtype 1 and 2 is not 4";
    }

    grouping bgp-capabilities-bits {

      // Low-level model info: Corresponds to the bit flags in the AMB_BGP_CAPABILITIES group.

      description
        "A set of capabilities used to report state.";

      leaf mp-ipv4-unicast {
        type empty;
        description
          "Multiprotocol BGP support for IPv4 unicast routes.";
      }

      leaf mp-ipv4-multicast {
        type empty;
        description
          "Multiprotocol BGP support for IPv4 multicast routes.";
      }

      leaf mp-ipv4-vpn {
        type empty;
        description
          "Multiprotocol BGP support for IPv4 VPN routes.";
      }

      leaf mp-ipv4-label {
        type empty;
        description
          "Multiprotocol BGP support for labeled IPv4 routes.";
      }

      leaf mp-ipv6-unicast {
        type empty;
        description
          "Multiprotocol BGP support for IPv6 unicast routes.";
      }

      leaf mp-ipv6-multicast {
        type empty;
        description
          "Multiprotocol BGP support for IPv6 multicast routes.";
      }

      leaf mp-ipv6-vpn {
        type empty;
        description
          "Multiprotocol BGP support for IPv6 VPN routes.";
      }

      leaf mp-ipv6-label {
        type empty;
        description
          "Multiprotocol BGP support for labeled IPv6 routes.";
      }

      leaf route-refresh {
        type empty;
        description
          "Support for Route Refresh messages.";
      }

      leaf graceful-restart {
        type empty;
        description
          "Support for graceful restart processing.";
      }

      leaf route-refresh-cisco {
        type empty;
        description
          "Support for pre-standard (Cisco) Route Refresh messages.";
      }

      leaf outbound-route-filter {
        type empty;
        description
          "Support for Outbound Route Filtering, for one or more";
      }

      leaf outbound-route-filter-cisco {
        type empty;
        description
          "Support for pre-standard (Cisco) Outbound Route Filtering,";
      }

      leaf four-octet-as {
        type empty;
        description
          "Support for four-octet AS numbers.";
      }

      leaf mp-l2vpn-vpls {
        type empty;
        description
          "Multiprotocol BGP support for AFI/SAFI = L2VPN/VPLS.";
      }

      leaf mp-l2vpn-evpn {
        type empty;
        description
          "Multiprotocol BGP support for AFI/SAFI = L2VPN/EVPN.";
      }

      leaf add-path {
        type empty;
        description
          "Support for additional BGP paths.";
      }

      leaf enhanced-route-refresh {
        type empty;
        description
          "Support for enhanced route refresh (RFC7313).";
      }

      leaf extended-next-hop-ipv4-unicast {
        type empty;
        description
          "Support for extended next-hop encoding for IPv4 unicast routes (RFC5549).";
      }

      leaf extended-next-hop-ipv4-multicast {
        type empty;
        description
          "Support for extended next-hop encoding for IPv4 multicast routes (RFC5549).";
      }

      leaf extended-next-hop-ipv4-label {
        type empty;
        description
          "Support for extended next-hop encoding for labeled IPv4 routes (RFC5549).";
      }

      leaf extended-next-hop-ipv4-vpn {
        type empty;
        description
          "Support for extended next-hop encoding for IPv4 VPN routes (RFC5549).";
      }

    }  // bgp-capabilities-bits

    grouping bgp-afi-safi-bits {

      // Low-level model info: Corresponds to the bit flags in the AMB_BGP_AFI_SAFI_BITS group.

      description
        "A set of address and subaddress families used to report state.";

      leaf ipv4-unicast {
        type empty;
      }

      leaf ipv4-multicast {
        type empty;
      }

      leaf ipv4-mpls-bgp-vpn {
        type empty;
      }

      leaf ipv6-unicast {
        type empty;
      }

      leaf ipv6-multicast {
        type empty;
      }

      leaf ipv6-mpls-bgp-vpn {
        type empty;
      }

      leaf ipv4-labeled {
        type empty;
      }

      leaf ipv6-labeled {
        type empty;
      }

      leaf l2vpn-vpls {
        type empty;
      }

      leaf l2vpn-evpn {
        type empty;
      }

    }  // bgp-afi-safi-bits


    grouping bgp-ext-community {

      choice extcommunity-type {

        case rt {

          container rt {

            user-ext:CLI-comm-help "Configure Route Target parameters";
            user-ext:CLI-no-comm-help "Configure Route Target parameters";

            leaf value {
              type meta:bgp-extended-community;
              description
                "BGP extended community number used when executing the action
                on the extended community.";

              user-ext:CLI-comm-help "Set extended community value";
              user-ext:CLI-no-comm-help "Remove extended community value";
              user-ext:CLI-param-help "Set extended community value";
            }

          } // rt

        } // rt

        case soo {

          container soo {

            user-ext:CLI-comm-help "Configure Site of Origin parameters";
            user-ext:CLI-no-comm-help "Configure Site of Origin parameters";

            leaf value {
              type meta:bgp-extended-community;
              description
                "BGP extended community number used when executing the action
                on the extended community.";

              user-ext:CLI-comm-help "Set extended community value";
              user-ext:CLI-no-comm-help "Remove extended community value";
              user-ext:CLI-param-help "Set extended community value";
            }
          } // soo

        } // soo

      } // extcommunity-type

    } // bgp-ext-community

    grouping bgp-redist {

      // Low-level model info: Corresponds to new route attributes in AMB_CIPR_RTM_REDIST (rtmRedistTable)
      // and AMB_CIPR_RTM_RDST_SET_FIELD (rtmRdstSetFieldTable)

      // Low-level model info: The following two fields correspond to
      // AMB_CIPR_RTM_RDST_SET_FIELD (rtmRdstSetFieldTable)
      // For simplicity, rtmRdstSetFieldListId and rtmRedistSetListId
      // will be set to above rtmRedistEntryId when rtmRdstSetFieldTable
      // entries need to be configured

      // Low-level model info: Corresponds to rtmRdstSetFieldValue
      // rtmRdstSetFieldNumber will be set to 1
      // rtmRdstSetFieldType will be set to "bgp-comm"
      leaf new-community {
        type meta:bgp-community;

        description
          "BGP community number to set in routing information sent to
          destination.";

        user-ext:CLI-comm-help "Set BGP community number";
        user-ext:CLI-no-comm-help "Remove BGP community number";
        user-ext:CLI-param-help "Set BGP community number";
      }

      // Low-level model info: Corresponds to rtmRdstSetFieldValue
      // rtmRdstSetFieldNumber will be set to 2
      // rtmRdstSetFieldType will be set to "bgp-ext-comm"
      container new-extcommunity {

        description
          "Extended BGP community number to set in routing information sent to
          destination.";

        user-ext:CLI-comm-help "Set BGP extended community number";
        user-ext:CLI-no-comm-help "Remove BGP extended community number";

        uses bgp-ext-community;

      } // new-extcommunity

      // Low-level model info: Corresponds to rtmRedistNwMed
      // If this field is set, rtmRedistAddMed will be set to true
      leaf new-med {
        type uint32 {
          range "0..4294967295";
        }

        description
          "BGP Multi-Exit Discriminator to set in routing information sent to destination.";

        user-ext:CLI-comm-help "Set BGP MED";
        user-ext:CLI-no-comm-help "Set BGP MED to default";
        user-ext:CLI-param-help "Set BGP MED";
      }

      // Low-level model info: Corresponds to rtmRedistNwWeight
      // If this field is set, rtmRedistAddWeight will be set to true
      leaf new-weight {
        type uint32 {
          range "0..4294967295";
        }
        default 32768;

        description
          "BGP weight to set in routing information sent to destination.";

        user-ext:CLI-comm-help "Set BGP weight";
        user-ext:CLI-no-comm-help "Set BGP weight to default";
        user-ext:CLI-param-help "Set BGP weight";
      }

      // Low-level model info: Corresponds to rtmRedistNwLocalPref
      // If this field is set, rtmRedistAddLocalPref will be set to true
      leaf new-local-preference {
        type uint32 {
          range "0..4294967295";
        }

        description
          "BGP local preference to set in routing information sent to destination.";

        user-ext:CLI-comm-help "Set BGP local preference";
        user-ext:CLI-no-comm-help "Set BGP local preference to default";
        user-ext:CLI-param-help "Set BGP local preference";
      }

    } // bgp-redist

    grouping global-graceful-restart-state-for-bgp {

      // Low-level model info: Corresponds to graceful restart state in AMB_BGP_RM_ENT (bgpRmEntTable).

      description "BGP graceful restart state.";

      leaf graceful-restart-remaining-time {
        type uint32;
        units "seconds";
        description
          "Remaining time before BGP graceful restart times out.";
        config false;
      }

      leaf graceful-restart-exit-reason {
        type bgp-restart-exit-reason;
        description
          "Describes the outcome of the last attempt at a graceful
          restart.  If the value is 'none', no restart has yet been
          attempted.  If the value is 'in-progress', a restart
          attempt is currently underway.";
        config false;
      }

      leaf graceful-restart-time {
        type router-bgp-graceful-restart-restart-time;
        description
          "Restart time announced to neighbors";
        config false;
      }

    } // global-graceful-restart-state-for-bgp

    grouping global-state-for-bgp {

      // Low-level model info: Corresponds to state in AMB_BGP_RM_ENT (bgpRmEntTable).

      description "BGP state.";

      leaf number-aro-routes {
        type uint32;
        description
          "The total number of Adj-RIB-Out routes currently allocated
          across all Adj-RIBs-Out.

          When additional paths are enabled, routes with different
          path ID values count as different prefixes.";
        config false;
      }

      leaf peak-number-aro-routes {
        type uint32;
        description
          "The peak number of Adj-RIB-Out routes that have been
          allocated at any one time.

          When additional paths are enabled, routes with different
          path ID values count as different prefixes.";
        config false;
      }

      leaf remain-delay-time {
        type uint32;
        description
          "The maximum time remaining until route selection takes
          place following a restart, in hundredths of a second.";
        config false;
      }

      leaf path-attrs {
        type uint32;
        description
          "The total number of path attributes present.";
        config false;
      }

      leaf enforce-first-as {
        type boolean;

        description
          "Enabled first AS in path and peer AS equal proof";
        config false;
      }

      leaf update-delay {
        type router-bgp-update-delay;

        description
          "BGP update delay";
        config false;
      }

      uses global-graceful-restart-state-for-bgp;

    } // global-state-for-bgp

    grouping neighbor-state {

      // Low-level model info: Corresponds to AMB_BGP_PEER_STATUS (bgpPeerStatusTable).

      description "BGP neighbor state.";

      // Low-level model info: Corresponds to bgpPeerRemoteAddr(Type).
      leaf remote-address {
        type interfaces:iface-ip-address-t;
        description
          "The remote address for the peering session.

          For configured peers this field has the same value as
          the remote address configured for the peer.

          For dynamic peers this field is the address of the BGP peer
          as determined from the incoming connection.";
        config false;
      }

      leaf local-address {
        type interfaces:iface-ip-address-allow-zero-t;
        description
          "The local address configured for the peering session, or
          a zero length address if not specified.

          For configured peers this field has the same value as
          the local address configured for the peer.

          For dynamic peers this field is a zero-length address.

          The selected-local-address shows the local address actually in use.";
        config false;
      }

      leaf local-port {
        type uint32 {
          range "0..65535";
        }
        description
          "The local port configured for the peering session, or zero
          if not specified.

          For configured peers this field has the same value as
          local port configured.

          For dynamic peers this field is zero.

          The selected-local-port shows the local port actually in use.";
        config false;
      }

      leaf remote-port {
        type uint32 {
          range "0..65535";
        }
        description
          "The remote port configured for the peering session, or
          zero if not specified.

          For configured peers this field has the same value as
          remote port configured for the peer.

          For dynamic peers this field is zero.

          The selected-remote-port shows the remote port actually in use.";
        config false;
      }

      leaf local-address-scope-id {
        type uint32;
        description
          "The scope ID of the local and remote adresses.  The scope ID is
          required if the address is an IPv6 link-local address.  Otherwise,
          this field must be set to zero.

          For configured peers this field has the same value as
          configured scope ID.

          For dynamic peers this field is the scope ID of the
          remote address as determined from the incoming connection.";
        config false;
      }

      leaf interface {
        type interfaces:iface-name;
        description
          "The name of the interface on which the address is reachable.
           For neighbors configured by interface name, this matches the
           neighbor-interface key and is otherwise absent.";
        config false;
      }

      leaf identifier {
        type meta:router-id;
        description
          "The BGP Identifier of this entry's BGP peer.

          This entry is zero unless the state is open-confirm or established.";
        config false;
      }

      leaf state {
        type bgp-peer-state;
        description
          "The BGP peer's FSM state.";
        config false;
      }

      leaf dynamic-peer {
        type boolean;
        description
          "Whether the peer is dynamic (true) or individually
          configured (false).";
        config false;
      }

      leaf remote-as {
        type uint32;
        description
          "The remote autonomous system number in use on the session.
          For configured peers not yet active, this is the
          configured value.

          This value may be different from the configured value
          if the configured value has been changed since the peer session
          was started.";
        config false;
      }

      leaf index {
        type uint32;
        description
          "The peer index.

          The peer index is a unique index for the peer.  It is used to
          provide an index value for other lists whose data is
          logically per-peer.

          The peer index value is fixed until the entry in the
          peer is destroyed, but it changes if the entry is destroyed and
          recreated.

          For a dynamic BGP peer, if the BGP session terminates and
          then restarts outside the graceful restart period, the
          peer index value may change.";
        config false;
      }

      leaf capabilities-supported {
        type boolean;
        description
          "Whether or not this peer accepted our local capabilities
          optional parameter sent on the OPEN message.  This field
          will not be relevant until the peer has reached open-confirm
          state.  Note that this field indicates support or otherwise
          of the capabilities optional parameter, not a specific
          capability.";
        config false;
      }

      leaf last-error {
        type bgp-last-error;
        description
          "The last error code and subcode sent or received on this
          connection.  If no error has occurred, this field is zero.
          Otherwise, the first byte of this two byte string
          contains the error code, and the second byte contains the
          subcode.";
        config false;
      }

      leaf last-error-data {
        type bgp-last-error-data;
        description
          "The last error code's data seen by this peer on this
          connection.";
        config false;
      }

      leaf fsm-established-time {
        type uint32;
        units "seconds";
        description
          "This timer indicates how long in seconds this peer has
          been in the Established state or how long since this peer
          was last in the Established state.  It is set to zero when
          a new peer is configured or the router is booted.";
        config false;
      }

      leaf in-updates-elapsed-time {
        type uint32;
        units "seconds";
        description
          "Elapsed time in seconds since the last BGP message was
          received from the peer.  Each time in-updates is
          incremented, the value of this object is set to zero (0).";
        config false;
      }

      leaf hold-time {
        type int32;
        units "seconds";
        description
          "Time interval in seconds for the Hold Timer established
          with the peer.

          The Hold Timer interval is calculated by this BGP speaker by
          using the smaller of the configured hold-time
          value and the Hold Time received in the OPEN message.

          A value of zero indicates that the Hold Timer has not been
          established with the peer.";
        config false;
      }

      leaf keepalive-time {
        type int32;
        units "seconds";
        description
          "Time interval in seconds for the KeepAlive Timer
          established with the peer.

          The KeepAlive Timer interval is calculated by this BGP
          speaker such that, when compared with the Hold Time,
          it has the same proportion as the configured keep-alive value has
          when compared with the configured hold-time value.

          A value of zero indicates that the KeepAlive Timer has not
          been established with the peer.";
        config false;
      }

      leaf in-opens {
        type uint32;
        description
          "The number of BGP OPEN messages received on this
          connection.  This object is initialized to zero when the
          connection is established.";
        config false;
      }

      leaf out-opens {
        type uint32;
        description
          "The number of BGP OPEN messages transmitted on this
          connection.  This object is initialized to zero when the
          connection is established.";
        config false;
      }

      leaf in-notifications {
        type uint32;
        description
          "The number of BGP NOTIFICATION messages received on this
          connection.  This object is initialized to zero when the
          connection is established.";
        config false;
      }

      leaf out-notifications {
        type uint32;
        description
          "The number of BGP NOTIFICATION messages transmitted on
          this connection.  This object is initialized to zero when
          the connection is established.";
        config false;
      }

      leaf in-updates {
        type uint32;
        description
          "The number of BGP UPDATE messages received on this
          connection.  This object is initialized to zero when the
          connection is established.";
        config false;
      }

      leaf out-updates {
        type uint32;
        description
          "The number of BGP UPDATE messages transmitted on this
          connection.  This object is initialized to zero when the
          connection is established.";
        config false;
      }

      leaf in-keepalives {
        type uint32;
        description
          "The number of BGP KEEPALIVE messages received on this
          connection.  This object is initialized to zero when the
          connection is established.";
        config false;
      }

      leaf out-keepalives {
        type uint32;
        description
          "The number of BGP KEEPALIVE messages transmitted on this
          connection.  This object is initialized to zero when the
          connection is established.";
        config false;
      }

      leaf in-refreshes {
        type uint32;
        description
          "The number of BGP ROUTE REFRESH messages received on this
          connection.  This object is initialized to zero when the
          connection is established.";
        config false;
      }

      leaf out-refreshes {
        type uint32;
        description
          "The number of BGP ROUTE REFRESH messages transmitted on
          this connection.  This object is initialized to zero when
          the connection is established.";
        config false;
      }

      leaf in-total-messages {
        type uint32;
        description
          "The total number of messages received from the remote peer
          on this connection.  This object is initialized to zero when
          the connection is established.";
        config false;
      }

      leaf out-total-messages {
        type uint32;
        description
          "The total number of messages transmitted to the remote
          peer on this connection.  This object is initialized to zero
          when the connection is established.";
        config false;
      }

      leaf fsm-established-transitions {
        type uint32;
        description
          "The total number of times the BGP FSM transitioned into
          the established state for this peer.";
        config false;
      }

      leaf connect-retry-count {
        type uint32;
        description
          "The current connect retry count of this peer.

          This is incremented each time the peer session flaps, and is
          used to determine the time to wait before retrying the
          session.

          Note this is only incremented when an active session
          terminates abnormally, and not when it simply fails to come
          up.

          This field is not used for dynamic peers.";
        config false;
      }

      leaf peer-group {
        type uint32;
        description
          "The index of the peer group this neighbor belongs to, or
          zero if this neighbor does not belong to a peer group.";
        config false;
      }

      leaf stale-path-time {
        type uint32;
        units "seconds";
        description
          "The maximum time in seconds that BGP will wait
          following a peer restart or peer session failure before
          removing stale routes from that peer.

          This is advertised by the peer in its OPEN message if it
          supports graceful restart.  If the advertised value is
          greater than the configured reatart-time, then that value
          will be used in preference.";
        config false;
      }

      leaf orf-entry-count {
        type uint32;
        description
          "The current number of ORF entries of all types that have
          been received from the peer.";
        config false;
      }

      leaf last-error-rcvd {
        type bgp-last-error;
        description
          "The last error code and subcode received from the peer on
          this connection.

          If no error has been received from the peer, this field is
          zero.  Otherwise, the first byte of this two byte string
          contains the error code, and the second byte contains
          the subcode.";
        config false;
      }

      leaf last-error-rcvd-time {
        type uint32;
        description
          "The value of sysUpTime when the last error was received
          from the peer on this connection.

          If no error has been received from the peer, this field is
          zero.";
        config false;
      }

      leaf last-error-sent {
        type bgp-last-error;
        description
          "The last error code and subcode sent to the peer on this
          connection.

          If no error has been sent to the peer, this field is zero.
          Otherwise, the first byte of this two byte string
          contains the error code, and the second byte contains the
          subcode.";
        config false;
      }

      leaf last-error-sent-time {
        type uint32;
        description
          "The value of sysUpTime when the last error was sent to the
          peer on this connection.

          If no error has been sent to the peer, this field is zero.";
        config false;
      }

      leaf last-state {
        type bgp-peer-state;
        description
          "The BGP peer's previous FSM state.";
        config false;
      }

      leaf last-event {
        type bgp-peer-events;
        description
          "The last input to be made to the BGP peer's FSM.";
        config false;
      }

      container caps-sent {
        uses bgp-capabilities-bits;
        description
          "The capabilities announced to the peer on the most recent
          Open message sent to the peer.  This field is set to zero
          before the first Open message is sent to the peer, and
          is unchanged if the session comes down.";
        config false;
      }

      container caps-rcvd {
        uses bgp-capabilities-bits;
        description
          "The capabilities received on the most recent Open message
          received from the peer.  This field is set to zero before
          the first Open message is received from the peer, and is
          unchanged if the session comes down.

          In the event that the peer signals a capability that DC-BGP
          does not recognize, this field will only contain those
          capabilities that BGP recognizes.";
        config false;
      }

      container caps-negotiated {
        uses bgp-capabilities-bits;
        description
          "The capabilities negotiated for the session with the peer.
          This field is set to zero before Open messages have been
          exchanged with the peer, and is unchanged if the session
          comes down.";
        config false;
      }

      leaf restart-support {
        type bgp-peer-restart-support;
        description
          "Whether the peer supports graceful restart.  This field is
          set to 'none' before an Open message has been received from
          a peer, and is unchanged if the session comes down.";
        config false;
      }

      container restart-family {
        uses bgp-afi-safi-bits;
        description
          "The address and subaddress families for which the peer
          supports graceful restart.  This field is set to zero before
          an Open message has been received from a peer, and is
          unchanged if the session comes down.";
        config false;
      }

      leaf restart-restart {
        type boolean;
        description
          "Whether the peer is currently in the process of
          restarting.";
        config false;
      }

      leaf restart-status {
        type bgp-peer-restart-status;
        description
          "The current state of the peer's restart processing.  If
          bgpPeerStatusRstrRestarting is false, this is set to
          notRestarting.";
        config false;
      }

      leaf restart-remain-time {
        type uint32;
        units "hundredths of a second";
        description
          "The time remaining in the current restart state, in
          hundredths of a second.  If bgpPeerStatusRstrStatus is
          notRestarting, this is set to zero.";
        config false;
      }

      leaf rcvd-msg-elapsed-time {
        type uint32;
        units "hundredths of a second";
        description
          "The elapsed time in hundredths of a second since anything
          was received from this peer.  If nothing has been received
          from this peer, this field is set to zero.  If the session
          comes down this value continues to increase.";
        config false;
      }

      leaf idle-hold-remain-time {
        type uint32;
        units "hundredths of a second";
        description
          "For a peer in 'idle' state, the time remaining in
          hundredths of a second until BGP will try to reactivate
          the connection.  If the peer is not in 'idle' state, this is
          set to zero.";
        config false;
      }

      leaf route-refresh-sent {
        type uint32;
        description
          "The number of Route Refresh messages sent to the peer.

          If the session comes down this value is unchanged, and will
          continue to increment if the session is reestablished.

          However, for dynamic peers the peer status entry is lost
          if the BGP session is not re-established within the graceful
          restart period, and in this case the value of this field
          is lost.";
        config false;
      }

      leaf route-refresh-received {
        type uint32;
        description
          "The number of Route Refresh messages received from the
          peer.

          If the session comes down this value is unchanged, and will
          continue to increment if the session is reestablished.

          However, for dynamic peers the peer status entry is lost
          if the BGP session is not re-established within the graceful
          restart period, and in this case the value of this field
          is lost.";
        config false;
      }

      leaf selected-local-addr {
        type interfaces:iface-ip-address-allow-zero-t;
        description
          "The local address used by the transport connection for the
          peering session.

          If a connection exists and a local-address is configured
          then these two fields will be identical.";
        config false;
      }

      leaf selected-local-port {
        type uint32 {
          range "0..65535";
        }
        description
          "The local port used by the transport connection for the
          peering session.

          If a connection exists and a local-port is configured then
          these two fields will be identical.

          A value of zero implies that there is currently no
          connection to this peer.";
        config false;
      }

      leaf selected-remote-port {
        type uint32 {
          range "0..65535";
        }
        description
          "The remote port used by the transport connection for the
          peering session.

          If a connection exists and a remote-port is configured
          then these two fields will be identical.

          A value of zero implies that there is currently no
          connection to this peer.";
        config false;
      }

      leaf bfd-status {
        type meta:bfd-sess-states;
        description
          "BFD session state for this peer.";
        config false;
      }

      leaf selected-local-as {
        type uint32;
        description
          "The local AS number used on this session or zero if the session
           is not established";
        config false;
      }

      leaf selected-remote-as {
        type uint32;
        description
          "The remote AS number used on this session or zero if the
           session is not established.";
        config false;
      }

      leaf in-prefixes {
        type uint32;
        description
          "The total number of prefixes received from this peer.

          When additional paths are enabled, routes with different
          path ID values count as different prefixes.";
        config false;
      }

      leaf out-prefixes {
        type uint32;
        description
          "The number of prefixes that are installed in all of this
          peer's Adj-RIBs-Out.

          When additional paths are enabled, routes with different
          path ID values count as different prefixes.";
        config false;
      }

      leaf out-prefixes-advertised {
        type uint32;
        description
          "The total number of prefixes advertised to this peer.

          When additional paths are enabled, routes with different
          path ID values count as different prefixes.

          Note that the value of this field may differ from out-prefixes
          since that field includes recently withdrawn routes which
          are undergoing suppression procedures.";
        config false;
      }

      leaf in-prefixes-denied-by-pol {
        type uint32;
        description
          "The number of times a received prefix has been denied, and
           therefore not installed in the Adj-RIB-In, because of
           local filter policy.

           When additional paths are enabled, routes with different
           path ID values count as different prefixes.";
        config false;
      }

      leaf out-prefixes-denied {
        type uint32;
        description
          "This is the number of prefixes in the Loc-RIB that have
           have failed export policy checks and so have not been
           installed in the Adj-RIB-Out.

           When additional paths are enabled, routes with different
           path ID values count as different prefixes.";
        config false;
      }

      leaf config-state {
        type bgp-peer-config-states;
        description
          "This field reports the state of the peer configuration.
          The peer configuration may be in one of the following
          states.

          -  Up to date.  That is, all configuration for
          this peer has been applied to the current peer session
          (if it exists).

          -  Out of date, requiring the peer's admin status to be
          set to down before all the current configuration
          for this peer can be applied.

          -  Out of date, requiring the peer's row status to be set
          to inactive before all the current configuration
          for this peer can be applied.

          A peer's configuration can become out of date for several
          reasons, including the following.

          -  Configuration has changed and the new value cannot be applied
          while the peer session is active.";
        config false;
      }

      leaf confederation-member {
        type boolean;
        description
          "The currently active value which indicates whether or not
          the peer is a member of the same confederation that this
          router is in.

          This value may be different from the current configured
          value for the peer if the value has been changed since the peer
          session was started.";
        config false;
      }

      leaf reflector-client {
        type bgp-peer-reflector-client;
        description
          "The currently active value which indicates whether the
          given peer is a reflector client of this router, or not.

          This value may be different from the current configured
          value for the peer if the value has been changed since the peer
          session was started.";
        config false;
      }

      leaf trap-established {
        type boolean;
        description
          "The currently active value which indicates whether or not
          the Established notification is used.

          This value may be different from the current configured
          value for the peer if the value has been changed since the peer
          session was started.";
        config false;
      }

      leaf trap-backward {
        type boolean;
        description
          "The currently active value which indicates whether or not
          the Backward Transition notification is used.

          This value may be different from the current configured
          value for the peer if the value has been changed since the peer
          session was started.";
        config false;
      }

      leaf connect-retry-interval {
        type uint32;
        units "seconds";
        description
          "The currently active time interval for the Connect Retry
          timer.

          This value may be different from the current configured
          value for the peer if the value has been changed since the peer
          session was started.";
        config false;
      }

      leaf passive {
        type boolean;
        description
          "The current in use value of the passive flag.  If true, then no
          outbound connections will be initiated and only incoming
          connections will be accepted.  If false, then outbound
          connections will be attempted to this peer and incoming
          connections will be accepted from this peer.

          This value may be different from the current configured
          value for the peer if the value has been changed since the peer
          session was started.

          For dynamic peers this field is always true.";
        config false;
      }

      leaf open-delay {
        type uint32;
        units "seconds";
        description
          "The currently active delay to enforce in between a TCP
          connection with this peer becoming established and a BGP
          Open message being sent.

          This value may be different from the current configured
          value for the peer if the value has been changed since the peer
          session was started.";
        config false;
      }

      leaf idle-hold-time {
        type uint32;
        units "seconds";
        description
          "The currently active time to hold this peer in Idle state
          after a BGP session has progressed beyond Idle state
          initially and then returned to it.

          This value may be different from the current configured
          value for the peer if the value has been changed since the peer
          session was started.";
        config false;
      }

      leaf time-to-live {
        type int32;
        description
          "The currently active Time To Live used by the connection
          on this peer.

          This value may be different from the current configured
          value for the peer if the value has been changed since the peer
          session was started.";
        config false;
      }

      leaf conf-alt-local-as {
        type uint32;
        description
          "The currently active alternative local AS number that can
          be used to establish a session with this peer.  This is
          used when merging two ASs into a single AS.

          This value may be different from the current configured
          value for the peer if the value has been changed since the peer
          session was started.";
        config false;
      }

      leaf conf-alt-local-as-mode {
        type bgp-alt-loc-as-mode;
        description
          "The currently active AS number mode.

          This value may be different from the current configured
          value for the peer if the value has been changed since the peer
          session was started.";
        config false;
      }

      leaf disable-route-refresh {
        type boolean;
        description
          "The currently active disable route refresh flag.  This
          indicates whether BGP should advertise support for
          Route Refresh messages to this peer.

          This value may be different from the current configured
          value for the peer if the value has been changed since the peer
          session was started.";
        config false;
      }

      leaf bfd-desired {
        type boolean;
        description
          "The currently active flag which indicates whether
          Bidirectional Forwarding Detection (BFD) is desired for
          this peer.

          This value may be different from the current configured
          value for the peer if the value has been changed since the peer
          session was started.";
        config false;
      }

      leaf configured-hold-time {
        type uint32 {
          range "0..65535";
        }
        units "seconds";
        description
          "The currently active time interval in seconds for the Hold
          Time configured for this BGP speaker with this peer.

          This value may be different from the current configured
          value for the peer if the value has been changed since the peer
          session was started.

          The time interval in seconds for the Hold Timer actually
          established with the peer is given by hold-time.";
        config false;
      }

      leaf configured-keepalive-time {
        type uint32 {
          range "0..65535";
        }
        units "seconds";
        description
          "The currently active time interval in seconds for the
          KeepAlive configured for this BGP speaker with this peer.

          This value may be different from the current configured
          value for the peer if the value has been changed since the peer
          session was started.

          The time interval in seconds for the Keep Alive actually
          established with the peer is given by keepalive-time.";
        config false;
      }

      container address-family {

        // Low-level model info: Corresponds to AMB_BGP_PEER_AFI_SAFI_STAT (bgpPeerAfiSafiStatusTable).

        description
          "State for address-family";
        config false;

        container ipv4 {
          description
            "State for IPv4";
          config false;

          container unicast {
            description
              "State for unicast";
            config false;

            uses router-bgp-neighbor-af-common-state;

          } // unicast

        } // ipv4

        container ipv6 {
          description
            "State for IPv6";
          config false;

          container unicast {
            description
              "State for unicast";
            config false;

            uses router-bgp-neighbor-af-common-state;

          } // unicast

        } // ipv6

      } // address-family

    } // neighbor-state

    grouping neighbor-state-actions {

      // Start yang1.1-only
      action clear-peer {

        description
          "Clear peer session.";

        user-ext:CLI-param-help "Clear peer session";

      } // clear-peer

      action send-route-refresh {

        description
          "Send Route-Refresh message to peer.";

        user-ext:CLI-param-help "Send Route-Refresh message to peer";

      } // send-route-refresh
      // End yang1.1-only

    } // neighbor-state-actions

    grouping neighbor-group-config {

        // Low-level model info: Corresponds to bgpPeerMinRouteAdvertiseInterval and bgpPeergrMinRteAdvertiseInterval.  Default is 30.
        leaf advertisement-interval {
            type router-bgp-adv-interval;
            units "seconds";

            description
                "Minimal interval between sending BGP updates";

            user-ext:CLI-comm-help "Set min interval between sending updates in seconds";
            user-ext:CLI-no-comm-help "Set default min interval between sending updates";
            user-ext:CLI-param-help "Set interval in seconds";
        }

        // Low-level model info: Corresponds to bgpPeerMinRouteWithdrawInterval and bgpPeergrMinRteWithdrawInterval.  Default is 30.
        leaf withdraw-interval {
            type router-bgp-wd-interval;
            units "seconds";

            description
                "Minimal interval between advertisement and subsequent withdrawal of a route";

            user-ext:CLI-comm-help "Set min interval from route advert to withdraw (secs)";
            user-ext:CLI-no-comm-help "Set default min interval from route advert to withdraw";
            user-ext:CLI-param-help "Set interval in seconds";
        }

        // Low-level model info: Corresponds to bgpPeerSoftResetWithStoredInfo and bgpPeergrSoftResetWithStoredInfo.
        leaf soft-reset-with-stored-info {
          type empty;

          description
            "Configure soft reset with stored routing information.
             This option causes all routes learned from a peer to be
             stored so that the Adj-Rib-In can be recalculated without
             performing a route refresh or restarting the peer session.
             When not configured, BGP does not perform soft reset
             for any address family.";

          user-ext:CLI-comm-help "Enable BGP soft reset";
          user-ext:CLI-no-comm-help "Disable BGP soft reset";
          user-ext:CLI-param-help "Enable BGP soft reset";
        }

        // Low-level model info: If the ebgp-multihop container does not exist, then use 1 for bgpPeerTtl for
        //                       eBGP peers and 255 for iBGP peers (determine peer state from remote-as object).
        container ebgp-multihop {
            presence "Enable EBGP-multihop on this neighbor";

            description
                "Enable EBGP-multihop on this neighbor";

            user-ext:CLI-comm-help  "Enable EBGP multihop for this neighbor";
            user-ext:CLI-no-comm-help  "Disable EBGP multihop for this neighbor";

            // Low-level model info: Corresponds to bgpPeerTtl and bgpPeergrTtl.  Default is 255.
            leaf ttl {
                type router-bgp-ttl;

                user-ext:CLI-comm-help "Set neighbor's TTL for session";
                user-ext:CLI-no-comm-help "Remove neighbor's TTL for session";
                user-ext:CLI-param-help "Set TTL";
            }
        }

        container enforce-first-as {
            description
                "Configure first AS in path and neighbor AS equal proof";

            user-ext:CLI-comm-help "Configure first AS number in AS PATH for EBGP nbrs";
            user-ext:CLI-no-comm-help "Configure first AS number in AS PATH for EBGP nbrs";

            // Low-level model info: Corresponds to bgpPeerCheckFirstAsNum and bgpPeergrCheckFirstAsNum.
            leaf disable {
                type empty;

                description
                    "Disable first AS in path and neighbor AS equal proof";
                user-ext:CLI-comm-help "Disable first AS number in AS PATH for EBGP neighbors";
                user-ext:CLI-no-comm-help "Enable first AS number in AS PATH for EBGP neighbors";
            }
        }

        // Low-level model info: Corresponds to bgpPeerConfAltLocalAs and bgpPeergrConfAltLocalAs.  Default is 0.
        //                       The bgpPeer(gr)ConfAltLocalAsMode field should be set to the default of "mode1".
        leaf local-as {
            type router-bgp-as;

            description
                "Local AS number for this session";

            user-ext:CLI-comm-help "Set alternative AS number for peer session";
            user-ext:CLI-no-comm-help "Remove alternative AS number for peer session";
            user-ext:CLI-param-help "Set alternative AS number for peer session";
        }

        // Low-level model info: Corresponds to bgpPeerPassword and bgpPeergrPassword.
        leaf password {
            type router-bgp-password-string;

            description
                "Password for BGP session";

            user-ext:CLI-comm-help "Set password for BGP session";
            user-ext:CLI-no-comm-help "Remove password for BGP session";
            user-ext:CLI-param-help "Set password";
        }

        // Low-level model info: Corresponds to bgpPeerRemoteAs and bgpPeergrRemoteAs.  Default is 0.
        leaf remote-as  {
            type router-bgp-as;

            description
                "Remote AS number for this session";

            user-ext:CLI-comm-help "Set remote AS number for this session";
            user-ext:CLI-no-comm-help "Remove remote AS number for this session";
            user-ext:CLI-param-help "Set AS number";
        }

        container timers {
            description
                "BGP session timers";

            user-ext:CLI-comm-help "Configure BGP session timers";
            user-ext:CLI-no-comm-help "Configure BGP session timers";

            // Check that the keepalive is non-zero and less than holdtime, or both are set to zero.
            // The default values are 180 and 60 seconds respectively for the holdtime and keepalive timers.
//            must "(((not(holdtime)) and (not(keepalive))) or " +
//                 " ((not(holdtime)) and ((180 >= keepalive) and (keepalive != 0))) or " +
//                 " ((not(keepalive)) and (holdtime >= 60)) or " +
//                 " (((keepalive) and (holdtime)) and " +
//                 "  (((keepalive = 0) and (holdtime = 0)) or " +
//                 "   ((keepalive > 0) and (number(holdtime) >= number(keepalive))))))" {
//              error-message "BGP neighbor keepalive must be non-zero and not greater than holdtime, or both set to zero";
//            }

            // Low-level model info: Corresponds to bgpPeerKeepAliveConfigd and bgpPeergrKeepAliveConfigd.  Default is 60.
            leaf keepalive {
                type router-bgp-ses-timer-keepalive;

                user-ext:CLI-comm-help "Set BGP session keepalive timer";
                user-ext:CLI-no-comm-help "Set default BGP session keepalive timer";
                user-ext:CLI-param-help "Set keepalive time";
            }

            // Low-level model info: Corresponds to bgpPeerHoldTimeConfigd and bgpPeergrHoldTimeConfigd.  Default is 180.
            leaf holdtime {
                type router-bgp-ses-timer-holdtime;

                user-ext:CLI-comm-help "Set BGP session holdtime timer";
                user-ext:CLI-no-comm-help "Set default BGP session holdtime timer";
                user-ext:CLI-param-help "Set hold time";
            }

            // Low-level model info: Corresponds to bgpPeerConnectRetryInterval and bgpPeergrConnectRetryInterval.  Default is 120.
            leaf connect-retry {
                type router-bgp-ses-timer-connect-retry;

                user-ext:CLI-comm-help "Set BGP connect retry timer";
                user-ext:CLI-no-comm-help "Set default BGP connect retry timer";
                user-ext:CLI-param-help "Set connect retry time";
            }
        }

        // Low-level model info: Corresponds to bgpPeerSendComm and bgpPeergrSendComm.
        leaf send-community {
            type empty;

            description
                "Enable/disable sending BGP community attributes to the peer";

            user-ext:CLI-comm-help "Enable sending BGP community to peer";
            user-ext:CLI-no-comm-help "Disable sending BGP community to peer";
        }

        // Low-level model info: Corresponds to bgpPeerSendExtComm and bgpPeergrSendExtComm.
        leaf send-community-ext {
            type empty;

            description
                "Enable/disable sending BGP extended community attributes
                to the peer";

            user-ext:CLI-comm-help "Enable sending BGP extended community to peer";
            user-ext:CLI-no-comm-help "Disable sending BGP extended community to peer";
        }

        // Low-level model info: Corresponds to bgpPeerAllowLocalAs and bgpPeergrAllowLocalAs.  Default is 0.
        leaf allow-local-as {
            type router-bgp-allow-local-as;

            description
                "The number of instances of the local AS identifier";

            user-ext:CLI-comm-help "Set local AS id count for sent route AS_PATH attribute";
            user-ext:CLI-no-comm-help "Set default local AS id count for sent route AS_PATH";
            user-ext:CLI-param-help "Set local AS id count for sent route AS_PATH attribute";
        }

        // Low-level model info: Corresponds to bgpPeerConfedMember and bgpPeergrConfedMember.
        leaf confederation-member {
            type empty;

            must "(../../../confederation-identifier) and  (../../../confederation-identifier != 0)" {
              error-message
                "BGP confederation-identifier must be configured" +
                " to enable neighbor confederation-member";
            }

            description
                "Whether the peer is a member of the same confederation that this router is in";

            user-ext:CLI-comm-help "Configure peer to be in same confederation as router";
            user-ext:CLI-no-comm-help "Configure to not be in same confederation as router";
        }

        // Low-level model info: Corresponds to bgpPeerReflectorClient and bgpPeergrReflectorClient.  Default is "non-client".
        leaf route-reflector-client {
            type bgp-peer-reflector-client;

            description
                "Whether the given peer is a reflector client of this router";

            user-ext:CLI-comm-help "Set route-reflector characteristics";
            user-ext:CLI-no-comm-help "Set default route-reflector characteristics";
            user-ext:CLI-param-help "Configure route-reflector characteristics";
        }

        container bfd {

            description
                "BFD parameters.";

            user-ext:CLI-comm-help "Configure BFD parameters for peer";
            user-ext:CLI-no-comm-help "Configure BFD parameters for peer";

            // Low-level model info: Corresponds to bgpPeerBfdDesired and bgpPeergrBfdDesired.
            leaf fast-detect {
                type empty;
                description
                    "Indicates whether Bidirectional Forwarding Detection (BFD)
                    is desired for this peer.

                    This leaf can be changed at any time.  However, if the
                    leaf is changed while the peer is up, the
                    change will only take effect after the peer has been
                    cycled down and then up, thus forcing the
                    peer session to be restarted.  In this case, until the
                    peer is set down, the peer will be marked as
                    out of date (as reported by the config_state field in the
                    bgp-peer-config-states leaf for the peer).";

                user-ext:CLI-comm-help "Enable BFD for this peer";
                user-ext:CLI-no-comm-help "Disable BFD for this peer";
            }

        } // bfd

        // Low-level model info: Corresponds to bgpPeerConfigMaxPrfx and bgpPeergrConfigMaxPrfx.  Default is 0.
        leaf max-prefixes {
            type router-bgp-max-prefixes;

            description
                "This is used to limit the number
                of prefixes that can be accepted from this peer.

                Setting router-bgp-max-prefixes to a non-zero value sets the
                maximum number of prefixes (totalled across all supported
                address families) that can be accepted from this peer.";

            user-ext:CLI-comm-help "Set maximum number of prefixes from peer";
            user-ext:CLI-no-comm-help "Set maximum number of prefixes from peer to default";
            user-ext:CLI-param-help "Set maximum number of prefixes";
        }

        // Low-level model info: Corresponds to bgpPeerConfigThreshold and bgpPeergrConfigThreshold.  Default is 75.
        leaf prefix-threshold {
            type router-bgp-prefix-threshold;
            default 75;

            description
                "Set percentage of maximum number of prefixes from peer at
                 which to send prefix-threshold notification.";

            user-ext:CLI-comm-help "Set percentage of maximum number of prefixes from peer at which to send prefix-threshold notification";
            user-ext:CLI-no-comm-help "Set percentage of maximum number of prefixes from peer at which to send prefix-threshold notification to default";
            user-ext:CLI-param-help "Set percentage of maximum number of prefixes";
        }

        // Low-level model info: Corresponds to bgpPeerMaxPrfxClear and bgpPeergrMaxPrfxClear.  Default is 0.
        leaf max-prefixes-clear {
            type router-bgp-max-prefixes;

            description
                "Set number of prefixes from peer at which to send
                 max-prefix-clear notification.";

            user-ext:CLI-comm-help "Set number of prefixes from peer at which to send max-prefix-clear notification";
            user-ext:CLI-no-comm-help "Set number of prefixes from peer at which to send max-prefix-clear notification to default";
            user-ext:CLI-param-help "Set number of prefixes to send prefix-clear notification";
        }

        // Low-level model info: Corresponds to bgpPeerPrfxThresholdClear and bgpPeergrPrfxThresholdClear.  Default is 0.
        leaf prefix-threshold-clear {
            type router-bgp-prefix-threshold;

            description
                "Set percentage of maximum number of prefixes from peer at
                 which to issue prefix-threshold-clear notification.";

            user-ext:CLI-comm-help "Set percentage of maximum number of prefixes from peer at which to issue prefix-threshold-clear notification";
            user-ext:CLI-no-comm-help "Set percentage of maximum number of prefixes from peer at which to issue prefix-threshold-clear notification to default";
            user-ext:CLI-param-help "Set percentage of maximum number of prefixes";
        }

        // Low-level model info: Corresponds to bgpPeerConfigDropWarn and bgpPeergrConfigDropWarn.  Default is "warn".
        leaf session-drop-warning {
            type router-bgp-sess-drop-warning;

            description
                "This is used to determine whether
                the session is dropped or a warning is generated when the
                maximum number of prefixes set is exceeded.";

            user-ext:CLI-comm-help "Drop or warn session when max prefixes is exceeded";
            user-ext:CLI-no-comm-help "Generate warning when max prefixes is exceeded";
            user-ext:CLI-param-help "Whether the session is dropped or a warning is generated";
        }

        // Low-level model info: Corresponds to bgpPeerMaxPrfxHold and bgpPeergrMaxPrfxHold.  Default is 90.
        leaf max-prefix-hold {
            type router-bgp-max-prefix-hold;
            units "seconds";

            description
                "The time interval in seconds between when this BGP session
                is torn down due to the number of prefixes received from
                this peer exceeding the maximum in router-bgp-max-prefixes
                and when BGP attempts to reestablish the session.";

            user-ext:CLI-comm-help "Set maximum prefix hold time interval";
            user-ext:CLI-no-comm-help "Set maximum prefix hold time interval to default";
            user-ext:CLI-param-help "Set interval in seconds";
        }

        // Low-level model info: Corresponds to bgpPeerSlowPeer and bgpPeergrSlowPeers
        leaf slow-peer {
            type empty;
            description
                "Marks the peer as a slow peer.

                When update groups are in use, slow peers are kept
                separate from other peers to prevent backpressure from the
                slow peers slowing down updates sent to the other peers.";

            user-ext:CLI-comm-help "Mark the peer as slow";
            user-ext:CLI-no-comm-help "Mark the peer as not slow";
        }

        // Low-level model info: Corresponds to bgpPeerTtlSecurityMinTtl and bgpPeergrTtlSecurityMinTtl
        leaf ttl-security-min-ttl {
            type router-bgp-ttl-sec-min-ttl;
            description
                "The minimum TTL (for IPv4) or Hop Limit (for IPv6) that
                must be set in BGP packets received from this peer.  Packets
                received with a lower TTL are dropped.

                This field is used to enable the Generalized TTL Security
                Mechanism (GTSM), as defined in RFC 5082.

                Changes to this field will not take affect until the peer
                next activates.";

            user-ext:CLI-comm-help "Set minimum allowed TTL for received packets from peer";
            user-ext:CLI-no-comm-help "Do not specify minimum allowed TTL for received packets from peer";
            user-ext:CLI-param-help "Set minimum allowed TTL for received packets";
        }

        // Low-level model info: Corresponds to bgpPeerRemovePrivateAs and bgpPeergrRemovePrivateAs
        container remove-private-as {
            presence "Whether private AS numbers are removed from the AS path
                      before sending an update to this peer.  This is only
                      relevant for an EBGP peer.";

            description
                "The list of remove private AS number parameters.";

            user-ext:CLI-comm-help "Remove private AS numbers";
            user-ext:CLI-no-comm-help "Do not remove private AS numbers";

            leaf all {
                type boolean;
                default "false";

                user-ext:CLI-comm-help "Remove private AS numbers from AS-paths with public and private AS numbers";
                user-ext:CLI-no-comm-help "Do not remove private AS numbers from AS-paths with public and private AS numbers";
            }

            leaf replace-as {
                type boolean;
                default "false";

                user-ext:CLI-comm-help "Replace private AS numbers with local AS number";
                user-ext:CLI-no-comm-help "Do not replace private AS numbers with local AS number";
            }
        }

    } // neighbor-group-config

    grouping neighbor-only-config {

        // Low-level model info: Corresponds to bgpPeerLocalAddr(Type).
        leaf update-source {
          type interfaces:iface-ip-address-t;

          description
            "Source address for peering";

          user-ext:CLI-comm-help "Update source address for peering";
          user-ext:CLI-no-comm-help "Remove source address for peering";
          user-ext:CLI-param-help "Update source address";
        }

        // Low-level model info: Corresponds to bgpPeerAdminStatus.
        leaf shutdown {
          type empty;
          description
            "Administratively shut down this neighbor";

          user-ext:CLI-comm-help "Administratively shut down this neighbor";
          user-ext:CLI-no-comm-help "Re-enable the session to this neighbor";
        }

        // Low-level model info: Corresponds to bgpPeerConfigPeergr.
        leaf peer-group-name {
          type bgp-peer-group-name;
          description
            "The name of the peer group this neighbor belongs to.";

          user-ext:CLI-comm-help "Configure the peer group";
          user-ext:CLI-no-comm-help "Remove the configured peer group";
          user-ext:CLI-param-help "Configure the peer group";
        }

    } // neighbor-only-config

    grouping neighbor-address-family-config {

       container address-family {

           // Low-level model info: Corresponds to AMB_BGP_PEER_AFI_SAFI (bgpPeerAfiSafiTable).

           description
               "Configure address-family for BGP neighbor";

           user-ext:CLI-comm-help "Configure address-family for BGP neighbor";
           user-ext:CLI-no-comm-help "Configure address-family for BGP neighbor";

           container ipv4 {

               description
                   "Configure IPv4 address-family for BGP neighbor";

               user-ext:CLI-comm-help "Configure IPv4 address-family for BGP neighbor";
               user-ext:CLI-no-comm-help "Configure IPv4 address-family for BGP neighbor";

               // Low-level model info: Corresponds to bgpPeerAfiSafiDisable for all bgpPeerAfiSafiTable ipv4 rows.
               leaf disable {
                   type empty;

                   user-ext:CLI-comm-help "Disable IPv4 address-family for BGP neighbor";
                   user-ext:CLI-no-comm-help "Enable IPv4 address-family for BGP neighbor";
               }

               container unicast {
                   description
                       "Configure unicast IPv4 address-family for BGP neighbor";

                   user-ext:CLI-comm-help "Configure unicast IPv4 address-family for BGP neighbor";
                   user-ext:CLI-no-comm-help "Configure unicast IPv4 address-family for BGP neighbor";

                   uses router-bgp-neighbor-af-v4v6-parameters;
                   uses router-bgp-neighbor-af-unicast-parameters;

               }

           } // ipv4

           container ipv6 {

               description
                   "Configure IPv6 address-family for BGP neighbor";

               user-ext:CLI-comm-help "Configure IPv6 address-family for BGP neighbor";
               user-ext:CLI-no-comm-help "Configure IPv6 address-family for BGP neighbor";

               // Low-level model info: Corresponds to bgpPeerAfiSafiDisable for all bgpPeerAfiSafiTable ipv4 rows.
               leaf disable {
                   type empty;

                   user-ext:CLI-comm-help "Disable IPv6 address-family for BGP neighbor";
                   user-ext:CLI-no-comm-help "Enable IPv6 address-family for BGP neighbor";
               }

               container unicast {
                   description
                       "Configure unicast IPv6 address-family for BGP neighbor";

                   user-ext:CLI-comm-help "Configure unicast IPv6 address-family for BGP neighbor";
                   user-ext:CLI-no-comm-help "Configure unicast IPv6 address-family for BGP neighbor";

                   uses router-bgp-neighbor-af-v4v6-parameters;
                   uses router-bgp-neighbor-af-unicast-parameters;

               }

           } // ipv6

       } // address-family

    } // neighbor-address-family-config

    grouping neighbor-address-family-vpn-config {

      container l2vpn {

          description
              "Configure L2VPN address-family for BGP neighbor";

          user-ext:CLI-comm-help "Configure L2VPN address-family for BGP neighbor";
          user-ext:CLI-no-comm-help "Configure L2VPN address-family for BGP neighbor";

          container vpls {
              description
                  "Configure unicast L2VPN address-family for BGP neighbor";

              user-ext:CLI-comm-help "Configure unicast L2VPN address-family for BGP neighbor";
              user-ext:CLI-no-comm-help "Configure unicast L2VPN address-family for BGP neighbor";

              uses router-bgp-neighbor-af-l2vpn-parameters;
          }

          container evpn {
              description
                  "Configure EVPN address-family for BGP neighbor";

              user-ext:CLI-comm-help "Configure EVPN address-family for BGP neighbor";
              user-ext:CLI-no-comm-help "Configure EVPN address-family for BGP neighbor";

              uses router-bgp-neighbor-af-l2vpn-parameters;
          }

      } // l2vpn

      container vpnv4 {

          description
              "Configure VPNv4 address-family for BGP neighbor";

          user-ext:CLI-comm-help "Configure VPNv4 address-family for BGP neighbor";
          user-ext:CLI-no-comm-help "Configure VPNv4 address-family for BGP neighbor";

          // Low-level model info: Corresponds to bgpPeerAfiSafiDisable for all bgpPeerAfiSafiTable ipv4 rows.
          leaf enable {
              type empty;

              user-ext:CLI-comm-help "Enable VPNv4 address-family for BGP neighbor";
              user-ext:CLI-no-comm-help "Disable VPNv4 address-family for BGP neighbor";
          }

          container unicast {
              description
                  "Configure unicast VPNv4 address-family for BGP neighbor";

              user-ext:CLI-comm-help "Configure unicast VPNv4 address-family for BGP neighbor";
              user-ext:CLI-no-comm-help "Configure unicast VPNv4 address-family for BGP neighbor";

              uses router-bgp-neighbor-af-v4v6-parameters;
          }

      } // vpnv4

      container vpnv6 {

          description
              "Configure VPNv6 address-family for BGP neighbor";

          user-ext:CLI-comm-help "Configure VPNv6 address-family for BGP neighbor";
          user-ext:CLI-no-comm-help "Configure VPNv6 address-family for BGP neighbor";

          // Low-level model info: Corresponds to bgpPeerAfiSafiDisable for all bgpPeerAfiSafiTable ipv6 rows.
          leaf enable {
              type empty;

              user-ext:CLI-comm-help "Enable VPNv6 address-family for BGP neighbor";
              user-ext:CLI-no-comm-help "Disable VPNv6 address-family for BGP neighbor";
          }

          container unicast {
              description
                  "Configure unicast VPNv6 address-family for BGP neighbor";

              user-ext:CLI-comm-help "Configure unicast VPNv6 address-family for BGP neighbor";
              user-ext:CLI-no-comm-help "Configure unicast VPNv6 address-family for BGP neighbor";

              uses router-bgp-neighbor-af-v4v6-parameters;
          }

      } // vpnv6

    } // neighbor-address-family-vpn-config

    grouping peer-group-only-config {

        // Low-level model info:  Corresponds to bgpPeergrResetPeerOnCfgChange
        leaf reset-peer-on-cfg-change {
          type empty;
          description
            "Changes to peer-group configuration that require a peer session
             to be reset to take effect will cause affected peer sessions to be
             reset.";

          user-ext:CLI-comm-help "Peer-group config changes reset peer sessions when required";
          user-ext:CLI-no-comm-help "Peer-group config changes do not automatically reset peer sessions";
        }

    } // peer-group-only-config

    grouping neighbor-config {

        uses neighbor-group-config;
        uses neighbor-only-config;
        uses neighbor-address-family-config;

    } // neighbor-config

    grouping peer-group-config {

        uses neighbor-group-config;
        uses peer-group-only-config;

    } // peer-group-config

    grouping nlri-state {

      // Low-level model info: Corresponds to AMB_BGP_NLRI (bgpNlriTable) and AMB_BGP_NLRI_PREFIX (bgpNlriPrefixTable).

      description "BGP NLRI state.";

      leaf peer-or-afm {
        type bgp-peer-or-afm;
        description
          "Whether this route was learned from a BGP peer or an AFM.";
        config false;
      }

      leaf peer-afm-index {
        type uint32;
        description
          "The index of either the BGP peer or AFM this route was
          learned from.";
        config false;
      }

      leaf afi {
        type bgp-afi;
        description
          "The address family of the prefix for this NLRI.";
        config false;
      }

      leaf safi {
        type bgp-safi;
        description
          "The subsequent address family of the prefix for this NLRI.";
        config false;
      }

      leaf prefix {
        type interfaces:iface-ip-prefix-t;
        description
          "An address prefix in the Network Layer Reachability
          Information field.

          This field contains the full line format BGP NLRI omitting
          any NLRI length field.

          For SAFI 128 the NLRI includes the MPLS label and Route
          Distinguisher as well as the IPv4 or IPv6 address prefix.";
        config false;
      }

      uses nlri-common-state;

    } // nlri-state

    grouping nlri-l2vpn-vpls-state {

      // Low-level model info: Corresponds to AMB_BGP_NLRI (bgpNlriTable) and AMB_BGP_NLRI_PREFIX (bgpNlriPrefixTable).

      description "BGP NLRI state for L2VPN VPLS afi/safi.";

      leaf peer-or-afm {
        type bgp-peer-or-afm;
        description
          "Whether this route was learned from a BGP peer or an AFM.";
        config false;
      }

      leaf peer-afm-index {
        type uint32;
        description
          "The index of either the BGP peer or AFM this route was
          learned from.";
        config false;
      }

      leaf afi {
        type bgp-afi;
        description
          "The address family of the prefix for this NLRI.";
        config false;
      }

      leaf safi {
        type bgp-safi;
        description
          "The subsequent address family of the prefix for this NLRI.";
        config false;
      }

      leaf rd {
        type meta:bgp-route-distinguisher;
        description
          "The local VPLS route distinguisher";
        config false;
      }

      leaf ve-id {
        type l2vpn-ve-id-t;
        description
          "The local VPLS VE ID";
        config false;
      }

      leaf ve-blk {
        type uint32;
        description
          "The local VPLS VE block offset";
        config false;
      }

      leaf ve-blk-size {
        type uint32;
        description
          "The local VPLS VE block size";
        config false;
      }

      leaf label-base {
        type uint32;
        description
          "The local VPLS label base";
        config false;
      }

      uses nlri-common-state;

    } // nlri-l2vpn-vpls-state

    grouping nlri-l2vpn-evpn-state {

      // Low-level model info: Corresponds to AMB_BGP_NLRI (bgpNlriTable) and AMB_BGP_NLRI_PREFIX (bgpNlriPrefixTable).

      description "BGP NLRI state for L2VPN EVPN afi/safi.";

      leaf peer-or-afm {
        type bgp-peer-or-afm;
        description
          "Whether this route was learned from a BGP peer or an AFM.";
        config false;
      }

      leaf peer-afm-index {
        type uint32;
        description
          "The index of either the BGP peer or AFM this route was
          learned from.";
        config false;
      }

      leaf afi {
        type bgp-afi;
        description
          "The address family of the prefix for this NLRI.";
        config false;
      }

      leaf safi {
        type bgp-safi;
        description
          "The subsequent address family of the prefix for this NLRI.";
        config false;
      }

      uses l2vpn-evpn-common-state;

      uses nlri-common-state;

    } // nlri-l2vpn-evpn-state

    grouping nlri-l3vpn-state {

      // Low-level model info: Corresponds to AMB_BGP_NLRI (bgpNlriTable) and AMB_BGP_NLRI_PREFIX (bgpNlriPrefixTable).

      description "BGP NLRI state for l3vpn address family.";

      leaf peer-or-afm {
        type bgp-peer-or-afm;
        description
          "Whether this route was learned from a BGP peer or an AFM.";
        config false;
      }

      leaf peer-afm-index {
        type uint32;
        description
          "The index of either the BGP peer or AFM this route was
          learned from.";
        config false;
      }

      leaf afi {
        type bgp-afi;
        description
          "The address family of the prefix for this NLRI.";
        config false;
      }

      leaf safi {
        type bgp-safi;
        description
          "The subsequent address family of the prefix for this NLRI.";
        config false;
      }

      leaf label {
        type uint32;
        description
          "The local l3vpn label";
        config false;
      }

      leaf rd {
        type meta:bgp-route-distinguisher;
        description
          "The local l3vpn route distinguisher";
        config false;
      }

      leaf ip-prefix {
        type interfaces:iface-ip-prefix-t;
        description
          "The local l3vpn ip prefix address";
        config false;
      }

      uses nlri-common-state;

    } // nlri-l3vpn-state

    grouping adj-rib-out-common-indices {

      // Low-level model info: Corresponds to AMB_BGP_ARO (bgpAdjRibOutTable).

      description "BGP Adj-RIB-Out common indices.";

      // Low-level model info: Corresponds to bgpPeerIndex.
      leaf peer-index {
        type uint32;
        description
          "The peer index.";
      }

      // Low-level model info: Corresponds to bgpAdjRibOutAfi.
      leaf afi {
        type bgp-afi;
        description
          "The address family of the prefix for this Adj-RIB Out
          route.";
      }

      // Low-level model info: Corresponds to bgpAdjRibOutSafi.
      leaf safi {
        type bgp-safi;
        description
          "The subsequent address family of the prefix for
          this Adj-RIB Out route.";
      }

      // Low-level model info: Corresponds to bgpAdjRibOutPathId.
      leaf path-id {
        type uint32;
        description
          "The path ID for this Adj-RIB Out route.

          If BGP additional path send capability was negotiated with
          the peer for this AFI/SAFI then this is the path ID sent for
          this Adj-RIB Out route, otherwise it is zero.";
      }

    } // adj-rib-out-common-indices

    grouping community-lists {

      list community {

          description
              "BGP communities advertised on a route";

          config false;

          leaf community {
              type binary;

              description
                  "BGP community in line format (4 bytes).";

              config false;
          }
      }

      list extended-community {

          description
              "BGP extended communities advertised on a route";

          config false;

          leaf extended-community {
              type binary;

              description
                  "BGP extended community in line format (8 bytes).";

              config false;
          }
      }

    } // community-lists

    grouping adj-rib-out-common-state {

      // Low-level model info: Corresponds to AMB_BGP_ARO (bgpAdjRibOutTable).

      description "BGP Adj-RIB-Out common state.";

      // Low-level model info: Corresponds to bgpAdjRibOutAdvertStatus.
      leaf advertisement-status {
        type bgp-aro-advert-status-t;
        description
          "This object indicates the current state of
          advertisement of the route to the peer.

          A value of advertised indicates that the route has
          been advertised to the peer.

          A value of suppressed indicates that the route is
          not currently advertised to the peer, but will be
          advertised when a minimum advertisement interval timer
          expires.

          A value of pendingWithdrawal indicates that the
          route is currently advertised to the peer, but will be
          withdrawn when the timer expires.

          A value of withdrawn indicates that the route has
          been withdrawn from the peer, and this entry will be
          removed from the Adj-RIB-Out on the expiry of the
          timer.";
        config false;
      }

      // Low-level model info: Corresponds to bgpAdjRibOutLocalAggrType.
      leaf local-aggregation-type {
        type bgp-aro-aggr-status-t;
        description
          "This object indicates any aggregation processing that
          has been applied to this Adj-RIB-Out route.

          A value of no-aggregation indicates that this route
          does not aggregate any other routes, and is not
          aggregated by any route.

          A value of aggregate-route indicates that this route
          is a locally configured aggregating route.

          A value of unsuppressed-aggregated-route indicates that this
          route has been aggregated by a locally configured
          aggregate route and is not suppressed - the route is
          still explicitly advertised to the peer.

          A value of suppressed-aggregated-route indicates that
          this route has been aggregated by a locally configured
          aggregate route and is flagged such that it should not be
          advertised along with the aggregate route.  Typically such
          routes are not installed on an Adj-RIB-Out.  If however
          the aggregate route itself is not permitted to be added to
          the Adj-RIB-Out then suppressed routes are advertised if
          they themselves are permitted by policy.";
        config false;
      }

      // Low-level model info: Corresponds to bgpAdjRibOutAsSize.
      leaf as-size {
        type bgp-as-size-t;
        description
          "Whether the as-path-string object contains
          two or four byte AS numbers.";
        config false;
      }

      // Low-level model info: Corresponds to bgpAdjRibOutASPathStr.
      leaf as-path-string {
        type string;
        description
          "This is a string containing the autonomous system path
          sent to this peer in the AS_PATH attribute for this
          Adj-RIB-Out route.  If this path contains four-octet AS
          numbers and the peer does not support these a two-octet
          AS_PATH attribute and associated AS4_PATH attribute will be
          advertised to the peer instead as detailed in RFC 4893.
          However, this field will report the four-octet AS_PATH that
          would  have been advertised to the peer if it had supported
          four-byte AS numbers.  Two-octet AS numbers appear as
          four-octet numbers by adding two bytes of zero padding.  The
          format of the string is simply the AS_PATH attribute.  This
          can be converted to a more readable format by the management
          agent.";
        config false;
      }

      // Low-level model info: Corresponds to bgpAdjRibOutOrigin.
      leaf origin {
        type bgp-origin-codes;
        description
          "The ultimate origin of the path information.";
        config false;
      }

      // Low-level model info: Corresponds to bgpAdjRibOutNextHop.
      leaf next-hop {
        type interfaces:iface-ip-address-t;
        description
          "The next hop address transmitted in the UPDATE packet.

          Note that for RFC 2545 style double nexthops, this object
          will always contain the global scope nexthop.
          link-local-next-hop will contain the link local
          scope nexthop, if it is present.";
        config false;
      }

      // Low-level model info: Corresponds to bgpAdjRibOutMultiExitDisc.
      leaf multi-exit-discrminator {
        type uint32;
        description
          "This metric is used to discriminate between multiple
          exit points to an adjacent autonomous system.";
        config false;
      }

      // Low-level model info: Corresponds to bgpAdjRibOutLocalPref.
      leaf local-preference {
        type uint32;
        description
          "The local preference for this Adj-RIB-Out route, as
          transmitted in the UPDATE message sent to the peer.";
        config false;
      }

      // Low-level model info: Corresponds to bgpAdjRibOutAtomicAggregate.
      leaf atomic-aggregate {
        type bgp-path-attr-atomic-agg;
        description
          "When this object is set to present, the
          ATOMIC_AGGREGATE Path Attribute was included in the
          UPDATE sent to the peer for this Adj-RIB-Out route.";
        config false;
      }

      // Low-level model info: Corresponds to bgpAdjRibOutAggregatorAS.
      leaf aggregator-as {
        type uint32;
        description
          "The AS number of the last BGP speaker that performed
          route aggregation.";
        config false;
      }

      // Low-level model info: Corresponds to bgpAdjRibOutAggregatorAddr.
      leaf aggregator-address {
        type interfaces:iface-ipv4-address-allow-zero-t;
        description
          "The IP address of the last BGP speaker that performed
          route aggregation.  A value of 0.0.0.0 indicates that
          this attribute was not included in the UPDATE message
          sent to the peer.";
        config false;
      }

      // Low-level model info: Corresponds to bgpAdjRibOutOrigId.
      leaf originator-id {
        type meta:router-id;
        description
          "The Originator-ID identifying the router that initially
          advertised this destination to a Route Reflector.  A
          value of 0.0.0.0 indicates the absence of this
          attribute.";
        config false;
      }

      // Low-level model info: Corresponds to bgpAdjRibOutAsLimAs.
      leaf as-path-limit-as {
        type uint32;
        description
          "If non-zero this is the number of the AS that attached the
          AS_PATHLIMIT attribute.";
        config false;
      }

      // Low-level model info: Corresponds to bgpAdjRibOutAsLimUpper.
      leaf as-path-limit-upper {
        type uint32;
        description
          "The upper bound on the number of ASes in the AS_PATH
          attribute after which the route will be filtered.  Only
          valid if as-path-limit-as is non-zero.";
        config false;
      }

      // Low-level model info: Corresponds to bgpAdjRibOutUserData.
      leaf user-data {
        type bgp-user-data-t;
        description
          "User data for this BGP ARO entry.";
        config false;
      }

      // Low-level model info: Corresponds to bgpAdjRibOutEcmp.
      leaf ecmp {
        type boolean;
        description
          "Whether or not this route was installed into the
          Forwarding Table as an ECMP route.";
        config false;
      }

      // Low-level model info: Corresponds to bgpAdjRibOutStale.
      leaf stale {
        type boolean;
        description
          "Whether or not this route was last sent by the peer before
          BGP detected that the peer was restarting.  If the route is
          not re-advertised by the peer before the restart completes,
          BGP will remove the route from its database.  This flag is
          set to 'false' if the peer is not restarting, or if the
          route has been advertised by the peer since the restart.";
        config false;
      }

      // Low-level model info: Corresponds to bgpAdjRibOutLinkLocalNextHop.
      leaf link-local-next-hop {
        type interfaces:iface-ip-address-t;
        description
          "The IPv6 link-local address sent in the UPDATE message.
          This object is only valid if an RFC 2545 style double
          nexthop was sent in the UPDATE.";
        config false;
      }

      // Low-level model info: Corresponds to bgpAdjRibOutMEDPrsnt.
      leaf multi-exit-discriminator-set {
        type boolean;
        description
          "If true, then the route has an associated MED attribute,
          whose value is given in multi-exit-discriminator.  If false,
          the route has no MED attribute.";
        config false;
      }

      // Low-level model info: Corresponds to bgpAdjRibOutRemoteAddr(Type).
      leaf peer-address {
        type interfaces:iface-ip-address-t;
        description
          "The address of the BGP peer.";
        config false;
      }

      // Low-level model info: Corresponds to bgpAdjRibOutRemoteAddrScopeId
      leaf peer-scope-id {
        type uint32;
        description
          "The scope ID of the BGP peer address.

          The scope ID is required if the address is an IPv6
          link-local address.  Otherwise, this field will be zero.";
        config false;
      }

      leaf peer-interface {
        type interfaces:iface-name;
        description
          "The local interface used to reach the BGP peer.";
        config false;
      }

      uses community-lists;

    } // adj-rib-out-common-state

    grouping adj-rib-out-ip-state {

      // Low-level model info: Corresponds to AMB_BGP_ARO (bgpAdjRibOutTable).

      description "BGP Adj-RIB-Out state for IP address family.";

      uses adj-rib-out-common-indices;

      // Low-level model info: Corresponds to bgpAdjRibOutPrfx(Len).
      leaf prefix {
        type interfaces:iface-ip-prefix-t;
        description
          "An address prefix in the Network Layer Reachability
          Information field for this Adj-RIB Out route.

          This field contains the full line format BGP NLRI omitting
          any NLRI length field.

          For SAFI 128 the NLRI includes the MPLS label and Route
          Distinguisher as well as the IPv4 or IPv6 address prefix.";
        config false;
      }

      uses adj-rib-out-common-state;

    } // adj-rib-out-ip-state

    grouping adj-rib-out-l2vpn-vpls-state {

      // Low-level model info: Corresponds to AMB_BGP_ARO (bgpAdjRibOutTable).

      description "BGP Adj-RIB-Out state for L2VPN VPLS afi/safi.";

      uses adj-rib-out-common-indices;

      // Low-level model info: The next 5 leafs correspond to bgpAdjRibOutPrfx(Len).
      leaf rd {
        type meta:bgp-route-distinguisher;
        description
          "The local VPLS route distinguisher";
        config false;
      }

      leaf ve-id {
        type l2vpn-ve-id-t;
        description
          "The local VPLS VE ID";
        config false;
      }

      leaf ve-blk {
        type uint32;
        description
          "The local VPLS VE block offset";
        config false;
      }

      leaf ve-blk-size {
        type uint32;
        description
          "The local VPLS VE block size";
        config false;
      }

      leaf label-base {
        type uint32;
        description
          "The local VPLS label base";
        config false;
      }

      uses adj-rib-out-common-state;

    } // adj-rib-out-l2vpn-vpls-state

    grouping adj-rib-out-l2vpn-evpn-state {

      // Low-level model info: Corresponds to AMB_BGP_ARO (bgpAdjRibOutTable).

      description "BGP Adj-RIB-Out state for L2VPN EVPN afi/safi.";

      uses adj-rib-out-common-indices;

      uses l2vpn-evpn-common-state;

      uses adj-rib-out-common-state;

    } // adj-rib-out-l2vpn-evpn-state


    grouping adj-rib-out-l3vpn-state {

      // Low-level model info: Corresponds to AMB_BGP_ARO (bgpAdjRibOutTable).

      description "BGP Adj-RIB-Out state for L3VPN address family.";

      uses adj-rib-out-common-indices;

      // Low-level model info: The next 3 leafs correspond to bgpAdjRibOutPrfx(Len).
      leaf label {
        type uint32;
        description
          "The local l3vpn label";
        config false;
      }

      leaf rd {
        type meta:bgp-route-distinguisher;
        description
          "The local l3vpn route distinguisher";
        config false;
      }

      leaf ip-prefix {
        type interfaces:iface-ip-prefix-t;
        description
          "The local l3vpn ip prefix address";
        config false;
      }

      uses adj-rib-out-common-state;

    } // adj-rib-out-l3vpn-state

    grouping router-bgp-advertise {

        // Low-level model info: Corresponds to AMB_BGP_RM_AFI_SAFI (bgpRmAfiSafiTable).

        // Low-level model info: Corresponds to bgpRmAfiSafiAdvertiseInactive.  Note that the default is flipped.
        container advertise {
            description
                "Configure BGP routing advertise";

            user-ext:CLI-comm-help "Configure BGP routing advertise";
            user-ext:CLI-no-comm-help "Configure BGP routing advertise";

            leaf inactive {
                type empty;

                description
                    "Enable BGP advertise inactive";

                user-ext:CLI-comm-help "Enable BGP advertise inactive";
                user-ext:CLI-no-comm-help "Disable BGP advertise inactive";
            }
        }

    } // router-bgp-advertise

    grouping router-bgp-additional-paths {

        // Low-level model info: Corresponds to AMB_BGP_RM_AFI_SAFI (bgpRmAfiSafiTable).

        // Low-level model info: Corresponds to bgpRmAfiSafiAddPathBestN (MIB does not have separate eBGP and iBGP settings so use single leaf).
        leaf maximum-paths {
            type router-bgp-maximum-paths;

            default 1;

            description
                "Limit of best paths to calculate";

            user-ext:CLI-comm-help "Set limit of best paths to calculate ";
            user-ext:CLI-no-comm-help "Set limit of best paths to calculate to the default";
            user-ext:CLI-param-help "Set calculation limit";
        }

        // Low-level model info: Corresponds to bgpRmAfiSafiAddPathCapCfg.
        leaf additional-paths {
            type bgp-add-path-caps-router;

            default "disable";

            description
                "The default BGP additional path capability for I-BGP
                sessions.

                This can be overridden at the BGP peer AFI/SAFI or peer
                group AFI/SAFI level.

                BGP additional path capability is never enabled by default
                for E-BGP sessions - instead it should be configured for
                specific E-BGP peers at the peer AFI/SAFI or peer group
                AFI/SAFI level.

                This field applies to all configured I-BGP peers including
                confederation peers in different member ASs.

                Valid values are:
                -  disable
                Disable sending and receiving additional BGP paths
                -  receive
                Receive but do not send additional BGP paths
                -  send
                Send but do not receive additional BGP paths
                -  both
                Send and receive additional BGP paths.

                Any update to this leaf will take effect the next time
                that the peer session reactivates.";

            user-ext:CLI-comm-help "Set additional path support";
            user-ext:CLI-no-comm-help "Disable additional path support";
            user-ext:CLI-param-help "Set additional path support";
        }

        // Low-level model info: Corresponds to bgpRmAfiSafiInstallBestNPaths.
        leaf best-n-paths {
            type router-bgp-best-n-paths;

            default 1;

            description
                "Number of paths to install for BGP Prefix Independent
                Convergence.";

            user-ext:CLI-comm-help "Set limit of best paths to install";
            user-ext:CLI-no-comm-help "Set limit of best paths to install to the default";
            user-ext:CLI-param-help "Set install limit";
        }
    } // router-bgp-additional-paths

    grouping router-bgp-martian-check {

        // Low-level model info: Corresponds to AMB_BGP_RM_AFI_SAFI (bgpRmAfiSafiTable).

        // Low-level model info: Corresponds to bgpRmAfiSafiCheckMartians.  Note that the default is flipped (yang enabled, MIB disabled).
        container martian-check {
            description
                "Martian-check switch";

            user-ext:CLI-comm-help "Configure martian check";
            user-ext:CLI-no-comm-help "Configure martian check";

            leaf disable {
                type empty;

                user-ext:CLI-comm-help "Disable martian check";
                user-ext:CLI-no-comm-help "Enable martian check";
            }
        }

    } // router-bgp-martian-check

    grouping router-bgp-max-ecmp-paths {

        // Low-level model info: Corresponds to bgpRmEntMaxIBgpEcmpRoutes.  Default is changed

        leaf max-ibgp-ecmp-paths {

            type router-bgp-max-ecmp-paths;

            default 32;

            description
                "Maximum number of ECMP next hops for IBGP routes";

            user-ext:CLI-comm-help "Configure max number of ECMP paths for IBGP routes";
            user-ext:CLI-no-comm-help "Configure max number of ECMP paths for IBGP routes";
            user-ext:CLI-param-help "Configure max number of ECMP paths for IBGP routes";
        }

        // Low-level model info: Corresponds to bgpRmEntMaxEBgpEcmpRoutes.  Default is changed.

        leaf max-ebgp-ecmp-paths {

            type router-bgp-max-ecmp-paths;

            default 32;

            description
                "Maximum number of ECMP next hops for EBGP routes";

            user-ext:CLI-comm-help "Configure max number of ECMP paths for EBGP routes";
            user-ext:CLI-no-comm-help "Configure max number of ECMP paths for EBGP routes";
            user-ext:CLI-param-help "Configure max number of ECMP paths for EBGP routes";
        }

    } // router-bgp-max-ecmp-paths

    grouping router-bgp-max-afi-safi-ecmp-paths {

        // Low-level model info: Corresponds to bgpRmAfiSafiMaxIBgpEcmpRoutes.  Default is changed

        leaf max-ibgp-ecmp-paths {

            type router-bgp-max-afi-safi-ecmp-paths;

            default 0;

            description
                "Maximum number of ECMP next hops for IBGP routes";

            user-ext:CLI-comm-help "Configure max number of ECMP paths for IBGP routes";
            user-ext:CLI-no-comm-help "Configure max number of ECMP paths for IBGP routes";
            user-ext:CLI-param-help "Configure max number of ECMP paths for IBGP routes";
        }

        // Low-level model info: Corresponds to bgpRmAfiSafiMaxEBgpEcmpRoutes.  Default is changed
        leaf max-ebgp-ecmp-paths {

            type router-bgp-max-afi-safi-ecmp-paths;

            default 0;

            description
                "Maximum number of ECMP next hops for EBGP routes";

            user-ext:CLI-comm-help "Configure max number of ECMP paths for EBGP routes";
            user-ext:CLI-no-comm-help "Configure max number of ECMP paths for EBGP routes";
            user-ext:CLI-param-help "Configure max number of ECMP paths for EBGP routes";
        }

    } // router-bgp-max-afi-safi-ecmp-paths

    grouping router-bgp-dampening {

        // Low-level model info: Corresponds to AMB_BGP_FLAP_CONFIG (bgpFlapConfigTable) per global afi-safi.

        container dampening {

            // Low-level model info: Set both bgpFlapConfigTmaxok and bgpFlapConfigTmaxng to 2701 (seconds).
            //                       This is just large enough to be greater than the maximum possible half-life value using the range below.

            presence "Enable route flap dampening";

            description
                "The list of Route Flap Dampening configuration parameters.";

            user-ext:CLI-comm-help "Enable route flap dampening";
            user-ext:CLI-no-comm-help "Disable route flap dampening";

            // Check that the suppress is at least the reuse.  The default value for suppress is 2000; the default value for reuse is 750.
            must "((not(suppress)) and (not(reuse))) or " +
                 "((not(suppress)) and (2000 >= reuse)) or " +
                 "((not(reuse)) and (suppress >= 750)) or " +
                 "(number(suppress) >= number(reuse))" {
              error-message "BGP dampening suppress value must be at least reuse value";
            }

            // Low-level model info: Corresponds to bgpRmAfiSafiFlapConfigMap.
            leaf route-map {
                type meta:route-map-name;
                description
                    "The name of the route map to use for route flap
                    configuration for this AFI/SAFI.";

                user-ext:CLI-comm-help "Apply route map to route flap configuration";
                user-ext:CLI-no-comm-help "Remove route flap route map";
                user-ext:CLI-param-help "Apply route map to route flap configuration";

            }

            // Low-level model info: Corresponds to both bgpFlapConfigDecayok and bgpFlapConfigDecayng.
            // Low-level model info: Note that the yang field uses minutes while the MIB field uses seconds.
            leaf half-life {
                type bgp-half-life-t;
                units "minutes";
                default 15;
                description
                    "The decay half life of the stability figure.";

                user-ext:CLI-comm-help "Dampening penalty half-life";
                user-ext:CLI-no-comm-help "Dampening penalty half-life";
                user-ext:CLI-param-help "Time in minutes after which a penalty is decreased";
            }

            // Low-level model info: Corresponds to bgpFlapConfigReuse.
            leaf reuse {
                type bgp-flap-threshold-t;
                default 750;
                description
                    "The reuse threshold expressed as a number of route
                    withdrawals.  Below this level the route will be reused.
                    The scale used is 100 times that used in RFC2439 so the
                    suggested value is 50, not 0.5 as suggested in the RFC.";

                user-ext:CLI-comm-help "Penalty before reusing suppressed route";
                user-ext:CLI-no-comm-help "Penalty before reusing suppressed route";
                user-ext:CLI-param-help "Reuse threshold as a number of route withdrawals";

            }

            // Low-level model info: Corresponds to bgpFlapConfigCut.
            leaf suppress {
                type bgp-flap-threshold-t;
                default 2000;
                description
                    "The cutoff threshold expressed as a number of route
                    withdrawals.  Above this level, the route will be
                    suppressed.  This value must be greater than or equal to
                    reuse.  The scale used is 100 times that used in
                    RFC2439 so the suggested value is 125, not 1.25 as
                    suggested in the RFC.";

                user-ext:CLI-comm-help "Dampening penalty to start suppressing a route";
                user-ext:CLI-no-comm-help "Dampening penalty to start suppressing a route";
                user-ext:CLI-param-help "Suppress threshold as a number of route withdrawals";
            }

            // Low-level model info: Corresponds to bgpFlapConfigThold.
            // Low-level model info: Note that the yang field uses minutes while the MIB field uses seconds.
            leaf max-suppress-time {
                type bgp-max-suppress-time-t;
                units "minutes";
                default 60;
                description
                    "The maximum time a route can be suppressed for (held).";

                user-ext:CLI-comm-help "Maximum dampening penalty";
                user-ext:CLI-no-comm-help "Maximum dampening penalty";
                user-ext:CLI-param-help "Maximum time in minutes that a route can be suppressed";
            }

        } // dampening

    } // router-bgp-dampening

    grouping router-bgp-af-vpn-common-parameters {

        // Low-level model info: Corresponds to AMB_BGP_RM_AFI_SAFI (bgpRmAfiSafiTable).

    }

    grouping router-bgp-af-l2vpn-common-parameters {

        // Low-level model info: Corresponds to AMB_BGP_RM_AFI_SAFI (bgpRmAfiSafiTable).

        uses router-bgp-af-vpn-common-parameters;

    }

    grouping router-bgp-af-common-parameters {

        // Low-level model info: Corresponds to AMB_BGP_RM_AFI_SAFI (bgpRmAfiSafiTable).

        uses router-bgp-af-l2vpn-common-parameters;
        uses router-bgp-additional-paths;
        uses router-bgp-dampening;

    }

    grouping router-bgp-af-aggr-addr-parameters {

        // Low-level model info: Corresponds to bgpAggrOptions (none, asSet and summaryAsSet).
        leaf as-set {
            type empty;

            description
                "AS-SET flag";

            user-ext:CLI-comm-help "Enable AS-SET";
            user-ext:CLI-no-comm-help "Disable AS-SET";
        }

        // Low-level model info: Corresponds to bgpAggrOptions (none, summary and summaryAsSet).
        leaf summary-only {
            type empty;

            description
                "Enable summary-only mode";

            user-ext:CLI-comm-help "Enable summary only mode (suppress inner path routes)";
            user-ext:CLI-no-comm-help "Disable summary only mode";
        }

        // Low-level model info: Corresponds to bgpAggrSuppressMap.
        leaf suppress-map {
            when "not(../summary-only)";
            type meta:route-map-name;

            description
                "The Route Map used to suppress routes.  The
                 match clauses of this route map are used to selectively
                 suppress more specific routes from being advertised.";

            user-ext:CLI-comm-help "Add route map to suppress routes";
            user-ext:CLI-no-comm-help "Do not use route map to suppress routes";
        }

        // Low-level model info: Corresponds to bgpAggrAdvertiseMap.
        leaf advertise-map {
            type meta:route-map-name;

            description
                "The Route Map used to advertise routes.  The
                 match clauses of this route map are used to select routes
                 which, although they match the aggregate address, should
                 not be aggregated.";

            user-ext:CLI-comm-help "Add route map to advertise routes";
            user-ext:CLI-no-comm-help "Do not use route map to advertise routes";
        }

        // Low-level model info: Corresponds to bgpAggrAttributeMap.
        leaf attribute-map {
            type meta:route-map-name;

            description
                "The Route Map used to set aggregated routes attributes.
                 The set clauses of this route map are used to set path
                 attributes of the aggregated route.";

            user-ext:CLI-comm-help "Add route map to set route attributes";
            user-ext:CLI-no-comm-help "Do not use route map to set route attributes";
        }

    } // router-bgp-af-aggr-addr-parameters

    grouping router-bgp-af-ipv4-parameters {

        // Low-level model info: Corresponds to AMB_BGP_RM_AFI_SAFI (bgpRmAfiSafiTable).

        list aggregate-address {

            // Low-level model info: Corresponds to AMB_BGP_AGGREGATE (bgpAggregateTable).

            description
                "BGP IPv4 aggregate-address";

            user-ext:CLI-comm-help "Configure aggregate address";
            user-ext:CLI-no-comm-help "Remove aggregate address";

            key "aa-prefix";

            // Low-level model info: Corresponds to bgpAggrPrefix and bgpAggrPrefixLength.
            leaf aa-prefix {
                type meta:ipv4-short-prefix;

                description
                    "Aggregate address";

                user-ext:CLI-param-help "IPv4 prefix";
            }

            uses router-bgp-af-aggr-addr-parameters;

        }

    } // router-bgp-af-ipv4-parameters

    grouping router-bgp-af-ipv6-parameters {

        // Low-level model info: Corresponds to AMB_BGP_RM_AFI_SAFI (bgpRmAfiSafiTable).

        list aggregate-address {

            // Low-level model info: Corresponds to AMB_BGP_AGGREGATE (bgpAggregateTable).

            description
                "BGP IPv6 aggregate-address";

            user-ext:CLI-comm-help "Configure aggregate address";
            user-ext:CLI-no-comm-help "Remove aggregate address";

            key "aa-prefix";

            // Low-level model info: Corresponds to bgpAggrPrefix and bgpAggrPrefixLength.
            leaf aa-prefix {
                type meta:ipv6-short-prefix;

                description
                    "Aggregate address";

                user-ext:CLI-param-help "IPv6 prefix";
            }

            uses router-bgp-af-aggr-addr-parameters;

        }

    } // router-bgp-af-ipv6-parameters

    grouping router-bgp-af-unicast-parameters {

        // Low-level model info: Corresponds to AMB_BGP_RM_AFI_SAFI (bgpRmAfiSafiTable).

        uses router-bgp-martian-check;
        uses router-bgp-max-afi-safi-ecmp-paths;
        uses router-bgp-advertise;

    } // router-bgp-af-unicast-parameters

    grouping router-bgp-neighbor-af-common-parameters {

        // Low-level model info: Corresponds to AMB_BGP_PEER_AFI_SAFI (bgpPeerAfiSafiTable).

        // Low-level model info: Corresponds to bgpPeerAfiSafiAllowLocalAs.  Default is 0.
        leaf allowas-in {
            type router-bgp-allow-local-as;

            description
                "Allow to receive announce from origin AS with next AS count";

            user-ext:CLI-comm-help "Set count of local AS allowed in sent route AS_PATH";
            user-ext:CLI-no-comm-help "Set default count of local AS in sent route AS_PATH";
            user-ext:CLI-param-help "Set count of local AS allowed in sent route AS_PATH attr";
        }

        // Low-level model info: Corresponds to bgpPeerAfiSafiNxtHopSlf.
        leaf next-hop-self {
            type router-bgp-next-hop-self;

            default false;

            description
                "Set the nexthop calculation action on this neighbor";

            user-ext:CLI-comm-help "Set the nexthop calculation action on this neighbor";
            user-ext:CLI-no-comm-help "Set the nexthop calculation action on this neighbor to default";
            user-ext:CLI-param-help "Set the nexthop calcuation on this neighbor";
        }

        container soft-reconfiguration {
            description
                "Enable soft-reconfiguration for this neighbor";

            user-ext:CLI-comm-help "Enable soft-reconfiguration for this neighbor";
            user-ext:CLI-no-comm-help "Disable soft-reconfiguration for this neighbor";

            // Low-level model info: Corresponds to bgpPeerAfiSafiSoftResetStore.
            leaf inbound {

                type empty;

                description
                    "Enable inbound soft-reconfiguration for this neighbor";

                user-ext:CLI-comm-help "Enable inbound soft-reconfiguration for this neighbor";
                user-ext:CLI-no-comm-help "Disable inbound soft-reconfiguration for this neighbor";
            }
        }

        container route-map {

          description
            "Configure the route maps.";

          user-ext:CLI-comm-help "Configure route maps";
          user-ext:CLI-no-comm-help "Configure route maps";

          // Low-level model info: Corresponds to bgpPeerAfiSafiImportMap.
          // Set to the bgpRouteMapIndex generated for the route map name.
          leaf in {
              type meta:route-map-name;
              description
                  "The name of the route map to use for route imports from
                  the peer for this AFI/SAFI.";

              user-ext:CLI-comm-help "Apply route map to inbound routes from peer";
              user-ext:CLI-no-comm-help "Remove inbound routes route map";
              user-ext:CLI-param-help "Apply route map to inbound routes from peer";
          }

          // Low-level model info: Corresponds to bgpPeerAfiSafiExportMap.
          // Set to the bgpRouteMapIndex generated for the route map name.
          leaf out {
              type meta:route-map-name;
              description
                  "The name of the route map to use for route exports to the
                  peer for this AFI/SAFI.";

              user-ext:CLI-comm-help "Apply route map to outbound routes to peer";
              user-ext:CLI-no-comm-help "Remove outbound routes route map";
              user-ext:CLI-param-help "Apply route map to outbound routes to peer";
          }

        } // route-map

        // Low-level model info: Corresponds to bgpPeerAfiSafiPreserveNh and bgpPeergrAfiSafiPreserveNh.
        leaf preserve-next-hop {
            type empty;

            description
                "This field is used to preserve the BGP next hop when
                forwarding routes to this eBGP peer.

                By default, the next hop of a route is preserved when
                advertising the route to an iBGP peer, but is updated when
                advertising the route to an eBGP peer.  Enabling this feature
                over-rides this behavior and preserves the next hop when routes
                are advertised to this eBGP peer.";

            user-ext:CLI-comm-help "Enable preserving next hop when sending routes to eBGP peers";
            user-ext:CLI-no-comm-help "Disable preserving next hop when sending routes to eBGP peers";
        }

        // Low-level model info: Corresponds to bgpPeerAfiSafiAcceptRemoteNextHop and bgpPeergrAfiSafiAcceptRemoteNextHop.
        leaf accept-remote-next-hop {
            type empty;

            description
                "Allow routes from directly-connected eBGP peer to use a next-hop not in a shared subnet.";

            user-ext:CLI-comm-help "Allow routes from directly-connected eBGP peer to use a next-hop not in a shared subnet.";
            user-ext:CLI-no-comm-help "Do not Allow routes from directly-connected eBGP peer to use a next-hop not in a shared subnet.";
        }

        // Low-level model info: Corresponds to bgpPeerAfiSafiDisableSndLpDetect and bgpPeergrAfiSafiDisSndLpDetect.
        leaf advertise-peer-as  {
            type empty;

            description
                "Disable sender-side detection of AS path loops when advertising routes to this peer";

            user-ext:CLI-comm-help "Disable sender-side loop detection for this session";
            user-ext:CLI-no-comm-help "Enable sender-side loop detection for this session";
        }

    } // router-bgp-neighbor-af-common-parameters

    grouping router-bgp-neighbor-af-v4v6-parameters {

        // Low-level model info: Corresponds to AMB_BGP_PEER_AFI_SAFI (bgpPeerAfiSafiTable).

        uses router-bgp-neighbor-af-common-parameters;

        // Low-level model info: Corresponds to a row in AMB_BGP_PEER_ORF_CAP (bgpPeerOrfCapabilityTable)
        // Low-level model info: If prefix leaf is not none (the default), then create row with bgpPeerOrfCapabilityOrfType = "prefix".
        // Low-level model info: Set bgpPeerOrfCapabilitySendReceive based on the value of prefix leaf (enumeration values are different).
        container capability {

            description
                "Configure capability announcement";

            user-ext:CLI-comm-help "Configure advertised capabilities";
            user-ext:CLI-no-comm-help "Configure advertised capabilities";

            container orf {

                description
                    "Configure ORF capability announcement";

                user-ext:CLI-comm-help "Configure ORF capability announcement";
                user-ext:CLI-no-comm-help "Configure ORF capability announcement";

                leaf prefix {
                    type router-bgp-orf-prefix;

                    default none;

                    description
                        "ORF capability";

                    user-ext:CLI-comm-help "Set ORF capability prefix";
                    user-ext:CLI-no-comm-help "Set ORF capability prefix to default";
                    user-ext:CLI-param-help "Set ORF capability prefix";
                }

            } // orf

        } // capability

    } // router-bgp-neighbor-af-v4v6-parameters

    grouping router-bgp-neighbor-af-l2vpn-parameters {

        // Low-level model info: Corresponds to AMB_BGP_PEER_AFI_SAFI (bgpPeerAfiSafiTable).

        // Low-level model info: Corresponds to bgpPeerAfiSafiDisable.
        leaf enable {
            type empty;

            user-ext:CLI-comm-help "Enable address-family for BGP neighbor";
            user-ext:CLI-no-comm-help "Disable address-family for BGP neighbor";
        }

        uses router-bgp-neighbor-af-common-parameters;

    } // router-bgp-neighbor-af-l2vpn-parameters

    grouping router-bgp-neighbor-af-unicast-parameters {

        container prefix-list {
          description
            "Configure the IP prefix lists.";

          user-ext:CLI-comm-help "Configure prefix lists";
          user-ext:CLI-no-comm-help "Configure prefix lists";

          // Low-level model info: Corresponds to bgpPeer(gr)AfiSafiImportIpAallPre.
          // Set to the aallPreAccessListListIndex generated for the IP prefix name.
          leaf in {
              type meta:ip-prefix-name;
              description
                  "The name of the IP prefix access list to use for
                  route imports from the peer for this AFI/SAFI.

                  Route import policy applies any import IP prefix access
                  list before any import route map, and the route must be
                  permitted by both to be imported.  The import route map
                  can apply its own prefix lists in addition to any import
                  IP prefix access list.

                  If the peer is a member of a peer group then BGP uses
                  peer import policy in preference to peer group policy.";

              user-ext:CLI-comm-help "Apply prefix list to inbound routes from peer";
              user-ext:CLI-no-comm-help "Remove inbound routes prefix list";
              user-ext:CLI-param-help "Apply prefix list to inbound routes from peer";
          }

          // Low-level model info: Corresponds to bgpPeer(gr)AfiSafiExportIpAallPre.
          // Set to the aallPreAccessListListIndex generated for the IP prefix name.
          leaf out {
              type meta:ip-prefix-name;
              description
                  "The name of the IP prefix access list to use for
                  route exports from the peer for this AFI/SAFI.

                  Route export policy applies any export IP prefix access
                  list before any export route map, and the route must be
                  permitted by both to be exported.  The export route map
                  can apply its own prefix lists in addition to any export
                  IP prefix access list.

                  If the peer is a member of a peer group then BGP always
                  uses peer group export policy in order to take advantage
                  of the economies of using peer groups.";

              user-ext:CLI-comm-help "Apply prefix list to outbound routes to peer";
              user-ext:CLI-no-comm-help "Remove outbound routes prefix list";
              user-ext:CLI-param-help "Apply prefix list to outbound routes to peer";
          }

        } // prefix-list

        // Low-level model info: Corresponds to bgpPeer(gr)AfiSafiAddPathBestN.  Default is 1.
        leaf max-advertised-paths {
            type router-bgp-maximum-paths;

            description
                "The number of best paths to advertise to this peer as
                additional paths for this AFI/SAFI.

                The number of candidate paths available to advertise to
                the peer depends on the value of maximum-paths configured at
                the router level.  This field specifies how
                many of the candidate paths to advertise to this peer.

                For the default value of 1 only the best path for each
                destination is advertised.

                A value of 2 is sufficient to advertise the best path and
                2nd best path for each destination.

                Any additional paths are advertised to peers subject to
                split horizon rules, export policy, and BGP ADD-PATH
                capability negotiation.  These filters apply after
                selecting the best N paths to advertise, so the actual
                number of paths advertised may be smaller.

                Changing the value of this field while the peer is active
                triggers BGP to advertise additional paths according to
                the new configuration.

                If the peer belongs to a peer group, this field is
                overridden by the peer group AFI/SAFI configuration.";

            user-ext:CLI-comm-help "Set limit of best paths to advertise to peer ";
            user-ext:CLI-no-comm-help "Set limit of best paths to advertise to peer to the default";
            user-ext:CLI-param-help "Set advertise limit";
        }

        // Low-level model info: Corresponds to bgpPeer(gr)AfiSafiAddPathCapCfg.  Default is "inherit" (from BGP address-family value).
        leaf additional-paths {
            type bgp-add-path-capabilities;

            description
                "The configured BGP additional path capability for this
                peer and AFI/SAFI.

                Valid values are:
                -  inherit: Inherit configuration from
                the entity AFI/SAFI level
                -  disable: Disable sending and receiving additional BGP paths
                -  receive: Receive but do not send additional BGP paths
                -  send: Send but do not receive additional BGP paths
                -  both: Send and receive additional BGP paths.

                The effective BGP additional path capabilities for the
                session are negotiated with the peer and are reported by
                the caps-negotiated/add-paths leaf.

                If the peer belongs to a peer group then the peer group
                configuration overrides peer configuration.

                Any update to this will take effect the next time
                that the BGP peer is activated.";

            user-ext:CLI-comm-help "Set additional path support";
            user-ext:CLI-no-comm-help "Use global setting for additional path support";
            user-ext:CLI-param-help "Set additional path support";
        }

        // Low-level model info: Corresponds to bgpPeer(gr)AfiSafiOrigDefault.
        container default-originate {
            presence "Originate a default route to this neighbor";

            description
                "Enable origination of a default route to this neighbor for this AFI/SAFI";

            user-ext:CLI-comm-help "Originate a default route to this neighbor";
            user-ext:CLI-no-comm-help "Do not originate a default route to this neighbor";

            // Low-level model info: Corresponds to bgpPeer(gr)AfiSafiOrigDefaultRtMap.
            leaf route-map {
                type meta:route-map-name;
                description
                    "The name of the route map to use for default route
                     origination.

                     The match clauses in the route map are used for conditional
                     advertisement of the default route.  A default route is
                     only originated for an address family if there is at
                     least one route in the loc-RIB matching the route map.

                     The set clauses in the route map determine the
                     attributes of the originated default route.";

                user-ext:CLI-comm-help "Apply route map to default route origination";
                user-ext:CLI-no-comm-help "Remove route map for default route origination";
                user-ext:CLI-param-help "Apply route map to default route origination";

            }
        }

    } // router-bgp-neighbor-af-unicast-parameters

    grouping router-bgp-peer-group-af-v4v6-parms {

        // Low-level model info: Corresponds to AMB_BGP_PEERGR_AFI_SAFI (bgpPeergrAfiSafiTable).

        uses router-bgp-neighbor-af-common-parameters;

    } // router-bgp-peer-group-af-v4v6-parms

    grouping router-bgp-peer-group-af-l2vpn-parms {

        // Low-level model info: Corresponds to AMB_BGP_PEERGR_AFI_SAFI (bgpPeergrAfiSafiTable).

        uses router-bgp-neighbor-af-common-parameters;

    } // router-bgp-peer-group-af-l2vpn-parms

    grouping router-bgp-peer-group-af-unicast-parms {

        // Low-level model info: Corresponds to AMB_BGP_PEERGR_AFI_SAFI (bgpPeergrAfiSafiTable).

        uses router-bgp-neighbor-af-unicast-parameters;

    } // router-bgp-peer-group-af-unicast-parms

    grouping bgp-peer-state-nbr-group-config {

      // Low-level model info: Corresponds to bgpPeerAdminStatus for a configured peer.  For a
      //                       dynamic peer, this is always 'false'
      leaf shutdown {
        type boolean;
        description
          "The desired state of the BGP connection.  This is not configurable
          via the Peer Group for dynamic peers and so is always returned as
          false in that case.";
        config false;
      }

      // Low-level model info: Corresponds to bgpPeerConfigPeergr for a configured peer or
      //                       bgpPeergrIndex for a dynamic peer.
      leaf peer-group-name {
        type bgp-peer-group-name;
        description
          "The name of the peer group this neighbor belongs to, or
          zero if this neighbor does not belong to a peer group.";
        config false;
      }

      // Low-level model info: Corresponds to bgpPeer(gr)ConfigMaxPrfx.
      leaf max-prefixes {
        type router-bgp-max-prefixes;
        description
          "This object is used to limit the number
          of prefixes that can be accepted from this peer.";
        config false;
      }

      // Low-level model info: Corresponds to bgpPeer(gr)ConfigThreshold.
      leaf prefix-threshold {
        type router-bgp-prefix-threshold;
        description
          "Percentage of maximum number of prefixes from peer at which to send
           prefix-threshold notification.";
        config false;
      }

      // Low-level model info: Corresponds to bgpPeer(gr)MaxPrfxClear.
      leaf max-prefixes-clear {
        type router-bgp-max-prefixes;
        description
          "Number of prefixes from peer at which to send max-prefix-clear
           notification.";
        config false;
      }

      // Low-level model info: Corresponds to bgpPeer(gr)PrfxThresholdClear.
      leaf prefix-threshold-clear {
        type router-bgp-prefix-threshold;
        description
          "Percentage of maximum number of prefixes from peer at which to issue
           prefix-threshold-clear notification.";
        config false;
      }

      // Low-level model info: Corresponds to bgpPeer(gr)MaxPrfxHold.
      leaf max-prefix-hold {
        type router-bgp-max-prefix-hold;
        units "seconds";
        description
          "The time interval in seconds between when this BGP session
          is torn down due to the number of prefixes received from
          this peer exceeding the maximum configured (max-prefixes)
          and when BGP attempts to reestablish the session.";
        config false;
      }

    } // bgp-peer-state-nbr-group-config

    grouping bgp-peer-state-config {

        uses bgp-peer-state-nbr-group-config;

    } // bgp-peer-state-config

    grouping bgp-peer-state-af-common-config {

      // Low-level model info: Corresponds to bgpPeer(gr)AfiSafiAllowLocalAs.
      leaf allowas-in {
        type router-bgp-allow-local-as;
        description
          "Allow to receive announce from origin AS with next AS count";
        config false;
      }

      // Low-level model info: Corresponds to bgpPeer(gr)AfiSafiNxtHopSlf.
      leaf next-hop-self {
        type router-bgp-next-hop-self;
        description
          "The nexthop calculation action on this neighbor";
        config false;
      }

      container soft-reconfiguration {

        config false;

        // Low-level model info: Corresponds to bgpPeer(gr)AfiSafiSoftResetStore.
        leaf inbound {
          type empty;
          description
            "Enable inbound soft-reconfiguration for this neighbor";
          config false;
        }

      } // soft-reconfiguration

      container route-map {

        config false;

        // Low-level model info: Corresponds to bgpPeer(gr)AfiSafiImportMap.
        leaf in {
          type meta:route-map-name;
          description
            "The name of the route map to use for route imports from
            the peer for this AFI/SAFI.";
          config false;
        }

        // Low-level model info: Corresponds to bgpPeer(gr)AfiSafiExportMap.
        leaf out {
          type meta:route-map-name;
          description
            "The name of the route map to use for route exports to the
            peer for this AFI/SAFI.";
          config false;
        }

      } // route-map

    } // bgp-peer-state-af-common-config

    grouping bgp-peer-state-af-v4v6-config {

      uses bgp-peer-state-af-common-config;

      // Low-level model info: Corresponds to a row in AMB_BGP_PEER_ORF_CAP (bgpPeerOrfCapabilityTable)
      container capability {

        config false;

        container orf {

          config false;

          leaf prefix {
            type router-bgp-orf-prefix;
            description
              "Indicates whether the sender is (a) willing to receive ORF
              entries from its peer, (b) would like to send ORF entries
              to its peer, or (c) both.  For a dynamic peer, this will
              always be both.";
            config false;
          }

        } // orf

      } // capability

    } // bgp-peer-state-af-v4v6-config

    grouping bgp-peer-state-af-l2vpn-config {

      // Low-level model info: Corresponds to bgpPeerAfiSafiDisable.
      leaf enabled {
        type boolean;
        description
          "Enable advertisement of Multiprotocol support to the peer for this
          address family.";
        config false;
      }

      uses bgp-peer-state-af-common-config;

    } // bgp-peer-state-af-l2vpn-config

    grouping bgp-peer-state-af-unicast-config {

      container prefix-list {

        config false;

        // Low-level model info: Corresponds to bgpPeer(gr)AfiSafiImportIpAallPre.
        leaf in {
          type meta:ip-prefix-name;
          description
            "The name of the IP prefix access list to use for
            route imports from the peer for this AFI/SAFI.";
          config false;
        }

        // Low-level model info: Corresponds to bgpPeer(gr)AfiSafiExportIpAallPre.
        leaf out {
          type meta:ip-prefix-name;
          description
            "The name of the IP prefix access list to use for
            route exports from the peer for this AFI/SAFI.";
          config false;
        }

      } // prefix-list

      // Low-level model info: Corresponds to bgpPeer(gr)AfiSafiAddPathBestN.
      leaf max-advertised-paths {
        type router-bgp-maximum-paths;
        description
          "The number of best paths to advertise to this peer as
          additional paths for this AFI/SAFI.";
        config false;
      }

      // Low-level model info: Corresponds to bgpPeer(gr)AfiSafiAddPathCapCfg.
      leaf additional-paths {
        type bgp-add-path-capabilities;
        description
          "The configured BGP additional path capability for this
          peer and AFI/SAFI.";
        config false;
      }

    } // bgp-peer-state-af-unicast-config

    grouping neighbor-state-config {

      container config {

        description
          "Peer configuration taken from either the Neighbor or Peer
           Group depending on whether this is a dynamic peer.";

        config false;

        container address-family {

          // Low-level model info: Corresponds to AMB_BGP_PEER_AFI_SAFI (bgpPeerAfiSafiTable) or AMB_BGP_PEERGR_AFI_SAFI (bgpPeergrAfiSafiTable).

          description
            "BGP Peer address family configuration";

          container ipv4 {

            description
              "BGP Peer IPv4 address family configuration";

            config false;

            // Low-level model info: Corresponds to bgpPeerAfiSafiDisable.
            leaf enabled {
              type boolean;
              description
                "Enable advertisement of Multiprotocol support to the peer for this
                address family.";
              config false;
            }

            container unicast {

              description
                "BGP Peer IPv4 unicast address family configuration";

              config false;

              uses bgp-peer-state-af-v4v6-config;
              uses bgp-peer-state-af-unicast-config;

            } // unicast

          } // ipv4

          container ipv6 {

            description
              "BGP Peer IPv6 address family configuration";

            config false;

            // Low-level model info: Corresponds to bgpPeerAfiSafiDisable.
            leaf enabled {
              type boolean;
              description
                "Enable advertisement of Multiprotocol support to the peer for this
                address family.";
              config false;
            }

            container unicast {

              description
                "BGP Peer IPv6 unicast address family configuration";

              config false;

              uses bgp-peer-state-af-v4v6-config;
              uses bgp-peer-state-af-unicast-config;

            } // unicast

          } // ipv6

        } // address-family

        // Low-level model info: Corresponds to AMB_BGP_PEER (bgpPeerTable) or AMB_BGP_PEERGR (bgpPeergrTable).
        uses bgp-peer-state-config;

      } // config

    } // neighbor-state-config

    grouping router-bgp-neighbor-af-common-state {

        leaf update-group {
            type uint32;
            description
                "The index of the update group that the peer is a member of
                for this AFI/SAFI.

                Zero if the peer is not a member of an update group.";
            config false;
        }

    } // router-bgp-neighbor-af-common-state

    grouping router-bgp-network-ipv4 {

      list network {

         // Low-level model info: Corresponds to AMB_CIPR_RTM_REDIST (rtmRedistTable).

         description
           "This list contains the set of network prefixes that should be advertised by
            BGP.";

         user-ext:CLI-comm-help "Configure BGP network information";
         user-ext:CLI-no-comm-help "Remove BGP network information";

         key "network-prefix";

         // Low-level model info: A unique rtmRedistEntryId will be generated for each entry
         // Low-level model info: Corresponds to rtmRedistAddrFilter.
         leaf network-prefix {
           type interfaces:iface-ipv4-prefix-t;
           description
              "Destination IP address prefix filter.  Do not match the source
               routing information to this entry if one of these fails:

               -  the destination IP address in the source routing
               information, with the IP address filter prefix length
               applied, matches the IP address filter with the IP address
               filter prefix length applied

               -  the destination IP address prefix length is greater
               than or equal to the IP address filter prefix length.";

           user-ext:CLI-param-help "Network prefix";
         }

      } // network

    } // router-bgp-network-ipv4

    grouping router-bgp-network-ipv6 {

      list network {

         // Low-level model info: Corresponds to AMB_CIPR_RTM_REDIST (rtmRedistTable).

         description
           "This list contains the set of network prefixes that should be advertised by
            BGP.";

         user-ext:CLI-comm-help "Configure BGP network information";
         user-ext:CLI-no-comm-help "Remove BGP network information";

         key "network-prefix";

         // Low-level model info: A unique rtmRedistEntryId will be generated for each entry
         // Low-level model info: Corresponds to rtmRedistAddrFilter.
         leaf network-prefix {
           type interfaces:iface-ipv6-prefix-t;
           description
              "Destination IP address prefix filter.  Do not match the source
               routing information to this entry if one of these fails:

               -  the destination IP address in the source routing
               information, with the IP address filter prefix length
               applied, matches the IP address filter with the IP address
               filter prefix length applied

               -  the destination IP address prefix length is greater
               than or equal to the IP address filter prefix length.";

           user-ext:CLI-param-help "Network prefix";
         }

      } // network

    } // router-bgp-network-ipv6

    grouping listen-group-config {

      // Low-level model info: Corresponds to bgpPeerRangeConfigPeergr.
      leaf peer-group-name {
        type leafref {
          path "../../peer-group/name";
        }
        mandatory true;
        description
          "The name of the peer group that neighbors in this peer
          range belongs to.

          The peer range must be assigned to a peer group so this
          field cannot be set to zero.

          If this field is changed while active then all dynamic peers
          based on the peer range entry are immediately updated.";

        user-ext:CLI-comm-help "Configure the peer group";
        user-ext:CLI-no-comm-help "Remove the configured peer group";
        user-ext:CLI-param-help "Configure the peer group";
      }

      // Low-level model info: Corresponds to bgpPeerRangeMaxPeers.
      leaf max-peers {
        type bgp-listen-range-max-peers-t;
        default "0";
        description
          "The maximum number of dynamic BGP peers for this peer
          range, or zero if there is no limit.

          If this limit is reached then BGP rejects incoming
          connections from new dynamic BGP peers until BGP session
          termination causes the number of dynamic BGP peers to fall
          back below the limit.

          If this limit is reduced below the current number of
          dynamic BGP peers then BGP will reject incoming
          connections from new dynamic BGP peers until the number
          of dynamic BGP peers falls below the new limit.  BGP
          does not terminate existing BGP sessions with dynamic BGP
          peers in this case.";

        user-ext:CLI-comm-help "Set the maximum number of dynamic peers";
        user-ext:CLI-no-comm-help "Don't limit the number of dynamic peers";
        user-ext:CLI-param-help "Set the maximum number of dynamic peers";
      }

    } // listen-group-config

    grouping listen-group-state {

      // Low-level model info: Corresponds to bgpPeerRangeNumPeers.
      leaf num-peers {
        type uint32;
        description
          "The current number of dynamic BGP peers for this peer
          range.";
        config false;
      }

    } // listen-group-state

    grouping bgp-ipv4-unicast-config  {

      container unicast {
        description
            "Configure IPv4 unicast BGP routing";

        user-ext:CLI-comm-help "Configure IPv4 unicast BGP routing";
        user-ext:CLI-no-comm-help "Configure IPv4 unicast BGP routing";

        leaf disable {
          type empty;

          description
            "Disable advertisement of this multiprotocol capability (enabled by default)";
        }

        uses router-bgp-af-common-parameters;
        uses router-bgp-af-ipv4-parameters;
        uses router-bgp-af-unicast-parameters;
        uses router-bgp-network-ipv4;

        container redistribution {

          // Low-level model info: Corresponds to AMB_CIPR_RTM_REDIST (rtmRedistTable).

          description
            "Redistribution information entries.
            This list is used to determine how routing information is
            redistributed to routing protocol managers (RPMs).  The RPM to which
            the information may be redistributed is called the
            destination RPM.  Routing information is received from RPMs
            and from configuration (for static routes); these are referred to
            as the routing information source.";

          user-ext:CLI-comm-help "Configure redistribution information";
          user-ext:CLI-no-comm-help "Remove redistribution information";

          // Low-level model info: Corresponds to rtmRedistInfoSrc = isis.
          list isis {

            user-ext:CLI-comm-help "Configure IS-IS redistribution rule";
            user-ext:CLI-no-comm-help "Remove IS-IS redistribution rule";

            key "name";

            // Low-level model info: An unique rtmRedistEntryId will be generated for each entry
            leaf name {
              type redist:redist-name-string;

              user-ext:CLI-param-help "Rule name";
              description
                "Redistribution rule name";
            }

            uses redist:common-redist-ipv4;

            leaf path-type-filter {
              type redist:isis-redist-path-types;
              default "none";
              description
                "Value of IS-IS path type filter, if in use.  If the filter is in
                use then do not match the source routing information to
                this entry if the path type in the source routing
                information does not match this filter value.";

              user-ext:CLI-comm-help "Set path type filter";
              user-ext:CLI-no-comm-help "Set path type filter to default";
              user-ext:CLI-param-help "Set path type filter";
            }

            uses bgp-redist;

            // Low-level model info: Corresponds to rtmRedistIsisTag and rtmRedistIsisTagFlt
            leaf admin-tag {
              type uint32 {
                range "0..4294967295";
              }
              description
                "Value of IS-IS tag.";

              user-ext:CLI-comm-help "Set IS-IS tag";
              user-ext:CLI-no-comm-help "Set IS-IS tag to default";
              user-ext:CLI-param-help "Set IS-IS tag";
            }
          }

          // Low-level model info: Corresponds to rtmRedistInfoSrc = ospf.
          list ospf {

            user-ext:CLI-comm-help "Configure OSPF redistribution rule";
            user-ext:CLI-no-comm-help "Remove OSPF redistribution rule";

            key "name";

            // Low-level model info: An unique rtmRedistEntryId will be generated for each entry
            leaf name {
              type redist:redist-name-string;

              user-ext:CLI-param-help "Rule name";
              description
                "Redistribution rule name";
            }

            uses redist:common-redist-ipv4;

            leaf path-type-filter {
              type redist:ospf-redist-path-types;
              default "none";
              description
                "Value of OSPF path type filter, if in use.  If the filter is in
                use then do not match the source routing information to
                this entry if the path type in the source routing
                information does not match this filter value.";

              user-ext:CLI-comm-help "Set path type filter";
              user-ext:CLI-no-comm-help "Set path type filter to default";
              user-ext:CLI-param-help "Set path type filter";
            }

            uses bgp-redist;
          }

          // Low-level model info: Corresponds to rtmRedistInfoSrc = rip.
          list rip {

            user-ext:CLI-comm-help "Configure RIP redistribution rule";
            user-ext:CLI-no-comm-help "Remove RIP redistribution rule";

            key "name";

            // Low-level model info: An unique rtmRedistEntryId will be generated for each entry
            leaf name {
              type redist:redist-name-string;

              user-ext:CLI-param-help "Rule name";
              description
                "Redistribution rule name";
            }

            uses redist:common-redist-ipv4;
            uses bgp-redist;
          }

          // Low-level model info: Corresponds to rtmRedistInfoSrc = static.
          list static {

            user-ext:CLI-comm-help "Configure static redistribution rule";
            user-ext:CLI-no-comm-help "Remove static redistribution rule";

            key "name";

            // Low-level model info: An unique rtmRedistEntryId will be generated for each entry
            leaf name {
              type redist:redist-name-string;

              user-ext:CLI-param-help "Rule name";
              description
                "Redistribution rule name";
            }

            uses redist:common-redist-ipv4;
            uses bgp-redist;
          }

          // Low-level model info: Corresponds to rtmRedistInfoSrc = i3-connected.
          list connected {

            user-ext:CLI-comm-help "Configure connected redistribution rule";
            user-ext:CLI-no-comm-help "Remove connected redistribution rule";

            key "name";

            // Low-level model info: An unique rtmRedistEntryId will be generated for each entry
            leaf name {
              type redist:redist-name-string;

              user-ext:CLI-param-help "Rule name";
              description
                "Redistribution rule name";
            }

            uses redist:common-redist-ipv4;
            uses bgp-redist;
          }

          // Low-level model info: Corresponds to rtmRedistPathType  = i3-local.
          list local {

            user-ext:CLI-comm-help "Configure local redistribution rule";
            user-ext:CLI-no-comm-help "Remove local redistribution rule";

            key "name";

            // Low-level model info: An unique rtmRedistEntryId will be generated for each entry
            leaf name {
              type redist:redist-name-string;

              user-ext:CLI-param-help "Rule name";
              description
                "Redistribution rule name";
            }

            uses redist:common-redist-ipv4;
            uses bgp-redist;

            // Low-level model info: Corresponds to rtmRedistFullSpecFilter.
            uses redist:fully-specified;
          }

        } // redistribution

      } // unicast

    } // bgp-ipv4-unicast-config

    grouping bgp-ipv6-unicast-config {

      container unicast  {
        description
            "Configure IPv6 unicast BGP routing";

        user-ext:CLI-comm-help "Configure IPv6 unicast BGP routing";
        user-ext:CLI-no-comm-help "Configure IPv6 unicast BGP routing";

        leaf enable {
          type empty;

          description
            "Enable advertisement of this multiprotocol capability (disabled by default)";
        }

        uses router-bgp-af-common-parameters;
        uses router-bgp-af-ipv6-parameters;
        uses router-bgp-af-unicast-parameters;
        uses router-bgp-network-ipv6;

        container redistribution {

          // Low-level model info: Corresponds to AMB_CIPR_RTM_REDIST (rtmRedistTable).

          description
            "Redistribution information entries.
            This list is used to determine how routing information is
            redistributed to routing protocol managers (RPMs).  The RPM to which
            the information may be redistributed is called the
            destination RPM.  Routing information is received from RPMs
            and from configuration (for static routes); these are referred to
            as the routing information source.";

          user-ext:CLI-comm-help "Configure redistribution information";
          user-ext:CLI-no-comm-help "Remove redistribution information";

          // Low-level model info: Corresponds to rtmRedistInfoSrc = isis.
          list isis {

            key "name";

            // Low-level model info: An unique rtmRedistEntryId will be generated for each entry
            leaf name {
              type redist:redist-name-string;

              user-ext:CLI-param-help "Rule name";
              description
                "Redistribution rule name";
            }

            user-ext:CLI-comm-help "Configure IS-IS redistribution rule";
            user-ext:CLI-no-comm-help "Configure IS-IS redistribution rule";

            uses redist:common-redist-ipv6;

            leaf path-type-filter {
              type redist:isis-redist-path-types;
              default "none";
              description
                "Value of IS-IS path type filter, if in use.  If the filter is in
                use then do not match the source routing information to
                this entry if the path type in the source routing
                information does not match this filter value.";

              user-ext:CLI-comm-help "Set path type filter";
              user-ext:CLI-no-comm-help "Set path type filter to default";
              user-ext:CLI-param-help "Set path type filter";
            }

            uses bgp-redist;

            // Low-level model info: Corresponds to rtmRedistIsisTag and rtmRedistIsisTagFlt
            leaf admin-tag {
              type uint32 {
                range "0..4294967295";
              }
              description
                "Value of IS-IS tag.";

              user-ext:CLI-comm-help "Set IS-IS tag";
              user-ext:CLI-no-comm-help "Set IS-IS tag to default";
              user-ext:CLI-param-help "Set IS-IS tag";
            }
          }

          // Low-level model info: Corresponds to rtmRedistInfoSrc = ospf.
          list ospf {

            user-ext:CLI-comm-help "Configure OSPF redistribution rule";
            user-ext:CLI-no-comm-help "Remove OSPF redistribution rule";

            key "name";

            // Low-level model info: An unique rtmRedistEntryId will be generated for each entry
            leaf name {
              type redist:redist-name-string;

              user-ext:CLI-param-help "Rule name";
              description
                "Redistribution rule name";
            }

            uses redist:common-redist-ipv6;

            leaf path-type-filter {
              type redist:ospf-redist-path-types;
              default "none";
              description
                "Value of OSPF path type filter, if in use.  If the filter is in
                use then do not match the source routing information to
                this entry if the path type in the source routing
                information does not match this filter value.";

              user-ext:CLI-comm-help "Set path type filter";
              user-ext:CLI-no-comm-help "Set path type filter to default";
              user-ext:CLI-param-help "Set path type filter";
            }

            uses bgp-redist;
          }

          // Low-level model info: Corresponds to rtmRedistInfoSrc = rip.
          list rip {

            user-ext:CLI-comm-help "Configure RIP redistribution rule";
            user-ext:CLI-no-comm-help "Remove RIP redistribution rule";

            key "name";

            // Low-level model info: An unique rtmRedistEntryId will be generated for each entry
            leaf name {
              type redist:redist-name-string;

              user-ext:CLI-param-help "Rule name";
              description
                "Redistribution rule name";
            }

            uses redist:common-redist-ipv6;
            uses bgp-redist;
          }

          // Low-level model info: Corresponds to rtmRedistInfoSrc = static.
          list static {

            user-ext:CLI-comm-help "Configure static redistribution rule";
            user-ext:CLI-no-comm-help "Remove static redistribution rule";

            key "name";

            // Low-level model info: An unique rtmRedistEntryId will be generated for each entry
            leaf name {
              type redist:redist-name-string;

              user-ext:CLI-param-help "Rule name";
              description
                "Redistribution rule name";
            }

            uses redist:common-redist-ipv6;
            uses bgp-redist;
          }

          // Low-level model info: Corresponds to rtmRedistInfoSrc = i3-connected.
          list connected {

            user-ext:CLI-comm-help "Configure connected redistribution rule";
            user-ext:CLI-no-comm-help "Remove connected redistribution rule";

            key "name";

            // Low-level model info: An unique rtmRedistEntryId will be generated for each entry
            leaf name {
              type redist:redist-name-string;

              user-ext:CLI-param-help "Rule name";
              description
                "Redistribution rule name";
            }

            uses redist:common-redist-ipv6;
            uses bgp-redist;
          }

          // Low-level model info: Corresponds to rtmRedistPathType  = i3-local.
          list local {

            user-ext:CLI-comm-help "Configure local redistribution rule";
            user-ext:CLI-no-comm-help "Remove local redistribution rule";

            key "name";

            // Low-level model info: An unique rtmRedistEntryId will be generated for each entry
            leaf name {
              type redist:redist-name-string;

              user-ext:CLI-param-help "Rule name";
              description
                "Redistribution rule name";
            }

            uses redist:common-redist-ipv6;
            uses bgp-redist;

            // Low-level model info: Corresponds to rtmRedistFullSpecFilter.
            uses redist:fully-specified;
          }

        } // redistribution

      } // unicast

    } // bgp-ipv6-unicast-config

    grouping bgp-router-parameters {

        container bgp {

           // Low-level model info: Corresponds to AMB_BGP_RM_ENT (bgpRmEntTable).

            description
                "Configure BGP global parameters";

            user-ext:CLI-comm-help "Configure BGP global parameters";
            user-ext:CLI-no-comm-help "Configure BGP global parameters";

            container bestpath {
                description
                    "Configure BGP bestpath parameters";

                user-ext:CLI-comm-help "Configure BGP bestpath parameters";
                user-ext:CLI-no-comm-help "Configure BGP bestpath parameters";

                container as-path {
                    description
                        "Configure BGP AS-PATH";

                    user-ext:CLI-comm-help "Configure BGP AS-PATH";
                    user-ext:CLI-no-comm-help "Configure BGP AS-PATH";

                    // Low-level model info: Corresponds to bgpRmEntAsPathIgnore.
                    leaf ignore {
                        type empty;

                        description
                            "AS-PATH ignore flag";
                        user-ext:CLI-comm-help "Ignore as-path length for bestpath";
                        user-ext:CLI-no-comm-help "Don't ignore as-path length for bestpath";
                    }

                    // Low-level model info: Corresponds to bgpRmEntAsPathMultipathRelax.  The default is correct.
                    leaf multipath-relax {
                        type empty;

                        description
                            "AS-PATH multipath-relax flag";
                        user-ext:CLI-comm-help "Disable as-path length proof for bestpath if multipath routes";
                        user-ext:CLI-no-comm-help "Enable as-path length proof for bestpath if multipath routes";
                    }
                }

                container med  {
                    description
                        "Configure BGP MED parameters";

                    user-ext:CLI-comm-help "Configure BGP MED parameters";
                    user-ext:CLI-no-comm-help "Configure BGP MED parameters";

                    // Low-level model info: Corresponds to bgpRmEntAlwaysCompMed.
                    leaf always {
                        type empty;

                        description
                            "MED always equal routes flag";
                        user-ext:CLI-comm-help "Enable MED always compare equal routes";
                        user-ext:CLI-no-comm-help "Disable MED always compare equal routes";
                    }

                    // Low-level model info: Corresponds to bgpRmEntMedConfed.
                    leaf confed {
                        type empty;

                        description
                            "MED equal between confed path";
                        user-ext:CLI-comm-help "Enable MED equal between confederation paths";
                        user-ext:CLI-no-comm-help "Disable MED equal between confederation paths";
                    }

                    // Low-level model info: Corresponds to bgpRmEntDeterministicMed.
                    leaf non-deterministic {
                        type empty;

                        description
                            "MED comparison is non-deterministic";
                        user-ext:CLI-comm-help "Enable non-deterministic MED comparison";
                        user-ext:CLI-no-comm-help "Disable non-deterministic MED comparison";
                    }

                    // Low-level model info: Corresponds to bgpRmEntMedMissingAsWorst.
                    leaf missing-as-worst {
                        type empty;

                        description
                            "MED minimal";
                        user-ext:CLI-comm-help "Enable MED minimal if not set";
                        user-ext:CLI-no-comm-help "Disable MED minimal if not set";
                    }
                }

            }

            // Low-level model info: Corresponds to bgpRmEntDefLocalPref.
            container default {
                description
                    "Configure BGP default local-preference";

                user-ext:CLI-comm-help "Configure BGP default local preference";
                user-ext:CLI-no-comm-help "Configure BGP default local preference";

                leaf local-preference {
                    type router-bgp-local-preference;

                    description
                        "BGP default local-preference";

                    user-ext:CLI-comm-help "Set BGP default local preference";
                    user-ext:CLI-no-comm-help "Remove BGP default local preference";
                    user-ext:CLI-param-help "Set preference";
                }
            }

            // Low-level model info: Corresponds to bgpRmEntCheckFirstAsNum.  Default is correct.
            container enforce-first-as {
                description
                    "Configure first AS in path and peer AS equal proof";

                user-ext:CLI-comm-help "Configure first AS number in AS PATH for EBGP nbrs";
                user-ext:CLI-no-comm-help "Configure first AS number in AS PATH for EBGP nbrs";

                leaf disable {
                    type empty;

                    description
                        "Disable first AS in path and peer AS equal proof";
                    user-ext:CLI-comm-help "Disable first AS number in AS PATH for EBGP nbrs";
                    user-ext:CLI-no-comm-help "Enable first AS number in AS PATH for EBGP nbrs";
                }
            }

            // Low-level model info: Corresponds to bgpRmEntFastExtFallover.  Default is flipped.
            container fast-external-fallover {
                description
                    "Configure fallover EBGP session";

                user-ext:CLI-comm-help "Configure fallover for EBGP session";
                user-ext:CLI-no-comm-help "Configure fallover for EBGP session";

                leaf disable {
                    type empty;

                    description
                        "Disable immediate fallover EBGP session if iface with direct-connect is down";

                    user-ext:CLI-comm-help "Disable immediate fallover if interface with direct-connect is down";
                    user-ext:CLI-no-comm-help "Enable immediate fallover if interface with direct-connect is down";
                }
            }

            uses router-bgp-max-ecmp-paths;

            // Low-level model info: Corresponds to bgpRmEntPreferExistingRoute.  Default is flipped.
            container compare-routerid {
                description
                    "Configure whether to compare-routerid when comparing route with existing best";

                user-ext:CLI-comm-help "Configure compare router ID";
                user-ext:CLI-no-comm-help "Configure compare router ID";

                leaf enable {
                    type empty;

                    description
                        "Enable comparison of router IDs when comparing route to existing best";

                    user-ext:CLI-comm-help "Enable router ID comparison (so do not prefer existing route)";
                    user-ext:CLI-no-comm-help "Disable router ID comparison (so we prefer existing route)";
                }
            }

            container graceful-restart {

                description
                    "Configure BGP graceful restart";

                user-ext:CLI-comm-help "Configure BGP graceful restart";
                user-ext:CLI-no-comm-help "Configure BGP graceful restart";

                // Low-level model info: Corresponds to bgpRmEntRestartSupported.  Default is correct.
                leaf enable {
                    type empty;

                    description
                        "Enable BGP graceful restart";
                    user-ext:CLI-comm-help "Enable BGP graceful restart";
                    user-ext:CLI-no-comm-help "Disable BGP graceful restart";
                }

                // Low-level model info: Corresponds to bgpRmEntMaxRestartTime.
                leaf restart-time {
                    type router-bgp-graceful-restart-restart-time;

                    default 120;

                    description
                        "Restart time to announce to neighbors";

                    user-ext:CLI-comm-help "Set maximum time to wait for neighbor to come [back] online";
                    user-ext:CLI-no-comm-help "Set default max time to wait for neighbor to come [back] online";
                    user-ext:CLI-param-help "Set maximum time to wait for neighbor to come [back] online";
                }

                // Low-level model info: Corresponds to bgpRmEntStalePathTime.
                leaf stale-path-time {
                    type router-bgp-graceful-restart-restart-time;

                    default 150;

                    description
                        "The maximum time to wait for neighbor to restart before
                        removing stale routes from that neighbor";

                    user-ext:CLI-comm-help "Set maximum time to wait before removing stale routes from neighbor";
                    user-ext:CLI-no-comm-help "Set default max time to wait before removing stale routes from neighbor";
                    user-ext:CLI-param-help "Set maximum time to wait before removing stale routes from neighbor";
                }

                // Low-level model info: Corresponds to bgpRmEntSelectDeferTime.
                leaf select-defer-time {
                    type router-bgp-graceful-restart-restart-time;

                    default 150;

                    description
                        "The maximum time to wait following local restart before performing
                        route selection";

                    user-ext:CLI-comm-help "Set maximum time to wait before performing route selection";
                    user-ext:CLI-no-comm-help "Set default max time to wait before performing route selection";
                    user-ext:CLI-param-help "Set maximum time to wait before performing route selection";
                }

                // Check that the stale-path-time is at least the restart-time.
                // The default values 150 and 120 seconds respectively.
                must "((not(enable)) or " +
                     " ((not(stale-path-time)) and (not(restart-time))) or " +
                     " ((not(stale-path-time)) and (150 >= restart-time)) or " +
                     " ((not(restart-time)) and (stale-path-time >= 120)) or " +
                     "  (((stale-path-time) and (restart-time)) and " +
                     "   (number(stale-path-time) >= number(restart-time))))" {
                  error-message "BGP stale-path-time must be greater than or equal to restart-time";
                }

                // Check that the select-defer-time is at least the restart-time.
                // The default values 150 and 120 seconds respectively.
                must "((not(enable)) or " +
                     " ((not(select-defer-time)) and (not(restart-time))) or " +
                     " ((not(select-defer-time)) and (150 >= restart-time)) or " +
                     " ((not(restart-time)) and (select-defer-time >= 120)) or " +
                     "  (((select-defer-time) and (restart-time)) and " +
                     "   (number(select-defer-time) >= number(restart-time))))" {
                  error-message "BGP select-defer-time must be greater than or equal to restart-time";
                }

                // Low-level model info: Corresponds to bgpRmEntHelperOnly.  Default is correct.
                leaf restart-helper-mode {
                    type empty;

                    description
                        "Enable BGP graceful restart helper mode";
                    user-ext:CLI-comm-help "Enable BGP graceful restart helper mode";
                    user-ext:CLI-no-comm-help "Disable BGP graceful restart helper mode";
                }

                // Check that restart-helper-mode and enable are not both set.
                must "((not(enable)) or (not(restart-helper-mode)))" {
                  error-message "BGP cannot have graceful restart enabled and be in restart helper mode at the same time";
                }

            } // graceful-restart

            container update-groups {

                description
                    "Configure BGP update groups";

                user-ext:CLI-comm-help "Configure BGP update groups";
                user-ext:CLI-no-comm-help "Configure BGP update groups";

                // Low-level model info: Corresponds to bgpRmEntUpdateGroups.  Default is correct.
                // If this is set, bgpRmEntAggSplitHorizon must be false.
                leaf enable {
                    type empty;

                    description
                        "Enable BGP update groups";
                    user-ext:CLI-comm-help "Enable BGP update groups";
                    user-ext:CLI-no-comm-help "Disable BGP update groups";
                }

            } // update-groups

            // Low-level model info: Corresponds to bgpRmEntLocalIdentifier.  If not set, mapper should use value obtained from the I3 stub.
            // The BGP product code insists that, if set, this is a non-zero unicast address.
            leaf router-id  {
                type meta:ipv4-unicast-address;

                mandatory true;

                description
                    "BGP router-id";
                user-ext:CLI-comm-help "Set BGP router ID";
                user-ext:CLI-no-comm-help "Remove BGP router ID";
                user-ext:CLI-param-help "Set router ID";
            }

            // Low-level model info: Corresponds to bgpRmEntPhase3DelayTime.
            leaf update-delay {
                type router-bgp-update-delay;

                default 120;

                description
                    "BGP update delay";
                user-ext:CLI-comm-help "Set BGP update delay";
                user-ext:CLI-no-comm-help "Set BGP update delay to default";
                user-ext:CLI-param-help "Set delay";
            }

            leaf cluster-id  {
                type interfaces:iface-ipv4-address-t;

                description
                    "BGP cluster-id";
                user-ext:CLI-comm-help "Set BGP cluster ID";
                user-ext:CLI-no-comm-help "Remove BGP cluster ID";
                user-ext:CLI-param-help "Set cluster ID";
            }

            leaf rib-size-limit {
                type uint32;

                description
                    "Limit on the total number of BGP routes";
                user-ext:CLI-comm-help "Set RIB size limit";
                user-ext:CLI-no-comm-help "Remove RIB size limit";
                user-ext:CLI-param-help "Set RIB size limit";
            }

            container state {

              config false;

              uses global-state-for-bgp;

            } // state

        } // bgp

    } // bgp-router-parameters

    grouping bgp-nlri-prefix-state {

      container nlri-prefix-state-list {

          description
            "Container to hold NLRI Prefix state for the IP address family.";

          config false;

          list nlri-prefix-state {

            // Low-level model info: Corresponds to AMB_BGP_NLRI_PREFIX (bgpNlriPrefixTable).

            description
              "This table contains information about paths to destination
              networks received from all BGP peers.";

            config false;

            uses nlri-state;

          } // nlri-prefix-state

        } // nlri-prefix-state-list

    } // bgp-nlri-prefix-state

    grouping bgp-adj-rib-ip-out {

      container adj-rib-out-list {

          description
            "Container to hold BGP Adj-RIB-Out Table state for the IP address family.";

          config false;

          list adj-rib-out {

            // Low-level model info: Corresponds to AMB_BGP_ARO (bgpAdjRibOutTable).

            description
              "The BGP Adj-RIB-Out Table contains the set of routes
              advertised to each peer.";

            config false;

            uses adj-rib-out-ip-state;

          } // adj-rib-out

        } // adj-rib-out-list

    } // bgp-adj-rib-ip-out

    augment "/bgp:router/bgp:bgp/bgp:global" {

      container nlri-l2vpn-vpls-prefix-state-list {

        description
          "Container to hold NLRI Prefix state for the L2VPN VPLS afi/safi.";

        config false;

        list nlri-l2vpn-vpls-prefix-state {

          // Low-level model info: Corresponds to AMB_BGP_NLRI_PREFIX (bgpNlriPrefixTable).

          description
            "This table contains information about paths to destination
             networks received from all BGP peers.";

          config false;

          uses nlri-l2vpn-vpls-state;

        } // nlri-l2vpn-vpls-prefix-state

      } // nlri-l2vpn-vpls-prefix-state-list

      container adj-rib-out-l2vpn-vpls-list {

        description
          "Container to hold BGP Adj-RIB-Out Table state for the L2VPN VPLS afi/safi.";

        config false;

        list adj-rib-out-l2vpn-vpls {

            // Low-level model info: Corresponds to AMB_BGP_ARO (bgpAdjRibOutTable).

            description
              "The BGP Adj-RIB-Out Table contains the set of routes
              advertised to each peer.";

          config false;

          uses adj-rib-out-l2vpn-vpls-state;

        } // adj-rib-out-l2vpn-vpls

      } // adj-rib-out-l2vpn-vpls-list

      container nlri-l2vpn-evpn-prefix-state-list {

        description
          "Container to hold NLRI Prefix state for the L2VPN EVPN afi/safi.";

        config false;

        list nlri-l2vpn-evpn-prefix-state {

          // Low-level model info: Corresponds to AMB_BGP_NLRI_PREFIX (bgpNlriPrefixTable).

          description
            "This table contains information about paths to destination
             networks received from all BGP peers.";

          config false;

          uses nlri-l2vpn-evpn-state;

        } // nlri-l2vpn-evpn-prefix-state

      } // nlri-l2vpn-evpn-prefix-state-list

      container adj-rib-out-l2vpn-evpn-list {

        description
          "Container to hold BGP Adj-RIB-Out Table state for the L2VPN EVPN afi/safi.";

        config false;

        list adj-rib-out-l2vpn-evpn {

            // Low-level model info: Corresponds to AMB_BGP_ARO (bgpAdjRibOutTable).

            description
              "The BGP Adj-RIB-Out Table contains the set of routes
              advertised to each peer.";

          config false;

          uses adj-rib-out-l2vpn-evpn-state;

        } // adj-rib-out-l2vpn-evpn

      } // adj-rib-out-l2vpn-evpn-list

      container nlri-l3vpn-prefix-state-list {

        description
          "Container to hold NLRI Prefix state for the l3vpn address family.";

        config false;

        list nlri-l3vpn-prefix-state {

          // Low-level model info: Corresponds to AMB_BGP_NLRI_PREFIX (bgpNlriPrefixTable).

          description
            "This table contains information about paths to destination
             networks received from all BGP peers.";

          config false;

          uses nlri-l3vpn-state;

        } // nlri-l3vpn-prefix-state

      } // nlri-l3vpn-prefix-state-list

      container adj-rib-out-l3vpn-list {

        description
          "Container to hold BGP Adj-RIB-Out Table state for the l3vpn address family.";

        config false;

        list adj-rib-out-l3vpn {

            // Low-level model info: Corresponds to AMB_BGP_ARO (bgpAdjRibOutTable).

            description
              "The BGP Adj-RIB-Out Table contains the set of routes
              advertised to each peer.";

          config false;

          uses adj-rib-out-l3vpn-state;

        } // adj-rib-out-l3vpn

      } // adj-rib-out-l3vpn-list

    } // augment - l2vpn and l3vpn address family nlri and adj-rib-out

    grouping bgp-route-administrative-distance {

        container admin-distance {

          description
            "Configure administrative distances for BGP routes";

          user-ext:CLI-comm-help "Configure administrative distances for BGP routes";
          user-ext:CLI-no-comm-help "Configure administrative distances for BGP routes";

          // Low-level model info: Corresponds to rtmEntityDsIntBgp
          leaf bgp-internal {
            type redist:rtm-admin-distance;
            default "200";

            user-ext:CLI-comm-help "Set administrative distance used for internal and VPN BGP routes";
            user-ext:CLI-no-comm-help "Set administrative distance used for internal and VPN BGP routes to default";
            user-ext:CLI-param-help "Set administrative distance used for internal and VPN BGP routes";
            description
              "The administrative distance to use for internal and VPN BGP routes.  The lower
              the administrative distance for a type of route, the more likely a route
              of this type will be used as the active route for the given destination.";
          }

          // Low-level model info: Corresponds to rtmEntityDstExtBgp
          leaf bgp-external {
            type redist:rtm-admin-distance;
            default "20";

            user-ext:CLI-comm-help "Set administrative distance used for BGP external routes";
            user-ext:CLI-no-comm-help "Set administrative distance used for BGP external routes to default";
            user-ext:CLI-param-help "Set administrative distance used for BGP external routes";
            description
              "The administrative distance to use for BGP external routes.  The lower
              the administrative distance for a type of route, the more likely a route
              of this type will be used as the active route for the given destination.";
          }
        }

    } // bgp-route-administrative-distance

    grouping bgp-base-router {

        // The configuration available when configuring BGP.  This model is augmented
        // for the non-VRF case to support additional address families.

        container address-family {
            description
                "Configure BGP routing for address-family";

            user-ext:CLI-comm-help "Configure BGP routing for address-family";
            user-ext:CLI-no-comm-help "Configure BGP routing for address-family";

            container ipv4 {
                description
                    "Configure IPv4 BGP routing";

                user-ext:CLI-comm-help "Configure IPv4 BGP routing";
                user-ext:CLI-no-comm-help "Configure IPv4 BGP routing";

                uses bgp-ipv4-unicast-config;
                uses bgp-route-administrative-distance;

            } // ipv4

            container ipv6 {
                description
                    "Configure IPv6 BGP routing";

                user-ext:CLI-comm-help "Configure IPv6 BGP routing";
                user-ext:CLI-no-comm-help "Configure IPv6 BGP routing";

                uses bgp-ipv6-unicast-config;
                uses bgp-route-administrative-distance;

            } // ipv6

        } // address-family

        uses bgp-router-parameters;

        list neighbor {

            // Low-level model info: Corresponds to AMB_BGP_PEER (bgpPeerTable).

            user-ext:CLI-comm-help "Configure a BGP neighbor";
            user-ext:CLI-no-comm-help "Remove a BGP neighbor";

            key "address";

            // Low-level model info: Corresponds to bgpPeerRemoteAddr(Type).
            leaf address {
                type interfaces:iface-ip-address-t;

                description
                    "Neighbor address";

                user-ext:CLI-param-help "Neighbor address";
            }

            uses neighbor-config;

            // Check that neighbor address and update-source (local-address) are
            // of the same type.
            must "(not(update-source) or " +
                 " ((substring-after(address, ':') = '') and " +
                 "  (substring-after(update-source, ':') = '')) or " +
                 " ((substring-after(address, ':') != '') and " +
                 "  (substring-after(update-source, ':') != '')))" {
              error-message "BGP neighbor address and update-source must have the same IP address type";
            }

            // Check that the advertisement-interval is at least the withdraw-interval.
            // The default values for both are 30 seconds.
            must "(((not(advertisement-interval)) and (not(withdraw-interval))) or " +
                 " ((not(advertisement-interval)) and (30 >= withdraw-interval)) or " +
                 " ((not(withdraw-interval)) and (advertisement-interval >= 30)) or " +
                 "  (((advertisement-interval) and (withdraw-interval)) and " +
                 "   (number(advertisement-interval) >= number(withdraw-interval))))" {
              error-message "BGP neighbor advertisement-interval must be at least withdraw-interval";
            }

            // eBGP configuration fields should not be set if this is an iBGP neighbor.
            // The neighbor is eBGP if the neighbor's remote AS does not equal either the BGP router's local AS or the neighbor's alternative local AS.
            // The defaults for the neighbor's remote AS and alternative local AS are both zero; the BGP router's local AS must have been set.
            // The must statement checks that either the neighbor is eBGP or (so iBGP) the ebgp-multihop fields has not been set.

            must "(((((not(remote-as)) and (local-as)) and " +
                 "   (local-as != 0)) or " +
                 "  (((remote-as) and (not(local-as))) and " +
                 "   ((remote-as != 0) and (number(remote-as) != number(../../as-num)))) or " +
                 "  (((remote-as) and (local-as)) and " +
                 "   (((remote-as != 0) and (number(remote-as) != number(../../as-num))) or " +
                 "    ((local-as != 0) and (number(remote-as) != number(local-as)))))) or " +
                 " (not(ebgp-multihop)))" {
              error-message "eBGP configuration fields should not be set if this is an iBGP neighbor";
            }

        } // neighbor

        list neighbor-interface {

            // Low-level model info: Corresponds to AMB_BGP_PEER (bgpPeerTable).

            user-ext:CLI-comm-help "Configure a BGP neighbor by interface name";
            user-ext:CLI-no-comm-help "Configure a BGP neighbor by interface name";

            key "interface";

            // Low-level model info: The interface index of the interface
            // corresponds to bgpPeerLocalAddrScopeId.
            leaf interface {
              type custom:iface-name;

              description
                "Name of interface on which the neighbor is reachable";

              user-ext:CLI-param-help "Name of interface on which the neighbor is reachable";
            }

            uses neighbor-config;

            // Check that update-source (local-address) is not set.
            must "(not(update-source))" {
              error-message "BGP update-source not supported for neighbors configured by interface";
            }

            // Check that the advertisement-interval is at least the withdraw-interval.
            // The default values for both are 30 seconds.
            must "(((not(advertisement-interval)) and (not(withdraw-interval))) or " +
                 " ((not(advertisement-interval)) and (30 >= withdraw-interval)) or " +
                 " ((not(withdraw-interval)) and (advertisement-interval >= 30)) or " +
                 "  (((advertisement-interval) and (withdraw-interval)) and " +
                 "   (number(advertisement-interval) >= number(withdraw-interval))))" {
              error-message "BGP neighbor advertisement-interval must be at least withdraw-interval";
            }

            // ebgp-multihop must not be set for neighbors configured by interface.
            // Low-level model info: Always use 1 for bgpPeerTtl for peers configured by interface name.

            must "(not(ebgp-multihop))" {
              error-message "ebgp-multihop must not be set for neighbors configured by interface";
            }

        } // neighbor-interface

        container neighbor-state-list {

          description
            "Container to hold state for configured and dynamic Neighbors.";

          config false;

          list neighbor-state {

            // Low-level model info: Corresponds to AMB_BGP_PEER_STATUS (bgpPeerStatusTable).

            description
              "Configured and dynamic state.";

            config false;

            // Actions in state lists require keyed lists.
            key "remote-address";

            uses neighbor-state-actions;
            uses neighbor-state;
            uses neighbor-state-config;

          } // neighbor-state

        } // neighbor-state-list

        container neighbor-interface-state-list {

          description
            "Container to hold state for configured unnumbered Neighbors.";

          config false;

          list neighbor-interface-state {

            // Low-level model info: Corresponds to AMB_BGP_PEER_STATUS (bgpPeerStatusTable).

            description
              "Configured and dynamic state.";

            config false;

            // Actions in state lists require keyed lists.
            key "interface";

            uses neighbor-state-actions;
            uses neighbor-state;
            uses neighbor-state-config;

          } // neighbor-state

        } // neighbor-interface-state-list

        list listen-range {

          // Low-level model info: Corresponds to AMB_BGP_PEER_RANGE (bgpPeerRangeTable).

          description
            "Peer range table.

            This table allows a user to configure BGP dynamic neighbors.
            Instead of being configured individually in the BGP peer
            table, BGP dynamic neighbors are configured as ranges of
            remote addresses with associated peer groups.  Each range
            is configured as a remote address prefix.  Any BGP peer with
            a remote address that matches the remote address prefix
            becomes a member of the associated peer group.

            Each entry in this table configures a remote address prefix
            and specifies the associated peer group.

            BGP handles incoming connections from BGP peers as
            follows.
            -  If the connection matches a peer configured in the
            BGP peer table then the peer is a configured peer.
            -  Otherwise if the connection matches a remote address
            prefix in the BGP peer range table then the peer is
            a dynamic peer.
            -  Otherwise if the listen socket is configured to accept
            all incoming connections then the connection is accepted
            and uses the default peer configuration.
            -  Otherwise the connection is rejected.

            If an incoming connection matches multiple peer range
            entries then the entry with the longest remote address
            prefix is selected.

            Although it is possible to configure overlapping peer ranges
            with different remote address prefix lengths, this is not
            recommended - peer range configuration is simpler and
            clearer if peer ranges do not overlap.";

          user-ext:CLI-comm-help "Configure a BGP dynamic peer range";
          user-ext:CLI-no-comm-help "Remove a BGP dynamic peer range";

          key "prefix";

          // Low-level model info: Corresponds to bgpPeerRangeRemoteAddr.
          leaf prefix {
            type interfaces:iface-ip-prefix-t;
            description
              "The remote address prefix.";

            user-ext:CLI-param-help "Peer range prefix";
          }

          uses listen-group-config;

          container state {

            config false;

            uses listen-group-state;

          } // state

        } // listen-range

        list peer-group {

            // Low-level model info: Corresponds to AMB_BGP_PEERGR (bgpPeergrTable).

            description
                "The list of peer groups.

                A peer group is a set of peers that share a common peer
                group configuration.

                Using peer groups simplifies peer configuration.  Instead of
                configuring many peers with the same set of configuration
                values, you can configure a single peer group and then
                assign peers to the peer group.

                The configuration fields for a peer group mirror
                configuration fields for individual peers.";

            user-ext:CLI-comm-help "Configure a BGP peer group";
            user-ext:CLI-no-comm-help "Remove a BGP peer group";

            key "name";

            // Low-level model info: Generate unique bgpPeergrIndex for each name.
            leaf name {
                type bgp-peer-group-name;

                description
                    "The name of this BGP Route Map.";

                user-ext:CLI-param-help "Set peer group name";
            }

            container address-family {

                // Low-level model info: Corresponds to AMB_BGP_PEER_AFI_SAFI (bgpPeerAfiSafiTable).

                description
                    "Configure address family for BGP peer group";

                user-ext:CLI-comm-help "Configure address family for BGP peer group";
                user-ext:CLI-no-comm-help "Configure address family for BGP peer group";

                container ipv4 {

                    description
                        "Configure IPv4 address family for BGP peer group";

                    user-ext:CLI-comm-help "Configure IPv4 address family for BGP peer group";
                    user-ext:CLI-no-comm-help "Configure IPv4 address family for BGP peer group";

                    container unicast {
                        description
                            "Configure unicast IPv4 address family for BGP peer group";

                        user-ext:CLI-comm-help "Configure unicast IPv4 address family for BGP peer group";
                        user-ext:CLI-no-comm-help "Configure unicast IPv4 address family for BGP peer group";

                        uses router-bgp-peer-group-af-v4v6-parms;
                        uses router-bgp-peer-group-af-unicast-parms;

                    }

                } // ipv4

                container ipv6 {

                    description
                        "Configure IPv6 address family for BGP peer group";

                    user-ext:CLI-comm-help "Configure IPv6 address family for BGP peer group";
                    user-ext:CLI-no-comm-help "Configure IPv6 address family for BGP peer group";

                    container unicast {
                        description
                            "Configure unicast IPv6 address family for BGP peer group";

                        user-ext:CLI-comm-help "Configure unicast IPv6 address family for BGP peer group";
                        user-ext:CLI-no-comm-help "Configure unicast IPv6 address family for BGP peer group";

                        uses router-bgp-peer-group-af-v4v6-parms;
                        uses router-bgp-peer-group-af-unicast-parms;

                    }

                } // ipv6

            } // address family

            uses peer-group-config;

            // Check that the advertisement-interval is at least the withdraw-interval.
            // The default values for both are 30 seconds.
            must "(((not(advertisement-interval)) and (not(withdraw-interval))) or " +
                 " ((not(advertisement-interval)) and (30 >= withdraw-interval)) or " +
                 " ((not(withdraw-interval)) and (advertisement-interval >= 30)) or " +
                 "  (((advertisement-interval) and (withdraw-interval)) and " +
                 "   (number(advertisement-interval) >= number(withdraw-interval))))" {
              error-message "BGP peer group advertisement-interval must be at least withdraw-interval";
            }

            // eBGP configuration fields should not be set if this is an iBGP neighbor.
            // The neighbor is eBGP if the neighbor's remote AS does not equal either the BGP router's local AS or the neighbor's alternative local AS.
            // The defaults for the neighbor's remote AS and alternative local AS are both zero; the BGP router's local AS must have been set.
            // The must statement checks that either the neighbor is eBGP or (so iBGP) the ebgp-multihop fields has not been set.

            must "(((((not(remote-as)) and (local-as)) and " +
                 "   (local-as != 0)) or " +
                 "  (((remote-as) and (not(local-as))) and " +
                 "   ((remote-as != 0) and (number(remote-as) != number(../../as-num)))) or " +
                 "  (((remote-as) and (local-as)) and " +
                 "   (((remote-as != 0) and (number(remote-as) != number(../../as-num))) or " +
                 "    ((local-as != 0) and (number(remote-as) != number(local-as)))))) or " +
                 " (not(ebgp-multihop)))" {
              error-message "eBGP configuration fields should not be set if this is an iBGP neighbor";
            }

        } // peer-group

        container update-group-state-list {

            description
                "Container to hold Update Group state.";

            config false;

            list update-group-state {

                // Low-level model info: Corresponds to AMB_BGP_UPDATE_GROUP (bgpUpdateGroupTable).

                description
                   "Update group table.";

                config false;

                leaf update-group-index {
                  // Low-level model info: Corresponds to bgpUpdateGroupIndex.
                  type uint32;
                  description
                    "Identifies an update group.";
                  config false;
                }

                leaf member-count {
                  // Low-level model info: Corresponds to bgpUpdateGroupMemberCount.
                  type uint32;
                  description
                    "The count of members in this update group.";
                  config false;
                } // member-count

                list member {

                  // Low-level model info: Corresponds to AMB_BGP_UPD_GP_MBRSHP (bgpUpdateGroupMembershipTable).

                  description
                    "Update Group member";
                  config false;

                  leaf address {
                    type interfaces:iface-ip-address-t;
                    description
                       "Neighbor address";
                    config false;
                  }

                } // member

                leaf afi {
                  // Low-level model info: Corresponds to bgpUpdateGroupAfi.
                  type bgp-afi;
                  description
                    "The address family for this update group.";
                  config false;
                } // afi

                leaf safi {
                  // Low-level model info: Corresponds to bgpUpdateGroupSafi.
                  type bgp-safi;
                  description
                    "The subsequent address family for this update group.";
                  config false;
                } // safi

                leaf local-address-afi {
                  // Low-level model info: Corresponds to bgpUpdateGroupLocalAddressAfi.
                  type bgp-afi;
                  description
                    "The AFI of the local address used if next-hop-self is in
                    use.";
                  config false;
                } // local-address-afi

                leaf local-address-safi {
                  // Low-level model info: Corresponds to bgpUpdateGroupLocalAddressSafi.
                  type bgp-safi;
                  description
                    "The SAFI of the local address used if next-hop-self is in
                    use.";
                  config false;
                } // local-address-safi

                leaf local-address-length {
                  // Low-level model info: Corresponds to bgpUpdateGroupLocalAddressLength.
                  type uint32;
                  description
                    "The length, in bytes, of the local address used if
                    next-hop-self is in use.";
                  config false;
                } // local-address-length

                leaf as-size {
                  // Low-level model info: Corresponds to bgpUpdateGroupAsSize.
                  type uint32;
                  description
                    "The number of bytes (agreed with the neighbor) that are
                  used for AS numbers.";
                  config false;
                } // as-size

                leaf neighbor-in-same-as {
                  // Low-level model info: Corresponds to bgpUpdateGroupNeighborInSameAs.
                  type boolean;
                  description
                    "Whether the neighbor is in the same AS as this router.";
                  config false;
                } // neighbor-in-same-as

                leaf confederation-member {
                  // Low-level model info: Corresponds to bgpUpdateGroupConfedMember.
                  type boolean;
                  description
                    "Whether the neighbor is in the same confederation as this
                    router.";
                  config false;
                } // confederation-member

                leaf conf-alt-local-as {
                  // Low-level model info: Corresponds to bgpUpdateGroupConfAltLocalAs.
                  type uint32;
                  description
                    "The configured alternative local AS number for the session
                    to the peers.";
                  config false;
                } // conf-alt-local-as

                leaf selected-local-as {
                  // Low-level model info: Corresponds to bgpUpdateGroupSelectedLocalAs.
                  type uint32;
                  description
                    "The local AS number for the session to the peers.";
                  config false;
                } // selected-local-as

                leaf alt-local-as-mode {
                  // Low-level model info: Corresponds to bgpUpdateGroupAltLocalAsMode.
                  type bgp-alt-loc-as-mode;
                  description
                    "The alternative local AS number mode.";
                  config false;
                } // alt-local-as-mode

                leaf aggregate-confed {
                  // Low-level model info: Corresponds to bgpUpdateGroupAggregateConfed.
                  type boolean;
                  description
                    "Whether or not the neighbor understands aggregated
                    confederation AS_PATH information.";
                  config false;
                } // aggregate-confed

                leaf reflector-client {
                  // Low-level model info: Corresponds to bgpUpdateGroupReflectorClient.
                  type bgp-peer-reflector-client;
                  description
                    "The peer's type of Route Reflector client.";
                  config false;
                } // reflector-client

                leaf next-hop-self {
                  // Low-level model info: Corresponds to bgpUpdateGroupNextHopSelf.
                  type router-bgp-next-hop-self;
                  description
                    "Whether or not next-hop-self is configured.";
                  config false;
                } // next-hop-self

                leaf third-party-nh-enabled {
                  // Low-level model info: Corresponds to bgpUpdateGroupTPNHEnabled.
                  type boolean;
                  description
                    "Whether or not third-party next hop is enabled.";
                  config false;
                } // third-party-nh-enabled

                leaf third-party-nh-addr-prefix {
                  // Low-level model info: Corresponds to bgpUpdateGroupTPNHAddrPrefix.
                  type interfaces:iface-ip-prefix-t;
                  description
                    "Prefix to match on for third-party next hop.

                    If third-party next hop is disabled for this peer, this
                    field is empty.";
                  config false;
                } // third-party-nh-addr-prefix

                leaf peering-type {
                  // Low-level model info: Corresponds to bgpUpdateGroupPeeringType.
                  type bgp-peering-type;
                  description
                    "The type of peering relationship associated with the peer.";
                  config false;
                } // peering-type

                leaf slow-peer {
                  // Low-level model info: Corresponds to bgpUpdateGroupSlowPeer.
                  type boolean;
                  description
                    "Whether the peer has been marked as slow.";
                  config false;
                } // slow-peer

                leaf remove-private-as-numbers {
                  // Low-level model info: Corresponds to bgpUpdateGroupRemovePrivateASNumbers.
                  type boolean;
                  description
                    "Whether private AS numbers are removed from the AS path
                    before sending an update to the peer.";
                  config false;
                } // remove-private-as-numbers

                leaf conditional-advertisement {
                  // Low-level model info: Corresponds to bgpUpdateGroupCondAdv.
                  type boolean;
                  description
                    "Whether conditional advertisement is enabled.";
                  config false;
                } // conditional-advertisement

                leaf ca-advertise-map-index {
                  // Low-level model info: Corresponds to bgpUpdateGroupCAAdvMap.
                  type uint32;
                  description
                    "The index of the route map used as the advertise map for
                    conditional advertisement.";
                  config false;
                } // ca-advertise-map-index

                leaf ca-non-exist-map-index {
                  // Low-level model info: Corresponds to bgpUpdateGroupCANExMap.
                  type uint32;
                  description
                    "The index of the route map used as the non-exist map for
                    conditional advertisement.";
                  config false;
                } // ca-non-exist-map-index

                leaf config-export-map-index {
                  // Low-level model info: Corresponds to bgpUpdateGroupConfExpMap.
                  type uint32;
                  description
                    "The index of the route map used for filtering exported
                    routes, specified in the peer's configuration.";
                  config false;
                } // config-export-map-index

                leaf send-community {
                  // Low-level model info: Corresponds to bgpUpdateGroupSendComm.
                  type boolean;
                  description
                    "Whether or not to send BGP community attributes.";
                  config false;
                } // send-community

                leaf send-extcommunity {
                  // Low-level model info: Corresponds to bgpUpdateGroupSendExtComm.
                  type boolean;
                  description
                    "Whether or not to send BGP extended community attributes.";
                  config false;
                } // send-extcommunity

                leaf originate-default {
                  // Low-level model info: Corresponds to bgpUpdateGroupOriginateDefault.
                  type boolean;
                  description
                    "Whether BGP should originate a default route.";
                  config false;
                } // originate-default

                leaf originate-default-route-map {
                  // Low-level model info: Corresponds to bgpUpdateGroupOriginateDefaultRtMap.
                  type uint32;
                  description
                    "The index of the route map that is used for default
                    routes.  This is zero if originate_default is false.";
                    config false;
                } // originate-default-route-map

                leaf add-path-send-capability {
                  // Low-level model info: Corresponds to bgpUpdateGroupAddPathSend.
                  type boolean;
                  description
                    "The negotiated BGP additional path (ADD-PATH) send
                    capability.";
                  config false;
                } // add-path-send-capability

                leaf add-path-best-n {
                  // Low-level model info: Corresponds to bgpUpdateGroupAddPathBestN.
                  type uint32;
                  description
                    "The number of best paths to advertise to these peers as
                    additional paths.";
                  config false;
                } // add-path-best-n

                leaf distribution-list-acl-out {
                  // Low-level model info: Corresponds to bgpUpdateGroupDistListAclOut.
                  type int32;
                  description
                    "The Access List index identifying the Access List used
                    to filter routes advertised.  Zero indicates no Access
                    List.";
                  config false;
                } // distribution-list-acl-out

                leaf distribution-list-pl-out {
                  // Low-level model info: Corresponds to bgpUpdateGroupDistListPlOut.
                  type int32;
                  description
                    "The Prefix List index identifying the Prefix List used to
                    filter routes advertised.  Zero indicates no Prefix List.";
                  config false;
                } // distribution-list-pl-out

                leaf filter-list-out {
                  // Low-level model info: Corresponds to bgpUpdateGroupFilterListOut.
                  type uint32;
                  description
                    "The Filter List index identifying the Filter List used to
                    filter routes advertised.  Zero indicates no Filter List.";
                  config false;
                } // filter-list-out

                leaf export-map-index {
                  // Low-level model info: Corresponds to bgpUpdateGroupExportMapIndex.
                  type uint32;
                  description
                    "The index of the route map used for filtering exported
                    routes.";
                  config false;
                } // export-map-index

                leaf export-prefix-list-is-aall {
                  // Low-level model info: Corresponds to bgpUpdateGroupExportPreIsAall.
                  type boolean;
                  description
                    "Whether the export prefix list is an IP prefix access
                    list.";
                  config false;
                } // export-prefix-list-is-aall

                leaf export-prefix-list {
                  // Low-level model info: Corresponds to bgpUpdateGroupExportIpPre.
                  type uint32;
                  description
                    "The index of the prefix list used for route exports.";
                  config false;
                } // export-prefix-list

                leaf use-export-local-pref {
                  // Low-level model info: Corresponds to bgpUpdateGroupUseExportLocalPref.
                  type boolean;
                  description
                    "Whether the peers in this update group have an override
                    local preference value configured.";
                  config false;
                } // use-export-local-pref

                leaf export-local-pref {
                  // Low-level model info: Corresponds to bgpUpdateGroupExportLocalPref.
                  type uint32;
                  description
                    "The override local preference value used for updates sent
                    to the peers in this group.  Zero if an override value is
                    not in use.";
                  config false;
                } // export-local-pref

                leaf min-as-origination-interval {
                  // Low-level model info: Corresponds to bgpUpdateGroupMinASOriginationInt.
                  type uint32;
                  units "seconds";
                  description
                    "Time interval in seconds for determining the minimum
                    amount of time that must elapse between successive
                    advertisements of UPDATE messages that report changes to a
                    route within the advertising BGP speaker's own autonomous
                    system.";
                  config false;
                } // min-as-origination-interval

                leaf min-route-advertise-interval {
                  // Low-level model info: Corresponds to bgpUpdateGroupMinRouteAdvertiseInterval.
                  type uint32;
                  units "seconds";
                  description
                    "Time interval in seconds for the
                    MinRouteAdvertisementInterval timer.  This determines the
                    minimum time between a BGP UPDATE to a peer advertising or
                    withdrawing a route and a subsequent BGP UPDATE to the
                    peer advertising a route to the same destination.";
                  config false;
                } // min-route-advertise-interval

                leaf min-route-withdraw-interval {
                  // Low-level model info: Corresponds to bgpUpdateGroupMinRouteWithdrawInterval.
                  type uint32;
                  units "seconds";
                  description
                    "Time interval in seconds for the MinRouteWithdrawInterval
                    timer.  This is the interval which is enforced between
                    advertisement and subsequent withdrawal of a route.";
                  config false;
                } // min-route-withdraw-interval

                leaf preserve-next-hop {
                  // Low-level model info: Corresponds to bgpUpdateGroupPreserveNh.
                  type boolean;
                  description
                    "Indicates whether the BGP next hop is preserved when
                    forwarding routes to eBGP peers in this update group.";
                  config false;
                } // preserve-next-hop

            } // update-group-state

        } // update-group-state-list

        uses bgp-nlri-prefix-state;
        uses bgp-adj-rib-ip-out;

    } // bgp-base-router

    augment "/bgp:router/bgp:bgp/bgp:global/bgp:address-family" {

      container l2vpn {
          description
              "Configure L2VPN VPLS or EVPN routing";

          user-ext:CLI-comm-help "Configure L2VPN VPLS or EVPN routing";
          user-ext:CLI-no-comm-help "Configure L2VPN VPLS or EVPN routing";

          container vpls {
              description
                  "Configure L2VPN VPLS BGP routing";

              user-ext:CLI-comm-help "Configure L2VPN VPLS BGP routing";
              user-ext:CLI-no-comm-help "Configure L2VPN VPLS BGP routing";

              leaf enable {
                type empty;

                description
                  "Enable advertisement of this multiprotocol capability (disabled by default)";
              }

              uses router-bgp-dampening;

          } // vpls

          container evpn {
              description
                  "Configure L2VPN EVPN BGP routing";

              user-ext:CLI-comm-help "Configure L2VPN EVPN BGP routing";
              user-ext:CLI-no-comm-help "Configure L2VPN EVPN BGP routing";

              leaf enable {
                type empty;

                description
                  "Enable advertisement of this multiprotocol capability (disabled by default)";
              }

              uses router-bgp-dampening;

          } // evpn

      } // l2vpn

      container vpnv4 {
          description
              "Configure VPNv4 BGP routing";

          user-ext:CLI-comm-help "Configure VPNv4 BGP routing";
          user-ext:CLI-no-comm-help "Configure VPNv4 BGP routing";

          container unicast {
              description
                  "Configure VPNv4 unicast BGP routing";

              user-ext:CLI-comm-help "Configure VPNv4 unicast BGP routing";
              user-ext:CLI-no-comm-help "Configure VPNv4 unicast BGP routing";

              leaf enable {
                type empty;

                description
                  "Enable advertisement of this multiprotocol capability (disabled by default)";
              }

              uses router-bgp-af-common-parameters;

          } // unicast

      } // vpnv4

      container vpnv6 {
          description
              "Configure VPNv6 BGP routing";

          user-ext:CLI-comm-help "Configure VPNv6 BGP routing";
          user-ext:CLI-no-comm-help "Configure VPNv6 BGP routing";

          container unicast {
              description
                  "Configure VPNv6 unicast BGP routing";

              user-ext:CLI-comm-help "Configure VPNv6 unicast BGP routing";
              user-ext:CLI-no-comm-help "Configure VPNv6 unicast BGP routing";

              leaf enable {
                type empty;

                description
                  "Enable advertisement of this multiprotocol capability (disabled by default)";
              }

              uses router-bgp-af-common-parameters;

          } // unicast

      } // vpnv6

    } // augment - non-VRF address families

    augment "/bgp:router/bgp:bgp/bgp:global/bgp:neighbor/bgp:address-family" {

      uses neighbor-address-family-vpn-config;

    } // augment - non-VRF neighbor address-families

    augment "/bgp:router/bgp:bgp/bgp:global/bgp:neighbor-interface/bgp:address-family" {

      uses neighbor-address-family-vpn-config;

    } // augment - non-VRF neighbor-interface address-families

    augment "/bgp:router/bgp:bgp/bgp:global/bgp:peer-group/bgp:address-family" {

      container l2vpn {

          description
              "Configure L2VPN address family for BGP peer group";

          user-ext:CLI-comm-help "Configure L2VPN address family for BGP peer group";
          user-ext:CLI-no-comm-help "Configure L2VPN address family for BGP peer group";

          container vpls {
              description
                  "Configure unicast L2VPN address family for BGP peer group";

              user-ext:CLI-comm-help "Configure unicast L2VPN address family for BGP peer group";
              user-ext:CLI-no-comm-help "Configure unicast L2VPN address family for BGP peer group";

              uses router-bgp-peer-group-af-l2vpn-parms;
          }

          container evpn {
              description
                  "Configure EPVN address family for BGP peer group";

              user-ext:CLI-comm-help "Configure EVPN address family for BGP peer group";
              user-ext:CLI-no-comm-help "Configure EVPN address family for BGP peer group";

              uses router-bgp-peer-group-af-l2vpn-parms;
          }

      } // l2vpn

      container vpnv4 {

          description
              "Configure VPNv4 address family for BGP peer group";

          user-ext:CLI-comm-help "Configure VPNv4 address family for BGP peer group";
          user-ext:CLI-no-comm-help "Configure VPNv4 address family for BGP peer group";

          container unicast {
              description
                  "Configure unicast VPNv4 address family for BGP peer group";

              user-ext:CLI-comm-help "Configure unicast VPNv4 address family for BGP peer group";
              user-ext:CLI-no-comm-help "Configure unicast VPNv4 address family for BGP peer group";

              uses router-bgp-peer-group-af-v4v6-parms;
          }

      } // vpnv4

      container vpnv6 {

          description
              "Configure VPNv6 address family for BGP peer group";

          user-ext:CLI-comm-help "Configure VPNv6 address family for BGP peer group";
          user-ext:CLI-no-comm-help "Configure VPNv6 address family for BGP peer group";

          container unicast {
              description
                  "Configure unicast VPNv6 address family for BGP peer group";

              user-ext:CLI-comm-help "Configure unicast VPNv6 address family for BGP peer group";
              user-ext:CLI-no-comm-help "Configure unicast VPNv6 address family for BGP peer group";

              uses router-bgp-peer-group-af-v4v6-parms;
          }

      } // vpnv6

    } // augment - non-VRF peer group address families

    augment "/bgp:router/bgp:bgp/bgp:global/bgp:neighbor-state-list/bgp:neighbor-state/bgp:address-family" {

      container l2vpn {

          description
              "State for L2VPN";

          container vpls {
              description
                  "State for VPLS";

              uses router-bgp-neighbor-af-common-state;
          }

          container evpn {
              description
                  "State for EVPN";

              uses router-bgp-neighbor-af-common-state;
          }

      } // l2vpn

      container vpnv4 {

          description
              "State for VPNv4";

          container unicast {
              description
                  "State for unicast";

              uses router-bgp-neighbor-af-common-state;
          }

      } // vpnv4

      container vpnv6 {

          description
              "State for VPNv6";

          container unicast {
              description
                  "State for unicast";

              uses router-bgp-neighbor-af-common-state;
          }

      } // vpnv6

    } // augment - non-VRF neighbor address family state

    augment "/bgp:router/bgp:bgp/bgp:global/bgp:neighbor-state-list/bgp:neighbor-state/bgp:config/bgp:address-family" {

      // Low-level model info: Corresponds to AMB_BGP_PEER_AFI_SAFI (bgpPeerAfiSafiTable) or AMB_BGP_PEERGR_AFI_SAFI (bgpPeergrAfiSafiTable).

      container l2vpn {

        description
          "BGP Peer L2VPN address family configuration";

        config false;

        container vpls {

          description
            "BGP Peer L2VPN VPLS address-family configuration";

          config false;

          uses bgp-peer-state-af-l2vpn-config;

        } // vpls

        container evpn {

          description
            "BGP Peer EVPN address-family configuration";

          config false;

          uses bgp-peer-state-af-l2vpn-config;

        } // evpn

      } // l2vpn

      container vpnv4 {

        description
          "BGP Peer VPNv4 address family configuration";

        config false;

        // Low-level model info: Corresponds to bgpPeerAfiSafiDisable.
        leaf enabled {
          type boolean;
          description
            "Whether advertisement of Multiprotocol support to the peer is
            enabled for this address family.";
          config false;
        }

        container unicast {

          description
            "BGP Peer VPNv4 unicast address-family configuration";

          config false;

          uses bgp-peer-state-af-v4v6-config;

        } // unicast

      } // vpnv4

      container vpnv6 {

        description
          "BGP Peer VPNv6 address family configuration";

        config false;

        // Low-level model info: Corresponds to bgpPeerAfiSafiDisable.
        leaf enabled {
          type boolean;
          description
            "Whether advertisement of Multiprotocol support to the peer is
            enabled for this address family.";
          config false;
        }

        container unicast {

          description
            "BGP Peer VPNv6 unicast address-family configuration";

          config false;

          uses bgp-peer-state-af-v4v6-config;

        } // unicast

      } // vpnv6

    } // augment - non-VRF neighbor address family configuration state

    grouping nlri-common-state {

      leaf path-id {
        type uint32;
        description
          "The path ID for this NLRI.

          If BGP additional path receive capability was negotiated
          with the peer for this AFI/SAFI then this is the received
          path ID for this NLRI, otherwise it is zero.";
        config false;
      }

      leaf best-route {
        type boolean;
        description
          "An indication of whether or not this route was chosen as
          the best BGP route.";
        config false;
      }

      leaf as-size {
        type bgp-as-size-t;
        description
          "Whether the as-path-string contains two or four
          byte AS numbers.";
        config false;
      }

      leaf as-path-string {
        type string;
        description
          "This is a string depicting the autonomous system path to
          this network which was received from the peer which
          advertised it.  If as-size is four-octet and the peer
          does not support four octet AS numbers this string
          represents the AS_PATH formed by combining the AS_PATH and
          AS4_PATH attributes as detailed in RFC 4893.  Two-octet AS
          numbers appear as four-octet numbers by adding two bytes of
          zero padding.  The format of the string is simply the
          AS_PATH attribute.  It can be converted to a more readable
          format by the management agent.";
        config false;
      }

      leaf origin {
        type bgp-origin-codes;
        description
          "The ultimate origin of the path information.";
        config false;
      }

      leaf next-hop {
        type interfaces:iface-ip-address-allow-zero-t;
        description
          "The address of the border router that should be used to
          access the destination network.  This address is the nexthop
          address received in the UPDATE packet.  The address family
          of this object will be the same as that of the prefix in
          this row.

          Note that for RFC 2545 style double nexthops, this object
          will always contain the global scope nexthop.
          link-local-next-hop will contain the link local
          scope nexthop, if it is present.";
        config false;
      }

      leaf multi-exit-discriminator {
        type uint32;
        description
          "This metric is used to discriminate between multiple exit
          points to an adjacent autonomous system.";
        config false;
      }

      leaf local-preference {
        type uint32;
        description
          "The originating BGP speaker's degree of preference for an
          advertised route.";
        config false;
      }

      leaf atomic-aggregate {
        type bgp-path-attr-atomic-agg;
        description
          "When this object is set to present,
          the ATOMIC_AGGREGATE Path Attribute is present and indicates
          that the NLRI MUST NOT be made more specific.";
        config false;
      }

      leaf aggregator-as {
        type uint32;
        description
          "The AS number of the last BGP speaker that performed
          route aggregation.";
        config false;
      }

      leaf aggregator-address {
        type interfaces:iface-ipv4-address-allow-zero-t;
        description
          "The IP address of the last BGP speaker that performed
          route aggregation.  A value of zero indicates the absence of
          this attribute.  Note propagation of AS of zero is illegal
          in the Internet.";
        config false;
      }

      leaf calculated-local-preference {
        type uint32;
        description
          "The degree of preference calculated by the receiving BGP
          speaker for an advertised route.";
        config false;
      }

      leaf originator-id {
        type meta:router-id;
        description
          "The Originator-ID identifying the router that initially
          advertised this destination to a Route Reflector.  A value
          of 0.0.0.0 indicates the absence of this attribute.";
        config false;
      }

      leaf weight {
        type uint32;
        description
          "The local degree of preference assigned to this route.";
        config false;
      }

      leaf route-flap-config-index {
        type uint32;
        description
          "The index of the route flap configuration table entry
          containing the settings being applied to this route for
          dampening.";
        config false;
      }

      leaf route-flap-penalty {
        type uint32;
        description
          "The current penalty value of this route.  If it is greater
          than the cutoff threshold the route is suppressed.";
        config false;
      }

      leaf route-flap-count {
        type uint32;
        description
          "The number of times this route has flapped since
          statistics were last cleared.";
        config false;
      }

      leaf route-flap-suppressed {
        type boolean;
        description
          "Whether or not this route is suppressed.";
        config false;
      }

      leaf route-flap-time-left {
        type uint32;
        units "seconds";
        description
          "The time left until this route is no longer suppressed.
          Only valid if the route is suppressed.";
        config false;
      }

      leaf ecmp {
        type boolean;
        description
          "Whether or not this route was installed into the
          Forwarding Table as an ECMP route (it may or may not be the
          best BGP route advertised to BGP peers).";
        config false;
      }

      leaf as-path-limit-as {
        type uint32;
        description
          "The AS number of the speaker that attached the
          AS_PATHLIMIT attribute.  A value of 0 indicates the absence
          of this attribute.  Note that propagation of AS of zero is
          illegal in the Internet.";
        config false;
      }

      leaf as-path-limit-upper {
        type uint32;
        description
          "The upper bound on the number of ASes in the AS_PATH
          associated with this route before the route will be
          filtered.  Only valid if as-path-limit-as is non-zero.";
        config false;
      }

      leaf is-active {
        type bgp-nlri-is-active;
        description
          "An indication of whether or not this route is installed in
          the forwarding table.

          If advertise/inactive is set to 'false', then
          this is set to

          - 'active' if the route is installed in the forwarding
          table, or is a route redistributed from another routing
          protocol instance

          - 'inactive' otherwise.

          If advertise/inactive is set to 'true', BGP does
          not track active routes and this leaf set to 'not-tracked'.";
        config false;
      }

      leaf user-data {
        type bgp-user-data-t;
        description
          "User data for this BGP NLRI entry.";
        config false;
      }

      leaf stale {
        type boolean;
        description
          "Whether or not this route was last sent by the peer before
          BGP detected that the peer was restarting.  If the route is
          not re-advertised by the peer before the restart completes,
          BGP will remove the route from its database.  This flag is
          set to 'false' if the peer is not restarting, or if the
          route has been advertised by the peer since the restart.";
        config false;
      }

      leaf flap-start-time {
        type uint32;
        description
          "The value of sysUpTime when this route first flapped.
          This field is only valid if the route has flapped.";
        config false;
      }

      leaf link-local-next-hop {
        type interfaces:iface-ip-address-t;
        description
          "The IPv6 link-local address of the border router that
          should be used to access the destination network.  This
          object is only valid for a prefix with a received RFC 2545
          style double nexthop.";
        config false;
      }

      leaf multi-exit-discriminator-set {
        type boolean;
        description
          "If true, then the route has an associated MED attribute,
          whose value is given in multi-exit-discriminator.  If false,

          the route has no MED attribute, and the value of
          multi-exit-discriminator is undefined.";
        config false;
      }

      leaf history {
        type boolean;
        description
          "If true, then the route is a history route.  If false it
          is current.";
        config false;
      }

      leaf peer-type {
        type bgp-nlri-peer-type;
        description
          "The type of peer that a route was received from, if any.";
        config false;
      }

      // Low-level model info: Corresponds to bgpNlri(Prefix)RemoteAddr(Type).
      leaf peer-address {
        type interfaces:iface-ip-address-t;
        description
          "The address of the BGP peer that a route was learned from, if any.";
        config false;
      }

      // Low-level model info: Corresponds to bgpNlri(Prefix)RemoteAddrScopeId
      leaf peer-scope-id {
        type uint32;
        description
          "The scope ID of the BGP peer address.

          The scope ID is required if the address is an IPv6
          link-local address.  Otherwise, this field will be zero.";
        config false;
      }

      leaf peer-interface {
        type interfaces:iface-name;
        description
          "The local interface used to reach the BGP peer.";
        config false;
      }

      uses community-lists;

    } // nlri-common-state

    grouping l2vpn-evpn-common-state {

      // Low-level model info: Corresponds to AMB_BGP_NLRI (bgpNlriTable) and AMB_BGP_NLRI_PREFIX (bgpNlriPrefixTable).

      choice route-type {

        description
          "The Route Type field defines the encoding of the rest of the EVPN
          NLRI (Route Type specific EVPN NLRI).";

        case auto-discovery {

          container auto-discovery {

            description
              "Ethernet Auto-Discovery (A-D) route.";

            leaf rd {
              type meta:bgp-route-distinguisher;
              description
                "The local EVPN route distinguisher.";
              config false;
            }

            leaf esi {
              type es:esi-t;
              description
                "Ethernet Segment Identifier (ESI).";
              config false;
            }

            leaf ethernet-tag {
              type uint32;
              description
                "Ethernet tag.";
              config false;
            }

            leaf label {
              type uint32;
              description
                "The label or VNI associated with the route.";
              config false;
            }

          } // auto-discovery

        } // auto-discovery

        case mac-ip {

          container mac-ip {

            description
              "MAC/IP Advertisement route.";

            leaf rd {
              type meta:bgp-route-distinguisher;
              description
                "The local EVPN route distinguisher.";
              config false;
            }

            leaf esi {
              type es:esi-t;
              description
                "Ethernet Segment Identifier (ESI).";
              config false;
            }

            leaf ethernet-tag {
              type uint32;
              description
                "Ethernet tag.";
              config false;
            }

            leaf mac-address {
              type meta:mac-address;
              description
                "MAC address.";
              config false;
            }

            leaf ip-addr {
              type interfaces:iface-ip-address-t;
              description
                "IP address.";
              config false;
            }

            leaf label1 {
              type uint32;
              description
                "The first label or VNI associated with the route.";
              config false;
            }

            leaf label2 {
              type uint32;
              description
                "The second label or VNI associated with the route.";
              config false;
            }

          } // mac-ip

        } // mac-ip

        case inclusive-mcast {

          container inclusive-mcast {

            description
              "Inclusive Multicast Ethernet Tag route.";

            leaf rd {
              type meta:bgp-route-distinguisher;
              description
                "The local EVPN route distinguisher.";
              config false;
            }

            leaf ethernet-tag {
              type uint32;
              description
                "Ethernet tag.";
              config false;
            }

            leaf originating-router-addr {
              type interfaces:iface-ip-address-t;
              description
                "The originating router address.";
              config false;
            }

          } // inclusive-mcast

        } // inclusive-mcast

        case ethernet-segment {

          container ethernet-segment {

            description
              "Ethernet Segment route.";

            leaf rd {
              type meta:bgp-route-distinguisher;
              description
                "The local EVPN route distinguisher.";
              config false;
            }

            leaf esi {
              type es:esi-t;
              description
                "Ethernet Segment Identifier (ESI).";
              config false;
            }

            leaf originating-router-addr {
              type interfaces:iface-ip-address-t;
              description
                "The originating router address.";
              config false;
            }

          } // ethernet-segment

        } // ethernet-segment

        case ip-prefix {

          container ip-prefix {

            description
              "IP Prefix route.";

            leaf rd {
              type meta:bgp-route-distinguisher;
              description
                "The local EVPN route distinguisher.";
              config false;
            }

            leaf esi {
              type es:esi-t;
              description
                "Ethernet Segment Identifier (ESI).";
              config false;
            }

            leaf ethernet-tag {
              type uint32;
              description
                "Ethernet tag.";
              config false;
            }

            leaf ip-prefix {
              type interfaces:iface-ip-prefix-t;
              description
                "IP prefix.";
              config false;
            }

            leaf gw-ip-addr {
              type interfaces:iface-ip-address-t;
              description
                "GW IP address.";
              config false;
            }

            leaf label {
              type uint32;
              description
                "The first label or VNI associated with the route.";
              config false;
            }

          } // ip-prefix

        } // ip-prefix

      } // route-type (choice)

    } // l2vpn-evpn-common-state

    // Fields common to all peer-scoped notifications
    grouping peer-notification-id
    {
      leaf vrf-name {
        type meta:l3vpn-vrf-name;
        description
          "The name of the VRF associated with the peer session.  This leaf
           reports an empty string for the global VRF";
      }

      leaf peer-local-address {
        type interfaces:iface-ip-address-t;
        description
          "The local address in use for the Peer Session";
      }

      leaf peer-remote-address {
        type interfaces:iface-ip-address-t;
        description
          "The remote address in use for the Peer Session";
      }

      leaf local-interface {
        type custom:iface-name;

        description
          "Name of local interface on which the neighbor is reachable";
      }
    }

    container router {

        description
            "Configure router";

        user-ext:CLI-comm-help "Configure router";
        user-ext:CLI-no-comm-help "Configure router";

        list bgp {

            description
                "BGP AS configuration";

            user-ext:CLI-comm-help "Configure BGP AS";
            user-ext:CLI-no-comm-help "Remove BGP AS";
            user-ext:CLI-max-elements-errmsg "maximum elements for 'router bgp' exceeded";

//            max-elements "1";

            key "vrf-name";

            leaf vrf-name {
              type meta:l3vpn-vrf-name;
              description
                      "The name of this VRF.  This MAY be equivalent to the RFC2685 VPN-ID.";

              user-ext:CLI-comm-help "Associate configuration with VRF";
              user-ext:CLI-no-comm-help "Clear VRF association";

              must "(not(../global/bgp/router-id) or (../global/bgp/router-id != '0.0.0.0'))" {
                  error-message "If configured, the BGP VRF router-id must be a non-zero unicast address";
              }
            }

            // Low-level model info: Use a value of "four-octet" for bgpRmEntAsSize.
            // Low-level model info: If confederation-identifier is non-zero, then the BGP router belongs to a confederation.
            leaf as-num {
                type router-bgp-as;

                mandatory true;

                description
                    "BGP AS number.";

                user-ext:CLI-param-help "BGP AS number";

                must "(not(../global/bgp/router-id) or (../global/bgp/router-id != '0.0.0.0'))" {
                    error-message "If configured, the BGP router-id must be a non-zero unicast address";
                }              
            }

            // Low-level model info: Corresponds to bgpRmEntConfederationId.
            // Low-level model info: When the router is not in a confederation, the AS number is configured using
            //                       bgpRmEntLocalAs.  When the router is in a confederation, the AS number to use outside
            //                       the confederation is configured using bgpRmEntConferationId.  In this case, the AS
            //                       number to use inside the confederation (i.e. the Member-AS number) is bgpRmEntLocalAs.
            leaf confederation-identifier {
                type router-bgp-as;

                default 0;

                description
                    "The confederation idenifier";

                user-ext:CLI-comm-help "Set the confederation identifier";
                user-ext:CLI-no-comm-help "Set the confederation identifier to default";
                user-ext:CLI-param-help "Set the confederation identifier";
            }

            container global {

              user-ext:CLI-not-command;
              uses bgp-base-router;

              must "((./bgp/router-id) and (./bgp/router-id != '0.0.0.0'))" {
                  error-message "A valid router-id must be configured for BGP";
              }

            }

            list vrf {

              description
                  "BGP VRF configuration";

              user-ext:CLI-comm-help "Configure BGP VRF";
              user-ext:CLI-no-comm-help "Configure or remove BGP VRF";

              key "vrf-name";

              leaf vrf-name {
                type meta:l3vpn-vrf-name;
                description
                        "The name of this VRF.  This MAY be equivalent to the RFC2685 VPN-ID.";

                user-ext:CLI-comm-help "Associate configuration with VRF";
                user-ext:CLI-no-comm-help "Clear VRF association";

                must "(not(../bgp/router-id) or (../bgp/router-id != '0.0.0.0'))" {
                    error-message "If configured, the BGP VRF router-id must be a non-zero unicast address";
                }

              }

              uses bgp-base-router;

            } // vrf

        } // bgp

    } // router

    // -- start RPCs --
    grouping bgp-rm-config {
      leaf as-num {
        type router-bgp-as;
        mandatory true;
        description
            "BGP AS number.";
        user-ext:CLI-param-help "Set AS number";
      }
      leaf vrf-name {
        type meta:l3vpn-vrf-name;
        description
          "The name of this VRF. This may be equivalent to the RFC2685 VPN-ID.";
        user-ext:CLI-comm-help "Set VRF name";
      }
    }

    grouping peer-address-config {
      leaf peer-address {
        type interfaces:iface-ip-address-t;
        mandatory true;
        description
          "Peer address";
          user-ext:CLI-param-help "Set peer address";
      }
    }

    rpc bgp-peer-clear-counters {
      description
        "Clear the bgp counters associated with this peer";
      input {
        uses bgp-rm-config;
        uses peer-address-config;
      }
    }

    rpc bgp-peer-clear-flap-stats {
      description
        "Clear the bgp flap statistics counters associated with this peer";
      input {
        uses bgp-rm-config;
        uses peer-address-config;
        leaf flap-clear-map {
          type uint32;
          description
            "This field is an index to the table of BGP Route Maps. The
             number of times the route has flapped in all routes matching the
             Route Map are cleared. Entries in the Route Map may be set to permit
             (to cause a match) or to deny (to prevent a match).";
        }
      }
    }

    rpc bgp-rm-clear-stats {
      description
        "Reset the peak number of Adj-RIB-Out routes
         and clear the total number of memory allocations for prefixes,
         the total number of memory allocations for routes,
         the total number of memory frees for prefixes and
         the total number of memory frees for routes counters.";
      input {
        uses bgp-rm-config;
      }
    }

    // -- end RPCs --

    // -- start notifications --
    // Low-level model info:  Corresponds to bgpPeerSessionEstablished
    notification session-established {
      description
        "BGP Peer Session has moved into Established state.";
      uses peer-notification-id;
    }

    // Low-level model info:  Corresponds to bgpPeerSessionBackward
    notification session-backward {
      description
        "BGP Peer Session FSM state has undergone a backward transition.";
      uses peer-notification-id;

      leaf new-fsm-state {
        type bgp-peer-state;
        description
          "The BGP Peer's new FSM state";
      }

      leaf old-fsm-state {
        type bgp-peer-state;
        description
          "The BGP Peer's old FSM state";
      }

      leaf error-sent-received {
        type enumeration {
          enum sent {
            description
              "Error was caused by local node sending a Notification";
          }
          enum received {
            description
              "Error was caused by receiving a Notification from remote node";
          }
          enum other {
            description
              "Error was not due to a sent or received Notification";
          }
        }
        description
          "Whether the error was caused by sending or receiving a
           Notification message";
      }

      leaf error-code {
        type identityref {
          base bgp-error-code;
        }
        description "The error code reported in the Notification";
      }

      leaf error-subcode {
        type identityref {
          base bgp-error-subcode;
        }
        description "The error subcode reported in the Notification";
      }
    }
    // Low-level model info:  Corresponds to bgpPeerMaxPrefix
    notification peer-max-prefix {
      description
        "BGP Peer has sent more prefixes than the configured maximum.";

      uses peer-notification-id;
    }

    // Low-level model info:  Corresponds to bgpPeerMaxPrefixClear
    notification peer-max-prefix-clear {
      description
        "BGP Peer has no longer sent more prefixes than the configured
        maximum.";

      uses peer-notification-id;
    }
    // Low-level model info:  Corresponds to bgpPeerAfiSafiPrefixThreshold
    notification peer-prefix-threshold {
      description
        "BGP Peer has sent more prefixes than the configured threshold.";

      uses peer-notification-id;
    }

    // Low-level model info:  Corresponds to bgpPeerAfiSafiPrfxThrshldClear
    notification peer-prefix-threshold-clear {
      description
        "BGP Peer has no longer sent more prefixes than the configured
        threshold.";

      uses peer-notification-id;
    }
    // Low-level model info:  Corresponds to bgpEntRestartHelperChange
    notification peer-restart-helper-change {
      description
        "Restart helper status for a BGP Peer has changed.";

      leaf restart-status {
        type bgp-peer-restart-status;
        description
          "The current state of the peer's restart processing.";
      }

      uses peer-notification-id;
    }

    // Low-level model info:  Corresponds to bgpEntRibSizeWarnTrap
    notification rib-size-warn {
      description
        "The total number of routes in BGP's Adj-RIBs-In has exceeded or
        dropped back below the configured limit.";
      leaf vrf-name {
        type meta:l3vpn-vrf-name;
        description
          "The name of the VRF associated with this BGP instance.  This leaf
           reports an empty string for the global VRF";
      }
      leaf over-limit {
        type boolean;
        description
          "Whether the total number of routes is over the limit or not.";
      }
    }
    // -- end notifications --

} // bgp
