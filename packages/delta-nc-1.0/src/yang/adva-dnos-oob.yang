module adva-dnos-oob {

  yang-version "1";

  // namespace
  namespace  "http://www.advaoptical.com/cim/adva-dnos-oob";

  prefix "adva-dnos-oob";

  import iana-if-type { prefix ift; }
  import openconfig-inet-types { prefix oc-inet; }
  import openconfig-interfaces { prefix oc-if; }
  import openconfig-if-ip { prefix oc-ip; }
  import openconfig-extensions { prefix oc-ext; }
  
  // meta
  organization "ADVA Optical Networking";

  contact
    "ADVA Optical Networking
    www.advaoptical.com";

  description
    "This module defines data related to ADVA out-of-band interface  components in the
    OpenConfig interface model for Agema family.";

  oc-ext:openconfig-version "0.1.1";

  revision "2019-03-05" {
    description
      "Initial revision.";
    reference "0.1.0";
  }

  // OpenConfig specific extensions for module metadata.

  // identity statements

  // typedef statements

  // grouping statements

  // data definition statements

  // augment statements

  // deviate statements

}
