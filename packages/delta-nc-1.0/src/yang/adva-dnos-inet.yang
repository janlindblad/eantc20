module adva-dnos-inet {

  yang-version "1";

  // namespace
  namespace  "http://www.advaoptical.com/cim/adva-dnos-inet";

  prefix "adva-dnos-inet";

  import iana-if-type { prefix ift; }
  import openconfig-inet-types { prefix oc-inet; }
  import openconfig-interfaces { prefix oc-if; }
  import openconfig-if-ip { prefix oc-ip; }
  import openconfig-extensions { prefix oc-ext; }
  import openconfig-vlan { prefix oc-vlan; }
  
  // meta
  organization "ADVA Optical Networking";

  contact
    "ADVA Optical Networking
    www.advaoptical.com";

  description
    "This module defines data related to ADVA INET interface  components in the
    OpenConfig interface model for Agema family.";

  oc-ext:openconfig-version "0.1.1";

  revision "2019-03-05" {
    description
      "Initial revision.";
    reference "0.1.0";
  }

  // OpenConfig specific extensions for module metadata.

  // identity statements

  // typedef statements

  // grouping statements

  // typedef inet-vlan-tag {
  //   type uint32 {
  //     range "2 .. 4095";
  //   }
  //   description "Layer 2 Virtual LAN using 802.1Q";
  // }
  
  // data definition statements

  // augment statements

  // deviate statements

}
