module ldp {

  namespace "http://metaswitch.com/yang/nbu/ldp/201512230000Z";

  prefix ldp;

  import user-extensions { prefix "user-ext"; }
  import interfaces { prefix "interfaces"; }
  import metaswitch-yang-types { prefix meta; }
  import redist { prefix redist; }
//  import metaswitch-custom-yang-types { prefix "custom"; }
  import metaswitch-mpls { prefix "mpls"; }
  import qos { prefix "qos"; }
  import openconfig-interfaces { prefix oc-if; }

  organization "Metaswitch Networks";

  contact "Postal: Metaswitch Networks
                   100 Church Street
                   Enfield
                   EN2 6BQ
                   United Kingdom
           Tel:    +44 20 8366 1177
           E-mail: info@metaswitch.com";

  description
    "Label Distribution Protocol";

  revision 2015-12-23 {
    description "Initial revision.";
  }

  typedef peer-ldp-id {
    type string {
      pattern
        '(([0-9]|[1-9][0-9]|1[0-9][0-9]|2[0-4][0-9]|25[0-5])\.){3}' +
        '([0-9]|[1-9][0-9]|1[0-9][0-9]|2[0-4][0-9]|25[0-5]):' +
        '((6553[0-5])|(655[0-2][0-9])|(65[0-4][0-9]{2})' +
        '|(6[0-4][0-9]{3})|([1-5][0-9]{4})|([0-9]{1,4}))';
    }

    description
      "Peer LDP ID in ldp-ip:label-space format
      (something like 192.168.10.23:65535).";
  }

  typedef ldp-ent-oper-status {
    type enumeration {
      enum unknown                          { value 1; }
      enum enabled                          { value 2; }
      enum disabled                         { value 3; }
    }
    description
      "LDP Entity oper status.";
  }

  typedef ldp-lbl-dist-method {
    type enumeration {
      enum downstream-on-demand             { value 1; }
      enum downstream-unsolicited           { value 2; }
    }
    description
      "LDP label distribution method.";
  }

  typedef ldp-sess-state {
    type enumeration {
      enum nonexistent                      { value 1; }
      enum initialized                      { value 2; }
      enum open-received                    { value 3; }
      enum open-sent                        { value 4; }
      enum operational                      { value 5; }
    }
    description
      "LDP session state.";
  }

  typedef ldp-sess-role {
    type enumeration {
      enum unknown                          { value 1; }
      enum active                           { value 2; }
      enum passive                          { value 3; }
    }
    description
      "LDP session role.";
  }

  typedef ldp-fec-type {
    type enumeration {
      enum prefix                           { value 1; description "Prefix"; }
      enum host-addr                        { value 2; description "Host address"; }
    }
    description
      "LDP FEC type";
  }

  typedef ldp-fec-label-installed {
    type enumeration {
      enum yes                              { value 0; }
      enum no-policy                        { value 1; }
      enum no-liberal                       { value 2; }
    }
    description
      "LDP FEC label installed state.";
  }

  typedef ldp-gr-reconnect {
    type uint32 {
      range "0..1800";
    }
    description
      "(0-1800)";
  }

  typedef ldp-gr-holdtime {
    type uint32 {
      range "1..1800";
    }
    description
      "(1-1800)";
  }

  typedef ldp-keep-alive-hold-timer {
    type uint32 {
      range "1..65535";
    }
    description
      "SECS (1-65535)";
  }

  typedef ldp-hello-hold-timer {
    type uint32 {
      range "0..65535";
    }
    description
      "SECS (0-65535)";
  }

  typedef ldp-upstream-fsm-state {
    type enumeration {
      enum initial                          { value 0; }
      enum querying-route                   { value 1; }
      enum reserving-resources              { value 2; }
      enum ordered-wait                     { value 3; }
      enum cross-connecting                 { value 4; }
      enum sending-mapping-upstream         { value 5; }
      enum mapping-established              { value 6; }
      enum withdrawing-mapping              { value 7; }
      enum releasing-resources              { value 8; }
      enum sending-error                    { value 9; }
      enum rerouting                        { value 10; }
      enum stale-mapping                    { value 11; }
      enum sending-wrong-c-bit              { value 12; }
      enum releasing-after-wrong-c-bit      { value 13; }
    }
    description
      "The current state of an upstream label.";
  }

  typedef ldp-downstream-fsm-state {
    type enumeration {
      enum initial                          { value 0; }
      enum getting-label-req-buf            { value 1; }
      enum awaiting-label-map               { value 2; }
      enum out-seg-processing               { value 3; }
      enum mapping-established              { value 4; }
      enum mapping-liberally-retained       { value 5; }
      enum label-req-retry                  { value 6; }
      enum getting-label-rel-buf            { value 7; }
      enum stale-mapping                    { value 8; }
      enum sending-query-fec                { value 9; }
    }
    description
      "The current state of a downstream label.";
  }

  typedef ldp-egress-label-t {
    type enumeration {
      enum implicit-null      { value 1; description "Use the implicit-NULL label for egress."; }
      enum explicit-null      { value 2; description "Use the explicit-NULL label for egress."; }
    }
    description
      "LDP egress label type";
  }


  feature ldp-lsps {
    description
      "This feature means that the device supports LDP LSPs";
  }


  grouping graceful-restart-config {

    // Low-level model info: Corresponds to AMB_CLDP_PM (dccrldpPmTable).

    container graceful-restart {

      description
        "Configure LDP graceful restart";

      user-ext:CLI-comm-help "Configure LDP graceful restart";
      user-ext:CLI-no-comm-help "Configure LDP graceful restart";

      // Low-level model info: Corresponds to dccrldpPmRestartCapable.
      leaf enable {
        type empty;
        description
            "Enable LDP graceful restart";

        user-ext:CLI-comm-help "Enable LDP graceful restart";
        user-ext:CLI-no-comm-help "Disable LDP graceful restart";
      }

      // Low-level model info: Corresponds to dccrldpPmReconnectTime.
      // Low-level model info: Note that the yang field uses seconds while the MIB field uses milliseconds.
      // Low-level model info: Note that the yang default is different to the MIB default.
      leaf reconnect-timeout {
        type ldp-gr-reconnect;
        default 240;
        units "seconds";
        description
            "Graceful restart reconnection timeout";

        user-ext:CLI-comm-help "Set reconnection timeout in seconds";
        user-ext:CLI-no-comm-help "Set reconnection timeout to default";
        user-ext:CLI-param-help "Set reconnection timeout in seconds";
      }

      // Low-level model info: Corresponds to dccrldpPmRecoveryTime.
      // Low-level model info: Note that the yang field uses seconds while the MIB field uses milliseconds.
      // Low-level model info: Note that the yang default is different to the MIB default.
      leaf forwarding-state-holdtime {
          type ldp-gr-holdtime;
          default 240;
          units "seconds";
          description
              "Graceful restart forwarding state holdtime";

          user-ext:CLI-comm-help "Set forwarding state holdtime in seconds";
          user-ext:CLI-no-comm-help "Set forwarding state holdtime to default";
          user-ext:CLI-param-help "Set forwarding state holdtime in seconds";
      }

    } // graceful-restart

  } // graceful-restart-config

  grouping global-config-for-ldp {

    uses graceful-restart-config;

    // Low-level model info: Corresponds to dccrldpPmDistPrefixTargetSess.
    leaf dist-prefix-target-sess {
      type boolean;
      default true;

      description
        "Configure label distribution for Prefix and Host FECs on
        targeted sessions (that is sessions for which the only
        underlying adjacency is a targeted adjacency)";

        user-ext:CLI-param-help "Set whether label distribution for Prefix and Host FECs on targeted sessions is enabled";
        user-ext:CLI-no-comm-help "Use default enable/disable setting";
        user-ext:CLI-param-help "Set whether label distribution for Prefix and Host FECs on targeted sessions is enabled";

    } // dist-prefix-target-sess

    // Low-level model info: Corresponds to dccrldpPmLdpEntityAutoCreate.
    leaf session-auto-create {
      type empty;

      description
        "DC-LDP creates Entities automatically
        based on known interfaces.  When set to 'false', Entities
        are not automatically created.";

        user-ext:CLI-param-help "Enable LDP sessions auto create";
        user-ext:CLI-no-comm-help "Disable LDP sessions auto create";

    } // session-auto-create

    // Low-level model info: Corresponds to dccrldpPmPolicySupportFlags
    leaf pwe-labels-only {
      type empty;

      description
        "DC-LDP will enforce policy decisions made by the user
        through a number of user exits.";

        user-ext:CLI-param-help "Restrict export/import of LDP labels for PWE FEC only";
        user-ext:CLI-no-comm-help "Remove restriction for export/import of LDP labels";

    } // pwe-labels-only

  } // global-config-for-ldp

  grouping adjacency-config {

    // Low-level model info: Corresponds to fields in both AMB_CLDP_ENT (mplsLdpEntityTable) and AMB_CLDP_IF (mplsLdpInterfaceTable).

    // Low-level model info: Set mplsLdpEntityLabelRetentionMode to liberal.
    // Low-level model info: Set mplsLdpEntityLabelDistMethod to downstream-unsolicited.
    // Low-level model info: Set mplsLdpEntityLabelType to generic.

    container bfd {

      description
        "BFD parameters.";

      user-ext:CLI-comm-help "Configure BFD parameters";
      user-ext:CLI-no-comm-help "Configure BFD parameters";

      // Low-level model info: Corresponds to mplsLdpEntityBfdDesired and mplsLdpInterfaceBfdDesired.
      leaf fast-detect {
        type empty;
        description
          "Indicates whether Bidirectional Forwarding Detection (BFD)
          is desired.";

        user-ext:CLI-comm-help "Enable BFD";
        user-ext:CLI-no-comm-help "Disable BFD";
      }

    } // bfd

    // Low-level model info: Corresponds to mplsLdpEntityKeepAliveHoldTimer and mplsLdpInterfaceKeepAliveHoldTimer.
    // Low-level model info: The default in both cases is 40s.
    leaf holdtime-interval {
      type ldp-keep-alive-hold-timer;
      default 40;
      units "seconds";
      description
        "Keep alive hold timer";

      user-ext:CLI-comm-help "Set keep alive hold timer in seconds";
      user-ext:CLI-no-comm-help "Set keep alive hold timer to default";
      user-ext:CLI-param-help "Set keep alive hold timer in seconds";
    }

    // Low-level model info: Corresponds to mplsLdpEntityHelloHoldTimer and mplsLdpInterfaceHelloHoldTimer.
    // Low-level model info: The default should be 0s for mplsLdpEntityHelloHoldTimer and 15s for mplsLdpInterfaceHelloHoldTimer.
    leaf hello-interval {
      type ldp-hello-hold-timer;
      units "seconds";
      description
        "Hello interval";

      user-ext:CLI-comm-help "Set hello interval in seconds";
      user-ext:CLI-no-comm-help "Set hello interval to default";
      user-ext:CLI-param-help "Set hello interval in seconds";
    }

  } // adjacency-config

  grouping adjacency-state {

    // Low-level model info: Corresponds to read-only fields in AMB_CLDP_ENT (mplsLdpEntityTable).

    leaf oper-status {
      type ldp-ent-oper-status;
      description
        "The operational status of this LDP Entity.

        The value of unknown indicates that the operational
        status cannot be determined at this time.  The value of
        unknown should be a transient condition before changing to
        enabled or disabled.";
      config false;
    }

    container bfd {

      config false;
      description
        "BFD parameters.";

      // Low-level model info: Corresponds to mplsLdpEntityBfdDesired.
      leaf fast-detect {
        type boolean;
        description
          "Indicates whether Bidirectional Forwarding Detection (BFD)
          is configured for this targeted peer.";
      }

    } // bfd

  } // adjacency-state

  grouping adjacency-parameters {

    // Low-level model info: Corresponds to AMB_CLDP_ENT (mplsLdpEntityTable).

    uses adjacency-config;

    container state {

      config false;

      uses adjacency-state;

    } // state

  } // adjacency-parameters

  grouping interface-parameters {

    // Low-level model info: Corresponds to AMB_CLDP_IF (mplsLdpInterfaceTable).

    // Low-level model info: Corresponds to mplsLdpInterfaceEnabled.
    leaf disable {
      type empty;
      description
          "Disable LDP on this interface";

      user-ext:CLI-comm-help "Disable LDP on this interface";
      user-ext:CLI-no-comm-help "Enable LDP on this interface";
    }

    // Low-level model info: Corresponds to mplsLdpInterfaceEgressLabelType.
    leaf egress-label-type {
      type ldp-egress-label-t;
      default "implicit-null";
      description
        "Whether to use standard labels or Implicit-NULL or Explicit-NULL
        egress labels";

      user-ext:CLI-param-help "Configure egress label type";
      user-ext:CLI-comm-help "Configure egress label type";
      user-ext:CLI-no-comm-help "Remove egress label type";
    }

    // Low-level model info: Corresponds to dcLdpIfPhpEnabled.
    leaf php-disable {
      type empty;
      description
        "Indicates whether PHP is disabled on RSVP-TE interface.";
    }

    // Low-level model info: Corresponds to dcLdpIfMaxPduLen.
    leaf max-pdu-length {
      type uint32 {
        range "1..65535";
      }
      units "octets";
      description
        "Maximum PDU length for the network interface.";
    }

    container igp-sync {

      description
        "Configure LDP-IGP sync mechanism";

      user-ext:CLI-comm-help "Config IGP-LDP synchronization";
      user-ext:CLI-no-comm-help "Config IGP-LDP synchronization";

      // Low-level model info: Corresponds to dcLdpIfIgpSyncEnabled.
      leaf enable {
        type empty;
        description
            "Enable IGP-LDP synchronization";

        user-ext:CLI-comm-help "Enable IGP-LDP synchronization";
        user-ext:CLI-no-comm-help "Disable IGP-LDP synchronization";
      }

      // Low-level model info: Corresponds to dcLdpIfIgpSyncHoldTimer.
      leaf holdtime {
        type uint32 {
          range "0..3600";
        }
        default 0;
        units "seconds";
        description
            "IGP-LDP synchronization hold time";

        user-ext:CLI-comm-help "IGP-LDP synchronization hold time in seconds";
        user-ext:CLI-no-comm-help "IGP-LDP synchronization hold time to default";
        user-ext:CLI-param-help "IGP-LDP synchronization hold time in seconds";
      }

    } // igp-sync
    
    uses adjacency-config;

  } // interface-parameters

  grouping neighbor-state {

    // Low-level model info: Corresponds to read-only fields in AMB_CLDP_PEER (mplsLdpPeerTable).

    // Low-level model info: Corresponds to mplsLdpPeerLdpId.
    leaf peer-ldp-id {
      type meta:ldp-id;
      description
        "The peer address";
      config false;
    }

    leaf label-distribution-method {
      type ldp-lbl-dist-method;
      description
        "For any given LDP session, the method of label
        distribution must be specified.";
      config false;
    }

    leaf path-vector-limit {
      type uint32 {
        range "0..255";
      }
      description
        "If the value of this object is 0 (zero) then Loop Dection
        for Path Vectors for this Peer is disabled.

        Otherwise, if this object has a value greater than  zero,
        then Loop Dection for Path Vectors for this peer is
        enabled and the Path Vector Limit is this value.";
      config false;
    }

  } // neighbor-state

  grouping ipv4-neighbor-state {

    // Low-level model info: Corresponds to read-only fields in AMB_CLDP_PEER (mplsLdpPeerTable).

    uses neighbor-state;

    leaf transport-addr {
      type interfaces:iface-ipv4-address-t;
      description
        "The Internet address advertised by the peer in the Hello
        Message or the Hello source address.";
      config false;
    }

  } // ipv4-neighbor-state

  grouping ipv6-neighbor-state {

    // Low-level model info: Corresponds to read-only fields in AMB_CLDP_PEER (mplsLdpPeerTable).

    uses neighbor-state;

    leaf transport-addr {
      type interfaces:iface-ipv6-address-t;
      description
        "The Internet address advertised by the peer in the Hello
        Message or the Hello source address.";
      config false;
    }

  } // ipv6-neighbor-state

  grouping session-state {

    // Low-level model info: Corresponds to read-only fields in AMB_CLDP_SESSION (mplsLdpSessionTable).

    leaf state-last-change {
      type uint32;
      description
        "The value of sysUpTime at the time this Session entered
        its current state as denoted by the mplsLdpSessionState
        object.";
      config false;
    }

    leaf state {
      type ldp-sess-state;
      description
        "The current state of the session.  All of the states
        are based on the state machine for session negotiation
        behavior.";
      config false;
    }

    leaf role {
      type ldp-sess-role;
      description
        "During session establishment the LSR/LER takes either the
        active role or the passive role based on address
        comparisons.  This object indicates whether this LSR/LER
        was behaving in an active role or passive role during this
        session's establishment.

        The value of unknown, indicates that the role is not
        able to be determined at the present time.";
      config false;
    }

    leaf protocol-version {
      type uint32 {
        range "1..65535";
      }
      description
        "The version of the LDP Protocol which this session is
        using.  This is the version of the LDP protocol which has
        been negotiated during session initialization.";
      config false;
    }

    leaf keep-alive-hold-time-remaining {
      type uint32;
      description
        "The keep alive hold time remaining for this session in
        units of hundredths of a second.";
      config false;
    }

    leaf keep-alive-time {
      type ldp-keep-alive-hold-timer;
      units "seconds";
      description
        "The negotiated Keep Alive Time which represents the amount
        of seconds between keep alive messages.";
      config false;
    }

    leaf max-pdu-length {
      type uint32 {
        range "1..65535";
      }
      units "octets";
      description
        "The value of maximum allowable length for LDP PDUs for
        this session.  This value may have been negotiated during
        the Session Initialization.";
      config false;
    }

    leaf discontinuity-time {
      type uint32;
      description
        "The value of sysUpTime on the most recent occasion at
        which any one or more of this session's counters suffered
        a discontinuity.

        If no counters have suffered a discontinuity, this is the value of
        sysUpTime when the component was initialised.";
      config false;
    }

    leaf configured-hold-time {
      type uint32;
      description
        "The locally configured keepalive hold time for this
        session, in seconds.  Note that the value of this field
        reflects configuration at the time of session
        initialization; this may differ from the configuration
        that would apply to a new session, if configuration has
        changed since this session was initialized.";
      config false;
    }

    leaf peer-hold-time {
      type uint32;
      description
        "The peer's advertised keepalive hold time for this session
        in seconds.  Note that the value of this field reflects
        the peer's configuration at the time of session
        initialization; this may differ from the configuration
        that would apply to a new session, if the peer's
        configuration has changed since this session was
        initialized.";
      config false;
    }

    leaf hold-time-in-use {
      type uint32;
      description
        "The keepalive hold time that is currently in use for this
        session, in seconds.";
      config false;
    }

    leaf peer-restart-supp {
      type boolean;
      description
        "Whether the LDP peer has advertized support for Graceful
        Restart on this session.  Derived from the peer's LDP
        initialization message.";
      config false;
    }

    leaf peer-reconnect-time {
      type uint32;
      description
        "The Reconnect Timeout advertized by the LDP peer, or zero
        if the peer has not advertised support for Graceful
        Restart.";
      config false;
    }

    leaf peer-recovery-time {
      type uint32;
      description
        "The Recovery Time advertized by the LDP peer, or zero if
        the peer has not advertised support for Graceful Restart.";
      config false;
    }

    leaf local-restart-supp {
      type boolean;
      description
        "Whether the local LDP router is using Graceful Restart
        procedures on this session.";
      config false;
    }

  } // session-state

  grouping session-stats {

    // Low-level model info: Corresponds to AMB_CLDP_SESS_STATS (mplsLdpSessionStatsTable).

    leaf unknown-message-count {
      type uint32;
      description
        "This object counts the number of Unknown Message Type
        Errors detected by this LSR/LER during this session.";
      config false;
    }

    leaf unknown-tlv-count {
      type uint32;
      description
        "This object counts the number of Unknown TLV Errors
        detected by this LSR/LER during this session.";
      config false;
    }

  } // session-stats

  grouping session-neighbor-addr-state {

    // Low-level model info: Corresponds to AMB_CLDP_SESS_PEER_ADDR
    // (mplsLdpSessionPeerAddrTable).

    leaf peer-addr-index {
      type uint32 {
        range "1..4294967295";
      }
      description
        "An index which uniquely identifies this entry within a
        given session.";
      config false;
    }

    leaf next-hop-address {
      type interfaces:iface-ip-address-t;
      description
        "The next hop address.";
      config false;
    }

  } // session-neighbor-addr-state

  grouping up-label-state {

    // Low-level model info: Corresponds to AMB_CLDP_UP_LABEL (mplsLdpUpLabelTable).

    // Low-level model info: Corresponds to mplsLdpUpLabelType.
    leaf type {
      type ldp-fec-type;
      description
        "The type of the FEC.  Only prefix and hostAddress FECs are
        shown in this table.";
    }

    // Low-level model info: Corresponds to mplsLdpUpLabelPeerId.
    leaf peer-ldp-id {
      type meta:ldp-id;
      description
        "The LDP ID of the peer the label was sent to.";
    }

    leaf label {
      type uint32;
      description
        "The label value.  Includes 0 (explicit NULL) and 3
        (implicit NULL) as well as real label values.";
      config false;
    }

    leaf state {
      type ldp-upstream-fsm-state;
      description
        "The internal LDP FSM state of this upstream label.";
      config false;
    }

    // Low-level model info: Corresponds to mplsLdpUpLabelInterface.
    uses interfaces:iface-id;

  } // up-label-state

  grouping ipv4-up-label-state {

    uses up-label-state;

    // Low-level model info: Corresponds to mplsLdpUpLabelAddressType
    // and mplsLdpUpLabelPrefix(Length).
    leaf label-prefix {
      type interfaces:iface-ipv4-prefix-t;
      description
        "The FEC address prefix.  Always an IPv4 address (length
        4) or IPv6 address (length 16).";
    }

  } // ipv4-up-label-state

  grouping ipv6-up-label-state {

    uses up-label-state;

    // Low-level model info: Corresponds to mplsLdpUpLabelAddressType
    // and mplsLdpUpLabelPrefix(Length).
    leaf label-prefix {
      type interfaces:iface-ipv6-prefix-t;
      description
        "The FEC address prefix.  Always an IPv4 address (length
        4) or IPv6 address (length 16).";
    }

  } // ipv6-up-label-state

  grouping down-label-state {

    // Low-level model info: Corresponds to AMB_CLDP_DOWN_LABEL (mplsLdpDownLabelTable).

    // Low-level model info: Corresponds to mplsLdpDownLabelType.
    leaf type {
      type ldp-fec-type;
      description
        "The type of the FEC.  Only prefix and hostAddress FECs are
        shown in this table.";
    }

    // Low-level model info: Corresponds to mplsLdpDownLabelPeerId.
    leaf peer-ldp-id {
      type meta:ldp-id;
      description
        "The LDP ID of the peer the label was received from.";
    }

    leaf label {
      type uint32;
      description
        "The label value.  Thismay be 0 (explicit NULL), 3
        (implicit NULL), or a real label values.";
      config false;
    }

    leaf installed {
      type ldp-fec-label-installed;
      description
        "Whether the label is installed in the mpls forwarding
        table, or why it was not installed.";
      config false;
    }

    leaf state {
      type ldp-downstream-fsm-state;
      description
        "The internal LDP FSM state of this downstream label.";
      config false;
    }

    leaf label-is-lfa {
      type boolean;
      description
        "Indicates whether or not this downstream label is a
        loop-free alternate label which is providing protection
        for a primary path.";
      config false;
    }

    // Low-level model info: Corresponds to mplsLdpDownLabelInterface.
    uses interfaces:iface-id;

  } // down-label-state

  grouping ipv4-down-label-state {

    // Low-level model info: Corresponds to AMB_CLDP_DOWN_LABEL (mplsLdpDownLabelTable).

    uses down-label-state;

    // Low-level model info: Corresponds to mplsLdpDownLabelAddressType
    // and mplsLdpDownLabelPrefix(Length).
    leaf label-prefix {
      type interfaces:iface-ipv4-prefix-t;
      description
        "The FEC address prefix.  Always an IPv4 address (length
        4) or IPv6 address (length 16).";
    }

    leaf next-hop-address {
      type interfaces:iface-ipv4-address-t;
      description
        "For installed downstream labels, this indicates the
        next-hop IP address.  Always an IPv4 address (length 4) or
        IPv6 address (length 16).

        For ECMP, if multiple out-segments have been programmed
        corresponding to a single downstream mapping (which is
        possible if there are multiple parallel interfaces between
        two peers), this address corresponds to the first such
        out-segment.";
      config false;
    }

  } // ipv4-down-label-state

  grouping ipv6-down-label-state {

    // Low-level model info: Corresponds to AMB_CLDP_DOWN_LABEL (mplsLdpDownLabelTable).

    uses down-label-state;

    // Low-level model info: Corresponds to mplsLdpDownLabelAddressType
    // and mplsLdpDownLabelPrefix(Length).
    leaf label-prefix {
      type interfaces:iface-ipv6-prefix-t;
      description
        "The FEC address prefix.  Always an IPv4 address (length
        4) or IPv6 address (length 16).";
    }

    leaf next-hop-address {
      type interfaces:iface-ipv6-address-t;
      description
        "For installed downstream labels, this indicates the
        next-hop IP address.  Always an IPv6 address (length 4) or
        IPv6 address (length 16).

        For ECMP, if multiple out-segments have been programmed
        corresponding to a single downstream mapping (which is
        possible if there are multiple parallel interfaces between
        two peers), this address corresponds to the first such
        out-segment.";
      config false;
    }

  } // ipv6-down-label-state


  container mpls {

    description
      "MPLS configuration.";

    user-ext:CLI-comm-help "Configure MPLS";
    user-ext:CLI-no-comm-help "Remove MPLS";

    container ldp {

      description
        "LDP global configuration.";

      user-ext:CLI-comm-help "Configure LDP";
      user-ext:CLI-no-comm-help "Remove LDP";

      presence "Enable LDP";

      must "(/mpls:mpls/mpls:router-id)" {
        error-message "If LDP is configured, an MPLS router-id must be defined";
      }

      // Low-level model info: The dccrldpSigUseIPv6Transport field should be set to true so that LDP supports IPv6.
      // Low-level model info: The dccrldpPmAsNumber field is marked in the MIB header as mandatory but can be left unset.
      // Low-level model info: The dccrldpSigIfDiscConfig field should be set to ifConfigUseI3AndMIB.

      uses global-config-for-ldp;

      // Low-level model info: Single entry in mplsLdpEntityTable, can just set mplsLdpEntityIndex to 1.

      // Low-level model info: Corresponds to dccrldpSigTosBits
      // Low-level model info: Note that the yang default is different to the MIB default.
      leaf dscp {
        type qos:dscp-t;
        default "56";
        description
          "The DSCP value to set on outgoing LDP protocol messages.";

        user-ext:CLI-comm-help "DSCP value to set on outgoing LDP protocol messages";
        user-ext:CLI-no-comm-help "Set DSCP value on outgoing LDP protocol messages to default";
        user-ext:CLI-param-help "DSCP value to set for outgoing LDP protocol messages";
      }

      list neighbor {

        // Low-level model info: Corresponds to AMB_CLDP_ENT (mplsLdpEntityTable) for targeted peers.

        description
          "Table containing information about the MPLS Label
           Distribution Protocol Entities which exist on this Label
           Switching Router (LSR) or Label Edge Router (LER).";

        user-ext:CLI-comm-help "Configure targeted peer";
        user-ext:CLI-no-comm-help "Remove targeted peer";

        key "peer-address";

        // Low-level model info: The Mapper should set mplsLdpEntityTargetPeer to true and use the peer address for mplsLdpEntityTargetPeerAddr.
        leaf peer-address {
          type interfaces:iface-ip-address-t;
          description
            "The value of the internetwork layer address used for the
            Extended Discovery.";

          user-ext:CLI-param-help "Peer address";
        }

        // Check that neighbor peer address and the global transport address are of the same type.
        // If no global transport address is specified, the default is an ipv4 Router Id.
        must "(((substring-after(peer-address, ':') = '') and " +
             "  ((not(/mpls:mpls/mpls:transport-address)) or " +
             "   (substring-after(/mpls:mpls/mpls:transport-address, ':') = ''))) or " +
             " ((substring-after(peer-address, ':') != '') and " +
             "  (substring-after(/mpls:mpls/mpls:transport-address, ':') != '')))" {
          error-message "The neighbor peer address and the global transport address must be of the same type";
        }

        uses adjacency-parameters;

      } // neighbor

      container ipv4-state {

        config false;

        container neighbor-state-list {

          description
            "Container to hold neighbor state list.";

          config false;

          list neighbor-state {

            // Low-level model info: Corresponds to AMB_CLDP_PEER
            // (mplsLdpPeerTable).
            // Low-level model info: Ignore the mplsLdpEntityIndex MIB index.

            description
              "Information about LDP peers.";

            config false;

            uses ipv4-neighbor-state;

            container session-state {

              // Low-level model info: Corresponds to AMB_CLDP_SESSION (mplsLdpSessionTable).

              description
                "A read-only list of Sessions between the LDP Entities and
                LDP Peers.  Each entry in this list represents a single
                session.";

              config false;

              uses session-state;

            } // session-state

            container session-stats {

              // Low-level model info: Corresponds to AMB_CLDP_SESS_STATS (mplsLdpSessionStatsTable).

              description
                "A table of statistics for Sessions between LDP Entities and
                LDP Peers.";

              config false;

              uses session-stats;

            } // session-stats

            container session-neighbor-addr-state-list {

              description
                "Container to hold session neighbor address state list.";

              config false;

              list session-neighbor-addr-state {

                // Low-level model info: Corresponds to AMB_CLDP_SESS_PEER_ADDR
                // (mplsLdpSessionPeerAddrTable).

                description
                  "Label Address Information from Label Address Messages
                   received by this LSR from Peers.";

                uses session-neighbor-addr-state;

              } // session-neighbor-addr-state

            } // session-neighbor-addr-state-list

          } // neighbor-state

        } // neighbor-state-list

      } // ipv4-state

      container ipv6-state {

        config false;

        container neighbor-state-list {

          description
            "Container to hold neighbor state list.";

          config false;

          list neighbor-state {

            // Low-level model info: Corresponds to AMB_CLDP_PEER
            // (mplsLdpPeerTable).
            // Low-level model info: Ignore the mplsLdpEntityIndex MIB index.

            description
              "Information about LDP peers.";

            config false;

            uses ipv6-neighbor-state;

            container session-state {

              // Low-level model info: Corresponds to AMB_CLDP_SESSION (mplsLdpSessionTable).

              description
                "A read-only list of Sessions between the LDP Entities and
                LDP Peers.  Each entry in this list represents a single
                session.";

              config false;

              uses session-state;

            } // session-state

            container session-stats {

              // Low-level model info: Corresponds to AMB_CLDP_SESS_STATS (mplsLdpSessionStatsTable).

              description
                "A table of statistics for Sessions between LDP Entities and
                LDP Peers.";

              config false;

              uses session-stats;

            } // session-stats

            container session-neighbor-addr-state-list {

              description
                "Container to hold session neighbor address state list.";

              config false;

              list session-neighbor-addr-state {

                // Low-level model info: Corresponds to AMB_CLDP_SESS_PEER_ADDR
                // (mplsLdpSessionPeerAddrTable).

                description
                  "Label Address Information from Label Address Messages
                   received by this LSR from Peers.";

                uses session-neighbor-addr-state;

              } // session-neighbor-addr-state

            } // session-neighbor-addr-state-list

          } // neighbor-state

        } // neighbor-state-list

      } // ipv6-state

      container discovery {

        description "Configure discovery parameters";

        user-ext:CLI-comm-help "Configure LDP discovery parameters";
        user-ext:CLI-no-comm-help "Configure LDP discovery parameters";

        container interfaces {

//          if-feature interfaces:standard-interfaces;
          user-ext:CLI-not-command;

          list interface {

            description "Per-interface LDP configuration.";
            user-ext:CLI-comm-help "Configure LDP on interface";
            user-ext:CLI-no-comm-help "Configure LDP on interface";

            key "if-name";

            leaf if-name {
              type leafref {
                path "/oc-if:interfaces/oc-if:interface/oc-if:name";
              }
              description
                "A unique identifier identifying the interface.";

              user-ext:CLI-comm-help "Set interface name";
              user-ext:CLI-param-help "Set interface name";
            }

            uses interface-parameters;

          } // interface

        } // interfaces

        container custom-interfaces {

          if-feature interfaces:custom-interfaces;
          user-ext:CLI-not-command;

          container interface {

            description "Per-interface LDP configuration.";
            user-ext:CLI-comm-help "Configure LDP on interface";
            user-ext:CLI-no-comm-help "Configure LDP on interface";

            container oneGE {

              user-ext:CLI-not-command;
              user-ext:CLI-comm-switch "gigabitethernet/gigabitethernet-sub";

              list gigabitethernet {

                description "1G interface";

                user-ext:CLI-comm-help "Add LDP configuration to 1G interface";
                user-ext:CLI-no-comm-help "Remove LDP configuration from 1G interface";

                key "if-num";

                leaf if-num {
                  type interfaces:eth-iface-num-t;
                  description "<unit>/<dev>/<port>";
                  user-ext:CLI-param-help "1G interface name";
                }

                uses interface-parameters;

              } // gigabitethernet

              list gigabitethernet-sub {

                description "1G subinterface";

                user-ext:CLI-comm-help "Add LDP configuration to 1G subinterface";
                user-ext:CLI-no-comm-help "Remove LDP configuration from 1G subinterface";

                key "if-num";

                leaf if-num {
                  type interfaces:eth-subiface-range-t;
                  description "<unit>/<dev>/<port>.<subid>";
                  user-ext:CLI-param-help "Set 1G subinterface name";
                }

                uses interface-parameters;

                } // gigabitethernet-sub

            } // oneGE

            container tenGE {

              user-ext:CLI-not-command;
              user-ext:CLI-comm-switch "tengigabitethernet/tengigabitethernet-sub";

              list tengigabitethernet {

                description "10G interface";

                user-ext:CLI-comm-help "Add LDP configuration to 10G interface";
                user-ext:CLI-no-comm-help "Remove LDP configuration from 10G interface";

                key "if-num";

                leaf if-num {
                  type interfaces:eth-iface-num-t;
                  description "<unit>/<dev>/<port>";
                  user-ext:CLI-param-help "10G interface name";
                }

                uses interface-parameters;

              } // tengigabitethernet

              list tengigabitethernet-sub {

                description "10G subinterface";

                user-ext:CLI-comm-help "Add LDP configuration to 10G subinterface";
                user-ext:CLI-no-comm-help "Remove LDP configuration from 10G subinterface";

                key "if-num";

                leaf if-num {
                  type interfaces:eth-subiface-range-t;
                  description "<unit>/<dev>/<port>.<subid>";
                  user-ext:CLI-param-help "Set 10G subinterface name";
                }

                uses interface-parameters;

              } // tengigabitethernet-sub

            } // tenGE

            container fortyGE {

              user-ext:CLI-not-command;
              user-ext:CLI-comm-switch "fortygigabitethernet/fortygigabitethernet-sub";

              list fortygigabitethernet {

                description "40G interface";

                user-ext:CLI-comm-help "Add LDP configuration to 40G interface";
                user-ext:CLI-no-comm-help "Remove LDP configuration from 40G interface";

                key "if-num";

                leaf if-num {
                  type interfaces:eth-iface-num-t;
                  description "<unit>/<dev>/<port>";
                  user-ext:CLI-param-help "40G interface name";
                }

                uses interface-parameters;

              } // fortygigabitethernet

              list fortygigabitethernet-sub {

                description "40G subinterface";

                user-ext:CLI-comm-help "Add LDP configuration to 40G subinterface";
                user-ext:CLI-no-comm-help "Remove LDP configuration from 40G subinterface";

                key "if-num";

                leaf if-num {
                  type interfaces:eth-subiface-range-t;
                  description "<unit>/<dev>/<port>.<subid>";
                  user-ext:CLI-param-help "Set 40G subinterface name";
                }

                uses interface-parameters;

              } // fortygigabitethernet-sub

            } // fortyGE

            container hundredGE {

              user-ext:CLI-not-command;
              user-ext:CLI-comm-switch "hundredgigabitethernet/hundredgigabitethernet-sub";

              list hundredgigabitethernet {

                description "100G interface";

                user-ext:CLI-comm-help "Add LDP configuration to 100G interface";
                user-ext:CLI-no-comm-help "Remove LDP configuration from 100G interface";

                key "if-num";

                leaf if-num {
                  type interfaces:eth-iface-num-t;
                  description "<unit>/<dev>/<port>";
                  user-ext:CLI-param-help "100G interface name";
                }

                uses interface-parameters;

              } // hundredgigabitethernet

              list hundredgigabitethernet-sub {

                description "100G subinterface";

                user-ext:CLI-comm-help "Add LDP configuration to 100G subinterface";
                user-ext:CLI-no-comm-help "Remove LDP configuration from 100G subinterface";

                key "if-num";

                leaf if-num {
                  type interfaces:eth-subiface-range-t;
                  description "<unit>/<dev>/<port>.<subid>";
                  user-ext:CLI-param-help "Set 100G subinterface name";
                }

                uses interface-parameters;

              } // hundredgigabitethernet-sub

            } // hundredGE

            container bundle-ifaces {

              user-ext:CLI-not-command;
              user-ext:CLI-comm-switch "bundle-ether/bundle-ether-sub";

              list bundle-ether {

                description "Specify the attachment bundle-ether interface";

                user-ext:CLI-comm-help "Configure attachment bundle-ether interface";
                user-ext:CLI-no-comm-help "Remove attachment bundle-ether interface";

                key "bundle-id";

                leaf bundle-id {
                  type interfaces:bundle-id-t;
                  description "Bundle-ether id";
                  user-ext:CLI-param-help "Bundle-ether interface";
                }

                uses interface-parameters;

              } // bundle-ether

              list bundle-ether-sub {

                description "Specify the attachment bundle-ether sub-interface";

                user-ext:CLI-comm-help "Configure attachment bundle-ether sub-interface";
                user-ext:CLI-no-comm-help "Remove attachment bundle-ether sub-interface";

                key "bundle-id";

                leaf bundle-id {
                  type interfaces:bundle-sub-id-t;
                  description "Bundle-ether id";
                  user-ext:CLI-param-help "Attachment bundle-ether sub-interface";
                }

                uses interface-parameters;

              } // bundle-ether-sub

            } // bundle-ifaces

          } // interface

        } // custom-interfaces

      } // discovery

      container address-family {

        description
          "Configure LDP  for address-family";

        user-ext:CLI-comm-help "Configure LDP for address-family";
        user-ext:CLI-no-comm-help "Configure LDP for address-family";

        container ipv4 {

          description
            "Configure IPv4 LDP";

          user-ext:CLI-comm-help "Configure IPv4 LDP";
          user-ext:CLI-no-comm-help "Configure IPv4 LDP";

          container unicast  {

            description
                "Configure IPv4 unicast LDP";

            user-ext:CLI-comm-help "Configure IPv4 unicast LDP";
            user-ext:CLI-no-comm-help "Configure IPv4 unicast LDP";

            container redistribution {

              // Low-level model info: Corresponds to AMB_CIPR_RTM_REDIST (rtmRedistTable).

              description
                "List of redistribution rules.  This list is used to determine
                how routing information is redistributed to routing protocols.";

              user-ext:CLI-comm-help "Configure redistribution information";
              user-ext:CLI-no-comm-help "Remove redistribution information";

              // Low-level model info: Corresponds to rtmRedistInfoSrc = bgp.
              list bgp {

                user-ext:CLI-comm-help "Configure BGP redistribution rule";
                user-ext:CLI-no-comm-help "Configure BGP redistribution rule";

                key "name";

                // Low-level model info: An unique rtmRedistEntryId will be generated for each entry
                leaf name {
                  type redist:redist-name-string;

                  user-ext:CLI-param-help "Redistribution rule name";
                  description
                    "Session name";
                }

                uses redist:common-redist-ipv4;

                leaf path-type-filter {
                  type redist:bgp-redist-path-types;
                  default "bgp-external";
                  description
                    "Value of BGP path type filter, if in use.  If the filter
                    is in use then do not match the source routing information
                    to this redistribution rule if the path type in the source
                    routing information does not match this filter value.";

                  user-ext:CLI-comm-help "Set path type filter";
                  user-ext:CLI-no-comm-help "Set path type filter to default";
                  user-ext:CLI-param-help "Set path type filter";
                }

              } // bgp

              // Low-level model info: Corresponds to rtmRedistInfoSrc = connected, rtmRedistPathType = i3-connected.
              list connected {

                user-ext:CLI-comm-help "Configure connected redistribution rule";
                user-ext:CLI-no-comm-help "Remove connected redistribution rule";

                key "name";

                // Low-level model info: An unique rtmRedistEntryId will be generated for each entry
                leaf name {
                  type redist:redist-name-string;

                  user-ext:CLI-param-help "Rule name";
                  description
                    "Redistribution rule name";
                }

                uses redist:common-redist-ipv4;

              } // connected

              // Low-level model info: Corresponds to rtmRedistInfoSrc = connected, rtmRedistPathType = i3-local.
              list local {

                user-ext:CLI-comm-help "Configure local redistribution rule";
                user-ext:CLI-no-comm-help "Remove local redistribution rule";

                key "name";

                // Low-level model info: An unique rtmRedistEntryId will be generated for each entry
                leaf name {
                  type redist:redist-name-string;

                  user-ext:CLI-param-help "Rule name";
                  description
                    "Redistribution rule name";
                }

                uses redist:common-redist-ipv4;

              } // local

            } // redistribution

          } // unicast

        } // ipv4

        container ipv6 {

          description
            "Configure IPv6 LDP";

          user-ext:CLI-comm-help "Configure IPv6 LDP";
          user-ext:CLI-no-comm-help "Configure IPv6 LDP";

          container unicast  {

            description
                "Configure IPv6 unicast LDP";

            user-ext:CLI-comm-help "Configure IPv6 unicast LDP";
            user-ext:CLI-no-comm-help "Configure IPv6 unicast LDP";

            container redistribution {

              // Low-level model info: Corresponds to AMB_CIPR_RTM_REDIST (rtmRedistTable).

              description
                "List of redistribution rules.  This list is used to determine
                how routing information is redistributed to routing protocols.";

              user-ext:CLI-comm-help "Configure redistribution information";
              user-ext:CLI-no-comm-help "Remove redistribution information";

              // Low-level model info: Corresponds to rtmRedistInfoSrc = bgp.
              list bgp {

                user-ext:CLI-comm-help "Configure BGP redistribution rule";
                user-ext:CLI-no-comm-help "Remove BGP redistribution rule";

                key "name";

                // Low-level model info: An unique rtmRedistEntryId will be generated for each entry
                leaf name {
                  type redist:redist-name-string;

                  user-ext:CLI-param-help "Redistribution rule name";
                  description
                    "Session name";
                }

                uses redist:common-redist-ipv6;

                leaf path-type-filter {
                  type redist:bgp-redist-path-types;
                  default "bgp-external";
                  description
                    "Value of BGP path type filter, if in use.  If the filter is in
                    use then do not match the source routing information to
                    this rule if the path type in the source routing
                    information does not match this filter value.";

                  user-ext:CLI-comm-help "Set path type filter";
                  user-ext:CLI-no-comm-help "Set path type filter to default";
                  user-ext:CLI-param-help "Set path type filter";
                }

              } // bgp

              // Low-level model info: Corresponds to rtmRedistInfoSrc = connected, rtmRedistPathFlt = i3-connected.
              list connected {

                user-ext:CLI-comm-help "Configure connected redistribution rule";
                user-ext:CLI-no-comm-help "Remove connected redistribution rule";

                key "name";

                // Low-level model info: An unique rtmRedistEntryId will be generated for each entry
                leaf name {
                  type redist:redist-name-string;

                  user-ext:CLI-param-help "Rule name";
                  description
                    "Redistribution rule name";
                }

                uses redist:common-redist-ipv6;

              } // connected

              // Low-level model info: Corresponds to rtmRedistInfoSrc = connected, rtmRedistPathFlt = i3-local.
              list local {

                user-ext:CLI-comm-help "Configure local redistribution rule";
                user-ext:CLI-no-comm-help "Remove local redistribution rule";

                key "name";

                // Low-level model info: An unique rtmRedistEntryId will be generated for each entry
                leaf name {
                  type redist:redist-name-string;

                  user-ext:CLI-param-help "Rule name";
                  description
                    "Redistribution rule name";
                }

                uses redist:common-redist-ipv6;

              } // local

            } // redistribution

          } // unicast

        } // ipv6

      } // address-family

      container ipv4-label-state {

        config false;

        container up-label-state-list {

          description
            "Container to hold up label state list.";

          config false;

          list up-label-state {

            // Low-level model info: Corresponds to AMB_CLDP_UP_LABEL
            // (mplsLdpUpLabelTable).

            description
              "List of all upstream labels that have been
              distributed for host and prefix FECs.";

            config false;

            uses ipv4-up-label-state;

          } // up-label-state

        } // up-label-state-list

        container down-label-state-list {

          description
            "Container to hold down label state list.";

          config false;

          list down-label-state {

            // Low-level model info: Corresponds to AMB_CLDP_DOWN_LABEL
            // (mplsLdpDownLabelTable).

            description
              "A read-only table showing all downstream labels that have
              been received and retained/installed for host and prefix
              FECs.";

            config false;

            uses ipv4-down-label-state;

          } // down-label-state

        } // down-label-state-list

      } // ipv4-label-state

      container ipv6-label-state {

        config false;

        container up-label-state-list {

          description
            "Container to hold up label state list.";

          config false;

          list up-label-state {

            // Low-level model info: Corresponds to AMB_CLDP_UP_LABEL
            // (mplsLdpUpLabelTable).

            description
              "A read-only table showing all upstream labels that have been
              distributed for host and prefix FECs.";

            config false;

            uses ipv6-up-label-state;

          } // up-label-state

        } // up-label-state-list

        container down-label-state-list {

          description
            "Container to hold down label state list.";

          config false;

          list down-label-state {

            // Low-level model info: Corresponds to AMB_CLDP_DOWN_LABEL
            // (mplsLdpDownLabelTable).

            description
              "A read-only table showing all downstream labels that have
              been received and retained/installed for host and prefix
              FECs.";

            config false;

            uses ipv6-down-label-state;

          } // down-label-state

        } // down-label-state-list

      } // ipv6-label-state

    } // ldp

  } // mpls

} // ldp
