module cfm {

  namespace "http://metaswitch.com/yang/nbu/cfm/201704210000Z";

  prefix cfm;

  import ietf-yang-types { prefix yang; }
  import interfaces { prefix interfaces; }
  import user-extensions { prefix "user-ext"; }
  import l2vpn { prefix l2vpn; }
  import metaswitch-yang-types { prefix meta; }
  import metaswitch-custom-yang-types { prefix "custom"; }

  organization "Metaswitch Networks";

  contact "Postal: Metaswitch Networks
                   100 Church Street
                   Enfield
                   EN2 6BQ
                   United Kingdom
           Tel:    +44 20 8366 1177
           E-mail: info@metaswitch.com";

  description
    "This YANG module contains the management data definitions for the
     management of Ethernet Services Operations, Administration and
     Maintenance for Connectivity Fault Management.
     Reference Overview:
     This YANG model is closely based on the MEF CFM YANG module
     (http://metroethernetforum.org/ns/yang/mef-cfm).  This is based on
     a number of base documents. The following are the abbreviations for the
     baseline documents:
     [802.1AB] refers to 'Station and Media Access Control Connectivity
     Discovery', IEEE 802.1AB-2009, September 2009
     [802.1q] refers to IEEE 802.1Q-2011 'IEEE Standard for Local and metropolitan
     area networks --Media Access Control (MAC) Bridges and Virtual
     Bridged Local Area Networks, August 2011
     [802-2001] refers to 'IEEE Standard for Local and Metropolitan Area
     Networks: Overview and Architecture', IEEE 802-2001, February 2002
     [MEF30] refers to MEF 30 'Service OAM Fault Management Implementation
     Agreement', January 2011
     [RFC 2737] refers to IETF RFC 2737 'Entity MIB (Version 2)', December 1999
     [RFC 2863] refers to IETF RFC 2863 'The Interfaces Group MIB', June 2000
     [RFC 3419] refers to IETF RFC 3419 'Textual Conventions for Transport
     Addresses', December 2002
     [Y.1731] refers to ITU-T Y.1731 'OAM functions and mechanisms for Ethernet
     based networks', July 2011.

     The differences between this model and the MEF standard comprise:
     - changes due to unsupported function
     - additions required by Metaswitch products.";

  revision 2017-09-21 {
    description "Draft Version 3.";
  }

  revision 2017-07-19 {
    description "Draft Version 2.";
  }

  revision 2017-04-21 {
    description "Initial revision.";
  }


  typedef port-number {
    type uint32 {
      range "0..65535";
    }
  }

  typedef md-domain-name-type {
    type string {
      pattern
        '((([a-zA-Z0-9_]([a-zA-Z0-9\-_]){0,61})?[a-zA-Z0-9]\.)*'
      + '([a-zA-Z0-9_]([a-zA-Z0-9\-_]){0,61})?[a-zA-Z0-9]\.?)'
      + '|\.';
      length "1..43";
    }
  }

  typedef md-name-char-string-type {
    type string {
      length "1..43";
    }
  }

  typedef md-mac-address-integer {
    type uint16 {
      range "0..65535";
    }
  }

  typedef ma-name-char-string-type {
    type string {
      length "1..45";
    }
  }

  typedef ma-name-integer {
    type uint16 {
      range "0..65535";
    }
  }

  typedef ma-icc-based-meg-id-type {
    type string {
      length "1..13";
    }
  }

  typedef mep-id-type {
    type uint32 {
      range "1..8191";
    }
    description
      "Maintenance association End Point Identifier (MEPID): A small integer,
       unique over a given Maintenance Association, identifying a
       specific MEP.";
    reference "[802.1q] 3.19 and 19.2.1";
  }

  // VLAN ID HARDWARE NOTE: VLAN IDs are restricted to 0-4092 with 4093 and
  // 4094 regarded as reserved.  If your hardware has different reserved VLAN
  // Ids or is able to support a range of 0-4094, then you should change the
  // typedef range here and any corresponding help text.
  typedef vlan-id-type {
    type uint32 {
      range "0..4092";
    }
    description
      "The 12-bit VLAN-ID used in the VLAN Tag header.";
    reference "[802.1q] 9.6";
  }

  typedef port-status-type {
    type enumeration {
      enum "no-status-tlv" {
        description
          "Indicates either that no CCM has been received or that
           no port status TLV was present in the last CCM received.";
      }
      enum "blocked" {
        description
          "Ordinary data cannot pass freely through the port on
           which the remote MEP resides. Value of enableRmepDefect
           is equal to false.";
      }
      enum "up" {
        description
          "Ordinary data can pass freely through the port on which
           the remote MEP resides. Value of enableRmepDefect is
           equal to true.";
      }
    }
    description
      "The set of values available from the Port Status TLV in CCM PDUs
       including the default no-status-tlv";
    reference
      "[802.1q] 20.19.3, 12.14.7.6.3:f
       IEEE8021-CFM-MIB.Dot1agCfmPortStatus";
  }

  typedef interface-status-type {
    type enumeration {
      enum "no-status-tlv" {
        description
          "Indicates either that no CCM has been received or that
           no interface status TLV was present in the last CCM received.";
      }
      enum "up" {
        description
          "The interface is ready to pass packets.";
      }
      enum "down" {
        description
          "The interface cannot pass packets.";
      }
      enum "testing" {
        description
          "The interface is in some test mode.";
      }
      enum "unknown" {
        description
          "The interface status cannot be determined for some reason.";
      }
      enum "dormant" {
        description
          "The interface is not in a state to pass packets but is in
           a pending state, waiting for some external event.";
      }
      enum "not-present" {
        description
          "Some component of the interface is missing.";
      }
      enum "lower-layer-down" {
        description
          "The interface is down due to state of the lower layer
           interfaces.";
      }
    }
    description
      "The set of values available from the Interface Status TLV in CCM PDUs
       including the default no-status-tlv";
    reference
      "[802.1q] 20.19.4, 12.14.7.6.3:g
       IEEE8021-CFM-MIB.Dot1agCfmInterfaceStatus";
  }

  typedef mhf-creation-type {
    type enumeration {
      enum "none" {
        description
          "No MHFs can be created for this VID(s).";
      }
      enum "default" {
        description
          "MHFs can be created for this VID(s) on any Bridge Port through which the
           VID(s) can pass where:
           - There are no lower active MD levels; or
           - There is a MEP at the next lower active MD-level on the port.";
      }
      enum "explicit" {
        description
          "MHFs can be created for this VID(s) only on Bridge Ports through which
           this VID(s) can pass, and only if there is a MEP at the next
           lower active MD-level on the port.";
      }
      enum "defer" {
        description
          "In the Maintenance Association managed object only, the control of MHF
           creation is deferred to the corresponding variable in the
           enclosing Maintenance Domain";
      }
    }
    description
      "An enumerated value indicating whether the management entity can create
       MHFs for this VID(s)";
    reference "[802.1q] 22.2.3, 12.14.3.1.3:d";
  }

  typedef port-status-tlv-type {
    type enumeration {
      enum none
      {
        value 0;
        description "none";
      }
      enum up {
        value 1;
        description "up";
      }
      enum down {
        value 2;
        description "down";
      }
      enum testing {
        value 3;
        description "testing";
      }
      enum unknown {
        value 4;
        description "unknown";
      }
      enum dormant {
        value 5;
        description "dormat";
      }
      enum not-present {
        value 6;
        description "not-present";
      }
      enum lower-layer-down {
        value 7;
        description "lower-layer-down";
      }
    }
    description
      "Port Status TLV type";
  }

  typedef interface-status-tlv-type {
    type enumeration {
      enum none {
        value 0;
        description "none";
      }
      enum blocked {
        value 1;
        description "blocked";
      }
      enum up {
        value 2;
        description "up";
      }
    }
    description
      "Interface Status TLV type";
  }

  typedef id-permission-type {
    type enumeration {
      enum "none" {
        description
          "The Sender ID TLV is not to be sent.";
      }
      enum "chassis" {
        description
          "The Chassis ID Length, Chassis ID Subtype, and Chassis ID fields of the
           Sender ID TLV are to be sent, but not the Management Address
           Length or Management Address fields.";
      }
      enum "manage" {
        description
          "The Management Address Length and Management Address of the Sender ID
           TLV are to be sent, but the Chassis ID Length is to be
           transmitted with a 0 value, and the Chassis ID Subtype and
           Chassis ID fields not sent;";
      }
      enum "chassis-manage" {
        description
          "The Chassis ID Length, Chassis ID Subtype, Chassis ID, Management
           Address Length, and Management Address fields are all to be
           sent.";
      }
      enum "defer" {
        description
          "The contents of the Sender ID TLV are determined by the Maintenance
           Domain managed object.";
      }
    }
    description
      "An enumerated value indicating what, if anything, is to be included in
       the Sender ID TLV transmitted by maintenance-points configured in the
       default Maintenance Domain";
    reference "[802.1q] 21.5.3, 12.14.3.1.3:e";
  }

  typedef fault-alarm-defect-type-high {
    type enumeration {
      enum "none" {
        description
          "No defect.";
      }
      enum "remote-rdi" {
        description
          "A remote MEP reported the RDI bit in its last CCM.";
      }
      enum "remote-mac-error" {
        description
          "Indicates that one or more of the remote MEPs is
           reporting a failure in its Port Status TLV or
           Interface Status TLV.";
      }
      enum "remote-invalid-ccm" {
        description
          "Indicates that at least one of the Remote MEP
           state machines is not receiving valid CCMs
           from its remote MEP.";
      }
      enum "invalid-ccm" {
        description
          "Indicates that one or more invalid CCMs has been
           received and that 3.5 times that CCMs transmission
           interval has not yet expired.";
      }
      enum "ccm-ma-level" {
        description
          "The MEP has received at least one CCM whose CCM Interval has
           not yet timed out with an MA level that does not match the
           local configuration.";
      }
      enum "ccm-err" {
        description
          "The MEP has received at least one invalid CCM whose CCM
           Interval has not yet timed out, that is not covered by
           invalid-ccm or ccm-ma-level.";
      }
      enum "cross-connect-ccm" {
        description
          "The MEP has received at least one CCM from another MAID.";
      }
    }
    description
      "An enumerated value indicating the highest priority defect.";
    reference "[802.1q] 20.33.9";
  }

  typedef fault-alarm-defect-type-low {
    type enumeration {
      enum "all" {
        description
          "All defects.";
      }
      enum "remote-rdi" {
        description
          "A remote MEP reported the RDI bit in its last CCM.";
      }
      enum "remote-mac-error" {
        description
          "Indicates that one or more of the remote MEPs is
           reporting a failure in its Port Status TLV or
           Interface Status TLV.";
      }
      enum "remote-invalid-ccm" {
        description
          "Indicates that at least one of the Remote MEP
           state machines is not receiving valid CCMs
           from its remote MEP.";
      }
      enum "invalid-ccm" {
        description
          "Indicates that one or more invalid CCMs has been
           received and that 3.5 times that CCMs transmission
           interval has not yet expired.";
      }
      enum "ccm-ma-level" {
        description
          "The MEP has received at least one CCM whose CCM Interval has
           not yet timed out with an MA level that does not match the
           local configuration.";
      }
      enum "ccm-err" {
        description
          "The MEP has received at least one invalid CCM whose CCM
           Interval has not yet timed out, that is not covered by
           invalid-ccm or ccm-ma-level.";
      }
      enum "cross-connect-ccm" {
        description
          "The MEP has received at least one CCM from another MAID.";
      }
      enum "none" {
        description
          "No defect.";
      }
    }
    description
      "An enumerated value indicating the highest priority defect.";
    reference "[802.1q] 20.33.9";
  }

  typedef transaction-status-type {
    type enumeration {
      enum "not-started" {
        description
          "No attempt has been made to start the Transaction.";
      }
      enum "starting" {
        description
          "An attempt is currently under way to start the Transaction.";
      }
      enum "running" {
        description
          "The Transaction is currently running.";
      }
      enum "complete" {
        description
          "The Transaction has completed successfully.";
      }
      enum "failed-not-started" {
        description
          "The Transaction has failed to start.";
      }
      enum "failed-incomplete" {
        description
          "The Transaction has started successfully but failed
           with incomplete information.";
      }
      enum "stopped" {
        description
          "A running Transaction has been stopped by user input.";
      }
    }
    description
      "An enumerated value indicating the status of an Ethernet OAM
       Loopback or Linktrace Transaction.";
  }

  typedef transaction-diagnostic-type {
    type enumeration {
      enum "no-diagnostic" {
        description
          "No diagnostic information available.";
      }
      enum "activating" {
        description
          "The Transaction is currently being programmed.";
      }
      enum "admin-down" {
        description
          "The Transaction is not active.";
      }
      enum "invalid-config" {
        description
          "The Transaction has received invalid configuration.";
      }
      enum "parent-down" {
        description
          "The parent object for this Transaction is not active.";
      }
      enum "interface-down" {
        description
          "The interface used by this Transaction has not been activated.";
      }
      enum "no-join" {
        description
          "A component required to supports this Transaction is not present.";
      }
      enum "unsuccessful" {
        description
          "A general failure was reported, either when programming the
           Transaction or by an error after the Transaction has been programmed.";
      }
      enum "parameter-error" {
        description
          "A parameter error was reported, either when programming the
           Transaction or by an error after the Transaction has been programmed.";
      }
      enum "resource-failure" {
        description
          "Insufficient resources were reported as available, either
           when programming the Transaction
           or by an error after it has been programmed.";
      }
      enum "timeout" {
        description
          "The request timed out, either when programming the Transaction
          or after it has been programmed.";
      }
      enum "internal-error" {
        description
          "An internal error was reported, either when programming the
           Transaction or by an error after it has been programmed.";
      }
      enum "disabled" {
        description
          "The requested feature is disabled or not initialized.";
      }
      enum "not-available" {
        description
          "The requested feature is not available.";
      }
      enum "not-found" {
        description
          "An attempt was made to configure a Transaction that did not exist.";
      }
      enum "exists" {
        description
          "An attempt was made to create a Transaction that already exists.";
      }
      enum "full" {
        description
          "An attempt to create a Transaction failed because
           the system reached the limit for the number of objects
           configurable.";
      }
      enum "not-started" {
        description
          "The Transaction did not start.";
      }
      enum "stopped" {
        description
          "The Transaction stopped.";
      }
      enum "outside-interval" {
        description
          "The Transaction is outside of configured interval.";
      }
    }
    description
      "An enumerated value indicating the diagnostic status of an Ethernet OAM
       Loopback or Linktrace Transaction.";
  }

  typedef session-id-t {
    type uint32;
    description
      "(0-4294967295)";
  }

  grouping maintenance-domain-name {
    description
      "This grouping uniquely identifies a maintenance domain name.";

    container name {
      description
        "Maintenance Domain name.";

      choice name-type {
        case character-string {
          leaf character-string {
            type md-name-char-string-type;
            description
              "RFC2579 Display String, except that the character
               codes 0-31 (decimal) are not used.";
          }
        }
        case domain-name {
          leaf domain-name {
            type md-domain-name-type;
            description
              "DNS domain name.";
          }
        }
        case ip-address {
          leaf ip-address {
            type interfaces:iface-ip-address-t;
            description
              "IP address.";
          }
        }
        case mac-address-and-uint {
          container mac-address-and-uint {
            description
              "A MAC address and a two-octet unsigned integer.";
            reference "[802.1q] IEEE8021-CFM-MIB.Dot1agCfmMaintDomainNameType";
            leaf mac-address {
              type meta:mac-address;
              description
                "MAC address.";
            }
            leaf integer {
              type md-mac-address-integer;
              description
                "MD name unsigned integer.";
            }
          }
        }
      }
    }
  }

  grouping maintenance-association-name {
    description
      "This grouping uniquely identifies a maintenance association name.";

    container name {
      description
        "Maintenance Association name.";

      when "(../y1731-compliant = 'false')";

      choice name-type {
        case vlan-id {
          leaf vlan-id {
            type vlan-id-type;
            description
              "Specifies the Primary VLAN ID.";
          }
        }
        case character-string {
          leaf character-string {
            type ma-name-char-string-type;
            description
              "RFC2579 Display String, except that the character
               codes 0-31 (decimal) are not used.";
          }
        }
        case integer {
          leaf integer {
            type ma-name-integer;
            description
              "2-octet integer/big endian.";
          }
        }
      }
    }
  }

  grouping maintenance-association-meg-id {
    description
      "This grouping uniquely identifies a maintenance association MEG ID.

       This enumeration indicates the format of the MEG ID that is
       sent in the OAM PDUs. The primary-vid, character-string,
       unsigned-int16, and rfc2865-vpn-id types are more fully
       explained in [802.1q] 17.5. The icc-based type is from [Y.1731]
       Annex A.";

    container meg-id {
      description
        "Maintenance Association MEG ID.";

      when "(../y1731-compliant = 'true')";

      choice meg-id-format {
        case vlan-id {
          leaf vlan-id {
            type vlan-id-type;
            description
              "Primary VLAN ID. 12 bits represented in a 2-octet integer:
               - 4 least significant bits of the first byte contains the
               4 most significant bits of the 12 bits primary VID
               - second byte contains the 8 least significant bits of the
               primary VID";
          }
        }
        case character-string {
          leaf character-string {
            type ma-name-char-string-type;
            description
              "RFC2579 Display String, except that the character
               codes 0-31 (decimal) are not used.";
          }
        }
        case integer {
          leaf integer {
            type ma-name-integer;
            description
              "2-octet integer/big endian.";
          }
        }
        case icc-based {
          leaf icc-based {
            type ma-icc-based-meg-id-type;
            description
              "ICC-based MEG ID Format, thirteen octet field";
          }
        }
      }
    }
  }

  grouping maintenance-association-bd {
    description
      "This grouping identifies a Bridge Domain type and ID.";

    container bd {
      description
        "Bridge Domain type and ID.";

      choice bd-type {
        case vlan {
          leaf vlan-id {
            type vlan-id-type;
            description
              "Specifies the VLAN ID.";
          }
        }
        case vpls {
          leaf vpls-name {
            type leafref {
              path "/l2vpn:l2vpn/l2vpn:bridge-domain/l2vpn:name";
            }
            description
              "Specifies the VPLS name.";
          }
        }
      }
    }
  }

  grouping fault-alarm-defect-bits-type {

    description
      "A set of bits indicating the the current defects:
       - cross-connect-ccm One or more cross connect CCMs has been received
       - invalid-ccm One or more invalid CCMs has been received
       - remote-invalid-ccm At least one of the Remote MEP state machines is not
       receiving valid CCMs from its remote MEP
       - remote-mac-error One or more of the remote MEPs is reporting a failure
       in its Port Status TLV or Interface Status
       - remote-rdi Indicates that at least one of the Remote MEP state machines is
       receiving valid CCMs from its remote MEP that has the RDI bit set.";
    reference "[802.1q] 20.33.9";

    leaf remote-rdi {
      type empty;
      description
        "Remote RDI";
      user-ext:CLI-comm-help "Remote RDI";
    }
    leaf remote-mac-error {
      type empty;
      description
        "Remote MAC error";
      user-ext:CLI-comm-help "Remote MAC error";
    }
    leaf remote-invalid-ccm {
      type empty;
      description
        "Remote invalid CCM";
      user-ext:CLI-comm-help "Remote invalid CCM";
    }
    leaf invalid-ccm {
      type empty;
      description
        "Invalid CCM";
      user-ext:CLI-comm-help "Invalid CCM";
    }
    leaf ccm-ma-level {
      type empty;
      description
        "MA level";
      user-ext:CLI-comm-help "MA level error";
    }
    leaf ccm-err {
      type empty;
      description
        "CCM error";
      user-ext:CLI-comm-help "CCM error";
    }
    leaf cross-connect-ccm {
      type empty;
      description
        "Cross-connect CCM";
      user-ext:CLI-comm-help "Cross-connect CCM";
    }
    leaf ais-received {
      type empty;
      description
        "AIS Received";
      user-ext:CLI-comm-help "AIS Received";
    }
  }

  typedef lbm-transaction-id-type {
    type uint32 {
        range "0..4294967295";
    }
    description
      "A loopback transaction identifier";
    reference "[802.1q] 21.7.3";
  }

  typedef ltm-transaction-id-type {
    type uint32 {
        range "0..4294967295";
    }
    description
      "A linktrace transaction identifier";
    reference "[802.1q] 21.8.3";
  }

  typedef md-level-type {
    type int32 {
      range "0..7";
    }
    description
      "Maintenance Domain Level (MD Level) identifier.  Higher numbers
       correspond to higher Maintenance Domains, those with the greatest
       physical reach, with the highest values for customers' CFM PDUs.
       Lower numbers correspond to lower Maintenance Domains, those with
       more limited physical reach, with the lowest values for CFM PDUs
       protecting single bridges or physical links.";
    reference "[802.1q] 18.3, 21.4.1, IEEE8021-CFM-MIB.Dot1agCfmMDLevel";
  }

  typedef priority-type {
    type uint32 {
      range "0..7";
    }
    description
      "A 3 bit priority value to be used in the VLAN tag, if present
       in the transmitted frame.";
    reference "[802.1q] 12.14.7.3.2:e";
  }

  typedef lm-priority-type {
    type uint32 {
      range "0..7 | 255";
    }
    description
      "A priority value to be used for Loss Measurement
      priority value.";
  }

  typedef remote-mep-state-type {
    type enumeration {
      enum "idle" {
        description
          "Indicates momentary state during reset.";
      }
      enum "start" {
        description
          "Indicates the timer has not expired since the state machine was
           reset, and no valid CCM has yet been received.";
      }
      enum "failed" {
        description
          "Indicates The timer has expired, both since the state machine
           was reset, and since a valid CCM was received.";
      }
      enum "ok" {
        description
          "Indicates The timer has not expired since a valid CCM was
           received.";
      }
    }
    description
      "An enumerated value indicating the operational state of a Remote
       MEP state machine for a remote MEP.";
    reference
      "[802.1q] 12.14.7.6.3:b
       IEEE8021-CFM-MIB.Dot1agCfmRemoteMepState";
  }

  typedef component-id-type {
    type uint32 {
      range "1..4294967295";
    }
    description
      "A Provider Backbone Bridge (PBB) can comprise a number of components,
       each of which can be managed in a manner essentially equivalent
       to an 802.1Q bridge.  In order to access these components easily,
       an index is used in a number of places. If any two lists are
       indexed by component-identifier, then entries in those
       tables indexed by the same value correspond to the same component";
    reference "IEEE8021-CFM-MIB.Dot1agCfmPbbComponentIdentifier";
  }

  grouping target-address-group {
    description
      "An indication of a destination MEP, either:
       1) The MEPID of a MEP; or
       2) An Individual destination MAC address";
    reference "[802.1q] 12.14.7.3.2:b";
    choice address-type {
      description
        "Address type.";
      case mac-address {
        leaf mac-address {
          type meta:mac-address;
          description
            "Target MAC address";
          user-ext:CLI-comm-help "Set target MAC address";
        }
      }
      case mep-id {
        leaf mep-id {
          type mep-id-type;
          description
            "Target MEP ID";
          user-ext:CLI-comm-help "Set target MEP ID";
        }
      }
    }
  }

  grouping loopback-parameters-group {
    description
      "This is the group of parameters associated with Loopback sessions. It is
       used for loopback RPC input.";
    container target-address {
      user-ext:CLI-comm-help "Configure Target Address parameters for Loopback";
      description
        "Target MAC address or MEP ID for the Loopback session.";
      uses target-address-group;
    }
    leaf number-of-messages {
      type uint32 {
        range "1..1024";
      }
      default "1";
      description
        "The number of LBM transmissions in a session.";
      user-ext:CLI-comm-help "Set the number of LBM transmissions in a session";
      reference "[802.1q] 12.14.7.3.2:c, [MEF30] R39";
    }
    leaf data-tlv {
      type binary;
      description
        "An arbitrary amount of data to be included in a Data TLV.";
      user-ext:CLI-comm-help "Set data included in a Data TLV";
      reference "[802.1q] 12.14.7.3.d, IEEE8021-CFM-MIB.dot1agCfmMepTransmitLbmDataTlv";
    }
    leaf vlan-priority {
      type priority-type;
      description
        "The priority parameter to be used in the transmitted LBMs";
      user-ext:CLI-comm-help "Set priority used in transmitted LBMs";
      reference "[802.1q] 12.14.7.3.2:e";
    }
    leaf vlan-drop-eligible {
      type boolean;
      default "true";
      description
        "The drop eligible parameter to be used in the transmitted LBMs";
      user-ext:CLI-comm-help "Set drop eligible value used in transmitted LBMs";
      reference "[802.1q] 12.14.7.3.2:e";
    }
  }

  grouping linktrace-parameters-group {
    description
      "This is the group of parameters associated with linktrace sessions. It is
       used for linktrace RPC input as well as linktrace database entries.";
    container target-address {
      description
        "Target MAC address or MEP ID for the Linktrace session.";
      user-ext:CLI-comm-help "Configure Target Address parameters for Linktrace";
      uses target-address-group;
    }
    container transmit-ltm-flags {
      leaf use-fdb-only
      {
        type empty;
        description
          "Use FBD only";
        user-ext:CLI-comm-help "Set FDB only flag for the Linktrace transaction";
      }
      description
        "The Flags field for LTMs transmitted by the MEP";
      reference "[802.1q] 12.14.7.4.2:b";
    }
    leaf default-ttl {
      type uint32 {
        range "1..255";
      }
      default "64";
      description
        "An initial value for the LTM TTL field";
      user-ext:CLI-comm-help "Set TTL used in Linktrace request";
      reference "[802.1q] 12.14.7.4.2:d";
    }
  }

  grouping md-level-group {
    description
      "Data definitions related to a default MD level";
    leaf md-level {
      type int32 {
        range "-1 | 0..7";
      }
      mandatory true;
      description
        "The MD Level at which MHFs are to be created and Sender ID TLV
         transmission by those MHFs is to be controlled, for the VLAN to
         which this entry's definitions apply. If this leaf has the value
         -1, the MD Level for MHF creation for this VLAN is controlled
         by the content of the default-md-levels container. -1 is not a
         valid value for this parameter when used in the
         default-md-levels.";
      user-ext:CLI-comm-help "Set MD Level";
      reference "[802.1q] 12.14.3.1.3:c";
    }
    leaf mhf-creation {
      type mhf-creation-type;
      default "none";
      description
        "This parameter indicates whether the management entity can create MHFs
         for this VID(s).
         The value 'defer' has different meanings depending on where the grouping is
         used:
         - The value 'defer' is not allowed when this grouping is used in the
         'default-md-levels' container
         - When used in a member of the 'default-md-level' list the value 'defer'
         means that MHF creation for the VLAN is controlled by the corresponding
         'mhf-creation' leaf in the 'default-md-levels' container.";
      user-ext:CLI-comm-help "Set MHF creation type";
      reference "[802.1q] 12.14.3.1.3:d";
    }
    leaf default-id-permission {
      type id-permission-type;
      mandatory true;
      description
        "This parameter indicates what, if anything, is to be included in the
         Sender ID TLV transmitted by MPs configured in a default MD Level";
      user-ext:CLI-comm-help "Set default ID permission";
      reference "[802.1q] 12.14.3.1.3:e";
    }
  }

  grouping port-id-tlv-group {
    description
      "Data definitions associated with the Port ID TLV";
    reference "[802.1AB] 9.5.3";
    choice port-id-subtype {
      config false;
      description
        "Port ID subtype.";
      leaf interface-alias {
        type string {
          length "0..64";
        }
        description
          "The interface alias";
        user-ext:CLI-comm-help "Set Interface alias";
        reference "[RFC2863]";
      }
      leaf port-component {
        type string {
          length "0..32";
        }
        description
          "EntPhysicalAlias when entPhysClass has a value of port(10) or
           backplane(4)";
        user-ext:CLI-comm-help "Set Port component";
        reference "[RFC2737]";
      }
      leaf mac-address-type {
        type meta:mac-address;
        description
          "A MAC address";
        user-ext:CLI-comm-help "Set MAC address";
      }
      leaf network-address {
        type string;
        description
          "network-address is an octet string that identifies a particular network
           address family and an associated network address that are
           encoded in network octet order. An IP address, for example,
           would be encoded with the first octet containing the IANA
           Address Family Numbers enumeration value for the specific
           address type and octets 2 through n containing the address
           value";
        user-ext:CLI-comm-help "Set Network address";
        reference "[802.1AB] Table 9.2";
      }
      leaf interface-name {
        type string {
          length "0..64";
        }
        description
          "The interface name";
        user-ext:CLI-comm-help "Set Interface name";
        reference "[RFC2863]";
      }
      leaf agent-circuit-id {
        type string;
        description
          "Agent circuit ID";
        user-ext:CLI-comm-help "Set Agent circuit ID";
        reference "[RFC3046]";
      }
      leaf local {
        type string;
        description
          "A locally defined identifier";
        user-ext:CLI-comm-help "Set locally defined identifier";
        reference "[802.1AB] Table 9.3";
      }
    }
  }

  grouping sender-id-tlv-group {
    description
      "Data definitions associated with the Sender ID TLV";
    reference "[802.1q] 21.5.3";
    choice chassis-id-subtype {
      config false;
      description
        "The chassis-id-subtype contains the chassis ID entity that is listed in
         the chassis ID field. This is a combination of the 'Chassis ID Subtype'
         and 'chsssis ID' fields";
      reference "[802.1AB] 9.5.2.2";
      leaf chassis-component {
        type string {
          length "0..32";
        }
        description
          "This leaf contains the content of EntPhysicalAlias when entPhysClass has
           a value of chassis(3)";
        reference "[RFC2737]";
      }
      leaf interface-alias {
        type string {
          length "0..64";
        }
        description
          "The interface alias";
        reference "[RFC2863]";
      }
      leaf port-component {
        type string {
          length "0..32";
        }
        description
          "The EntPhysicalAlias when entPhysClass has
           a value of port(10) or backplane(4)";
        reference "[RFC2737]";
      }
      leaf mac-address-type {
        type meta:mac-address;
        description
          "An IEEE 802-2001 Ethernet MAC Address";
        reference "[802-2001]";
      }
      leaf network-address {
        type string;
        description
          "network-address is an octet string that identifies a particular network
           address family and an associated network address that are encoded in
           network octet order. An IP address, for example, would be encoded with
           the first octet containing the IANA Address Family Numbers enumeration
           value for the specific address type and octets 2 through n containing
           the address value";
        reference "[802.1AB] Table 9.2";
      }
      leaf interface-name {
        type string {
          length "0..64";
        }
        description
          "IfName";
        reference "[RFC2863]";
      }
      leaf local {
        type string;
        description
          "A locally assigned alpha-numeric string.";
        reference "[802.1AB] Table 9.2";
      }
    }
    container management-address {
      config false;
      description
        "Data definitions related to the management address fields defined
         in a Sender ID TLV";
      reference "[802.1] Section 21.5.3";
      choice management-address {
        description
          "Management address.";
        case udp-ipv4 {
          description
            "Represents an IPv4 UDP transport address consisting of an IPv4 address,
             and a port number.";
          reference "[RFC3419] TRANSPORT-ADDRESS-MIB.transportDomainUdpIpv4";
          leaf udp-ipv4-address {
            type interfaces:iface-ipv4-address-t;
            description
              "IPv4 address.";
          }
          leaf udp-ipv4-port {
            type port-number;
            description
              "Port number.";
          }
        }
        case udp-ipv6 {
          description
            "Represents an IPv6 UDP transport address consisting of an IPv6 address,
             and a port number.";
          reference "[RFC3419] TRANSPORT-ADDRESS-MIB.transportDomainUdpIpv6";
          leaf udp-ipv6-address {
            type interfaces:iface-ipv6-address-t;
            description
              "IPv6 address.";
          }
          leaf udp-ipv6-port {
            type port-number;
            description
              "Port number.";
          }
        }
      }
    }
  }

  grouping maintenance-domain-reference {
    description
      "This grouping uniquely identifies a maintenance domain.";
    leaf maintenance-domain {
      type string;
      mandatory true;
      description
        "A unique identifier of a Maintenance Domain.";
      user-ext:CLI-comm-help "Set identifier for Maintenance Domain";
    }
  }

  grouping maintenance-association-reference {
    description
      "This grouping uniquely identifies a maintenance association. It consists
       of a maintence-domain-reference and a maintenance-association leaf";
    uses maintenance-domain-reference;
    leaf maintenance-association {
      type string;
      mandatory true;
      description
        "A unique identifier of a Maintenance Association.";
      user-ext:CLI-comm-help "Set identifier for Maintenance Association";
    }
  }

  grouping maintenance-association-end-point-reference {
    description
      "This grouping uniquely identifies a maintenance association end point.
       It consists of a maintenance-association-reference and a
       maintenance-association-end-point leaf";
    uses maintenance-association-reference;
    leaf maintenance-association-end-point {
      type mep-id-type;
      mandatory true;
      description
        "Integer that is unique among all the MEPs in the same MA. Other
         definition is: a small integer, unique over a given
         Maintenance Association, identifying a specific Maintenance
         association End Point.";
      user-ext:CLI-comm-help "Set identifier for MEP";
    }
  }

  container cfm {

  user-ext:CLI-comm-help "Configure CFM";

  list maintenance-domain {

    key "id";
    description
      "A Maintenance Domain managed object is required in order to create an MA
       with a MAID that includes that Maintenance Domain's Name. From
       this Maintenance Domain managed object, all Maintenance
       Association managed objects associated with that Maintenance
       Domain managed object can be accessed, and thus controlled.";
    reference "[802.1q] 12.14.5";
    user-ext:CLI-comm-help "Configure Maintenance Domains";

    leaf id {
      type string;
      description
        "A unique identifier of a Maintenance Domain";
      user-ext:CLI-comm-help "Set identifier for Maintenance Domain";
      reference "[802.1q] 12.14.5";
    }

    uses maintenance-domain-name;

    leaf md-level {
      type md-level-type;
      description
        "Integer identifying the Maintenance Domain Level (MD Level).  Higher
         numbers correspond to higher Maintenance Domains, those with the
         greatest physical reach, with the highest values for customers'
         CFM PDUs.  Lower numbers correspond to lower Maintenance
         Domains, those with more limited physical reach, with the lowest
         values for CFM PDUs protecting single bridges or physical links.";
         user-ext:CLI-comm-help "Set Maintenance Domain Level";
      reference "[802.1q] 12.14.5.1.3:b";
    }
    leaf mhf-creation {
      type mhf-creation-type;
      default "none";
      description
        "A value indicating if the Management entity can create MHFs
         (MIP Half Function) for this VID at this MD Level. The value
         'defer' means that MHF creation for the VLAN is controlled by
         the corresponding 'mhf-creation' leaf in the 'default-md-level'
         list entry.";
      user-ext:CLI-comm-help "Set MHF creation";
      reference "[802.1q] 22.2.3, 12.14.5.1.3:c";
    }
    leaf id-permission {
      type id-permission-type;
      default "none";
      description
        "This parameter indicates what, if anything, is to be included in the
         Sender ID TLV. Since, in this variable, there is no encompassing
         Maintenance Domain, the value 'defer' is not allowed";
      user-ext:CLI-comm-help "Set ID permission";
      reference "[802.1q] 21.5.3, 12.14.6.1.3:d";
    }

    list maintenance-association {
      key "id";
      description
        "This list represents Maintenance Entity Groups (Y.1731) or
         Maintenance Associations (802.1ag). MEGs/MAs are sets of
         MEPs, each configured to the same service inside a common
         OAM domain.";
      user-ext:CLI-comm-help "Configure Maintenance Associations";
      leaf id {
        type string;
        description
          "A unique identifier of a Maintenance Association";
        user-ext:CLI-comm-help "Set identifier for Maintenance Association";
        reference "[802.1q] 12.14.6";
      }

      uses maintenance-association-name;

      leaf mhf-creation {
        type mhf-creation-type;
        default "none";
        description
          "An enumerated value indicating whether the management entity can create
           MHFs for this MA. A value of 'defer' here means that control of
           MHF creation is deferred to the corresponding variable in
           the enclosing maintenance-domain.";
        user-ext:CLI-comm-help "Set MHF creation";
        reference "[802.1q] 12.14.6.1.3:c";
      }
      leaf id-permission {
        type id-permission-type;
        default "defer";
        description
          "This parameter indicates what, if anything, is to be included in the
           Sender ID TLV transmitted by MPs configured in this MA. A
           value of 'defer' means that the contents of the Sender ID
           TLV are determined by the enclosing maintenance-domain instance,";
        user-ext:CLI-comm-help "Set ID permission";
        reference "[802.1q] 12.14.6.1.3:d";
      }
      leaf ccm-interval {
        type enumeration {
          enum "invalid" {
            description
              "No CCMs are sent (disabled).";
          }
          enum "300-hz" {
            description
              "CCMs are sent every 3 1/3 milliseconds (300Hz).";
          }
          enum "10ms" {
            description
              "CCMs are sent every 10 milliseconds.";
          }
          enum "100ms" {
            description
              "CCMs are sent every 100 milliseconds.";
          }
          enum "1s" {
            description
              "CCMs are sent every 1 second.";
          }
          enum "10s" {
            description
              "CCMs are sent every 10 seconds.";
          }
          enum "1min" {
            description
              "CCMs are sent every minute.";
          }
          enum "10min" {
            description
              "CCMs are sent every 10 minutes.";
          }
        }
        default "1s";
        description
          "The interval between CCM transmissions to be used by all MEPs in the MA";
        user-ext:CLI-comm-help "Set CCM interval";
        reference
          "[802.1q] 12.14.6.1.3:e
           IEEE8021-CFM-MIB.Dot1agCfmCcmInterval";
      }
      leaf-list remote-meps {
        type mep-id-type;
        description
          "A list of the MEPIDs of the MEPs in the MA.";
        user-ext:CLI-comm-help "Set Remote MEPs";
        reference "[802.1q] 12.14.6.1.3:g";
      }
      leaf remote-mep-learning {
        type boolean;
        default true;
        description
          "Whether this MA learns remote MEPs from received
           Continuity Check Messages.
           When set to FALSE:
           - The set of remote MEPs for which this node expects to
           receive CCMs is defined by the ethOamMaMepListTable.
           A CCM from any other MEP is treated as an error.
           When set to TRUE:
           - The node accepts received CCMs from any MEP on this MA
           and reports its status on the ethOamMepDbTable.";
        user-ext:CLI-comm-help "Set Remote MEP learning";
      }

      uses maintenance-association-bd;

      list maintenance-association-end-point {
        key "mep-identifier";
        description
          "The list of Maintenance association End Points in a specific Maintenance
           Association.";
        user-ext:CLI-comm-help "Configure Maintenance Association End Points";
        leaf mep-identifier {
          type mep-id-type;
          description
            "Integer that is unique among all the MEPs in the same MA. Other
             definition is: a small integer, unique over a given
             Maintenance Association, identifying a specific Maintenance
             association End Point.";
          user-ext:CLI-comm-help "Set identifier for MEP";
          reference "[802.1q] 12.14.6.3.2:b";
        }
        leaf interface {
          type custom:iface-name;
          mandatory true;
          description
            "An interface, either a Bridge Port or an aggregated IEEE 802.3 port
             within a Bridge Port, to which the MEP is attached. Each interface in
             the system is uniquely identified by an interface-name. ";
          user-ext:CLI-comm-help "Set Interface";
          reference "[802.1q] 12.14.7.1.3:b";
        }
        leaf direction {
          type enumeration {
            enum "up" {
              description
                "Indicates when CFM frames are transmitted towards and
                 received from the bridging function.";
            }
            enum "down" {
              description
                "Indicates when CFM frames are transmitted towards and
                 received from the wire.";
            }
          }
          mandatory true;
          description
            "A value indicating the direction in which the MEP faces on the
             interface.";
          user-ext:CLI-comm-help "Set direction";
          reference "[802.1q] 12.14.7.1.3:c";
        }
        leaf primary-vid {
          type vlan-id-type;
          default 0;
          description
            "The Primary VLAN ID of the MEP. The value 0 indicates that either
             the Primary VLAN ID is that of the MEP's MA or that the MEP's MA
             is associated with no VID.
             If two VLAN tags are required, the VLAN ID for the outer
             VLAN tag is given by this field and the inner VLAN tag is
             specified by inner-vid.";
          user-ext:CLI-comm-help "Set Primary VLAN ID for MEP";
          reference "[802.1q] 12.14.7.1.3:d";
        }
        leaf inner-vid {
          type vlan-id-type;
          default 0;
          description
            "An integer indicating the inner VLAN ID to be used for OAM
             PDUs for the MEP.  A value of 0 indicates that no inner
             VLAN ID is used.";
          user-ext:CLI-comm-help "Set Inner VLAN ID for MEP";
        }
        leaf administrative-state {
          type enumeration {
            enum "up" {
              description
                "Indicates when CFM frames are transmitted towards and
                 received from the bridging function.";
            }
            enum "down" {
              description
                "Indicates when CFM frames are transmitted towards and
                 received from the wire.";
            }
          }
          default "up";
          description
            "The administrative state of the MEP";
          user-ext:CLI-comm-help "Set administrative state for MEP";
          reference "[802.1q] 12.14.7.1.3:e";
        }
        leaf ccm-priority {
          type priority-type;
          default 7;
          description
            "The priority parameter for CCMs transmitted by the MEP.";
          user-ext:CLI-comm-help "Set CCM priority";
          reference "[802.1q] 12.14.7.1.3:h";
        }
        leaf ltm-priority {
          type priority-type;
          default 7;
          description
            "The priority parameter for LTMs transmitted by the MEP.";
          user-ext:CLI-comm-help "Set LTM priority";
          reference "[802.1q] 12.14.7.1.3:h";
        }
        container continuity-check {
          description
            "Data definitions related to the Continuity Check function.";
          user-ext:CLI-comm-help "Configure Continuity Check function";
          container config {
            description
              "Continuity Check configuration.";
            user-ext:CLI-comm-help "Configure Continuity Check";
            leaf cci-enabled {
              type boolean;
              default "false";
              description
                "An indicator of whether the MEP is or is not to generate CCMs";
              user-ext:CLI-comm-help "Configure CCI";
              reference "[802.1q] 12.14.7.1.3:g";
            }
            leaf lowest-fault-priority-defect {
              type fault-alarm-defect-type-low;
              description
                "The lowest priority defect that is allowed to generate a Fault
                 Alarm. The non-existence of this leaf means that no
                 defects are to be reported";
              user-ext:CLI-comm-help "Set lowest priority defect allowed to generate a Fault Alarm";
              reference "[802.1q] 12.14.7.1.3:k";
            }
          }
          container state {
            config false;
            description
              "Continuity Check state.";
            leaf fng-state {
              type enumeration {
                enum "reset" {
                  description
                    "No defect has been present since the
                     fng-reset-time timer expired, or since
                     the state machine was last reset.";
                }
                enum "defect" {
                  description
                    "A defect is present, but not for a long enough
                     time to be reported (fng-alarm-time).";
                }
                enum "report-defect" {
                  description
                    "A momentary state during which the defect is
                     reported by sending a fault-alarm notification,
                     if that action is enabled.";
                }
                enum "defect-reported" {
                  description
                    "A defect is present, and some defect has been
                     reported.";
                }
                enum "defect-clearing" {
                  description
                    "No defect is present, but the fng-reset-time timer
                     has not yet expired.";
                }
              }
              config false;
              description
                "A value indicating the current state of the MEP Fault Notification
                 Generator state machine";
              reference
                "[802.1q] 12.14.7.1.3:f, 20.35
                 IEEE8021-CFM-MIB.Dot1agCfmFngState";
            }
            leaf highest-priority-defect-found {
              type fault-alarm-defect-type-high;
              config false;
              description
                "Value indicating the highest-priority defect that has been
                 present since the MEP Fault Notification Generator state machine
                 was last in the FNG_RESET state The non-existence of this
                 leaf represents that no defect has been present since the
                 last FNG_RESET state";
              reference "[802.1q] 12.14.7.1.3:n";
            }
            container active-defects {
              uses fault-alarm-defect-bits-type;
              config false;
              description
                "A bit field of potential active defects. The values are the same as the
                 content of the fault-alarm-defect-type.";
              reference "[802.1q] 12.14.7.1.3:o, p, q, r, s";
            }
            leaf ccm-sequence-error-count {
              type yang:counter32;
              config false;
              mandatory true;
              description
                "The total number of out-of-sequence CCMs received from all remote
                 MEPs.";
              reference "[802.1q] 12.14.7.1.3:v";
            }
            leaf sent-ccms {
              type yang:counter32;
              config false;
              mandatory true;
              description
                "The total number of CCMs transmitted.";
              reference "[802.1q] 12.14.7.1.3:w";
            }
          }
        }
        container state {
          config false;
          description
            "Maintenance Association End Point state.";
          leaf mac-address {
            type meta:mac-address;
            config false;
            description
              "The MAC address of the MEP";
            reference "[802.1q] 12.14.7.1.3:i";
          }
        } // state
        container loopback {
          config false;
          description
            "Data definitions related to the Loopback function.";
          leaf replies-received {
            type yang:counter32;
            config false;
            mandatory true;
            description
              "The total number of valid, in-order LBRs received.";
            reference "[802.1q] 12.14.7.1.3:y";
          }
          leaf replies-transmitted {
            type yang:counter32;
            config false;
            mandatory true;
            description
              "The total number of LBRs transmitted.";
            reference "[802.1q] 12.14.7.1.3:ad";
          }
          leaf out-of-order-replies-received {
            type yang:counter32;
            config false;
            mandatory true;
            description
              "The total number of valid, out-of-order LBRs received.";
            reference "[802.1q] 12.14.7.1.3:z";
          }
          leaf bad-msdu {
            type yang:counter32;
            config false;
            description
              "The total number of LBRs received whose mac_service_data_unit did not
               match (except for the OpCode) that of the corresponding LBM";
            reference "[802.1q] 12.14.7.1.3:aa";
          }
          leaf loopback-transaction-status {
            type transaction-status-type;
            config false;
            description
              "The status of an Ethernet OAM Loopback Transaction.";
          }
          leaf loopback-transaction-diagnostic {
            type transaction-diagnostic-type;
            config false;
            description
              "The diagnostic status of an Ethernet OAM Loopback Transaction.";
          }
          container multicast-database {
            config false;
            description
              "Data definitions related to the responses from a
               Multicast Loopback message.";
            list multicast-results {
              key "transaction-id receive-order";
              config false;
              description
                "The list of entries in a Multicast Loopback database.";
              leaf transaction-id {
                type lbm-transaction-id-type;
                description
                  "The LBM Transaction Identifier to which the LB entries will be
                   attached";
              }
              leaf receive-order {
                type uint32;
                description
                  "An index to distinguish among multiple LBRs with the same
                   LBR Transaction Identifier field value.
                   ethOamLbMulticastReceiveOrder are assigned sequentially
                   from 1, in the order that the Loopback Initiator received
                   the LBR.";
              }
              leaf reply-mac-address {
                type meta:mac-address;
                description
                  "Source MAC address returned in the LBR Ethernet frame.";
              }
            }
          }
        }
        container linktrace {
          config false;
          description
            "Data definitions related to the Linktrace function.";
          container linktrace-database {
            description
              "Data definitions related to the Linktrace database for a specific MEP";
            container linktrace {
              config false;
              description
                "The list of entries in a Linktrace database.";
              leaf transaction-id {
                type ltm-transaction-id-type;
                description
                  "The LTM Transaction Identifier to which the LTR entries will be
                   attached";
                reference "[802.1q] 12.14.7.5.2:b";
              }
              uses linktrace-parameters-group;
              leaf linktrace-transaction-status {
                type transaction-status-type;
                config false;
                description
                  "The status of an Ethernet OAM Linktrace Transaction.";
              }
              leaf linktrace-transaction-diagnostic {
                type transaction-diagnostic-type;
                config false;
                description
                  "The diagnostic status of an Ethernet OAM Linktrace Transaction.";
              }
              list reply {
                key "reply-order reply-ttl";
                description
                  "The list of LTRs associated with a specific Linktrace
                   transaction.";
                leaf reply-order {
                  type uint32;
                  description
                    "An index to distinguish among multiple LTRs with the same LTR
                     transaction-id field value. reply-order are
                     assigned sequentially from 1, in the order that the
                     Linktrace Initiator received the LTR";
                  reference "[802.1q] 12.14.7.5.2:c";
                }
                leaf reply-ttl {
                  type uint32;
                  description
                    "The integer Reply TTL field value returned in the LTR.";
                  reference "[802.1q] 12.14.7.5.3:b";
                }
                leaf forwarded {
                  type boolean;
                  description
                    "A Boolean value stating whether an LTM was forwarded by
                     the responding MP.";
                  reference "[802.1q] 12.14.7.5.3:c";
                }
                leaf terminal-mep {
                  type boolean;
                  description
                    "A Boolean value stating whether the forwarded LTM reached
                     a MEP for its MA.";
                  reference "[802.1q] 12.14.7.5.3:d";
                }
                leaf last-egress-identifier {
                  type meta:mac-address;
                  description
                    "The MAC address of the Last Egress Identifier
                     returned in the LTR Egress Identifier TLV of the LTR.";
                  reference "[802.1q] 12.14.7.5.3:e";
                }
                leaf next-egress-identifier {
                  type meta:mac-address;
                  description
                    "The MAC address of the Next Egress Identifier
                     returned in the LTR Egress Identifier TLV of the LTR";
                  reference "[802.1q] 12.14.7.5.3:f";
                }
                leaf ltr-relay {
                  type enumeration {
                    enum "hit" {
                      description
                        "Indicates the LTM reached an MP whose MAC
                         address matches the target MAC address.";
                    }
                    enum "filtering-database" {
                      description
                        "Indicates the Egress Port was determined by
                         consulting the Filtering Database.";
                    }
                    enum "mip-ccm-database" {
                      description
                        "Indicates the Egress Port was determined by
                         consulting the MIP CCM Database.";
                    }
                  }
                  description
                    "An enumerated value indicating the value returned in the
                     Relay Action field.";
                  reference
                    "[802.1q] 12.14.7.5.3:g, Table 21-27
                     IEEE8021-CFM-MIB.Dot1agCfmRelayActionFieldValue";
                }
                uses sender-id-tlv-group;
                leaf ingress-action {
                  type enumeration {
                    enum "no-tlv" {
                      description
                        "Indicates that the Linktrace Reply does
                         not contain an ingress TLV.";
                    }
                    enum "ok" {
                      description
                        "Indicates the target data frame would be
                         passed through to the MAC Relay Entity.";
                    }
                    enum "interface-down" {
                      description
                        "Indicates that the input interface is down.";
                    }
                    enum "port-blocked" {
                      description
                        "Indicates the target data frame would not
                         be forwarded if received on this Port due
                         to active topology enforcement.";
                    }
                    enum "vlan-filtered" {
                      description
                        "Indicates the ingress port is not in the
                         member set of the LTMs VID, and ingress
                         filtering is enabled, so the target data
                         frame would be filtered by ingress filtering.";
                    }
                  }
                  description
                    "An enumerated value indicating the value returned in the
                     Ingress Action field. This leaf is not present if no value
                     is returned in the LTR.";
                  reference
                    "[802.1q] 12.14.7.5.3:k, Table 21-30
                     IEEE8021-CFM-MIB.Dot1agCfmIngressActionFieldValue";
                }
                leaf ingress-mac {
                  type meta:mac-address;
                  description
                    "The MAC address returned in the Ingress MAC Address field.
                     This leaf is not present if no value is returned in the LTR.";
                  reference "[802.1q] 12.14.7.5.3:l";
                }
                container ingress-port-id {
                  uses port-id-tlv-group;
                  description
                    "The Ingress Port ID field and the corresponding port ID value.
                     This leaf is not present if no value is returned in the LTR.";
                  reference "[802.1q] 12.14.7.5.3:m";
                }
                leaf egress-action {
                  type enumeration {
                    enum "no-tlv" {
                      description
                        "Indicates that the Linktrace Reply does
                         not contain an egress TLV.";
                    }
                    enum "ok" {
                      description
                        "Indicates the targeted data frame would be
                         forwarded.";
                    }
                    enum "interface-down" {
                      description
                        "Indicates the Egress Port can be identified,
                         but that Bridge Ports MAC Operational
                         parameter is false.";
                    }
                    enum "port-blocked" {
                      description
                        "Indicates the Egress Port can be identified,
                         but the data frame would not pass through the
                         Egress Port due to active topology management, i.e.,
                         the Bridge Port is not in the Forwarding state.";
                    }
                    enum "vlan-filtered" {
                      description
                        "Indicates the Egress Port can be identified,
                         but the Bridge Port is not in the LTMs VIDs
                         member set, so would be filtered by egress
                         filtering.";
                    }
                  }
                  description
                    "An enumerated value indicating the value returned in the
                     Egress Action field. This leaf is not present if no value
                     is returned in the LTR.";
                  reference
                    "[802.1q] 12.14.7.5.3:o, Table 21-32
                     IEEE8021-CFM-MIB.Dot1agCfmIngressActionFieldValue";
                }
                leaf egress-mac {
                  type meta:mac-address;
                  description
                    "The MAC address returned in the Egress MAC Address field.
                     This leaf is not present if no value is returned in the LTR.";
                  reference "[802.1q] 12.14.7.5.3:p";
                }
                container egress-port-id {
                  uses port-id-tlv-group;
                  description
                    "The Egress Port ID field and the corresponding port ID value.
                     This leaf is not present if no value is returned in the LTR.";
                  reference "[802.1q] 12.14.7.5.3:p, 12.14.7.5.3:q";
                }
                leaf organization-specific-tlv {
                  type binary {
                    length "0|4 .. 1500";
                  }
                  description
                    "The OUI and contents of any Organization-Specific TLVs. This
                     leaf is not present if no value is returned in the LTR.";
                  reference "[802.1q] 12.14.7.5.3:s";
                }
              }
            }
          }
        }
        container remote-mep-database {
          config false;
          description
            "The MEP CCM database";
          list remote-mep {
            key "remote-mep-id";
            description
              "The list of remote MEPs in the MEP CCM database";
            reference "[802.1q] 12.14.7.6";
            leaf remote-mep-id {
              type mep-id-type;
              description
                "The MEPID of a remote MEP";
              reference "[802.1q] 12.14.7.6.2";
            }
            leaf remote-mep-state {
              type remote-mep-state-type;
              description
                "An enumerated value indicating the operational state of the
                 Remote MEP state machine for this remote MEP.";
              reference
                "[802.1q] 12.14.7.6.3:b
                 IEEE8021-CFM-MIB.Dot1agCfmRemoteMepState";
            }
            leaf failed-ok-time {
              type yang:timeticks;
              description
                "The time (SysUpTime, IETF RFC 3418) at which the Remote MEP state
                 machine last entered either the RMEP_FAILED or RMEP_OK
                 state, or 0 if it has not yet entered either of those
                 states";
              reference "[802.1q] 12.14.7.6.3:c";
            }
            leaf mac-address {
              type meta:mac-address;
              description
                "The MAC address of the remote MEP.";
              reference "[802.1q] 12.14.7.6.3:d";
            }
            leaf rdi {
              type boolean;
              description
                "An indication of the state of the RDI bit in the last received CCM,
                 true for RDI = 1, or false for RDI = 0 or if none has been
                 received.";
              reference "[802.1q] 12.14.7.6.3:e";
            }
            leaf port-status-tlv {
              type port-status-type;
              description
                "The enumerated value from the Port Status TLV from the last
                 CCM received from the remote MEP.";
              reference "[802.1q] 12.14.7.6.3:f";
            }
            leaf interface-status-tlv {
              type interface-status-type;
              description
                "The enumerated value from the Interface Status TLV from the
                 last CCM received from the remote MEP";
              reference "[802.1q] 12.14.7.6.3:g";
            }
            uses sender-id-tlv-group;
          }
        }
      }
    }
  } // maintenance-domain
  } // cfm


  rpc transmit-loopback {
    description
      "Start a loopback session on a specific MEP
       The counters in the loopback container of the associated MEP will be updated
       with the result of the loopback session until the configured number of messages
       have been sent.";
    reference "[802.1q] 12.14.7.3";
    input {
      uses maintenance-association-end-point-reference;
      uses loopback-parameters-group;
    }
  }
  rpc abort-loopback {
    description
      "Administratively abort a loopback session in progress on a specific MEP";
    reference "[MEF30] 8.2, R28";
    input {
      uses maintenance-association-end-point-reference;
    }
  }
  rpc destroy-loopback {
    description
      "Administratively destroy all state related to a loopback session on a
       specific MEP";
    input {
      uses maintenance-association-end-point-reference;
    }
  }
  rpc transmit-linktrace {
    description
      "Start a linktrace session on a specific MEP
       A list entry in the linktrace-database of the associated MEP will
       be created for each successfully started linktrace session. The
       RPC output transaction-id corresponds to the transaction-id in the
       database for the specific session.";
    reference "[802.1q] 12.14.7.4";
    input {
      uses maintenance-association-end-point-reference;
      uses linktrace-parameters-group;
    }
  }
  rpc abort-linktrace {
    description
      "Administratively abort a linktrace session in progress on a specific MEP";
    reference "[MEF30] 8.2, R28";
    input {
      uses maintenance-association-end-point-reference;
    }
  }
  rpc destroy-linktrace {
    description
      "Administratively destroy all state related to a linktrace session on a
       specific MEP";
    input {
      uses maintenance-association-end-point-reference;
    }
  }

  typedef interval-type-ais-lck-type {
    type enumeration {
      enum "1s" {
        description
          "A one second transmission interval";
      }
      enum "1min" {
        description
          "A one minute transmission interval";
      }
    }
    description
      "This enumeration data type defines the AIS/LCK interval (transmission
       period for a frame)";
    reference "[Y.1731] sections 7.4, 7.6; [MEF7.1] III.2";
  }

  typedef operational-state-type {
    type enumeration {
      enum "enabled" {
        description
          "The MEP is able to provide OAM capabilities and has been set to
           active via the 'administrative-state' leaf.";
      }
      enum "disabled" {
        description
          "The MEP is not able to provide OAM capabilities, for example
           because it has been disabled via the administrative-state leaf,
           has detected an operational failure condition, or has failed an
           internal test.";
      }
      enum "testing" {
        description
          "The MEP has been placed into a test mode, either a troubleshooting
           mode or ETH-Test 'Out-of-service' mode.";
      }
      enum "unknown" {
        description
          "The MEP is unable to report the operational state.";
      }
    }
    description
      "This attribute indicates the operational state (current capability) of
       a MEP.";
    reference "[MEF7.1] 9.2.5";
  }

  typedef test-pattern-type {
    type enumeration {
      enum "null-signal-without-crc-32" {
        description
          "Null signal without CRC-32";
      }
      enum "null-signal-with-crc-32" {
        description
          "Null signal with CRC-32";
      }
      enum "prbs-2311-without-crc-32" {
        description
          "PRBS 2^31-1 without CRC-32";
      }
      enum "prbs-2311-with-crc-32" {
        description
          "PRBS 2^31-1 with CRC-32";
      }
    }
    description
      "This enumeration data type indicates the type of test pattern to be
       sent in an OAM PDU Data TLV";
    reference "[Y.1731]";
  }

  grouping locked-signal-parameters-group {
    description
      "Data definitions related to the administrative locking state of the MEP";
    leaf state {
      type enumeration {
        enum "lock" {
          description
            "Indicates the resource is administratively prohibited from use.";
        }
        enum "unlock" {
          description
            "Indicates the resource is not administratively prohibited from use.";
        }
      }
      description
        "This attribute specifies the locking state. If state is 'lock',the
         MEP will be administratively locked. If state is 'unlock',
         the MEP will be administratively unlocked if previously
         locked.";
      reference "[MEF7.1] 9.3.4.2";
    }
    leaf interval {
      type interval-type-ais-lck-type;
      default "1s";
      description
        "This attribute specifies the ETH-LCK transmission period. The default
         value is 1 frame per second.";
      reference "[MEF7.1] 9.3.4.2";
    }
    leaf priority {
      type priority-type;
      description
        "This attribute specifies the priority of frames with ETH-LCK
         information.";
      reference "[MEF7.1] 9.3.4.2";
    }
    leaf client-meg-level {
      type md-level-type;
      description
        "The MEG/Maintenance Domain Level of the Client LCK PDU (transmitted
         level).";
      reference "[Y.1731] 7.6";
    }
  }

  augment "/cfm/maintenance-domain/maintenance-association" {
    description
      "This set of data definitions represents the Maintenance Entity Group (Y.1731)
       configuration that is unique from the Maintenance Association.";
    leaf y1731-compliant {
      type boolean;
      default "false";
      description
        "A boolean flag to indicate whether the MEG ID/MAID for this MEG operates
         in conformance with 802.1q (if false) or Y.1731 (if true).
         When set to false:
         - The format of the MAID (Maintenance Association ID) is controlled
         by the name-type and name in the maintenance-association instance,
         and the name-type and name in the maintenance-domain instance.
         - The meg-id-format and meg-level leafs are ignored.
         - The level is controlled by the md-level leaf.
         When set to true:
         - The MEG shall be in a maintenance-domain where name-type has the value
         none(1).
         - The format of the MEG ID is as defined by meg-id-format.
         - The name-type in the maintenance-association is ignored.
         - The name leaf contains the MEG ID value unless the meg-id-format
         is set to 'icc-based' in which case it contains the value of the
         'icc-name-value' leaf
         - The md-level leaf is ignored, and the level is controlled
         by the meg-level leaf.";
      user-ext:CLI-comm-help "Configure compliancy with 802.1q or Y.1731";
      reference "[MEF31], MEF-SOAM-FM-MIB.mefSoamNetCfgY1731Compliant";

      must "(not(../../md-level) or (. != 'true'))" {
        error-message "If y1731 compliant, the md-level should not be set";
      }

    }

    uses maintenance-association-meg-id;

    leaf meg-level {
      type md-level-type;
      when "(../y1731-compliant = 'true')";
      description
        "This attribute indicates the MEG Level of the MEG";
      user-ext:CLI-comm-help "Set MEG Level";
      reference "[MEF31] MEF-SOAM-FM-MIB.mefSoamNetCfgMegLevel";
    }
  }
  augment "/cfm/maintenance-domain/maintenance-association/maintenance-association-end-point/state" {
    description
      "This set of data definitions extends the MEG End Point (as described in
       Y.1731) or Maintenance association End Point (as described in 802.1q)
       defined in the MEF CFM module (MEF-CFM)";
    reference "[MEF7.1] 9.2.2";
    leaf operational-state {
      type operational-state-type;
      config false;
      description
        "This attribute indicates the operational state (current capability) of
         the MEP.";
      reference "[MEF7.1] 9.2.5";
    }
    leaf connectivity-status {
      type enumeration {
        enum "active" {
          description
            "Refers to the ability to exchange SOAM PDU frames among all the UNIs
             of an EVC.";
        }
        enum "partially-active" {
          description
            "Refers to the ability to exchange SOAM PDU frames among some but not
             all the UNIs of an EVC.";
        }
        enum "inactive" {
          description
            "Refers to the ability to exchange SOAM PDU frames among any of the UNIs
             of an EVC.";
        }
      }
      config false;
      description
        "This attribute indicates the connectivity status for a MEP in an EVC
         MEs. An 'active' MEP Connectivity Status refers to the ability
         to exchange SOAM PDU frames among all the UNIs of an EVC. A
         'partially-active' MEP Connectivity Status refers to the
         ability to exchange SOAM PDU frames among some but not all the
         UNIs of an EVC. An 'inactive' MEP Connectivity Status refers to
         the inability to exchange SOAM PDU frames among any of the UNIs
         of an EVC.";
      reference "[MEF7.1] 9.2.5";
    }
    leaf port-status {
      type port-status-type;
      config false;
      description
        "An enumerated value of the Port status TLV sent in the last CCM from the
         local MEP or the default value psNoPortStateTLV indicating no
         CCM has been sent or no Port Status TLV has been sent.";
      reference "[802.1q] 17.5";
    }
    leaf interface-status {
      type interface-status-type;
      config false;
      description
        "An enumerated value of the Interface status TLV sent in the last CCM
         from the local MEP or the default value no-status-tlv
         indicating no CCM has been sent or no Interface Status TLV has
         been sent.";
      reference "[802.1q] 17.5";
    }
    container last-defect-sent {
      uses fault-alarm-defect-bits-type;
      config false;
      description
        "This attribute indicates the state of the previous MEP defects,
         that was sent with the previous
         mep-defect-alarm notification. It is always some *previous*
         value of cfm:active-defects. Once an mep-defect-alarm is sent
         the mep-defect-alarm that was sent in the notification
         updates the contents of this leaf.
         If no mep-defect-alarm notification has been sent the value of
         this leaf is '0'.";
      reference "[MEF31] MEF-SOAM-FM-MIB.mefSoamMepStatusLastDefectSentStatus";
    }
    leaf rdi-transmit-status {
      type boolean;
      config false;
      description
        "Indicates whether the local MEP is generating a RDI bit in the CCM that
         it transmits. A value of 'true' indicates that a RDI bit was
         set in the last CCM that the MEP transmitted. A value of
         'false' indicates that the last CCM transmitted by the MEP did
         not set the RDI bit or that a CCM has never been transmitted by
         the MEP.";
      reference "[MEF7.1] 9.2.2";
    }
    leaf oam-frames-discarded {
      type yang:counter32;
      config false;
      description
        "This attribute indicates the count of incoming OAM frames discarded at
         the MEP. This count includes frames discarded because they have
         an unknown OpCode, and frames (other than CCMs) discarded
         because they have a level below the level of the MEP.  In other
         words, this attribute counts frames discarded by the MEP Equal
         OpCode Demultiplexer and the MEP Low OpCode Demultiplexer
         described in IEEE 802.1q Sn 19.2.7, Table 19-1 and Figure
         19-2.  This count does not include frames that are malformed,
         or that contain OpCode-specific errors (such as CCM defects or
         LBRs with bad data).";
      reference
        "[802.1q] 19.2.7, [MEF31]
         MEF-SOAM-FM-MIB.mefSoamMepFmStatsInOamFramesDiscarded";
    }
  }
  augment "/cfm/maintenance-domain/maintenance-association/maintenance-association-end-point/continuity-check/config" {
    description
      "This set of data definitions extends the proactive Ethernet OAM Fault
       Management and Performance Monitoring Continuity Check function
       (ETH-CC) as described in Y.1731 and 802.1q and defined in
       MEF-CFM";
    reference "[MEF7.1] 9.3.1";
    leaf drop-eligible {
      type boolean;
      default "false";
      description
        "This attribute specifies the eligibility of frames with ETH-CC and
         ETH-RDI information to be discarded when congestion conditions
         are encountered.
         The value 'true' indicates frames are eligible to be discarded.
         The value 'false' indicates frames are not eligible to be
         discarded.";
      user-ext:CLI-comm-help "Configure the eligibility of frames with CC to be discarded when congestion occurs";
      reference "[MEF7.1] 9.3.1.1";
    }
  }
  augment "/cfm/maintenance-domain/maintenance-association/maintenance-association-end-point/continuity-check/state" {
    leaf total-ccm-in {
      type yang:counter32;
      config false;
      description
        "This attribute indicates the count of the total number of valid (not
         malformed) CCMs received by the MEP.  In other words, it counts
         the frames received by the MEP Continuity Check Receiver
         described in IEEE 802.1q Sn 19.2.8 and Figure 19-2.  This
         includes CCMs at a lower level, CCMs with defects, CCMs from an
         unexpected peer MEP and out-of-sequence CCMs.  It does not
         include CCMs at a higher level than the MEP.";
      reference "[802.1q] 19.2.8, [MEF31] MEF-SOAM-FM-MIB.mefSoamMepFmStatsInCcmTotal";
    }
  }
  augment "/transmit-loopback/input" {
    description
      "This set of data definitions extends on-demand Ethernet OAM Fault
       Management Loopback function (ETH-LB) as defined in Y.1731 and
       802.1q and defined in MEF-CFM";
    reference "[MEF7.1] 9.3.2";
    leaf multicast-enabled {
      type boolean;
      default "false";
      description
        "This attribute specifies whether a MEP uses unicast or multicast
         to send the ETH-LB messages (LBM). The 802.1ag standard only allows
         unicast LBM. ITU-T Y.1731 allows LBM to be multicast. This attribute
         allows the MEP to send either multicast or unicast LBM on a per MEP
         basis.
         The value 'true' indicates multicast is enabled.
         The value 'false' indicates unicast is enabled.";
      user-ext:CLI-comm-help "Configure unicast or multicast for LBM";
      reference "[MEF7.1] 9.3.2.1";
    }
    leaf interval {
      type uint32 {
        range "0..60000";
      }
      units "milliseconds";
      default "1000";
      description
        "This attribute specifies the period between LBM transmissions in an LB
         Session. For an LB Session, the period for LBM transmission
         is configurable in the range 0 and sixty seconds (60 s). Granularity
         of 100ms is required.
         The transmission of the next LBM is not dependent upon the
         reception the first LBR. The next LBM is sent out based upon
         the interval count.
         An interval count of '0' indicates that the subsequent LBM is sent
         out with the minimum possible delay.";
      user-ext:CLI-comm-help "Set LBM transmissions interval";
      reference "[MEF7.1] 9.3.2.1";
    }
    leaf frame-size {
      type uint32 {
        range "64..9600";
      }
      units "bytes";
      must "not(../data-tlv)" {
        error-message
          "Specific frame-size not allowed, frame size is based on data-tlv";
      }
      description
        "This attribute specifies the LBM frame size. For an LB Session, the size
         of the LBM frame is configurable to any Ethernet frame size
         between 64 Bytes and the maximum transmission unit of the
         EVC.
         The range of frame sizes from 64 through 2000 octets, in 4 octet increments,
         MUST be supported, and the range of frame sizes from 2004 through 9600
         octets, in 4 octet increments, SHOULD be supported.
         The adjustment to the frame size of the standard LBM PDU size is accomplished
         by the addition of a Data TLV or a Test TLV.";
      user-ext:CLI-comm-help "Set LBM frame size";
      reference "[MEF7.1] 9.3.2.1";
    }
    leaf data-pattern {
      type enumeration {
        enum "zeroes" {
          description
            "Indicates the Data TLV contains all zeros.";
        }
        enum "ones" {
          description
            "Indicates the Data TLV contains all ones.";
        }
      }
      must "not(../data-tlv)" {
        error-message
          "Specific data-pattern not allowed, pattern is based on data-tlv";
      }
      default "zeroes";
      description
        "This attribute specifies the LBM data pattern included in a Data TLV
         when the size of the LBM frame is determined by the frame-size
         leaf and test-tlv-included is 'false'.";
      user-ext:CLI-comm-help "Set LBM data pattern included in a Data TLV";
      reference "[MEF31] MEF-SOAM-FM-MIB.mefSoamLbCfgDataPattern";
    }
    leaf test-tlv-included {
      type boolean;
      must "not(../data-tlv)" {
        error-message "test-tlv-included does not apply when data-tlv exists";
      }
      default "false";
      description
        "Indicates whether a Test TLV or Data TLV is included when the size of
         the LBM frame is determined by the frame-size leaf.
         A value of 'true' indicates that the Test TLV is to be
         included.
         A value of 'false' indicates that the Data TLV is to be
         included.";
      user-ext:CLI-comm-help "Configure Test TLV or Data TLV inclusion";
      reference "[Y.1731] 9.3, [MEF31] MEF-SOAM-FM-MIB.mefSoamLbCfgDataPattern";
    }
    leaf test-tlv-pattern {
      type test-pattern-type;
      must "not(../data-tlv)" {
        error-message "test-tlv-pattern does not apply when data-tlv exists";
      }
      default "null-signal-without-crc-32";
      description
        "This attribute specifies the type of test pattern to be sent in the LBM
         frame Test TLV when the size of LBM PDU is determined by the
         frame-size leaf and test-tlv-included is 'true'.";
      user-ext:CLI-comm-help "Set Test TLV pattern type";
      reference "[MEF7.1] 9.3.2.1, [MEF31] MEF-SOAM-FM-MIB.mefSoamLbCfgTestTlvPattern";
    }
    leaf timeout {
      type yang:gauge32 {
        range "1..10000";
      }
      default "5000";
      description
        "This attribute specifies the maximum amount of time to receive an LBR in
         response to a LBM. If a LBR is not received within the timeout
         value it is considered lost.";
      user-ext:CLI-comm-help "Set timeout value to receive a LBR in response to a LBM";
      reference "[MEF31] MEF-SOAM-FM-MIB.mefSoamLbCfgTimeout";
    }
  }

  augment "/cfm/maintenance-domain/maintenance-association/maintenance-association-end-point/loopback" {
    description
      "This set of data definitions extends on-demand Ethernet OAM Fault
       Management Loopback function (ETH-LB) as defined in Y.1731 and
       802.1q and defined in MEF-CFM";
    reference "[MEF7.1] 9.3.2";
    leaf crc-errors-in {
      type yang:counter32;
      config false;
      description
        "This attribute contains the count of the total number of LBR messages
         received with CRC errors. This is only applicable when the
         ETH-LB includes the test TLV with a test pattern of null-crc-32
         or pbrs-crc-32.";
      reference "[MEF7.1] 9.3.2.2";
    }
  }

  augment "/cfm/maintenance-domain/maintenance-association/maintenance-association-end-point/linktrace" {
    description
      "Augments to support the enhanced CFM Linktrace functionality";
    reference "[MEF30] 8.4";
    leaf ltm-msgs-transmitted {
      type yang:zero-based-counter32;
      config false;
      description
        "This attribute contains the count of the total number of LTM messages
         transmitted by the MEP";
      reference "[MEF31] MEF-SOAM-FM-MIB.mefSoamLtLtmTransmitted";
    }
    leaf ltr-msgs-received {
      type yang:zero-based-counter32;
      config false;
      description
        "This attribute contains the count of the total number of LTR messages
         received by the MEP";
      reference "[MEF31] MEF-SOAM-FM-MIB.mefSoamLtLtrReceived";
    }
    leaf ltm-msgs-received {
      type yang:zero-based-counter32;
      config false;
      description
        "This attribute contains the count of the total number of LTM messages
         received by the MEP";
      reference "[MEF31] MEF-SOAM-FM-MIB.mefSoamLtLtmReceived";
    }
    leaf ltr-msgs-transmitted {
      type yang:zero-based-counter32;
      config false;
      description
        "This attribute contains the count of the total number of LTR messages
         transmitted by the MEP";
      reference "[MEF31] MEF-SOAM-FM-MIB.mefSoamLtLtrTransmitted";
    }
  }
  augment "/cfm/maintenance-domain/maintenance-association/maintenance-association-end-point" {
    description
      "Augments to support the AIS functionality";
    reference "[Y.1731] 7.4, [MEF30] 8.5";
    container alarm-indication-signal {
      description
        "This set of data definitions covers the proactive Ethernet OAM Fault
         Management Alarm Indication Signal function (ETH-AIS) as
         defined in Y.1731 and extended in MEF30";
      reference "[Y.1731] 7.4, [MEF30] 8.5";
      user-ext:CLI-comm-help "Configure AIS functionality";
      leaf enabled {
        type boolean;
        default "false";
        description
          "This attribute specifies whether ETH-AIS transmission is enabled. The
           value 'true' indicates ETH-AIS transmission is enabled. The
           value 'false' indicates ETH-AIS transmission is disabled.";
        user-ext:CLI-comm-help "Configure AIS transmission";
        reference "[MEF7.1] 9.3.4.1, [MEF30] 8.4";
      }
      leaf interval {
        type interval-type-ais-lck-type;
        default "1s";
        description
          "This attribute specifies the ETH-AIS transmission period.";
        user-ext:CLI-comm-help "Set AIS transmission period";
        reference "[MEF7.1] 9.3.4.1";
      }
      leaf priority {
        type priority-type;
        description
          "This attribute specifies the priority of frames with ETH-AIS
           information. If ETH-AIS is supported, the default value for
           the CoS for AIS frame MUST be the value which yields the
           lowest frame loss performance for this EVC.";
        user-ext:CLI-comm-help "Set AIS frames priority";
        reference "[MEF7.1] 9.3.4.1";
      }
      leaf client-meg-level {
        type md-level-type;
        default "0";
        description
          "The MEG/Maintenance Domain Level of the Client ETH-AIS PDU (transmitted
           level).";
        user-ext:CLI-comm-help "Set level of transmitted AIS PDUs";
        reference "[Y.1731] 7.4";
      }
      leaf remote-rdi-trigger  {
        type boolean;
        default "false";
        description
          "Indicates whether AIS transmission is triggered as a result of
          a remote MEP reporting the RDI bit in its last CCM.";
        user-ext:CLI-comm-help "Configure Remote RDI trigger";
      }
      leaf mac-status-trigger {
        type boolean;
        default "false";
        description
          "Indicates whether AIS transmission is triggered as a result of
           some remote MEP reporting its Interface Status TLV
           as not isUp or all remote MEPs reporting a Port Status
           TLV that contains some value other than psUp.";
        user-ext:CLI-comm-help "Configure MAC status trigger";
      }
      leaf remote-ccm-trigger {
        type boolean;
        default "false";
        description
          "Indicates whether AIS transmission is triggered as a result of
           the MEP not receiving valid CCMs from at least one of the
           remote MEPs.";
        user-ext:CLI-comm-help "Configure Remote CCM trigger";
      }
      leaf ccm-period-trigger {
        type boolean;
        default "false";
        description
          "Indicates whether AIS transmission is triggered as a result of
           the MEP receiving at least one CCM with a time period that does
           not match the local configuration.";
        user-ext:CLI-comm-help "Configure CCM period trigger";
      }
      leaf ma-level-trigger {
        type boolean;
        default "false";
        description
          "Indicates whether AIS transmission is triggered as a result of
           the MEP receiving at least one CCM with an MA level that does not
           match the local configuration.";
        user-ext:CLI-comm-help "Configure MA level trigger";
      }
      leaf error-ccm-trigger {
        type boolean;
        default "false";
        description
          "Indicates whether AIS transmission is triggered as a result of
           the MEP receiving at least one invalid CCM, that is not covered by
           ccm-period-trigger or ma-level-trigger.";
        user-ext:CLI-comm-help "Configure error CCM trigger";
      }
      leaf maid-error-trigger {
        type boolean;
        default "false";
        description
          "Indicates whether AIS transmission is triggered as a result of
           the MEPP receiving at least one CCM from another MAID.";
        user-ext:CLI-comm-help "Configure MAID error trigger";

      }
      leaf ais-rcvd-trigger {
        type boolean;
        default "false";
        description
          "Indicates whether AIS transmission is triggered as a result of
           the MEP receiving an AIS indicating a fault at a lower level.";
        user-ext:CLI-comm-help "Configure AIS received trigger";
      }
      leaf if-down-triggers {
        type boolean;
        default "true";
        description
          "Indicates whether AIS transmission is triggered as a result of
          interface failure.";
        user-ext:CLI-comm-help "Configure Interface failure trigger";
      }

      container state {
        config false;
        description
          "Alarm Indication Signal state.";
        leaf transmit-status {
          type boolean;
          config false;
          description
            "This attribute specifies the current AIS transmission status of the
             MEP.
             The value 'true' indicates AIS frames are currently being
             transmitted by the MEP.
             The value 'false' indicates AIS frames are not currently
             being transmitted by the MEP.";
          reference "[Y.1731] 7.4";
        }
        leaf receive-status {
          type boolean;
          config false;
          description
            "This attribute specifies the current AIS receive status of the
             MEP. The value 'true' indicates an AIS PDU has been received
             and 3.5 times the interval defined in the PDU has not yet
             passed, otherwise it is 'false'.";
          reference "[Y.1731] 7.4";
        }
        leaf transmit-counter {
          type yang:zero-based-counter32;
          config false;
          description
            "This attribute contains the count of the total number of AIS messages
             sent by the MEP. The count is incremented every time an AIS
             PDU is transmitted by the MEP.";
          reference "[MEF7.1] 9.3.2.2";
        }
        leaf receive-counter {
          type yang:counter32;
          config false;
          description
            "This attribute contains the count of the total number of AIS messages
             received by the MEP. The count is incremented every time an
             AIS PDU is received by the MEP.";
          reference "[MEF7.1] 9.3.2.2";
        }
        leaf last-received-mac-address {
          type meta:mac-address;
          config false;
          description
            "The source MAC Address Field of last AIS received by the MEP.
             If no AIS PDU has been received by the NE the MAC address is
             set to all zeros.";
          reference "[Y.1731] 7.7";
        }
      } // state
    } // alarm-indication-signal

    // This set of data definitions extends the MEG End Point (as described in
    // Y.1731) or Maintenance End Point (as described in 802.1q) defined
    // in the MEF CFM module (MEF-CFM), specifically with regards to the
    // role of the MEP in PM tests.

    leaf loss-single-ended-responder {
      type boolean;
      default "true";
      description
        "This object specifies whether the Loss Measurement (LMM) single ended
         Responder is enabled.
         The value 'true' indicates the single-ended Loss Measurement
         Responder is enabled and if a LMM message is received a LMR
         will be sent in re-ply.
         The value 'false' indicates the single-ended Loss Measurement
         Responder is disabled. If a LMM message is received no
         response will be sent and the message will be discarded.
         This object needs to be persistent upon reboot or restart of a
         device.
         A MEP can be both a single-ended Responder and Controller
         simultaneously.";
      reference "MEF-SOAM-PM-MIB.mefSoamPmMepLmSingleEndedResponder";
      user-ext:CLI-comm-help "Configure Loss Measurement single ended Responder";
    }
    leaf delay-single-ended-responder {
      type boolean;
      default "true";
      description
        "This object specifies whether the Delay Measurement (DMM) single ended
         Responder is enabled.
         The value 'true' indicates the single-ended Delay Measurement
         Responder is enabled and if a DMM message is received a DMR
         will be sent in re-ply.
         The value 'false' indicates the single-ended Delay Measurement
         Responder is disabled. If a DMM message is received no
         response will be sent and the message will be discarded.
         This object needs to be persistent upon reboot or restart of a
         device.
         A MEP can be both a single-ended Responder and Controller
         simultaneously.";
      reference "MEF-SOAM-PM-MIB.mefSoamPmMepDmSingleEndedResponder";
      user-ext:CLI-comm-help "Configure Delay Measurement single ended Responder";
    }

    // This set of data definitions extends the MEG End Point (as described
    // Y.1731) or Maintenance End Point (as described in 802.1q) defined
    // in the MEF CFM module (MEF-CFM), specifically with regards to
    // Loss Measurement.

    container loss-measurements {
      description
        "This container contains a collection of data definitions related to
         Loss Measurements.";
      user-ext:CLI-comm-help "Configure Loss Measurements";
      list thresholds {
        key "id";
        user-ext:CLI-comm-help "Configure Loss Measurements Thresholds";
        description
          "This list contains the list of Loss Measurement configuration threshold
           values for LM Performance Monitoring.
           The main purpose of the threshold configuration list is to
           configure threshold alarm notifications indicating that a
           specific performance metric is not being met.";
        leaf id {
          type uint32;
          description
            "The index of the threshold number for the specific LM threshold
             entry.
             An index value of '1' needs to be supported. Other index
             values can also be supported.";
          user-ext:CLI-comm-help "Set Loss Measurements Threshold Id";
        }
        uses loss-threshold-group;
      }
    } // loss-measurements

    // This set of data definitions extends the MEG End Point (as described
    // Y.1731) or Maintenance End Point (as described in 802.1q) defined
    // in the MEF CFM module (MEF-CFM), specifically with regards to
    // Loss Measurement.

    container loss-measurement-list {
      config false;
      description
        "Loss measurement state list.";

      list loss-measurement {
        key "session-id";
        config false;
        description
          "A list of Loss Measurement PM Sessions where each instance is uniquely
           identified by an id attribute.";
        leaf session-id {
          type session-id-t;
          description
            "This object uniquely identifies a scheduled measurement. It is
             automatically generated by the server on creation of a new
             measurement.";
        }
        leaf session-status {
          type session-status-type;
          config false;
          description
            "This object indicates the current status of the LM session. A value
             of 'active' indicates the current LM session is active,
             i.e. the current time lies between the start time and the
             stop time, and enabled is true. A value of 'not-active'
             indicates the current LM session is not active, i.e. it has
             not started yet, has stopped upon reaching the stop time,
             or is disabled.";
        }
        uses loss-measurement-configuration-group;

        container thresholds {
          description
            "This container contains a collection of threshold values for
             Loss Measurements.";

          uses loss-threshold-group;

          container enabled-thresholds {
            description
              "A vector of bits that indicates the type of SOAM LM thresholds
               notifications that are enabled.
               A present but enables the specific SOAM LM threshold
               notifica-tion and when the specific counter is enabled and
               the threshold is crossed a notification is generated.
               A not present bit disables the specific SOAM LM threshold
               notification.
               If a particular SOAM LM threshold is not supported the BIT
               value is not present.";
            leaf measured-flr-forward {
              type empty;
              description
                "Measured flr forward";
            }
            leaf max-flr-forward {
              type empty;
              description
                "Max flr forward";
            }
            leaf average-flr-forward {
              type empty;
              description
                "Average flr forward";
            }
            leaf measured-flr-backward {
              type empty;
              description
                "Measured flr backward";
            }
            leaf max-flr-backward {
              type empty;
              description
                "Max flr backward";
            }
            leaf average-flr-backward {
              type empty;
              description
                "Average flr backward";
            }
            leaf forward-unavailable-count {
              type empty;
              description
                "Forward unavailable count";
            }
            leaf forward-available-ratio {
              type empty;
              description
                "Forward available ratio";
            }
            leaf backward-unavailable-count {
              type empty;
              description
                "Backward unavailable count";
            }
            leaf backward-available-ratio {
              type empty;
              description
                "Backward available ratio";
            }

          } //enabled-thresholds

        }

        uses remote-mep-group;
        uses measurement-timing-group;
        leaf measured-forward-flr {
          type yang:gauge32 {
            range "0..100000";
          }
          units "milli-percent";
          description
            "This object contains the Frame Loss Ratio in the forward direction
             calculated by this MEP from the last received SOAM PDU. The
             FLR value is a ratio that is expressed as a percent with a
             value of 0 (ratio 0.00) through 100000 (ratio 1.00).
             Units are in milli-percent, where 1 indicates 0.001
             per-cent.";
          reference "MEF-SOAM-PM-MIB.mefSoamLmMeasuredStatsForwardFlr";
        }
        leaf measured-backward-flr {
          type yang:gauge32 {
            range "0..100000";
          }
          units "milli-percent";
          description
            "This object contains the Frame Loss Ratio in the backward direction
             calculated by this MEP from the last received SOAM PDU. The
             FLR value is a ratio that is expressed as a percent with a
             value of 0 (ratio 0.00) through 100000 (ratio 1.00).
             Units are in milli-percent, where 1 indicates 0.001
             percent.";
          reference "MEF-SOAM-PM-MIB.mefSoamLmMeasuredStatsBackwardFlr";
        }
        leaf measured-availability-forward-status {
          type availability-type;
          description
            "This object indicates the availability status (the outcome of the
             last availability indicator) in the forward direction based upon
             the last received SOAM PDU.";
          reference "MEF-SOAM-PM-MIB.mefSoamLmMeasuredStatsAvailForwardStatus";
        }
        leaf measured-availability-backward-status {
          type availability-type;
          description
            "This object indicates the availability status (the outcome of the
             last availability indicator) in the backward direction based
             upon the last received SOAM PDU.";
          reference "MEF-SOAM-PM-MIB.mefSoamLmMeasuredStatsAvailBackwardStatus";
        }
        leaf measured-forward-last-transition-time {
          type yang:date-and-time;
          description
            "This object indicates the time of the last transition between
             available and unavailable in the forward direction.
             If there have been no transitions since the Loss
             Measurement Session was started, this is set to 0.";
          reference "MEF-SOAM-PM-MIB.mefSoamLmMeasuredStatsAvailForwardLastTransitionTime";
        }
        leaf measured-backward-last-transition-time {
          type yang:date-and-time;
          description
            "This object indicates the time of the last transition between
             available and unavailable in the backward direction.
             If there have been no transitions since the Loss Measurement
             Session was started, this is set to 0.";
          reference "MEF-SOAM-PM-MIB.mefSoamLmMeasuredStatsAvailBackwardLastTransitionTime";
        }
        container current-availability-stats {
          description
            "This container contains the current results for a SOAM Loss
             Measurement session for availability statistics gathered during the
             interval indicated by availability-measurement-interval.";
          leaf id {
            type uint32;
            description
              "The index for the current availability Measurement Interval for
               this PM session. This value will become the value for id of the
               history-availability-stats list once the Measurement
               Interval is completed.  The duration of the Measurement
               Interval is specified by availability-measurement-interval.";
          }
          leaf start-time {
            type yang:date-and-time;
            mandatory true;
            description
              "The time that the current Measurement Interval started.";
          }
          leaf elapsed-time {
            type uint32 {
              range "0..2147483647";
            }
            mandatory true;
            description
              "The time that the current Measurement Interval has been running,
               in 0.01 seconds.";
          }
          uses loss-availability-stats-group;
        }
        container current-measurement-stats {
          description
            "This container contains the results for the current Measurement
             Interval in a SOAM Loss Measurement session gathered during
             the interval indicated by measurement-interval.";
          leaf id {
            type uint32;
            description
              "The index for the current Measurement Interval for this PM
               session. This value will become the value for id of the
               history-measurement-stats list once the Measurement
               Interval is completed.";
          }
          leaf start-time {
            type yang:date-and-time;
            mandatory true;
            description
              "The time that the current Measurement Interval started.";
          }
          leaf elapsed-time {
            type uint32 {
              range "0..2147483647";
            }
            mandatory true;
            description
              "The time that the current Measurement Interval has been running,
               in 0.01 seconds.";
          }
          uses loss-measurement-stats-group;
        }
        list history-availability-stats {
          key "id";
          description
            "This list contains the results for availability history Measurement
             Intervals in a SOAM Loss Measurement session.";
          leaf id {
            type uint32;
            description
              "The index for the availability Measurement Interval within this
               PM session.";
          }
          leaf end-time {
            type yang:date-and-time;
            mandatory true;
            description
              "The time that the Measurement Interval ended.";
          }
          leaf elapsed-time {
            type uint32 {
              range "0..2147483647";
            }
            mandatory true;
            description
              "The length of time that the Measurement Interval ran for,
               in 0.01 seconds.";
          }
          uses loss-availability-stats-group;
        }
        list history-measurement-stats {
          key "id";
          description
            "This list contains the results for history Measurement
             Intervals in a SOAM Loss Measurement session.";
          leaf id {
            type uint32;
            description
              "The index for the Measurement Interval within this
               PM session.";
          }
          leaf end-time {
            type yang:date-and-time;
            mandatory true;
            description
              "The time that the Measurement Interval ended.";
          }
          leaf elapsed-time {
            type uint32 {
              range "0..2147483647";
            }
            mandatory true;
            description
              "The length of time that the Measurement Interval ran for,
               in 0.01 seconds.";
          }
          uses loss-measurement-stats-group;
        }

      } //loss-measurement

    } //loss-measurement-list

    // This set of data definitions extends the MEG End Point (as described in
    // Y.1731) or Maintenance End Point (as described in 802.1q)
    // defined in the MEF CFM module (MEF-CFM), specifically with
    // regards to Delay Measurement.

    container delay-measurements {
      description
        "This container contains a collection of data definitions related to
         Delay Measurements.";
      user-ext:CLI-comm-help "Configure Delay Measurements";
      list thresholds {
        key "id";
        description
          "This list contains the Delay Measurement threshold configuration values
           for DM Performance Monitoring.
           The main purpose of the threshold configuration list is to
           configure threshold alarm notifications indicating that a
           specific performance metric is not being met.";
        user-ext:CLI-comm-help "Configure Delay Measurements Thresholds";
        leaf id {
          type uint32 {
            range "1..2147483647";
          }
          description
            "The index of the threshold number for the specific DM threshold
             entry.
             An index value of '1' is to be supported. Other index values
             can be supported.";
          user-ext:CLI-comm-help "Set Delay Measurements Threshold Id";
          }
        uses delay-threshold-group;
      }
    } //delay-measurements

    // This set of data definitions extends the MEG End Point (as described in
    // Y.1731) or Maintenance End Point (as described in 802.1q)
    // defined in the MEF CFM module (MEF-CFM), specifically with
    // regards to Delay Measurement.

    container delay-measurement-list {
      config false;
      description
        "Delay measurement state list.";

      list delay-measurement {
        key "id";
        config false;
        description
          "A list of Delay Measurement PM Sessions where each instance is
           uniquely identified by an id attribute.";
        leaf id {
          type uint32;
          description
            "This object uniquely identifies a scheduled measurement. It is
             automatically generated by the server on creation of a new
             measurement.";
        }
        leaf session-status {
          type session-status-type;
          config false;
          description
            "This object indicates the current status of the DM session. A value
             of 'active' indicates the current DM session is active,
             i.e. the current time lies between the start time and the
             stop time, and enabled is true. A value of 'not-active'
             indicates the current DM session is not active, i.e. it has
             not started yet, has stopped upon reaching the stop time,
             or is disabled.";
        }
        uses delay-measurement-configuration-group;

        container thresholds {
          description
            "This container contains a collection of threshold values for
             Delay Measurements.";

          uses delay-threshold-group;

          container enabled-thresholds {
            description
                "A vector of bits that indicates the type of SOAM DM threshold
                 notifications that are enabled.
                 A present bit enables the specific SOAM DM threshold
                 notification and when the specific counter is enabled and the
                 threshold is crossed a notification is generated.
                 A not present bit disables the specific SOAM DM threshold
                 notification.
                 If a particular SOAM DM threshold is not supported the BIT
                 value is not present.";
            reference "MEF-SOAM-PM-MIB.mefSoamDmThresholdCfgEnable";
            leaf measured-frame-delay-two-way {
                type empty;
                description
                "Measured frame delay two way";
            }
            leaf max-frame-delay-two-way {
                type empty;
                description
                "Max frame delay two way";
            }
            leaf average-frame-delay-two-way {
                type empty;
                description
                "Average frame delay two way";
            }
            leaf measured-inter-frame-delay-variation-two-way {
                type empty;
                description
                "Measured inter frame delay variation two way";
            }
            leaf max-inter-frame-delay-variation-two-way {
                type empty;
                description
                "Max inter frame delay variation two way";
            }
            leaf average-inter-frame-delay-variation-two-way {
                type empty;
                description
                "Average inter frame delay variation two way";
            }
            leaf max-frame-delay-range-two-way {
                type empty;
                description
                "Max frame delay range two way";
            }
            leaf average-frame-delay-range-two-way {
                type empty;
                description
                "Average frame delay range two way";
            }
            leaf measured-frame-delay-forward {
                type empty;
                description
                "Measured frame delay forward";
            }
            leaf max-frame-delay-forward {
                type empty;
                description
                "Max frame delay forward";
            }
            leaf average-frame-delay-forward {
                type empty;
                description
                "Average frame delay forward";
            }
            leaf measured-inter-frame-delay-variation-forward {
                type empty;
                description
                "Measured inter frame delay variation forward";
            }
            leaf max-inter-frame-delay-variation-forward {
                type empty;
                description
                "Max inter frame delay variation forward";
            }
            leaf average-inter-frame-delay-variation-forward {
                type empty;
                description
                "Average inter frame delay variation forward";
            }
            leaf max-frame-delay-range-forward {
                type empty;
                description
                "Max frame delay range forward";
            }
            leaf average-frame-delay-range-forward {
                type empty;
                description
                "Average frame delay range forward";
            }
            leaf measured-frame-delay-backward {
                type empty;
                description
                "Measured frame delay backward";
            }
            leaf max-frame-delay-backward {
                type empty;
                description
                "max-frame-delay-backward";
            }
            leaf average-frame-delay-backward {
                type empty;
                description
                "Average frame delay backward";
            }
            leaf measured-inter-frame-delay-variation-backward {
                type empty;
                description
                "Measured inter frame delay variation backward";
            }
            leaf max-inter-frame-delay-variation-backward {
                type empty;
                description
                "Max inter frame delay variation backward";
            }
            leaf average-inter-frame-delay-variation-backward {
                type empty;
                description
                "Average inter frame delay variation backward";
            }
            leaf max-frame-delay-range-backward {
                type empty;
                description
                "Max frame delay range backward";
            }
            leaf average-frame-delay-range-backward {
                type empty;
                description
                "Average frame delay range backward";
            }

          }//enabled-thresholds

        }

        uses remote-mep-group;
        uses measurement-timing-group;

        leaf frame-delay-two-way {
          type yang:gauge32;
          units "microseconds";
          description
            "This object contains the two-way frame delay calculated by this MEP
             from the last received SOAM PDU.
             This object is undefined is measurement-type is
             1dm-transmitted or dm1-received.";
          reference "MEF-SOAM-PM-MIB.mefSoamDmMeasuredStatsFrameDelayTwoWay";
        }
        leaf frame-delay-forward {
          type yang:gauge32;
          units "microseconds";
          description
            "This object contains the frame delay in the forward direction
             calculated by this MEP from the last received SOAM PDU. The value
             of this object may not be accurate in the absence of
             sufficiently precise clock synchronization.
             This object is undefined is measurement-type is
             1dm-transmitted.";
          reference "MEF-SOAM-PM-MIB.mefSoamDmMeasuredStatsFrameDelayForward";
        }
        leaf frame-delay-backward {
          type yang:gauge32;
          units "microseconds";
          description
            "This object contains the frame delay in the backward direction
             calculated by this MEP from the last received SOAM PDU. The
             value of this object may not be accurate in the absence of
             sufficiently precise clock synchronization.
             This object is undefined is measurement-type is
             1dm-transmitted or dm1-received.";
          reference "MEF-SOAM-PM-MIB.mefSoamDmMeasuredStatsFrameDelayBackward";
        }
        leaf inter-frame-delay-variation-two-way {
          type yang:gauge32;
          units "microseconds";
          description
            "This object contains the last two-way inter-frame delay interval
             calculated by this MEP.
             The value of this object is undefined when measurement-type
             is 1dm-transmitted or dm1-received.";
          reference "MEF-SOAM-PM-MIB.mefSoamDmMeasuredStatsIfdvTwoWay";
        }
        leaf inter-frame-delay-variation-forward {
          type yang:gauge32;
          units "microseconds";
          description
            "This object contains the last one-way inter-frame delay interval in
             the forward direction calculated by this MEP.
             The value of this object is undefined when measurement-type
             is 1dm-transmitted.";
          reference "MEF-SOAM-PM-MIB.mefSoamDmMeasuredStatsIfdvForward";
        }
        leaf inter-frame-delay-variation-backward {
          type yang:gauge32;
          units "microseconds";
          description
            "This object contains the last one-way inter-frame delay interval in
             the backward direction calculated by this MEP.
             The value of this object is undefined when measurement-type
             is 1dm-transmitted or 1dm-received.";
          reference "MEF-SOAM-PM-MIB.mefSoamDmMeasuredStatsIfdvBackward";
        }
        container current-stats {
          description
            "This container contains the results for the current Measurement
             Interval in a SOAM Delay Measurement session gathered
             during the interval indicated by measurement-interval.";
          leaf start-time {
            type yang:date-and-time;
            mandatory true;
            description
              "The time that the current Measurement Interval started.";
          }
          leaf elapsed-time {
            type uint32 {
              range "0..2147483647";
            }
            mandatory true;
            description
              "The time that the current Measurement Interval has been running,
               in 0.01 seconds.";
          }
          uses delay-measurement-stats-group;
          uses delay-measurement-bins-group;
        }
        list history-stats {
          key "id";
          description
            "This list contains the results for history Measurement Intervals in
             a SOAM Delay Measurement session.";
          leaf id {
            type uint32;
            description
              "The identifier for the Measurement Interval within this
               PM session.";
          }
          leaf end-time {
            type yang:date-and-time;
            mandatory true;
            description
              "The time that the Measurement Interval ended.";
          }
          leaf elapsed-time {
            type uint32 {
              range "0..2147483647";
            }
            mandatory true;
            description
              "The length of time that the Measurement Interval ran for, in 0.01
               seconds.";
          }
          uses delay-measurement-stats-group;
          uses delay-measurement-bins-group;
        }

      } //delay-measurement

    } //delay-measurement-list

  }

  notification mep-defect-alarm {
    description
      "A mep-defect-alarm notification is generated when the value of
       mep-defects changes. It indicates a persistent defect in
       the MEP. This notification is sent whenever the
       cfm:active-defects of the MEP changes, regardless of the
       cfm:highest-priority-defect-found leaf.
       The inclusion of the cfm:remote-mep-state leaf is
       optional. It shall not be included if the defect is not based
       upon a specific MEP instance, e.g.. bDefErrorCCM.";
    reference "[MEF31] MEF-SOAM-FM-MIB.mefSoamMepDefectAlarm";
    uses maintenance-association-end-point-reference;
    container last-defect-sent {
      uses fault-alarm-defect-bits-type;
      description
        "The last defect sent on the specific MEP";
    }
    container active-defects {
      uses fault-alarm-defect-bits-type;
      description
        "The currently active defects on the specific MEP.";
    }
    leaf remote-mep-state {
      type remote-mep-state-type;
      description
        "The value of the remote MEP state on a specific MEP";
      reference "[802.1q] 12.14.7.6.3:b";
    }
  }
  notification ais-alarm {
    description
      "An ais-alarm notification is sent when the state of either
       transmit-status or receive-status changes. Transmit-status is set
       to 'true' when AIS frames are sent by the MEP and set to 'false'
       when the MEP stops sending AIS frames. Receive-status is set to
       'true' when AIS PDUs are received and is set to 'false' when AIS
       PDUs stop being received.";
    reference "[MEF31] MEF-SOAM-FM-MIB.mefSoamAisAlarm";
    uses maintenance-association-end-point-reference;
    leaf receive-status {
      type boolean;
      description
        "The value of the AIS receive-status of the affected MEP";
    }
    leaf transmit-status {
      type boolean;
      description
        "The value of the AIS transmit-status of the affected MEP";
    }
  }

  typedef suspect-status-type {
    type boolean;
    description
      "This boolean data type indicates whether the measurement interval
       has been marked as suspect.
       The object is set to false at the start of a measurement
       interval. It is set to true when there is a discontinuity in the
       performance measurements during the measurement interval.
       Conditions for a discontinuity include, but are not limited to
       the following:
       1 - The local time-of-day clock is adjusted by at least 10
       seconds
       2 - The conducting of a performance measurement is halted before
       the current measurement interval is completed
       3 - A local test, failure, or reconfiguration that disrupts
       service";
    reference "[MEF SOAM PM IA] R39, R40, 41 and R42";
  }

  typedef performance-monitoring-interval-type {
    type uint32 {
      range "3..3600000";
    }
    units "ms";
    description
      "This integer data type indicates the transmission time between the
       SOAM PM frames for session, in ms.";
  }

  typedef session-status-type {
    type enumeration {
      enum "active" {
        description
          "Indicates the measurement instance is active.";
      }
      enum "not-active" {
        description
          "Indicates the measurement instance is not active.";
      }
    }
    description
      "This enumeration data type defines the status of PM session of a MEP.";
    reference "MEF-SOAM-TC-MIB.MefSoamTcStatusType";
  }

  typedef availability-type {
    type enumeration {
      enum "available" {
        description
          "Indicates the MEP is available.";
      }
      enum "unavailable" {
        description
          "Indicates the MEP is unavailable.";
      }
      enum "unknown" {
        description
          "Indicates the availability is not known, for instance because
           insufficient time has passed to make an availability
           calculation, the time has been excluded because of a
           maintenance interval, or because availability measurement is
           not enabled.";
      }
    }
    description
      "This enumeration data type defines the availability of a session,
       measured by a loss measurement session.";
    reference "MEF-SOAM-TC-MIB.MefSoamTcAvailabilityType";
  }

  typedef measurement-bin-type {
    type enumeration {
      enum "two-way-frame-delay" {
        description
          "Indicates a measurement bin for two-way Frame Delay.";
      }
      enum "forward-frame-delay" {
        description
          "Indicates a measurement bin for one-way Frame Delay in the forward
           direction.";
      }
      enum "backward-frame-delay" {
        description
          "Indicates a measurement bin for one-way Frame Delay in the backward
           direction.";
      }
      enum "two-way-inter-frame-delay-variation" {
        description
          "Indicates a measurement bin for two-way Inter-frame Delay
           Variation.";
      }
      enum "forward-inter-frame-delay-variation" {
        description
          "Indicates a measurement bin for one-way Inter-frame Delay
           Variation in the forward direction.";
      }
      enum "backward-inter-frame-delay-variation" {
        description
          "Indicates a measurement bin for one-way Inter-frame Delay Variation
           in the backward direction.";
      }
      enum "two-way-frame-delay-range" {
        description
          "Indicates a measurement bin for two-way Frame Delay Range.";
      }
      enum "forward-frame-delay-range" {
        description
          "Indicates a measurement bin for one-way Frame Delay Range in the
           forward direction.";
      }
      enum "backward-frame-delay-range" {
        description
          "Indicates a measurement bin for one-way Frame Delay Range in the
           backward direction.";
      }
    }
    description
      "This enumeration data type indicates whether the bin number is for Frame
       Delay, Inter-Frame Delay Variation or Frame Delay Range.";
    reference "MEF-SOAM-TC-MIB.MefSoamTcDelayMeasurementBinType";
  }

  grouping remote-mep-group {
    description
      "This grouping includes objects which identify a remote MEP.";
    choice remote-mep {
      mandatory true;
      description
        "The remote MEP can be identified by either a MAC address or a MEP ID";
      case mac-address {
        leaf mac-address {
          type meta:mac-address;
          description
            "The Target MAC Address Field to be transmitted: A unicast
             destination MAC address.
             This object is only valid for the entity transmitting the
             SOAM Loss and Delay Measurement frames and is ignored by
             the entity receiving SOAM Loss and Delay Measurement
             frames.";
          user-ext:CLI-comm-help "Set Remote MEP MAC address";
        }
      }
      case mep-id {
        leaf mep-id {
          type mep-id-type;
          description
            "The Maintenance Association End Point Identifier of another MEP in
             the same Maintenance Association to which the SOAM Loss or Delay
             Measurement frame is to be sent.
             This object is only valid for the entity transmitting the
             SOAM Loss Measurement or Delay Measurement frames and is
             ignored by the entity receiving SOAM Loss Measurement or
             Delay Measurement frames.";
          user-ext:CLI-comm-help "Set Remote MEP Identifier";
        }
      }
    }
  }

  grouping measurement-timing-group {
    description
      "This grouping includes objects used for proactive and on-demand
       scheduling of PM measurement sessions.";
    container start-time {
      description
        "This container defines the session start time";
      user-ext:CLI-comm-help "Configure session start time";
      choice start-time {
        description
          "Measurement session start time can be immediate, relative or
           absolute.";
        container immediate {
          presence "Start the measurement session immediately.";
          description
            "This object specifies the start time to be immediately at the time
             of session creation.";
          user-ext:CLI-comm-help "Set Measurement Session to start immediately";
        }
        leaf relative {
          type yang:timeticks;
          description
            "This object specifies the relative start time, from the current
             system time, to perform on-demand ETH-DM.  This attribute has no
             meaning for proactive ETH-DM.";
          user-ext:CLI-comm-help "Set the relative start time for the Measurement Session";
        }
        leaf absolute {
          type yang:date-and-time;
          description
            "This object specifies the scheduled start date/time to perform the
             on-demand Performance Monitoring OAM operations. This attribute
             has no meaning for proactive Performance Monitoring OAM
             operations.";
          user-ext:CLI-comm-help "Set the absolute start time for the Measurement Session";
        }
      }
    }
    container stop-time {
      description
        "This container defines the session stop time";
      user-ext:CLI-comm-help "Configure session stop time";
      choice stop-time {
        description
          "Measurement session stop time can be none, relative or
           absolute.";
        container none {
          presence "Never end the measurement session.";
          description
            "This object specifies the measurement session to never end.";
          user-ext:CLI-comm-help "Set Measurement Session to never end";
        }
        leaf relative {
          type yang:timeticks;
          mandatory true;
          description
            "This object specifies the duration of the Delay Measurement PM
             Session.  The duration time can be specified as forever
             (represented by a zero value) or as relative time (e.g., a
             given number of hours, minutes, and seconds from the start
             time).  If the duration time is relative time, then the
             duration time should be equal to or greater than the frame
             transmission period of the PM function(s) comprising the PM
             Solution";
          user-ext:CLI-comm-help "Set the relative stop time for the Measurement Session";
        }
        leaf absolute {
          type yang:date-and-time;
          description
            "This object specifies the scheduled stop date and time to perform
             on-demand Performance Monitoring OAM operations.  This
             attribute has no meaning for proactive Performance
             Monitoring OAM operations.  The stop date and time value should
             be greater than or equal to the scheduled start date and time
             value.";
          user-ext:CLI-comm-help "Set the absolute stop time for the Measurement Session";
        }
      }
    }
    leaf repetition-period {
      type yang:timeticks;
      default "0";
      description
        "This object specifies a configurable repetition time between
         Measurement Intervals in a Measurement session in hundredths of a
         second.
         If the value is less than or equal to one Measurement Interval
         there is no time gap between the end of one Measurement
         Interval and the start of a new Measurement Interval. This is
         the normal usage case.
         If the value is greater than one Measurement Interval there is
         time gap between the end of one Measurement Interval and the
         start of the next Measurement Interval.";
      user-ext:CLI-comm-help "Set repetition time between Measurement Intervals";
      reference "[MEF SOAM PM IA] R18, D3, R19, R20";
    }
  }

  grouping loss-measurement-configuration-group {
    description
      "This grouping includes configuration objects for the Frame Loss
       Measurement function defined in [Y.1731] and [MEF SOAM PM IA].";
    reference "MEF-SOAM-PM-MIB.mefSoamLmCfgTable, [Y.1731] and [MEF SOAM PM IA]";
    leaf measurement-type {
      type enumeration {
        enum "lmm" {
          description
            "LMM SOAM PDU generated and received LMR responses tracked.";
        }
      }
      default "lmm";
      description
        "This object specifies what type of Loss Measurement will be
         performed.  Note this version supports LLM only.";
      user-ext:CLI-comm-help "Set Loss Measurement type";
      reference "MEF-SOAM-PM-MIB.mefSoamLmCfgType";
    }
    container enabled-counters {
      description
        "A vector of bits that indicates the type of SOAM LM counters found in
         the current-stats and history-stats that are enabled.
         A present bit enables the specific SOAM LM counter. A not present
         bit disables the SOAM LM counter.
         If a particular SOAM LM counter is not supported the BIT value
         is not present.
         Not all SOAM LM counters are supported for all SOAM LM types. ";
      reference "MEF-SOAM-PM-MIB.mefSoamLmCfgMeasurementEnable";
      user-ext:CLI-comm-help "Configure LM counters";
      leaf forward-transmitted-frames {
        type empty;
        description
          "Forward transmitted frames";
        user-ext:CLI-comm-help "Enable LM forward transmitted frames counter";
      }
      leaf forward-received-frames {
        type empty;
        description
          "Forward received frames";
        user-ext:CLI-comm-help "Enable LM forward received frames counter";
      }
      leaf forward-min-flr {
        type empty;
        description
          "Forward min flr";
        user-ext:CLI-comm-help "Enable LM forward minimum FLR counter";
      }
      leaf forward-max-flr {
        type empty;
        description
          "Forward max flr";
        user-ext:CLI-comm-help "Enable LM forward maximum FLR counter";
      }
      leaf forward-avg-flr {
        type empty;
        description
          "Forward average flr";
        user-ext:CLI-comm-help "Enable LM forward average FLR counter";
      }
      leaf backward-transmitted-frames {
        type empty;
        description
          "Backward transmitted frames";
        user-ext:CLI-comm-help "Enable LM backward transmitted frames counter";
      }
      leaf backward-received-frames {
        type empty;
        description
          "Backward received frames";
        user-ext:CLI-comm-help "Enable LM backward received frames counter";
      }
      leaf backward-min-flr {
        type empty;
        description
          "Backward min flr";
        user-ext:CLI-comm-help "Enable LM backward minimum FLR counter";
      }
      leaf backward-max-flr {
        type empty;
        description
          "Backward max flr";
        user-ext:CLI-comm-help "Enable LM backward maximum FLR counter";
      }
      leaf backward-avg-flr {
        type empty;
        description
          "Backward average flr";
        user-ext:CLI-comm-help "Enable LM backward average FLR counter";
      }
      leaf soam-pdus-sent {
        type empty;
        description
          "SOAM PDUs sent";
        user-ext:CLI-comm-help "Enable LM SOAM PDUs sent counter";
      }
      leaf soam-pdus-received {
        type empty;
        description
          "SOAM PDUs received";
        user-ext:CLI-comm-help "Enable LM SOAM PDUs received counter";
      }
      leaf availability-forward-available {
        type empty;
        description
          "Availability forward available";
        user-ext:CLI-comm-help "Enable LM availability forward available counter";
      }
      leaf availability-forward-unavailable {
        type empty;
        description
          "Availability forward unavailable";
        user-ext:CLI-comm-help "Enable LM availability forward unavailable counter";
      }
      leaf availability-forward-min-flr {
        type empty;
        description
          "Availability forward min flr";
        user-ext:CLI-comm-help "Enable LM availability forward minimum FLR counter";
      }
      leaf availability-forward-max-flr {
        type empty;
        description
          "Availability forward max flr";
        user-ext:CLI-comm-help "Enable LM availability forward maximum FLR counter";
      }
      leaf availability-forward-average-flr {
        type empty;
        description
          "Availability forward average flr";
        user-ext:CLI-comm-help "Enable LM availability forward average FLR counter";
      }
      leaf availability-backward-available {
        type empty;
        description
          "Availability backward available";
        user-ext:CLI-comm-help "Enable LM availability backward available counter";
      }
      leaf availability-backward-unavailable {
        type empty;
        description
          "Availability backward unavailable";
        user-ext:CLI-comm-help "Enable LM availability backward unavailable counter";
      }
      leaf availability-backward-min-flr {
        type empty;
        description
          "Availability backward min flr";
        user-ext:CLI-comm-help "Enable LM availability backward minimum FLR counter";
      }
      leaf availability-backward-max-flr {
        type empty;
        description
          "Availability backward max flr";
        user-ext:CLI-comm-help "Enable LM availability backward maximum FLR counter";
      }
      leaf availability-backward-average-flr {
        type empty;
        description
          "Availability backward average flr";
        user-ext:CLI-comm-help "Enable LM availability backward average FLR counter";
      }
      leaf measured-stats-forward-measured-flr {
        type empty;
        description
          "Measured stats forward measured flr";
        user-ext:CLI-comm-help "Enable LM measured stats forward measured FLR counter";
      }
      leaf measured-stats-backward-measured-flr {
        type empty;
        description
          "Measured stats backward measured flr";
        user-ext:CLI-comm-help "Enable LM measured stats backward measured FLR counter";
      }
      leaf measured-stats-availability-forward-status {
        type empty;
        description
          "Measured stats availability forward status";
        user-ext:CLI-comm-help "Enable LM measured stats availability forward status counter";
      }
      leaf measured-stats-availability-backward-status {
        type empty;
        description
          "Measured stats availability backward status";
        user-ext:CLI-comm-help "Enable LM measured stats availability backward status counter";
      }
    }
    leaf message-period {
      type performance-monitoring-interval-type;
      units "ms";
      default "1000";
      description
        "This object specifies the interval between Loss Measurement OAM message
         transmission. For Loss Measurement monitoring applications the
         default value is 1 sec.
         This object is not applicable if measurement-type is set to
         'ccm' and is ignored for that Loss Measurement Type.";
      user-ext:CLI-comm-help "Set interval between LM message transmission";
      reference "MEF-SOAM-PM-MIB.mefSoamLmCfgMessagePeriod";
    }
    leaf priority {
      type lm-priority-type;
      default 0;
      description
        "This object specifies the priority of frames with Performance
         Monitoring OAM message information.";
      user-ext:CLI-comm-help "Set priority for frames with LM message information";
      reference "MEF-SOAM-PM-MIB.mefSoamLmCfgPriority";
    }
    leaf frame-size {
      type uint32 {
        range "64 .. 9600";
      }
      units "bytes";
      default "64";
      description
        "This object specifies the Loss Measurement frame size between 64 bytes
         and the maximum transmission unit of the EVC.
         The range of frame sizes from 64 through 2000 octets need to be
         supported, and the range of frame sizes from 2001 through 9600
         octets is suggested be supported.
         The adjustment to the frame size of the standard frame size is
         accomplished by the addition of a Data or Test TLV. A Data or
         Test TLV is only added to the frame if the frame size is greater
         than 64 bytes.";
      user-ext:CLI-comm-help "Set Loss Measurement frame size";
      reference "MEF-SOAM-PM-MIB.mefSoamLmCfgFrameSize";
    }
    leaf data-pattern {
      type enumeration {
        enum "zeroes" {
          description
            "Indicates the Data TLV contains all zeros.";
        }
        enum "ones" {
          description
            "Indicates the Data TLV contains all ones.";
        }
      }
      default "zeroes";
      description
        "This object specifies the LM data pattern included in a Data TLV when
         the size of the LM frame is determined by the frame-size object
         and test-tlv-included is 'false'.
         If the frame size object does not define the LM frame size or
         test-tlv-included is 'true' the value of this object is ignored.";
      user-ext:CLI-comm-help "Set LM data pattern included in a Data TLV";
      reference "MEF-SOAM-PM-MIB.mefSoamLmCfgDataPattern";
    }
    leaf test-tlv-included {
      type boolean;
      default "false";
      description
        "This object indicates whether a Test TLV or Data TLV is included when
         the size of the LM frame is determined by the
         frame-size object.
         A value of 'true' indicates that the Test TLV is to be
         included. A value of 'false' indicates that the Data TLV is to
         be included.
         If the frame-size object does not define the LM frame size the
         value of this object is ignored.";
      user-ext:CLI-comm-help "Configure Test TLV or Data TLV inclusion";
      reference "MEF-SOAM-PM-MIB.mefSoamLmCfgTestTlvIncluded";
    }
    leaf test-tlv-pattern {
      type test-pattern-type;
      default "null-signal-without-crc-32";
      description
        "This object specifies the type of test pattern to be sent in the LM
         frame Test TLV when the size of LM PDU is determined by the
         frame-size object and test-tlv-included is 'true'. If the frame
         size object does not define the LM frame size or
         test-tlv-included is 'false' the value of this object is
         ignored.";
      user-ext:CLI-comm-help "Set Test TLV pattern type";
      reference "MEF-SOAM-PM-MIB.mefSoamLmCfgTestTlvPattern";
    }
    leaf measurement-interval {
      type uint32 {
        range "1..525600";
      }
      units "minutes";
      default "15";
      description
        "This object specifies the Measurement Interval for FLR statistics, in
         minutes.
         A Measurement Interval of 15 minutes needs to be supported,
         other intervals may be supported.";
      user-ext:CLI-comm-help "Set the Measurement Interval for FLR statistics";
      reference "MEF-SOAM-PM-MIB.mefSoamLmCfgMeasurementInterval";
    }
    leaf number-intervals-stored {
      type uint32 {
        range "2..1000";
      }
      default "32";
      description
        "This object specifies the number of completed measurement intervals to
         store in the history statistic table.
         At least 32 completed measurement intervals are to be
         stored. 96 measurement intervals are recommended to be stored.";
      user-ext:CLI-comm-help "Set the number of completed measurement intervals to be stored";
      reference "MEF-SOAM-PM-MIB.mefSoamLmCfgNumIntervalsStored";
    }
    leaf align-measurement-intervals {
      type boolean;
      default "false";
      description
        "This object specifies whether the measurement intervals for the Loss
         Measurement session are aligned with a zero offset to real
         time.
         The value 'true' indicates that each Measurement Interval
         starts at a time which is aligned to NE time source hour if the
         interval is a factor of an hour, i.e. 60min/15min = 4. For
         instance, a measurement time interval of 15 minutes would
         stop/start the measurement interval at 0, 15, 30, and 45
         minutes of an hour. A measurement interval of 7 minutes would
         not align to the hour since 7 minutes is NOT a factor of an
         hour, i.e. 60min/7min = 8.6, and the behavior is the same as
         if the object is set to 'false'.
         The value 'false' indicates that each Measurement Interval
         starts at a time which is indicated by repetition-period.
         One side effect of the usage of this parameter is that if the
         value is true and the repetition-period is not a factor of an
         hour then the start of the next Measurement Interval will be
         delayed until the next factor of an hour.";
      user-ext:CLI-comm-help "Configure the alignment of measurement intervals for LM session";
      reference "MEF-SOAM-PM-MIB.mefSoamLmCfgAlignMeasurementIntervals";
    }
    leaf align-measurement-offset {
      type uint32 {
        range "0..525600";
      }
      units "minutes";
      default "0";
      description
        "This object specifies the offset in minutes from the time of day value
         if align-measurement-intervals is 'true' and the repetition
         time is a factor of 60 minutes. If not, the value of this
         object is ignored.
         If the Measurement Interval is 15 minutes and
         align-measurement-intervals is true and if this object was set
         to 5 minutes, the Measurement Intervals would start at 5, 20,
         35, 50 minutes past each hour.";
      user-ext:CLI-comm-help "Set the alignment offset of measurement intervals for LM session";
      reference "MEF-SOAM-PM-MIB.mefSoamLmCfgAlignMeasurementOffset";
    }
    leaf availability-measurement-interval {
      type uint32 {
        range "1..525600";
      }
      units "minutes";
      default "15";
      description
        "This object specifies the availability measurement interval in minutes.
         A measurement interval of 15 minutes is to be supported, other
         intervals can be supported.";
      user-ext:CLI-comm-help "Set the availability measurement interval";
      reference "MEF-SOAM-PM-MIB.mefSoamLmCfgAvailabilityMeasurementInterval";
    }
    leaf availability-number-consecutive-flr-measurements {
      type uint32 {
        range "1..1000000";
      }
      default "10";
      description
        "This object specifies a configurable number of consecutive loss
         measurement PDUs to be used in evaluating the
         availability/unavailability status of each availability
         indicator per MEF 10.2.1.  Loss Measurement PDUs (LMMs, CCMs or
         SLMs) are sent regularly with a period defined by
         message-period.  Therefore, this object, when multiplied by
         message-period, is equivalent to the Availability parameter of
         'delta_t' as specified by MEF 10.2.1.
         If the measurement-type is lmm or ccm, this object defines the
         number of LMM or CCM PDUs transmitted during each 'delta_t'
         period.  The Availability flr for a given 'delta_t' can be
         calculated based on the counters in the last LMM/R or CCM
         during this 'delta_t' and the last LMM/R or CCM in the previous
         'delta_t'.
         If the measurement-type is slm, this object defines the number
         of SLM PDUs transmitted during each 'delta_t' period.  The
         Availability flr for a given 'delta_t' is calculated based on
         the number of those SLM PDUs that are lost.
         If the measurement-type is lmm or ccm, the number range of 1
         through 10 must be supported. The number range of 10 through
         1000000 may be supported, but is not mandatory.
         If the measurement-type is slm, the number range of 10 through
         100 must be supported. The number range of 100 through 1000000
         may be supported, but is not mandatory.";
      user-ext:CLI-comm-help "Set the number of LM PDUs used in evaluating the status of each availability indicator";
      reference "MEF-SOAM-PM-MIB.mefSoamLmCfgAvailabilityNumConsecutiveMeasPdus";
    }
    leaf availability-flr-threshold {
      type uint32 {
        range "0..100000";
      }
      units "milli-percent";
      default "50000";
      description
        "This object specifies a configurable availability threshold to be used
         in evaluating the availability/unavailability status of an
         availability indicator per MEF 10.2.1. The availability
         threshold range of 0.00 (0) through 1.00 (100000) is
         supported. This parameter is equivalent to the Availability
         parameter of 'C' as specified by MEF 10.2.1.
         Units are in milli-percent, where 1 indicates 0.001 percent.";
      user-ext:CLI-comm-help "Set the threshold used in evaluating the status of an availability indicator";
      reference "MEF-SOAM-PM-MIB.mefSoamLmCfgAvailabilityFlrThreshold";
    }
    leaf availability-number-consecutive-intervals {
      type uint32 {
        range "1..1000";
      }
      default "10";
      description
        "This object specifies a configurable number of consecutive availability
         indicators to be used to determine a change in the availability
         status as indicated by MEF 10.2.1. This parameter is equivalent
         to the Availability parameter of 'n' as specified by MEF
         10.2.1.
         The number range of 1 through 10 must be supported. The number
         range of 1 through 1000 may be supported, but is not mandatory.";
      user-ext:CLI-comm-help "Set the number of indicators used in evaluating the availability status";
      reference "MEF-SOAM-PM-MIB.mefSoamLmCfgAvailabilityNumConsecutiveIntervals";
    }
    leaf availability-number-consecutive-high-flr {
      type uint32 {
        range "1..1000";
      }
      default "5";
      description
        "This object specifies a configurable number of consecutive availability
         indicators to be used for assessing CHLI.  This parameter is
         equivalent to the Resilency parameter of 'p' as specified by
         MEF 10.2.1.
         Availability-consecutive-high-flr must be strictly less than
         availability-number-consecutive-intervals. If not, the count of
         high loss intervals over time, and the count of consecutive
         high loss levels, is disabled.
         The number range of 1 through 10 must be supported. The number
         range of 1 through 1000 may be supported, but is not mandatory.";
      user-ext:CLI-comm-help "Set the number of indicators used for assessing CHLI";
      reference "MEF-SOAM-PM-MIB.mefSoamLmCfgAvailabilityNumConsecutiveHighFlr";
    }
    leaf session-type {
      type enumeration {
        enum "proactive" {
          description
            "The current session is 'proactive'";
        }
        enum "on-demand" {
          description
            "The current session is 'on-demand'";
        }
      }
      default "proactive";
      description
        "This object indicates whether the current session is defined to be
         'proactive' or 'on-demand'.";
      user-ext:CLI-comm-help "Set the LM Session type";
      reference "[MEF SOAM IA] R3";
    }
    leaf threshold-profile {
      type uint32;
      description
        "This object indicates the index of the threshold profile to use for
         this measurement.";
      user-ext:CLI-comm-help "Set the index of the threshold profile for this measurement";
    }
  }

  grouping loss-threshold-group {
    description
      "Loss thresholds";
    leaf measured-flr-forward {
      type uint32 {
        range "0..100000";
      }
      units "milli-percent";
      description
        "This object is used to set the measured forward frame loss ratio
         threshold value that will be used to determine if a threshold
         notification is generated.";
      user-ext:CLI-comm-help "Set the measured forward FLR threshold";
      reference "MEF-SOAM-PM-MIB.mefSoamLmThresholdCfgMeasuredFlrForwardThreshold";
    }
    leaf max-flr-forward {
      type uint32 {
        range "0..100000";
      }
      units "milli-percent";
      description
        "This object is used to set the maximum forward frame loss ratio
         threshold value that will be used to determine if a threshold
         notification is generated.";
      user-ext:CLI-comm-help "Set the maximum forward FLR threshold";
      reference "MEF-SOAM-PM-MIB.mefSoamLmThresholdCfgMaxFlrForwardThreshold";
    }
    leaf average-flr-forward {
      type uint32 {
        range "0..100000";
      }
      units "milli-percent";
      description
        "This object is used to set the average forward frame loss ratio
         threshold value that will be used to determine if a threshold
         notification is generated.";
      user-ext:CLI-comm-help "Set the average forward FLR threshold";
      reference "MEF-SOAM-PM-MIB.mefSoamLmThresholdCfgAvgFlrForwardThreshold";
    }
    leaf measured-flr-backward {
      type uint32 {
        range "0..100000";
      }
      units "milli-percent";
      description
        "This object is used to set the measured backward frame loss ratio
         threshold value that will be used to determine if a threshold
         notification is generated.";
      user-ext:CLI-comm-help "Set the measured backward FLR threshold";
      reference "MEF-SOAM-PM-MIB.mefSoamLmThresholdCfgMeasuredFlrBackwardThreshold";
    }
    leaf max-flr-backward {
      type uint32 {
        range "0..100000";
      }
      units "milli-percent";
      description
        "This object is used to set the maximum backward frame loss ratio
         threshold value that will be used to determine if a threshold
         notification is generated.";
      user-ext:CLI-comm-help "Set the maximum backward FLR threshold";
      reference "MEF-SOAM-PM-MIB.mefSoamLmThresholdCfgMaxFlrBackwardThreshold";
    }
    leaf average-flr-backward {
      type uint32 {
        range "0..100000";
      }
      units "milli-percent";
      description
        "This object is used to set the average backward frame loss ratio
         threshold value that will be used to determine if a threshold
         notification is generated.";
      user-ext:CLI-comm-help "Set the average backward FLR threshold";
      reference "MEF-SOAM-PM-MIB.mefSoamLmThresholdCfgAvgFlrBackwardThreshold";
    }
    leaf forward-unavailable-count {
      type uint32;
      description
        "This object is used to set the forward unavailability threshold value
         that will be used to determine if a threshold notification is
         generated.";
      user-ext:CLI-comm-help "Set the forward unavailability threshold";
      reference "MEF-SOAM-PM-MIB.mefSoamLmThresholdCfgForwardUnavailCountThreshold";
    }
    leaf forward-available-ratio {
      type uint32 {
        range "0..100000";
      }
      units "milli-percent";
      description
        "This object is used to set the forward availability/total time ratio
         threshold value that will be used to determine if a
         thresh-old notification is generated if the ratio drops below
         the configured value.
         The ratio value is expressed as a percent with a value of 0
         (ra-tio 0.00) through 100000 (ratio 1.00)
         Units are in milli-percent, where 1 indicates 0.001 percent.";
      user-ext:CLI-comm-help "Set the forward availability ratio threshold";
      reference "MEF-SOAM-PM-MIB.mefSoamLmThresholdCfgForwardAvailRatioThreshold";
    }
    leaf backward-unavailable-count {
      type uint32;
      description
        "This object is used to set the backward unavailability threshold
         value that will be used to determine if a threshold notification is
         generated.";
      user-ext:CLI-comm-help "Set the backward unavailability threshold";
      reference "MEF-SOAM-PM-MIB.mefSoamLmThresholdCfgBackwardUnavailCountThreshold";
    }
    leaf backward-available-ratio {
      type uint32 {
        range "0..100000";
      }
      units "milli-percent";
      description
        "This object is used to set the backward availability/total time ratio
         threshold value that will be used to determine if a
         thresh-old notification is generated if the ratio drops below
         the configured value.
         The ratio value is expressed as a percent with a value of 0
         (ratio 0.00) through 100000 (ratio 1.00)
         Units are in milli-percent, where 1 indicates 0.001 percent.";
      user-ext:CLI-comm-help "Set the backward availability ratio threshold";
      reference "MEF-SOAM-PM-MIB.mefSoamLmThresholdCfgBackwardAvailRatioThreshold";
    }
  }

  grouping loss-availability-stats-group {
    description
      "This grouping includes availability statistics objects for a SOAM Loss
       Measurement session.";
    leaf suspect-status {
      type suspect-status-type;
      description
        "This object indicates whether the Measurement Interval has been marked
         as suspect.
         The object is set to false at the start of a measurement
         interval. It is set to true when there is a discontinuity in
         the performance measurements during the Measurement Interval.
         Conditions for a discontinuity include, but are not limited to
         the following:
         1 - The local time-of-day clock is adjusted by at least 10 seconds
         2 - The conducting of a performance measurement is halted before the
         current Measurement Interval is completed
         3 - A local test, failure, or reconfiguration that disrupts service";
      config false;
    }
    leaf forward-available {
      type yang:gauge32;
      description
        "This object contains the number of availability indicators during a
         small time interval evaluated as available (low frame loss) in
         the forward direction by this MEP during this measurement
         interval.";
      config false;
      reference "MEF-SOAM-PM-MIB.mefSoamLmCurrentAvailStatsForwardAvailable";
    }
    leaf backward-available {
      type yang:gauge32;
      description
        "This object contains the number of availability indicators during a
         small time interval evaluated as available (low frame loss) in
         the backward direction by this MEP during this measurement
         interval.";
      config false;
      reference "MEF-SOAM-PM-MIB.mefSoamLmCurrentAvailStatsBackwardAvailable";
    }
    leaf forward-unavailable {
      type yang:gauge32;
      description
        "This object contains the number of availability indicators during a
         small time interval evaluated as unavailable (high frame loss)
         in the forward direction by this MEP during this measurement
         interval.";
      config false;
      reference "MEF-SOAM-PM-MIB.mefSoamLmCurrentAvailStatsForwardUnavailable";
    }
    leaf backward-unavailable {
      type yang:gauge32;
      description
        "This object contains the number of availability indicators during a
         small time interval evaluated as unavailable (high frame loss)
         in the backward direction by this MEP during this measurement
         interval.";
      config false;
      reference "MEF-SOAM-PM-MIB.mefSoamLmCurrentAvailStatsBackwardUnavailable";
    }
    leaf forward-min-frame-loss-ratio {
      type uint32 {
        range "0..100000";
      }
      units "milli-percent";
      description
        "This object contains the minimum one-way availability flr in the
         forward direction, from among the set of availability flr values
         calculated by the MEP in this Measurement Interval.  There is
         one availability flr value for each 'delta_t' time period
         within the Measurement Interval, as specified in MEF 10.2.1.
         The flr value is a ratio that is expressed as a percent with a
         value of 0 (ratio 0.00) through 100000 (ratio 1.00).
         Units are in milli-percent, where 1 indicates 0.001 percent.";
      config false;
      reference "MEF-SOAM-PM-MIB.mefSoamLmCurrentAvailStatsForwardMinFlr";
    }
    leaf forward-max-frame-loss-ratio {
      type uint32 {
        range "0..100000";
      }
      units "milli-percent";
      description
        "This object contains the maximum one-way availability flr in the
         forward direction, from among the set of availability flr
         values calculated by the MEP in this Measurement Interval.
         There is one availability flr value for each 'delta_t' time
         period within the Measurement Interval, as specified in MEF
         10.2.1.
         The flr value is a ratio that is expressed as a percent with a
         value of 0 (ratio 0.00) through 100000 (ratio 1.00).
         Units are in milli-percent, where 1 indicates 0.001 percent.";
      config false;
      reference "MEF-SOAM-PM-MIB.mefSoamLmCurrentAvailStatsForwardMaxFlr";
    }
    leaf forward-average-frame-loss-ratio {
      type uint32 {
        range "0..100000";
      }
      units "milli-percent";
      description
        "This object contains the average one-way availability flr in the
         for-ward direction, from among the set of availability flr
         values calculated by the MEP in this Measurement Interval.
         There is one availability flr value for each 'delta_t' time
         period within the Measurement Interval, as specified in MEF
         10.2.1.
         The flr value is a ratio that is expressed as a percent with a
         value of 0 (ratio 0.00) through 100000 (ratio 1.00).
         Units are in milli-percent, where 1 indicates 0.001 percent.";
      config false;
      reference "MEF-SOAM-PM-MIB.mefSoamLmCurrentAvailStatsForwardAvgFlr";
    }
    leaf backward-min-frame-loss-ratio {
      type uint32 {
        range "0..100000";
      }
      units "milli-percent";
      description
        "This object contains the minimum one-way availability flr in the
         backward direction, from among the set of availability flr
         values calculated by the MEP in this Measurement Interval.
         There is one availability flr value for each 'delta_t' time
         period within the Measurement Interval, as specified in MEF
         10.2.1.
         The flr value is a ratio that is expressed as a percent with a
         value of 0 (ratio 0.00) through 100000 (ratio 1.00).
         Units are in milli-percent, where 1 indicates 0.001 percent.";
      config false;
      reference "MEF-SOAM-PM-MIB.mefSoamLmCurrentAvailStatsBackwardMinFlr";
    }
    leaf backward-max-frame-loss-ratio {
      type uint32 {
        range "0..100000";
      }
      units "milli-percent";
      description
        "This object contains the maximum one-way availability flr in the
         backward direction, from among the set of availability flr
         values calculated by the MEP in this Measurement Interval.
         There is one availability flr value for each 'delta_t' time
         period within the Measurement Interval, as specified in MEF
         10.2.1.
         The flr value is a ratio that is expressed as a percent with a
         value of 0 (ratio 0.00) through 100000 (ratio 1.00).
         Units are in milli-percent, where 1 indicates 0.001 percent.";
      config false;
      reference "MEF-SOAM-PM-MIB.mefSoamLmCurrentAvailStatsBackwardMaxFlr";
    }
    leaf backward-average-frame-loss-ratio {
      type uint32 {
        range "0..100000";
      }
      units "milli-percent";
      description
        "This object contains the average one-way availability flr in the
         backward direction, from among the set of availability flr
         values calculated by the MEP in this Measurement Interval.
         There is one availability flr value for each 'delta_t' time
         period within the Measurement Interval, as specified in MEF
         10.2.1.
         The flr value is a ratio that is expressed as a percent with a
         value of 0 (ratio 0.00) through 100000 (ratio 1.00).
         Units are in milli-percent, where 1 indicates 0.001 percent.";
      config false;
      reference "MEF-SOAM-PM-MIB.mefSoamLmCurrentAvailStatsBackwardAvgFlr";
    }
  }

  grouping loss-measurement-stats-group {
    description
      "This grouping includes statistics objects for a SOAM Loss Measurement
       session.";
    leaf suspect-status {
      type suspect-status-type;
      description
        "Whether the Measurement Interval has been marked as suspect.
         The object is set to false at the start of a measurement
         interval. It is set to true when there is a discontinuity in
         the performance measurements during the Measurement Interval.
         Conditions for a discontinuity include, but are not limited to
         the following:
         1 - The local time-of-day clock is adjusted by at least 10 seconds
         2 - The conducting of a performance measurement is halted before the
         current Measurement Interval is completed
         3 - A local test, failure, or reconfiguration that disrupts service";
      config false;
      reference "MEF-SOAM-PM-MIB.mefSoamLmCurrentStatsSuspect";
    }
    leaf forward-transmitted-frames {
      type yang:gauge32;
      mandatory true;
      description
        "This object contains the number of frames transmitted in the forward
         direction by this MEP.
         For a PM Session of types lmm or ccm this includes Ethernet
         Service Frames and SOAM PDUs that are in a higher MEG level
         only.
         For a PM Session of type slm this includes the count of SOAM
         ETH-SLM frames only.";
      config false;
      reference "MEF-SOAM-PM-MIB.mefSoamLmCurrentStatsForwardTransmittedFrames";
    }
    leaf forward-received-frames {
      type yang:gauge32;
      mandatory true;
      description
        "This object contains the number of frames received in the forward
         direction by this MEP.
         For a PM Session of types lmm or ccm this includes Ethernet
         Service Frames and SOAM PDUs that are in a higher MEG level only.
         For a PM Session of type slm this includes the count of SOAM
         ETH-SLM frames only.";
      config false;
      reference "MEF-SOAM-PM-MIB.mefSoamLmCurrentStatsForwardReceivedFrames";
    }
    leaf forward-min-frame-loss-ratio {
      type uint32 {
        range "0..100000";
      }
      units "milli-percent";
      description
        "This object contains the minimum one-way frame loss ratio in the
         forward direction calculated by this MEP for this Measurement
         Interval. The FLR value is a ratio that is expressed as a
         percent with a value of 0 (ratio 0.00) through 100000 (ratio
         1.00).
         Units are in milli-percent, where 1 indicates 0.001 percent.";
      config false;
      reference "MEF-SOAM-PM-MIB.mefSoamLmCurrentStatsForwardMinFlr";
    }
    leaf forward-max-frame-loss-ratio {
      type uint32 {
        range "0..100000";
      }
      units "milli-percent";
      description
        "This object contains the maximum one-way frame loss ratio in the
         forward direction calculated by this MEP for this Measurement
         Interval. The FLR value is a ratio that is expressed as a
         percent with a value of 0 (ratio 0.00) through 100000 (ratio
         1.00).
         Units are in milli-percent, where 1 indicates 0.001 percent.";
      config false;
      reference "MEF-SOAM-PM-MIB.mefSoamLmCurrentStatsForwardMaxFlr";
    }
    leaf forward-average-frame-loss-ratio {
      type uint32 {
        range "0..100000";
      }
      units "milli-percent";
      description
        "This object contains the average one-way frame loss ratio in the
         forward direction calculated by this MEP for this Measurement
         Interval. The FLR value is a ratio that is expressed as a
         percent with a value of 0 (ratio 0.00) through 100000 (ratio
         1.00).
         Units are in milli-percent, where 1 indicates 0.001 percent.";
      config false;
      reference "MEF-SOAM-PM-MIB.mefSoamLmCurrentStatsForwardAvgFlr";
    }
    leaf backward-transmitted-frames {
      type yang:gauge32;
      mandatory true;
      description
        "This object contains the number of frames transmitted in the backward
         direction by this MEP.
         For a PM Session of type lmm or ccm this includes Ethernet
         Service Frames and SOAM PDUs that are in a higher MEG level
         only.
         For a PM Session of type slm this includes the count of SOAM
         ETH-SLM frames only.";
      config false;
      reference "MEF-SOAM-PM-MIB.mefSoamLmCurrentStatsBackwardTransmittedFrames";
    }
    leaf backward-received-frames {
      type yang:gauge32;
      mandatory true;
      description
        "This object contains the number of frames received in the backward
         direction by this MEP.
         For a PM Session of type lmm this includes Ethernet Service
         Frames and SOAM PDUs that are in a higher MEG level only.
         For a PM Session of type slm this includes the count of SOAM
         ETH-SLM frames only.";
      config false;
      reference "MEF-SOAM-PM-MIB.mefSoamLmCurrentStatsBackwardReceivedFrames";
    }
    leaf backward-min-frame-loss-ratio {
      type uint32 {
        range "0..100000";
      }
      units "milli-percent";
      description
        "This object contains the minimum one-way frame loss ratio in the
         backward direction calculated by this MEP for this Measurement
         Interval. The FLR value is a ratio that is expressed as a
         percent with a value of 0 (ratio 0.00) through 100000 (ratio
         1.00).
         Units are in milli-percent, where 1 indicates 0.001 percent.";
      config false;
      reference "MEF-SOAM-PM-MIB.mefSoamLmCurrentStatsBackwardMinFlr";
    }
    leaf backward-max-frame-loss-ratio {
      type uint32 {
        range "0..100000";
      }
      units "milli-percent";
      description
        "This object contains the maximum one-way frame loss ratio in the
         backward direction calculated by this MEP for this Measurement
         Interval. The FLR value is a ratio that is expressed as a
         percent with a value of 0 (ratio 0.00) through 100000 (ratio
         1.00).
         Units are in milli-percent, where 1 indicates 0.001 percent.";
      config false;
      reference "MEF-SOAM-PM-MIB.mefSoamLmCurrentStatsBackwardMaxFlr";
    }
    leaf backward-average-frame-loss-ratio {
      type uint32 {
        range "0..100000";
      }
      units "milli-percent";
      description
        "This object contains the average one-way frame loss ratio in the
         backward direction calculated by this MEP for this Measurement
         Interval. The FLR value is a ratio that is expressed as a
         percent with a value of 0 (ratio 0.00) through 100000 (ratio
         1.00).
         Units are in milli-percent, where 1 indicates 0.001 percent.";
      config false;
      reference "MEF-SOAM-PM-MIB.mefSoamLmCurrentStatsBackwardAvgFlr";
    }
    leaf soam-pdus-sent {
      type yang:gauge32;
      description
        "This object contains the count of the number of SOAM PDUs sent during
         this Measurement Interval.
         This object applies when type is lmm, slm or ccm. It indicates
         the number of LMM, CCM, or SLM SOAM frames transmitted.";
      config false;
      reference "MEF-SOAM-PM-MIB.mefSoamLmCurrentStatsSoamPdusSent";
    }
    leaf soam-pdus-received {
      type yang:gauge32;
      description
        "This object contains the count of the number of SOAM PDUs PDUs received
         in this Measurement Interval.
         This object applies when type is lmm, slm, or ccm. This object
         indicates the number of LMR, CCM, or SLR SOAM frames received.";
      config false;
      reference "MEF-SOAM-PM-MIB.mefSoamLmCurrentStatsSoamPdusReceived";
    }
  }

  grouping delay-measurement-configuration-group {
    description
      "This grouping includes configuration objects for the Delay Measurement
       function defined in [Y.1731] and [MEF SOAM PM IA].";
    reference "MEF-SOAM-PM-MIB.mefSoamDmCfgTable, [Y.1731], and [MEF SOAM PM IA].";
    leaf measurement-type {
      type enumeration {
        enum "dmm" {
          description
            "DMM SOAM PDU generated, DMR responses received (one-way or two-way
             measurements).";
        }
      }
      default "dmm";
      description
        "This object indicates what type of Delay Measurement is to be
         performed.
         The exact PDUs to use are specified by this object in
         combination with version.";
      user-ext:CLI-comm-help "Set Delay Measurement type";
    }
    container measurement-enable {
      user-ext:CLI-comm-help "Configure DM counters";
      description
        "A vector of bits that indicates the type of SOAM DM counters that
         are enabled.
         A present bit enables the specific SOAM DM counter.
         A not present bit disables the SOAM DM counter.
         If a particular SOAM DM counter is not supported the BIT value
         is not present.
         Not all SOAM DM counters are supported for all SOAM DM types.";
      leaf soam-pdus-sent {
        type empty;
        description
          "SOAM PDUs sent";
        user-ext:CLI-comm-help "Enable DM SOAM PDUs sent counter";
      }
      leaf soam-pdus-received {
        type empty;
        description
          "SOAM PDUs received";
        user-ext:CLI-comm-help "Enable DM SOAM PDUs received counter";
      }
      leaf frame-delay-two-way-bins {
        type empty;
        description
          "Frame delay two way bins";
        user-ext:CLI-comm-help "Enable frame delay two way bins";
      }
      leaf frame-delay-two-way-min {
        type empty;
        description
          "Frame delay two way min";
        user-ext:CLI-comm-help "Enable frame delay two way minimum counter";
      }
      leaf frame-delay-two-way-max {
        type empty;
        description
          "Frame delay two way max";
        user-ext:CLI-comm-help "Enable frame delay two way maximum counter";
      }
      leaf frame-delay-two-way-average {
        type empty;
        description
          "Frame delay two way average";
        user-ext:CLI-comm-help "Enable frame delay two way average counter";
      }
      leaf frame-delay-forward-bins {
        type empty;
        description
          "Frame delay forward bins";
        user-ext:CLI-comm-help "Enable frame delay forward bins";
      }
      leaf frame-delay-forward-min {
        type empty;
        description
          "Frame delay forward min";
        user-ext:CLI-comm-help "Enable frame delay forward minimum counter";
      }
      leaf frame-delay-forward-max {
        type empty;
        description
          "Frame delay forward max";
        user-ext:CLI-comm-help "Enable frame delay forward maximum counter";
      }
      leaf frame-delay-forward-average {
        type empty;
        description
          "Frame delay forward average";
        user-ext:CLI-comm-help "Enable frame delay forward average counter";
      }
      leaf frame-delay-backward-bins {
        type empty;
        description
          "Frame delay backward bins";
        user-ext:CLI-comm-help "Enable frame delay backward bins";
      }
      leaf frame-delay-backward-min {
        type empty;
        description
          "Frame delay backward min";
        user-ext:CLI-comm-help "Enable frame delay backward minimum counter";
      }
      leaf frame-delay-backward-max {
        type empty;
        description
          "Frame delay backward max";
        user-ext:CLI-comm-help "Enable frame delay backward maximum counter";
      }
      leaf frame-delay-backward-average {
        type empty;
        description
          "Frame delay backward average";
        user-ext:CLI-comm-help "Enable frame delay backward average counter";
      }
      leaf inter-frame-delay-variation-forward-bins {
        type empty;
        description
          "Inter frame delay variation forward bins";
        user-ext:CLI-comm-help "Enable inter frame delay variation forward bins";
      }
      leaf inter-frame-delay-variation-forward-min {
        type empty;
        description
          "Inter frame delay variation forward min";
        user-ext:CLI-comm-help "Enable inter frame delay variation forward minimum counter";
      }
      leaf inter-frame-delay-variation-forward-max {
        type empty;
        description
          "Inter frame delay variation forward max";
        user-ext:CLI-comm-help "Enable inter frame delay variation forward maximum counter";
      }
      leaf inter-frame-delay-variation-forward-average {
        type empty;
        description
          "Inter frame delay variation forward average";
        user-ext:CLI-comm-help "Enable inter frame delay variation forward average counter";
      }
      leaf inter-frame-delay-variation-backward-bins {
        type empty;
        description
          "Inter frame delay variation backward bins";
        user-ext:CLI-comm-help "Enable inter frame delay variation backward bins";
      }
      leaf inter-frame-delay-variation-backward-min {
        type empty;
        description
          "Inter frame delay variation backward min";
        user-ext:CLI-comm-help "Enable inter frame delay variation backward minimum counter";
      }
      leaf inter-frame-delay-variation-backward-max {
        type empty;
        description
          "Inter frame delay variation backward max";
        user-ext:CLI-comm-help "Enable inter frame delay variation backward maximum counter";
      }
      leaf inter-frame-delay-variation-backward-average {
        type empty;
        description
          "Inter frame delay variation backward average";
        user-ext:CLI-comm-help "Enable inter frame delay variation backward average counter";
      }
      leaf inter-frame-delay-variation-two-way-bins {
        type empty;
        description
          "Inter frame delay variation two way bins";
        user-ext:CLI-comm-help "Enable inter frame delay variation two way bins";
      }
      leaf inter-frame-delay-variation-two-way-min {
        type empty;
        description
          "Inter frame delay variation two way min";
        user-ext:CLI-comm-help "Enable inter frame delay variation two way minimum counter";
      }
      leaf inter-frame-delay-variation-two-way-max {
        type empty;
        description
          "Inter frame delay variation two way max";
        user-ext:CLI-comm-help "Enable inter frame delay variation two way maximum counter";
      }
      leaf inter-frame-delay-variation-two-way-average {
        type empty;
        description
          "Inter frame delay variation two way average";
        user-ext:CLI-comm-help "Enable inter frame delay variation two way average counter";
      }
      leaf frame-delay-range-forward-bins {
        type empty;
        description
          "Frame delay range forward bins";
        user-ext:CLI-comm-help "Enable frame delay range forward bins";
      }
      leaf frame-delay-range-forward-max {
        type empty;
        description
          "Frame delay range forward max";
        user-ext:CLI-comm-help "Enable frame delay range forward maximum counter";
      }
      leaf frame-delay-range-forward-average {
        type empty;
        description
          "Frame delay range forward average";
        user-ext:CLI-comm-help "Enable frame delay range forward average counter";
      }
      leaf frame-delay-range-backward-bins {
        type empty;
        description
          "Frame delay range backward bins";
        user-ext:CLI-comm-help "Enable frame delay range backward bins";
      }
      leaf frame-delay-range-backward-max {
        type empty;
        description
          "Frame delay range backward max";
        user-ext:CLI-comm-help "Enable frame delay range backward maximum counter";
      }
      leaf frame-delay-range-backward-average {
        type empty;
        description
          "Frame delay range backward average";
        user-ext:CLI-comm-help "Enable frame delay range backward average counter";
      }
      leaf frame-delay-range-two-way-bins {
        type empty;
        description
          "Frame delay range two way bins";
        user-ext:CLI-comm-help "Enable frame delay range two way bins";
      }
      leaf frame-delay-range-two-way-max {
        type empty;
        description
          "Frame delay range two way max";
        user-ext:CLI-comm-help "Enable frame delay range two way maximum counter";
      }
      leaf frame-delay-range-two-way-average {
        type empty;
        description
          "Frame delay range two way average";
        user-ext:CLI-comm-help "Enable frame delay range two way average counter";
      }
      leaf measured-stats-frame-delay-two-way {
        type empty;
        description
          "Measured stats frame delay two way";
        user-ext:CLI-comm-help "Enable measured stats frame delay two way counter";
      }
      leaf measured-stats-frame-delay-forward {
        type empty;
        description
          "Measured stats frame delay forward";
        user-ext:CLI-comm-help "Enable measured stats frame delay forward counter";
      }
      leaf measured-stats-frame-delay-backward {
        type empty;
        description
          "Measured stats frame delay backward";
        user-ext:CLI-comm-help "Enable measured stats frame delay backward counter";
      }
      leaf measured-stats-inter-frame-delay-variation-two-way {
        type empty;
        description
          "Measured stats inter frame delay variation two way";
        user-ext:CLI-comm-help "Enable measured stats inter frame delay variation two way counter";
      }
      leaf measured-stats-inter-frame-delay-variation-forward {
        type empty;
        description
          "Measured stats inter frame delay variation forward";
        user-ext:CLI-comm-help "Enable measured stats inter frame delay variation forward counter";
      }
      leaf measured-stats-inter-frame-delay-variation-backward {
        type empty;
        description
          "Measured stats inter frame delay variation backward";
        user-ext:CLI-comm-help "Enable measured stats inter frame delay variation backward counter";
      }
    }
    leaf message-period {
      type performance-monitoring-interval-type;
      default "100";
      description
        "This object specifies the interval between Delay Measurement OAM
         message transmission. For Delay Measurement monitoring applications,
         the default value is 100ms.";
      user-ext:CLI-comm-help "Set interval between DM message transmission";
    }
    leaf priority {
      type priority-type;
      default 7;
      description
        "This object specifies the priority of frames with Performance
         Monitoring OAM message information.";
      user-ext:CLI-comm-help "Set priority for frames with DM message information";
    }
    leaf frame-size {
      type uint32 {
        range "64 .. 9600";
      }
      default "64";
      description
        "This object specifies the Delay Measurement frame size between 64 bytes
         and the maximum transmission unit of the EVC.
         The range of frame sizes from 64 through 2000 octets need to be
         supported, and the range of frame sizes from 2001 through 9600
         octets is suggested to be supported.
         The adjustment to the frame size of the standard frame size is
         accomplished by the addition of a Data or Test TLV. A Data or
         Test TLV is only added to the frame if the frame size is
         greater than 64 bytes.";
      user-ext:CLI-comm-help "Set Delay Measurement frame size";
    }
    leaf data-pattern {
      type enumeration {
        enum "zeroes" {
          description
            "Indicates the Data TLV contains all zeros.";
        }
        enum "ones" {
          description
            "Indicates the Data TLV contains all ones.";
        }
      }
      default "zeroes";
      description
        "This object specifies the DM data pattern included in a Data TLV when
         the size of the DM frame is determined by the frame-size object
         and test-tlv-included is 'false'.  If the frame size object
         does not define the DM frame size or test-tlv-included is
         'true' the value of this object is ignored.";
      user-ext:CLI-comm-help "Set DM data pattern included in a Data TLV";
    }
    leaf test-tlv-included {
      type boolean;
      default "false";
      description
        "Indicates whether a Test TLV or Data TLV is included when the size of
         the LBM frame is determined by the frame-size leaf.
         A value of 'true' indicates that the Test TLV is to be
         included.
         A value of 'false' indicates that the Data TLV is to be
         included.";
      user-ext:CLI-comm-help "Configure Test TLV or Data TLV inclusion";
      reference "[Y.1731] 9.3";
    }
    leaf test-tlv-pattern {
      type test-pattern-type;
      default "null-signal-without-crc-32";
      description
        "This object specifies the type of test pattern to be sent in the DM
         frame Test TLV when the size of DM PDU is determined by the
         frame-size object and test-tlv-included is 'true'. If the frame
         size object does not define the DM frame size or
         test-tlv-included is 'false' the value of this object can be
         ignored.";
      user-ext:CLI-comm-help "Set Test TLV pattern type";
    }
    leaf measurement-interval {
      type uint32 {
        range "1..1440";
      }
      units "minutes";
      default "15";
      description
        "This object specifies a Measurement Interval in minutes.
         A Measurement Interval 15 minutes needs to be supported, other
         intervals may be supported.";
      user-ext:CLI-comm-help "Set DM measurement interval";
      reference "MEF-SOAM-PM-MIB.mefSoamDmCfgMeasurementInterval";
    }
    leaf number-intervals-stored {
      type uint32 {
        range "2..1000";
      }
      default "32";
      description
        "This object specifies the number of completed measurement intervals to
         store in the history statistic table.
         At least 32 completed measurement intervals are to be
         stored. 96 measurement intervals are recommended to be stored.";
      user-ext:CLI-comm-help "Set the number of completed measurement intervals to be stored";
    }
    leaf align-measurement-intervals {
      type boolean;
      default "false";
      description
        "This object specifies whether the Measurement Intervals for the Delay
         Measurement session are aligned with a zero offset to real
         time.
         The value 'true' indicates that each Measurement Interval
         starts at a time which is aligned to NE time source hour, if
         the repetition time (or the Measurement Interval, if the
         repetition time is 0) is a factor of an hour, i.e. 60min/15min
         = 4. For instance, a Measurement Interval/Repetition Time of 15
         minutes would stop/start the Measurement Interval at 0, 15, 30,
         and 45 minutes of an hour. A Measurement Interval/Repetition
         Time of 7 minutes would not align to the hour since 7 minutes
         is NOT a factor of an hour, i.e. 60min/7min = 8.6.  In this
         case the behavior is the same as if the object is set to
         'false'.
         The value 'false' indicates that the first Measurement Interval
         starts at an arbitrary time and each subsequent Measurement
         Interval starts at a time which is determined by
         repetition-time.";
      user-ext:CLI-comm-help "Configure the alignment of measurement intervals for DM session";
    }
    leaf align-measurement-offset {
      type uint32 {
        range "0..525600";
      }
      units "minutes";
      default "0";
      description
        "This object specifies the offset in minutes from the time of day value
         if align-measurement-intervals is 'true' and the repetition
         time is a factor of 60 minutes. If not, the value of this
         object is ignored.
         If the Measurement Interval is 15 minutes and
         align-measurement-intervals is true and if this object was set
         to 5 minutes, the Measurement Intervals would start at 5, 20,
         35, 50 minutes past each hour.";
      user-ext:CLI-comm-help "Set the alignment offset of measurement intervals for DM session";
    }
    leaf bins-per-fd-interval {
      type uint32 {
        range "2..100";
      }
      default "3";
      description
        "This object specifies the number of measurement bins per Measurement
         Interval for Frame Delay measurements.
         At least 3 bins are to be supported; at least 10 bins are
         recommended to be supported.";
      user-ext:CLI-comm-help "Set the number of bins per interval for Frame Delay measurements";
    }
    leaf bins-per-ifdv-interval {
      type uint32 {
        range "2..100";
      }
      default "2";
      description
        "This object specifies the number of measurement bins per Measurement
         Interval for Inter-Frame Delay Variation measurements.
         The minimum number of measurement bins to be supported is
         2. The desired number of measurements bins to be supported is
         10.";
      user-ext:CLI-comm-help "Set the number of bins per interval for Inter-Frame Delay Variation measurements";
    }
    leaf ifdv-selection-offset {
      type yang:gauge32 {
        range "1..100";
      }
      default "1";
      description
        "This object specifies the selection offset for Inter-Frame Delay
         Variation measurements.  If this value is set to n, then the
         IFDV is calculated by taking the difference in frame delay
         between frame F and frame (F+n).";
      user-ext:CLI-comm-help "Set the selection offset for Inter-Frame Delay Variation measurements";
      reference "MEF-SOAM-PM-MIB.mefSoamDmCfgInterFrameDelayVariationSelectionOffset";
    }
    leaf bins-per-fdr-interval {
      type uint32 {
        range "2..100";
      }
      default "2";
      description
        "This object specifies the number of measurement bins per Measurement
         Interval for Frame Delay Range measurements.";
      user-ext:CLI-comm-help "Set the number of bins per interval for Frame Delay Range measurements";
      reference
        "[MEF SOAM PM IA] R31, D15, R32, D16
         MEF-SOAM-PM-MIB.mefSoamDmCfgNumMeasBinsPerFrameDelayRangeInterval";
    }
    leaf session-type {
      type enumeration {
        enum "proactive" {
          description
            "The current session is 'proactive'";
        }
        enum "on-demand" {
          description
            "The current session is 'on-demand'";
        }
      }
      default "proactive";
      description
        "This object indicates whether the current session is defined to be
         'proactive' or 'on-demand'.";
      user-ext:CLI-comm-help "Set DM Session type";
      reference "[MEF SOAM IA] R3";
    }

    leaf threshold-profile {
      type uint32;
      description
        "This object indicates the index of the threshold profile to use for
         this measurement.";
      user-ext:CLI-comm-help "Set the index of the threshold profile for this measurement";
    }

  }

  grouping delay-threshold-group {
      description
        "Delay thresholds";
    leaf measured-frame-delay-two-way {
      type yang:gauge32;
      units "microseconds";
      description
        "This object is used to set the measurement two-way delay threshold
         value that will be used to determine if a threshold
         notification is generated.";
      user-ext:CLI-comm-help "Set the measurement two-way delay threshold";
      reference "MEF-SOAM-PM-MIB.mefSoamDmThresholdCfgMeasuredFrameDelayTwoWayThreshold";
    }
    leaf max-frame-delay-two-way {
      type yang:gauge32;
      units "microseconds";
      description
        "This object is used to set the maximum two-way delay threshold value
         that will be used to determine if a threshold notification is
         generated.";
      user-ext:CLI-comm-help "Set the maximum two-way delay threshold";
      reference "MEF-SOAM-PM-MIB.mefSoamDmThresholdCfgMaxFrameDelayTwoWayThreshold";
    }
    leaf average-frame-delay-two-way {
      type yang:gauge32;
      units "microseconds";
      description
        "This object is used to set the average two-way delay threshold value
         that will be used to determine if a threshold notification is
         generated.";
      user-ext:CLI-comm-help "Set the average two-way delay threshold";
      reference "MEF-SOAM-PM-MIB.mefSoamDmThresholdCfgAvgFrameDelayTwoWayThreshold";
    }
    leaf measured-inter-frame-delay-variation-two-way {
      type yang:gauge32;
      units "microseconds";
      description
        "This object is used to set the measurement two-way IFDV threshold
         value that will be used to determine if a threshold notification is
         generated.";
      user-ext:CLI-comm-help "Set the measurement two-way IFDV threshold";
      reference "MEF-SOAM-PM-MIB.mefSoamDmThresholdCfgMeasuredIfdvTwoWayThreshold";
    }
    leaf max-inter-frame-delay-variation-two-way {
      type yang:gauge32;
      units "microseconds";
      description
        "This object is used to set the maximum two-way IFDV threshold value
         that will be used to determine if a threshold notification is
         generated.";
      user-ext:CLI-comm-help "Set the maximum two-way IFDV threshold";
      reference "MEF-SOAM-PM-MIB.mefSoamDmThresholdCfgMaxIfdvTwoWayThreshold";
    }
    leaf average-inter-frame-delay-variation-two-way {
      type yang:gauge32;
      units "microseconds";
      description
        "This object is used to set the average two-way IFDV threshold value
         that will be used to determine if a threshold notification is
         generated.";
      user-ext:CLI-comm-help "Set the average two-way IFDV threshold";
      reference "MEF-SOAM-PM-MIB.mefSoamDmThresholdCfgAvgIfdvTwoWayThreshold";
    }
    leaf max-frame-delay-range-two-way {
      type yang:gauge32;
      units "microseconds";
      description
        "This object is used to set the maximum two-way Frame Delay Range
         threshold value that will be used to determine if a threshold
         notification is generated.";
      user-ext:CLI-comm-help "Set the maximum two-way Frame Delay Range threshold";
      reference "MEF-SOAM-PM-MIB.mefSoamDmThresholdCfgMaxFrameDelayRangeTwoWayThreshold";
    }
    leaf average-frame-delay-range-two-way {
      type yang:gauge32;
      units "microseconds";
      description
        "This object is used to set the average two-way Frame Delay Range
         threshold value that will be used to determine if a threshold
         notification is generated.";
      user-ext:CLI-comm-help "Set the average two-way Frame Delay Range threshold";
      reference "MEF-SOAM-PM-MIB.mefSoamDmThresholdCfgAvgFrameDelayRangeTwoWayThreshold";
    }
    leaf measured-frame-delay-forward {
      type yang:gauge32;
      units "microseconds";
      description
        "This object is used to set the measurement forward delay threshold
         value that will be used to determine if a threshold
         notification is generated.";
      user-ext:CLI-comm-help "Set the measurement forward delay threshold";
      reference "MEF-SOAM-PM-MIB.mefSoamDmThresholdCfgMeasuredFrameDelayForwardThreshold";
    }
    leaf max-frame-delay-forward {
      type yang:gauge32;
      units "microseconds";
      description
        "This object is used to set the maximum forward delay threshold value
         that will be used to determine if a threshold notification is
         generated.";
      user-ext:CLI-comm-help "Set the maximum forward delay threshold";
      reference "MEF-SOAM-PM-MIB.mefSoamDmThresholdCfgMaxFrameDelayForwardThreshold";
    }
    leaf average-frame-delay-forward {
      type yang:gauge32;
      units "microseconds";
      description
        "This object is used to set the average forward delay threshold value
         that will be used to determine if a threshold notification is
         generated.";
      user-ext:CLI-comm-help "Set the average forward delay threshold";
      reference "MEF-SOAM-PM-MIB.mefSoamDmThresholdCfgAvgFrameDelayForwardThreshold";
    }
    leaf measured-inter-frame-delay-variation-forward {
      type yang:gauge32;
      units "microseconds";
      description
        "This object is used to set the measurement IFDV threshold value that
         will be used to determine if a threshold notification is
         generated.";
      user-ext:CLI-comm-help "Set the measurement IFDV threshold";
      reference "MEF-SOAM-PM-MIB.mefSoamDmThresholdCfgMeasuredIfdvForwardThreshold";
    }
    leaf max-inter-frame-delay-variation-forward {
      type yang:gauge32;
      units "microseconds";
      description
        "This object is used to set the maximum IFDV threshold value that will
         be used to determine if a threshold notification is generated.";
      user-ext:CLI-comm-help "Set the maximum IFDV threshold";
      reference "MEF-SOAM-PM-MIB.mefSoamDmThresholdCfgMaxIfdvForwardThreshold";
    }
    leaf average-inter-frame-delay-variation-forward {
      type yang:gauge32;
      units "microseconds";
      description
        "This object is used to set the average IFDV threshold value that will
         be used to determine if a threshold notification is generated.";
      user-ext:CLI-comm-help "Set the average IFDV threshold";
      reference "MEF-SOAM-PM-MIB.mefSoamDmThresholdCfgAvgIfdvForwardThreshold";
    }
    leaf max-frame-delay-range-forward {
      type yang:gauge32;
      units "microseconds";
      description
        "This object is used to set the maximum Frame Delay Range threshold
         value that will be used to determine if a threshold
         notification is generated.";
      user-ext:CLI-comm-help "Set the maximum Frame Delay Range threshold";
      reference "MEF-SOAM-PM-MIB.mefSoamDmThresholdCfgMaxFrameDelayRangeForwardThreshold";
    }
    leaf average-frame-delay-range-forward {
      type yang:gauge32;
      units "microseconds";
      description
        "This object is used to set the average Frame Delay Range threshold
         value that will be used to determine if a threshold
         notification is generated.";
      user-ext:CLI-comm-help "Set the average Frame Delay Range threshold";
      reference "MEF-SOAM-PM-MIB.mefSoamDmThresholdCfgAvgFrameDelayRangeForwardThreshold";
    }
    leaf measured-frame-delay-backward {
      type yang:gauge32;
      units "microseconds";
      description
        "This object is used to set the measurement backward delay threshold
         value that will be used to determine if a threshold
         notification is generated.";
      user-ext:CLI-comm-help "Set the measurement backward delay threshold";
      reference "MEF-SOAM-PM-MIB.mefSoamDmThresholdCfgMeasuredFrameDelayBackwardThreshold";
    }
    leaf max-frame-delay-backward {
      type yang:gauge32;
      units "microseconds";
      description
        "This object is used to set the maximum backward delay threshold value
         that will be used to determine if a threshold notification is
         generated.";
      user-ext:CLI-comm-help "Set the maximum backward delay threshold";
      reference "MEF-SOAM-PM-MIB.mefSoamDmThresholdCfgMaxFrameDelayBackwardThreshold";
    }
    leaf average-frame-delay-backward {
      type yang:gauge32;
      units "microseconds";
      description
        "This object is used to set the average backward delay threshold value
         that will be used to determine if a threshold notification is
         generated.";
      user-ext:CLI-comm-help "Set the average backward delay threshold";
      reference "MEF-SOAM-PM-MIB.mefSoamDmThresholdCfgAvgFrameDelayBackwardThreshold";
    }
    leaf measured-inter-frame-delay-variation-backward {
      type yang:gauge32;
      units "microseconds";
      description
        "This object is used to set the measurement backward IFDV threshold
         value that will be used to determine if a threshold
         notification is generated.";
      user-ext:CLI-comm-help "Set the measurement backward IFDV threshold";
      reference "MEF-SOAM-PM-MIB.mefSoamDmThresholdCfgMeasuredIfdvBackwardThreshold";
    }
    leaf max-inter-frame-delay-variation-backward {
      type yang:gauge32;
      units "microseconds";
      description
        "This object is used to set the maximum backward IFDV threshold value
         that will be used to determine if a threshold notification is
         generated.";
      user-ext:CLI-comm-help "Set the maximum backward IFDV threshold";
      reference "MEF-SOAM-PM-MIB.mefSoamDmThresholdCfgMaxIfdvBackwardThreshold";
    }
    leaf average-inter-frame-delay-variation-backward {
      type yang:gauge32;
      units "microseconds";
      description
        "This object is used to set the average backward IFDV threshold value
         that will be used to determine if a threshold notification
         is generated.";
      user-ext:CLI-comm-help "Set the average backward IFDV threshold";
      reference "MEF-SOAM-PM-MIB.mefSoamDmThresholdCfgAvgIfdvBackwardThreshold";
    }
    leaf max-frame-delay-range-backward {
      type yang:gauge32;
      units "microseconds";
      description
        "This object is used to set the maximum backward Frame Delay Range
         threshold value that will be used to determine if a threshold
         notification is generated.";
      user-ext:CLI-comm-help "Set the maximum backward Frame Delay Range threshold";
      reference "MEF-SOAM-PM-MIB.mefSoamDmThresholdCfgMaxFrameDelayRangeBackwardThreshold";
    }
    leaf average-frame-delay-range-backward {
      type yang:gauge32;
      units "microseconds";
      description
        "This object is used to set the average backward Frame Delay Range
         threshold value that will be used to determine if a threshold
         notification is generated.";
      user-ext:CLI-comm-help "Set the average backward Frame Delay Range threshold";
      reference "MEF-SOAM-PM-MIB.mefSoamDmThresholdCfgAvgFrameDelayRangeBackwardThreshold";
    }
  }

  grouping delay-measurement-stats-group {
    description
      "This grouping includes statistics objects for a SOAM Delay Measurement
       session.";
    leaf suspect-status {
      type suspect-status-type;
      description
        "Whether the Measurement Interval has been marked as suspect.
         The object is to be set to false at the start of a measurement
         interval. It is set to true when there is a discontinuity in
         the performance measurements during the Measurement Interval.
         Conditions for a discontinuity include, but are not limited to
         the following:
         1 - The local time-of-day clock is adjusted by at least 10 seconds
         2 - The conducting of a performance measurement is halted before the
         current Measurement Interval is completed
         3 - A local test, failure, or reconfiguration that disrupts service";
      config false;
    }
    leaf frame-delay-two-way-min {
      type yang:gauge32;
      units "microseconds";
      description
        "This object contains the minimum two-way frame delay calculated by this
         MEP for this Measurement Interval.
         This object is undefined if measurement-type is 1dm-transmitted
         or 1dm-received.";
      config false;
    }
    leaf frame-delay-two-way-max {
      type yang:gauge32;
      units "microseconds";
      description
        "This object contains the maximum two-way frame delay calculated by this
         MEP for this Measurement Interval.
         This object is undefined if measurement-type is dm1DmTx or
         1dm1-received.";
      config false;
    }
    leaf frame-delay-two-way-average {
      type yang:gauge32;
      units "microseconds";
      description
        "This object contains the average two-way frame delay calculated by this
         MEP for this Measurement Interval.
         This object is undefined if measurement-type is 1dm-transmitted or
         1dm-received.";
      config false;
    }
    leaf frame-delay-forward-min {
      type yang:gauge32;
      units "microseconds";
      description
        "This object contains the minimum one-way frame delay in the forward
         direction calculated by this MEP for this Measurement
         Interval. The value of this object may not be accurate in the
         absence of sufficiently precise clock synchronization.
         This object is undefined if measurement-type is 1dm-transmitted.";
      config false;
    }
    leaf frame-delay-forward-max {
      type yang:gauge32;
      units "microseconds";
      description
        "This object contains the maximum one-way frame delay in the forward
         direction calculated by this MEP for this Measurement
         Interval. The value of this object may not be accurate in the
         absence of sufficiently precise clock synchronization.
         This object is undefined if measurement-type is 1dm-transmitted.";
      config false;
    }
    leaf frame-delay-forward-average {
      type yang:gauge32;
      units "microseconds";
      description
        "This object contains the average one-way frame delay in the forward
         direction calculated by this MEP for this Measurement
         Interval. The value of this object may not be accurate in the
         absence of sufficiently precise clock synchronization.
         This object is undefined if measurement-type is 1dm-transmitted.";
      config false;
    }
    leaf frame-delay-backward-min {
      type yang:gauge32;
      units "microseconds";
      description
        "This object contains the minimum one-way frame delay in the backward
         direction calculated by this MEP for this Measurement
         Interval. The value of this object may not be accurate in the
         absence of sufficiently precise clock synchronization.
         This object is undefined if measurement-type is 1dm-transmitted
         or dm1-received.";
      config false;
    }
    leaf frame-delay-backward-max {
      type yang:gauge32;
      units "microseconds";
      description
        "This object contains the maximum one-way frame delay in the backward
         direction calculated by this MEP for this Measurement
         Interval. The value of this object may not be accurate in the
         absence of sufficiently precise clock synchronization.
         This object is undefined if measurement-type is 1dm-transmitted or
         dm1-received.";
      config false;
    }
    leaf frame-delay-backward-average {
      type yang:gauge32;
      units "microseconds";
      description
        "This object contains the average one-way frame delay in the backward
         direction calculated by this MEP for this Measurement
         Interval. The value of this object may not be accurate in the
         absence of sufficiently precise clock synchronization.
         This object is undefined if measurement-type is 1dm-transmitted or
         dm1-received.";
      config false;
    }
    leaf inter-frame-delay-variation-forward-min {
      type yang:gauge32;
      units "microseconds";
      description
        "This object contains the minimum one-way inter-frame delay interval in
         the forward direction calculated by this MEP for this
         Measurement Interval.
         The value of this object is undefined when measurement-type is
         1dm-transmitted.";
      config false;
    }
    leaf inter-frame-delay-variation-forward-max {
      type yang:gauge32;
      units "microseconds";
      description
        "This object contains the maximum one-way inter-frame delay interval in
         the forward direction calculated by this MEP for this
         Measurement Interval.
         The value of this object is undefined when measurement-type is
         1dm-transmitted.";
      config false;
    }
    leaf inter-frame-delay-variation-forward-average {
      type yang:gauge32;
      units "microseconds";
      description
        "This object contains the average one-way inter-frame delay interval in
         the forward direction calculated by this MEP for this
         Measurement Interval.
         The value of this object is undefined when measurement-type is
         1dm-transmitted.";
      config false;
    }
    leaf inter-frame-delay-variation-backward-min {
      type yang:gauge32;
      units "microseconds";
      description
        "This object contains the minimum one-way inter-frame delay interval in
         the backward direction calculated by this MEP for this
         Measurement Interval.
         The value of this object is undefined when measurement-type is
         1dm-transmitted or dm1-received.";
      config false;
    }
    leaf inter-frame-delay-variation-backward-max {
      type yang:gauge32;
      units "microseconds";
      description
        "This object contains the maximum one-way inter-frame delay interval in
         the backward direction calculated by this MEP for this
         Measurement Interval.
         The value of this object is undefined when measurement-type is
         1dm-transmitted or dm1-received.";
      config false;
    }
    leaf inter-frame-delay-variation-backward-average {
      type yang:gauge32;
      units "microseconds";
      description
        "This object contains the average one-way inter-frame delay interval in
         the backward direction calculated by this MEP for this
         Measurement Interval.
         The value of this object is undefined when measurement-type is
         1dm-transmitted or dm1-received.";
      config false;
    }
    leaf inter-frame-delay-variation-two-way-min {
      type yang:gauge32;
      units "microseconds";
      description
        "This object contains the minimum two-way inter-frame delay interval
         calculated by this MEP for this Measurement Interval.
         The value of this object is undefined when measurement-type is
         1dm-transmitted or dm1-received.";
      config false;
    }
    leaf inter-frame-delay-variation-two-way-max {
      type yang:gauge32;
      units "microseconds";
      description
        "This object contains the maximum two-way inter-frame delay interval
         calculated by this MEP for this Measurement Interval.
         The value of this object is undefined when measurement-type is
         1dm-transmitted or dm1-received.";
      config false;
    }
    leaf inter-frame-delay-variation-two-way-average {
      type yang:gauge32;
      units "microseconds";
      description
        "This object contains the average two-way inter-frame delay interval
         calculated by this MEP for this Measurement Interval.
         The value of this object is undefined when measurement-type is
         1dm-transmitted or dm1-received.";
      config false;
    }
    leaf frame-delay-range-forward-max {
      type yang:gauge32;
      units "microseconds";
      description
        "This object contains the maximum one-way Frame Delay Range in the
         forward direction calculated by this MEP for this Measurement
         Interval.
         The value of this object is undefined when measurement-type is
         1dm-transmitted.";
      config false;
    }
    leaf frame-delay-range-forward-average {
      type yang:gauge32;
      units "microseconds";
      description
        "This object contains the average one-way Frame Delay Range in the
         forward direction calculated by this MEP for this Measurement
         Interval.
         The value of this object is undefined when measurement-type is
         1dm-transmitted.";
      config false;
    }
    leaf frame-delay-range-backward-max {
      type yang:gauge32;
      units "microseconds";
      description
        "This object contains the maximum one-way Frame Delay Range in the
         backward direction calculated by this MEP for this Measurement
         Interval.
         The value of this object is undefined when measurement-type is
         1dm-transmitted or dm1-received.";
      config false;
    }
    leaf frame-delay-range-backward-average {
      type yang:gauge32;
      units "microseconds";
      description
        "This object contains the average one-way Frame Delay Range in the
         backward direction calculated by this MEP for this Measurement
         Interval.
         The value of this object is undefined when measurement-type is
         1dm-transmitted or dm1-received.";
      config false;
    }
    leaf frame-delay-range-two-way-max {
      type yang:gauge32;
      units "microseconds";
      description
        "This object contains the maximum two-way Frame Delay Range calculated
         by this MEP for this Measurement Interval.
         The value of this object is undefined when measurement-type is
         1dm-transmitted or dm1-received.";
      config false;
    }
    leaf frame-delay-range-two-way-average {
      type yang:gauge32;
      units "microseconds";
      description
        "This object contains the average two-way Frame Delay Range calculated
         by this MEP for this Measurement Interval.
         The value of this object is undefined when measurement-type is
         1dm-transmitted or dm1-received.";
      config false;
    }
    leaf soam-pdus-sent {
      type yang:gauge32;
      description
        "This object contains the count of the number of SOAM PDUs sent during
         this Measurement Interval.
         This object applies when measurement-type is dmm or
         1dm-transmitted and is undefined if measurement-type is
         dm1-received. It indicates the number of DMM or 1DM SOAM frames
         transmitted.";
      config false;
    }
    leaf soam-pdus-received {
      type yang:gauge32;
      description
        "This object contains the count of the number of SOAM PDUs received in
         this Measurement Interval.
         This object indicates the number of DMR and 1DM SOAM frames
         received. This object applies when measurement-type is dmm or
         dm1-received and is undefined if measurement-type is
         1dm-transmitted.";
      config false;
    }
  }

  grouping delay-measurement-bins-content-group {
    description
      "This grouping contains result measurement bin objects for a SOAM Delay
       Measurement session.";
    leaf type {
      type measurement-bin-type;
      description
        "This object specifies whether the bin number is for Frame De-lay,
         Inter-Frame Delay Variation or Frame Delay Range.";
      config false;
    }
    leaf number {
      type uint32;
      description
        "This object specifies the bin number for the configured boundary.  The
         first bin has bin number 1.";
      config false;
    }
    leaf lower-bound {
      type yang:gauge32;
      units "microseconds";
      description
        "This object specifies the lower boundary for a measurement bin. The
         upper boundary is defined by the next bin value or infinite for
         the last bin defined.  The measurement boundary for each
         measurement bin is to be larger than the measurement boundary
         of the preceding measurement bin. By default, the next bin is
         set to 5000us larger than the lower bin boundary.
         The values in a bin boundary object represents the time range
         used to segregate delay data into the appropriate statistical
         data bin. For five bins with default values, each bin has the
         following time range:
         bin 1 = 0, range is 0us
         bin 2 = 5000, range is 5,000us
         bin 3 = 10000, range is 10,000us
         bin 4 = 15000, range is 15,000us
         bin 5 = 20000, range is 20,000us
         The first bin boundary (number set to 1) always contains the
         value of 0. Attempting to write a non-zero value to this bin
         will result in an error.";
      config false;
    }
    leaf counter {
      type yang:gauge32;
      description
        "This object contains the count of the number of completed measurements
         initiated in this Measurement Interval whose value falls within
         the range specified for this bin (that is, greater than or
         equal to the measurement boundary for the bin, and (unless the
         bin is the last bin) less than the measurement boundary for the
         following bin.";
      config false;
      reference "MEF-SOAM-PM-MIB.mefSoamDmCurrentStatsBinsCounter";
    }
  }

  grouping delay-measurement-bins-group {
    description
      "This grouping contains the top-level structure for the three types of
       measurements (frame delay, inter frame delay variation, and frame
       delay range)";
    container bins {
      config false;
      description
        "This container defines the bins content for FD, IFDR, and FDR
         sessions.";
      list frame-delay {
        key "type number";
        uses delay-measurement-bins-content-group;
        description
          "Data definitions related to frame delay bins content.";
      }
      list inter-frame-delay-variation {
        key "type number";
        uses delay-measurement-bins-content-group;
        description
          "Data definitions related to inter frame delay bins content.";
      }
      list frame-delay-range {
        key "type number";
        uses delay-measurement-bins-content-group;
        description
          "Data definitions related to frame delay range bins content.";
      }
    }
  }

  rpc create-loss-measurement {
    description
      "Schedule a one-way and two-way on-demand and proactive performance
       monitoring loss measurements on a specific MEP.
       A list entry associated with the newly created session will be
       created in the loss-measurements container and the assigned
       session identifier will be returned in the output parameter.";
    input {
      uses maintenance-association-end-point-reference;
      leaf session-id {
        type session-id-t;
        mandatory true;
        description
          "The session identifier of the newly created loss measurement
           session.";
      }
      uses loss-measurement-configuration-group;
      uses remote-mep-group;
      uses measurement-timing-group;
    }
  }
  rpc abort-loss-measurement {
    description
      "Abort a currently running or scheduled single-ended on-demand ETH-LM
       function. This operation is not applicable to dual-ended
       proactive ETH-LM.";
    input {
      uses maintenance-association-end-point-reference;
      leaf session-id {
        type session-id-t;
        mandatory true;
        description
          "The session ID of the measurement session to be aborted.";
      }
    }
  }
  rpc destroy-loss-measurement {
    description
      "Destroy all state related to a single-ended on-demand ETH-LM
       function.";
    input {
      uses maintenance-association-end-point-reference;
      leaf session-id {
        type session-id-t;
        mandatory true;
        description
          "The session ID of the measurement session to be deleted.";
      }
    }
  }
  rpc clear-loss-history-stats {
    description
      "Clear the Loss Measurement history list (history-availability-stats and
       history-measurement-stats) for a specific session. All instance
       data is deleted.";
    input {
      uses maintenance-association-end-point-reference;
      leaf session-id {
        type session-id-t;
        mandatory true;
        description
          "The session ID of the loss measurement session of which the loss
           measurement history should be cleared";
      }
    }
  }
  rpc create-delay-measurement {
    description
      "Schedule one-way and two-way on-demand and proactive performance
       monitoring frame delay measurements on a specific MEP.
       A list entry associated with the newly created session will be
       created in the delay-measurements container and the assigned
       session identifier will be returned in the output parameter.";
    input {
      uses maintenance-association-end-point-reference;
      leaf session-id {
        type session-id-t;
        mandatory true;
        description
          "The session identifier of the newly created delay measurement
           session.";
      }
      uses delay-measurement-configuration-group;
      uses remote-mep-group;
      uses measurement-timing-group;
    }
  }
  rpc abort-delay-measurement {
    description
      "Abort a pre-scheduled instances of performance monitoring";
    input {
      uses maintenance-association-end-point-reference;
      leaf session-id {
        type session-id-t;
        mandatory true;
        description
          "The session ID of the measurement session to be aborted.";
      }
    }
  }
  rpc destroy-delay-measurement {
    description
      "Destroy all state related to a Delay Measurement";
    input {
      uses maintenance-association-end-point-reference;
      leaf session-id {
        type session-id-t;
        mandatory true;
        description
          "The session ID of the measurement session to be deleted.";
      }
    }
  }
  rpc clear-delay-history-stats {
    description
      "Clear the Delay Measurement history list (history-stats) for a specific
       session. All instance data is deleted.";
    input {
      uses maintenance-association-end-point-reference;
      leaf session-id {
        type session-id-t;
        mandatory true;
        description
          "The session ID of the loss measurement session of which the loss
           measurement history should be cleared";
      }
    }
  }
  notification availability-change-alarm {
    description
      "An availability-change-alarm notification is sent when the state of
       measured-availability-forward-status or
       measured-availability-backward-status associated with a specific
       loss-measurement session changes.";
    reference "MEF-SOAM-PM-MIB.mefSoamAvailabilityChangeAlarm";
    uses maintenance-association-end-point-reference;
    leaf session-id {
      type session-id-t;
      mandatory true;
      description
        "A reference to the loss-measurement session in which the availability
         change alarm occurred.";
    }
    leaf measured-availability-forward-status {
      type availability-type;
      description
        "The current value of measured-availability-forward-status of the
         referenced loss-measurement session.";
    }
    leaf measured-availability-backward-status {
      type availability-type;
      description
        "The current value of measured-availability-backward-status of the
         referenced loss-measurement session.";
    }
    leaf measured-forward-last-transition-time {
      type yang:date-and-time;
      description
        "The current value of measured-forward-last-transition-time of the
         referenced loss-measurement session.";
    }
    leaf measured-backward-last-transition-time {
      type yang:date-and-time;
      description
        "The current value of measured-backward-last-transition-time of the
         referenced loss-measurement session.";
    }
    leaf forward-available {
      type yang:gauge32;
      description
        "The current value of forward-available of the referenced
         loss-measurement session.";
    }
    leaf backward-available {
      type yang:gauge32;
      description
        "The current value of backward-available of the referenced
         loss-measurement session.";
    }
    leaf forward-unavailable {
      type yang:gauge32;
      description
        "The current value of forward-unavailable of the referenced
         loss-measurement session.";
    }
    leaf backward-unavailable {
      type yang:gauge32;
      description
        "The current value of backward-unavailable of the referenced
         loss-measurement session.";
    }
  }
  notification threshold-crossing-alarm {
    description
      "A threshold-crossing-alarm notification is sent if the following
       conditions are met for a particular type.
       For an above-alarm five conditions need to be met:
       - measurement of the parameter is enabled via enabled-thresholds
       for a LM or a DM crossing; and
       - the parameter threshold is configured in the thresholds list
       for an LM or DM session.
       - the threshold crossing type of threshold-above-alarm is
       enabled in alarm-enable; and
       - the measured value of the parameter exceeds the value
       configured in the thresholds list for an LM or DM crossing
       entry for a type of threshold-above-alarm.
       - no previous threshold-crossing-alarm notifications with type
       above-alarm have been sent relating to the same threshold and
       the same parameter, during this measurement interval.
       For a set-alarm five conditions need to be met:
       - measurement of the parameter is enabled via measurement-enable
       for a LM or a DM crossing; and
       - the parameter threshold is configured in the thresholds list
       for an LM or DM session.
       - the threshold crossing type of threshold-set-clear-alarm is
       enabled in alarm-enable; and
       - the measured value of the parameter exceeds the value
       configured in the thresholds list for an LM or DM crossing
       entry for a type of threshold-set-clear-alarm.
       - no previous threshold-crossing-alarm notifications with type
       threshold-set-clear have been sent relating to the same
       threshold and the same parameter, during this measurement
       interval.
       For a clear-alarm five conditions need to be met:
       - measurement of the parameter is enabled via enabled-thresholds
       for a LM or a DM crossing; and
       - the parameter threshold is configured in the thresholds list
       for an LM or DM session.
       - the threshold crossing type of threshold-set-clear-alarm is
       enabled in alarm-enable; and
       - no previous threshold-crossing-alarm notifications with type
       threshold-set-clear have been sent relating to the same
       threshold and the same parameter, during this measurement
       interval.
       In the case of thresholds applied to a maximum or average
       measurement counter, the previous measured value is the value of
       the counter at the end of the preceding measurement interval.
       In the case of thresholds applied to the last measured value, it
       is the previous measured value.
       An agent is not to generate more than one
       threshold-crossing-alarm of a given type per LM or DM session as
       specified by alarm-interval. A 'notification-event' is the
       transmission of a single notification to a list of notification
       destinations.
       If additional threshold crossing events occur within the
       alarm-interval period, then notification generation for these
       changes are suppressed by the agent until the current alarm
       interval expires. At the end of an alarm interval period, one
       notification-event is generated if any threshold crossing events
       occurred since the start of the alarm interval period.  In such
       a case, another alarm interval period is started right away.";
    reference "MEF-SOAM-PM-MIB.mefSoamPmThresholdCrossingAlarm";
    uses maintenance-association-end-point-reference;
    container measurement-id {
      description
        "This container describes the measurement ID for a loss or delay
         measurement.";
      choice measurement-id {
        mandatory true;
        description
          "The measurement ID can reference either a loss or a delay measurement
           session.";
        leaf loss-measurement-session-id {
          type uint32;
          description
            "The session identifier for the loss-measurement session affected by
             the notification.";
        }
        leaf delay-measurement-session-id {
          type uint32;
          description
            "The session identifier for the delay-measurement session affected
             by the notification.";
        }
      }
    }
    leaf notification-crossing-type {
      type enumeration {
        enum "above-alarm" {
          description
            "Indicates that the crossing type alarm was an above threshold.";
        }
        enum "set-alarm" {
          description
            "Indicates that the crossing type alarm was a set threshold.";
        }
        enum "clear-alarm" {
          description
            "Indicates that the crossing type alarm was a clear threshold.";
        }
      }
      description
        "This object indicates the crossing type that caused the generation of
         the notification.";
      reference "MEF-SOAM-PM-MIB.mefSoamPmNotificationObjCrossingType";
    }
    leaf threshold-id {
      type enumeration {
        enum "measured-flr-forward" {
          description
            "Indicates the measured Frame Loss Ratio forward threshold generated
             the notification.";
        }
        enum "max-flr-forward" {
          description
            "Indicates the maximum Frame Loss Ration forward threshold generated
             the notification.";
        }
        enum "average-flr-forward" {
          description
            "Indicates the average Frame Loss Ratio forward threshold generated
             the notification.";
        }
        enum "measured-flr-backward" {
          description
            "Indicates the measured Frame Loss Ratio backward threshold
             generated the notification.";
        }
        enum "max-flr-backward" {
          description
            "Indicates the maximum Frame Loss Ratio backward threshold generated
             the notification.";
        }
        enum "average-flr-backward" {
          description
            "Indicates the average Frame Loss Ratio backward threshold generated
             the notification.";
        }
        enum "forward-unavailable-count" {
          description
            "Indicates the forward Unavailable count threshold generated the
             notification.";
        }
        enum "forward-available-ratio" {
          description
            "Indicates the forward Available ration threshold generated the
             notification.";
        }
        enum "backward-unavailable-count" {
          description
            "Indicates the backward Unavailable count threshold generated the
             notification.";
        }
        enum "backward-available-ratio" {
          description
            "Indicates the backward Available ratio threshold generated the
             notification.";
        }
        enum "measured-frame-delay-two-way" {
          description
            "Indicates the measured Frame Delay two-way threshold generated
             the notification.";
        }
        enum "max-frame-delay-two-way" {
          description
            "Indicates the maximum Frame Delay two-way threshold generated the
             notification.";
        }
        enum "average-frame-delay-two-way" {
          description
            "Indicates the average Frame Delay two-way threshold generated the
             notification.";
        }
        enum "measured-inter-frame-delay-variation-two-way" {
          description
            "Indicates the measured IFDV two-way threshold generated the
             notification.";
        }
        enum "max-inter-frame-delay-variation-two-way" {
          description
            "Indicates the maximum IFDV two-way threshold generated the
             notification.";
        }
        enum "average-inter-frame-delay-variation-two-way" {
          description
            "Indicates the average IFDV two-way threshold generat-ed the
             notification.";
        }
        enum "max-frame-delay-range-two-way" {
          description
            "Indicates the maximum Frame Delay Range two-way threshold generated
             the notification.";
        }
        enum "average-frame-delay-range-two-way" {
          description
            "Indicates the average Frame Delay Range two-way threshold generated
             the notification.";
        }
        enum "measured-frame-delay-forward" {
          description
            "Indicates the measured Frame Delay forward threshold generated the
             notification.";
        }
        enum "max-frame-delay-forward" {
          description
            "Indicates the maximum Frame Delay forward threshold generated the
             notification.";
        }
        enum "average-frame-delay-forward" {
          description
            "Indicates the average Frame Delay forward threshold generated the
             notification.";
        }
        enum "measured-inter-frame-delay-variation-forward" {
          description
            "Indicates the measured IFDV forward threshold generated the
             notification.";
        }
        enum "max-inter-frame-delay-variation-forward" {
          description
            "Indicates the maximum IFDV forward threshold generated the
             notification.";
        }
        enum "average-inter-frame-delay-variation-forward" {
          description
            "Indicates the average IFDV forward threshold generated the
             notification.";
        }
        enum "max-frame-delay-range-forward" {
          description
            "Indicates the maximum Frame Delay Range forward threshold generated
             the notification.";
        }
        enum "average-frame-delay-range-forward" {
          description
            "Indicates the average Frame Delay Range forward threshold generated
             the notification.";
        }
        enum "measured-frame-delay-backward" {
          description
            "Indicates the measured Frame Delay backward threshold generated the
             notification.";
        }
        enum "max-frame-delay-backward" {
          description
            "Indicates the maximum Frame Delay backward threshold generated the
             notification.";
        }
        enum "average-frame-delay-backward-threshold" {
          description
            "Indicates the average Frame Delay backward threshold generated the
             notification.";
        }
        enum "measured-inter-frame-delay-variation-backward" {
          description
            "Indicates the measured IFDV backward threshold gener-ated the
             notification.";
        }
        enum "max-inter-frame-delay-variation-backward" {
          description
            "Indicates the maximum IFDV backward threshold gener-ated the
             notification.";
        }
        enum "average-inter-frame-delay-variation-backward" {
          description
            "Indicates the average IFDV backward threshold gener-ated the
             notification.";
        }
        enum "max-frame-delay-range-backward" {
          description
            "Indicates the maximum Frame Delay Range backward threshold
             generated the notification.";
        }
        enum "average-frame-delay-range-backward" {
          description
            "Indicates the average Frame Delay Range backward threshold
             generated the notification.";
        }
      }
      description
        "This object identifies the threshold that caused the generation of the
         notification.";
      reference "MEF-SOAM-PM-MIB.mefSoamPmNotificationObjThresholdId";
    }
    leaf threshold-config-value {
      type uint32;
      description
        "The configured threshold value of the object that caused the generation
         of the notification.";
      reference "MEF-SOAM-PM-MIB.mefSoamPmNotificationObjThresholdConfig";
    }
    leaf measured-value {
      type uint32;
      description
        "The measured value of the object at the time of the generation of the
         notification.";
      reference "MEF-SOAM-PM-MIB.mefSoamPmNotificationObjThresholdValue";
    }
    leaf suspect {
      type suspect-status-type;
      description
        "The suspect flag for the current measurement interval in which the
         notification was generated.";
      reference "MEF-SOAM-PM-MIB.mefSoamPmNotificationObjSuspect";
    }
  }
}
