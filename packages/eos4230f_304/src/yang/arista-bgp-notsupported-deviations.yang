module arista-bgp-notsupported-deviations {
  namespace "http://arista.com/yang/openconfig/bgp/deviations";
  prefix arista-bgp-notsupported-deviations;

  import openconfig-bgp {
    prefix oc-bgp;
  }

  organization
    "Arista Networks, Inc.";
  contact
    "Arista Networks, Inc.
     Product Support";
  description
    "This module contains OpenConfig bgp deviations in Arista EOS.
     Copyright (c) 2020 Arista Networks, Inc. All rights reserved.";

  revision 2020-01-23 {
    description
      "Not-supported deviations file.";
  }

  deviation "/oc-bgp:bgp" {
    description
      "Not-supported deviation.";
    deviate not-supported;
  }
}
