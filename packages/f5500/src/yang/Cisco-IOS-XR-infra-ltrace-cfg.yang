module Cisco-IOS-XR-infra-ltrace-cfg {

  /*** NAMESPACE / PREFIX DEFINITION ***/

  namespace "http://cisco.com/ns/yang/Cisco-IOS-XR-infra-ltrace-cfg";


  prefix "Cisco-IOS-XR-infra-ltrace-cfg";

  /*** LINKAGE (IMPORTS / INCLUDES) ***/

  import Cisco-IOS-XR-config-mda-cfg { prefix "node"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-ltrace package configuration.

     This YANG module augments the
       Cisco-IOS-XR-config-mda-cfg
     module with configuration data.

     Copyright (c) 2013-2018 by Cisco Systems, Inc.
     All rights reserved.";

  revision "2015-11-09" {
    description
      "IOS XR 6.0 revision.";
  }

  typedef Infra-ltrace-mode {
    type enumeration {
      enum static {
        value 1;
        description "Set ltrace memory allocation to static mode";
      }
      enum dynamic {
        value 2;
        description "Set ltrace memory allocation to dynamic mode";
      }
    }
    description "Infra ltrace mode";
  }
  typedef Infra-ltrace-scale {
    type enumeration {
      enum 0 {
        value 0;
        description "Use platform-defined scale-factor";
      }
      enum 1 {
        value 1;
        description "Do not scale down ltrace memory request";
      }
      enum 2 {
        value 2;
        description "Scale down ltrace memory request by 2";
      }
      enum 4 {
        value 4;
        description "Scale down ltrace memory request by 4";
      }
      enum 8 {
        value 8;
        description "Scale down ltrace memory request by 8";
      }
      enum 16 {
        value 16;
        description "Scale down ltrace memory request by 16";
      }
    }
    description "Infra ltrace scale";
  }

  grouping NODE-CFG {
    description "active/preconfigured nodes configuration";

    container ltrace {
      description "Ltrace Memory configuration";

      container allocation-params {
        description "Select Ltrace mode and scale-factor";
        leaf mode {
          type Infra-ltrace-mode;
          description
            "Select an allocation mode (static:1, dynamic
            :2)";
        }
        leaf scale-factor {
          type Infra-ltrace-scale;
          description "Select a scaling down factor";
        }
      }
    }
  }

  augment "/node:active-nodes/node:active-node" {
    uses NODE-CFG;
    description "This augment extends active nodes configuration";
  }

  augment "/node:preconfigured-nodes/node:preconfigured-node" {
    uses NODE-CFG;
    description
      "This augment extends preconfigured nodes
      configuration";
  }
}
