module Cisco-IOS-XR-config-valid-ccv-oper {

  /*** NAMESPACE / PREFIX DEFINITION ***/

  namespace "http://cisco.com/ns/yang"+
    "/Cisco-IOS-XR-config-valid-ccv-oper";


  prefix "Cisco-IOS-XR-config-valid-ccv-oper";

  /*** LINKAGE (IMPORTS / INCLUDES) ***/

  import Cisco-IOS-XR-config-cfgmgr-oper { prefix "a1"; }

  include Cisco-IOS-XR-config-valid-ccv-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR config-valid-ccv package operational data.

     This YANG module augments the
       Cisco-IOS-XR-config-cfgmgr-oper
     module with state data.

     Copyright (c) 2013-2018 by Cisco Systems, Inc.
     All rights reserved.";

  revision "2015-11-09" {
    description
      "IOS XR 6.0 revision.";
  }


  augment "/a1:config/a1:global" {

    container validation {
      description "Configuration validation operational data";

      container unsupported-configs {
        description
          "Unsupported config warnings present in running
          configuration";

        list unsupported-config {
          key "xpath";
          description "Information about an unsupported warning";
          leaf xpath {
            type string;
            description "XPath of the unsupported configuration";
          }
          uses CCV-YVE-VALIDATION-FAILURE-ITEM-BAG;
        }
      }

      container persistent-failures {
        description
          "Validation failures present in running
          configuration";

        list persistent-failure {
          key "xpath";
          description "Information about a validation failure";
          leaf xpath {
            type string;
            description "XPath of the failed configuration";
          }
          uses CCV-YVE-VALIDATION-FAILURE-ITEM-BAG;
        }
      }
    }
    description
      "This augment extends the operational data of
      'Cisco-IOS-XR-config-cfgmgr-oper'";
  }
}
