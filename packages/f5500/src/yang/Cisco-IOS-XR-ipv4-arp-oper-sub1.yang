submodule Cisco-IOS-XR-ipv4-arp-oper-sub1 {

  belongs-to Cisco-IOS-XR-ipv4-arp-oper {
    prefix Cisco-IOS-XR-ipv4-arp-oper-sub1;
  }

  /*** LINKAGE (IMPORTS / INCLUDES) ***/

  import ietf-inet-types { prefix "inet"; }

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ipv4-arp package operational data.

     Copyright (c) 2013-2018 by Cisco Systems, Inc.
     All rights reserved.";

  revision "2017-05-01" {
    description
      "Fixing backward compatibility error in module.";
  }

  revision "2016-12-19" {
    description
      "IOS XR 6.2.1 revision.";
  }

  revision "2015-11-09" {
    description
      "IOS XR 6.0 revision.";
  }

  typedef Ip-arp-bag-encap {
    type enumeration {
      enum none {
        value 0;
        description "No encapsulation";
      }
      enum arpa {
        value 1;
        description "ARPA";
      }
      enum snap {
        value 2;
        description "SNAP";
      }
      enum ieee802-1q {
        value 3;
        description "802 1Q";
      }
      enum srp {
        value 4;
        description "SRP";
      }
      enum srpa {
        value 5;
        description "SRPA";
      }
      enum srpb {
        value 6;
        description "SRPB";
      }
    }
    description "ARP encapsulation";
  }
  typedef Ip-arp-bag-flags {
    type enumeration {
      enum flag-none {
        value 0;
        description "No Flag";
      }
      enum flag-dynamic {
        value 1;
        description "Dynamic learnt entry";
      }
      enum flag-evpn-sync {
        value 2;
        description "EVPN Synced entry";
      }
      enum flag-max {
        value 3;
        description "Maximum Flag number";
      }
    }
    description "ARP flags";
  }
  typedef Ip-arp-bag-state {
    type enumeration {
      enum state-none {
        value 0;
        description "No state";
      }
      enum state-interface {
        value 1;
        description "Interface";
      }
      enum state-standby {
        value 2;
        description "Standby";
      }
      enum state-static {
        value 3;
        description "Static";
      }
      enum state-alias {
        value 4;
        description "Alias";
      }
      enum state-mobile {
        value 5;
        description "Mobile";
      }
      enum state-incomplete {
        value 6;
        description "Incomplete";
      }
      enum state-deleted {
        value 7;
        description "Deleted";
      }
      enum state-dynamic {
        value 8;
        description "Dynamic";
      }
      enum state-probe {
        value 9;
        description "Probe";
      }
      enum state-purge-delayed {
        value 10;
        description "Purge delayed";
      }
      enum state-dhcp {
        value 11;
        description "DHCP installed";
      }
      enum state-vxlan {
        value 12;
        description "VXLAN installed";
      }
      enum state-evpn-sync {
        value 13;
        description "EVPN-SYNC installed";
      }
      enum state-sat {
        value 14;
        description "Satellite installed";
      }
      enum state-r-sync {
        value 15;
        description "Geo-redundancy sync'ed";
      }
      enum state-drop-adj {
        value 16;
        description "Drop adjacency";
      }
      enum state-stale {
        value 17;
        description "Stale";
      }
      enum state-max {
        value 18;
        description "Maximum state number";
      }
    }
    description "ARP state";
  }
  typedef Ip-arp-bag-media {
    type enumeration {
      enum media-arpa {
        value 0;
        description "ARPA";
      }
      enum media-srp {
        value 1;
        description "SRP";
      }
      enum media-unknown {
        value 2;
        description "Unknown";
      }
    }
    description "ARP media type";
  }
  typedef Arp-issu-version {
    type enumeration {
      enum version1 {
        value 0;
        description "Version 1";
      }
      enum version2 {
        value 1;
        description "Version 2";
      }
    }
    description "Arp issu version";
  }
  typedef Arp-issu-phase {
    type enumeration {
      enum phase-not-started {
        value 0;
        description "An ISSU event has not started";
      }
      enum phase-load {
        value 1;
        description "ISSU Load Phase";
      }
      enum phase-run {
        value 2;
        description "ISSU Run Phase";
      }
      enum phase-completed {
        value 3;
        description "An ISSU event has completed successfully";
      }
      enum phase-aborted {
        value 4;
        description "An ISSU event has aborted";
      }
    }
    description "Arp issu phase";
  }
  typedef Arp-issu-role {
    type enumeration {
      enum role-primary {
        value 0;
        description "Primary role";
      }
      enum role-secondary {
        value 1;
        description "Secondary role";
      }
    }
    description "Arp issu role";
  }
  typedef Arp-resolution-history-status {
    type enumeration {
      enum status-none {
        value 0;
        description "No Status";
      }
      enum status-resolution-request {
        value 1;
        description "Resolution Request Received";
      }
      enum status-resolved-reply {
        value 2;
        description "Resolved with ARP reply";
      }
      enum status-resolved-grat-arp {
        value 3;
        description "Resolved with Grat ARP";
      }
      enum status-resolved-request {
        value 4;
        description "Resolved with ARP Request";
      }
      enum status-resolved-lc-sync {
        value 5;
        description "Resolved via a Linecard sync";
      }
      enum status-resolved-lc-sync-purge-delay {
        value 6;
        description
          "Resolved via a Linecard sync while purge
          delayed";
      }
      enum status-resolved-client {
        value 7;
        description "Resolved from an ARP API client";
      }
      enum status-removed-client {
        value 8;
        description "Removed by an ARP API client";
      }
      enum status-already-resolved {
        value 9;
        description "Already Resolved";
      }
      enum status-failed {
        value 10;
        description "Resolution Failed";
      }
      enum status-dropped-interface-down {
        value 11;
        description "Dropped because the Interface was down";
      }
      enum status-dropped-broadcast-disabled {
        value 12;
        description
          "Dropped because the Interface was broadcast
          disabled";
      }
      enum status-dropped-interface-unavailable {
        value 13;
        description
          "Dropped because the Interface was unavailable
          to arp";
      }
      enum status-dropped-bad-subnet {
        value 14;
        description
          "The requested IP address didn't belong to the
          subnet";
      }
      enum status-dropped-dynamic-learning-disabled {
        value 15;
        description
          "Dynamic learning of ARP entries is disabled on
          the interface";
      }
      enum status-dropped-out-of-subnet-disabled {
        value 16;
        description
          "Out of Subnet address learning is disabled on
          the interface";
      }
      enum status-removed-client-sweep {
        value 17;
        description "Removed by an ARP API client during a resync";
      }
      enum status-added-client {
        value 18;
        description "Added by an ARP API client";
      }
      enum status-added-v1 {
        value 19;
        description "Added by replication from ARP V1 during ISSU";
      }
      enum status-removed-v1 {
        value 20;
        description
          "Removed by replication from ARP V1 during ISSU";
      }
      enum status-resolved-peer-sync {
        value 21;
        description "Resolved via a Peer Router sync";
      }
      enum status-dropped-unsolicited-pak {
        value 22;
        description
          "Learning unsolicited ARP packets is disabled on
          this Interface";
      }
      enum status-drop-adjacency-added {
        value 23;
        description "Adding drop adjacency entry for the address";
      }
    }
    description "Arp resolution history status";
  }

  grouping IP-ARP-TABLE-ENTRY {
    description "IP ARP Table entry";
    leaf media-type {
      type Ip-arp-bag-media;
      description "Media type for this entry";
    }
    leaf state {
      type Ip-arp-bag-state;
      description "State of this entry";
    }
    leaf flag {
      type Ip-arp-bag-flags;
      description "Flags of this entry";
    }
    leaf age {
      type uint64;
      description "Age of this entry";
    }
    leaf encapsulation-type {
      type Ip-arp-bag-encap;
      description "Source encapsulation type";
    }
    leaf hardware-length {
      type uint8;
      description "Source hardware length";
    }
    leaf hardware-address {
      type yang:mac-address;
      description "Hardware address";
    }
  }

  grouping IP-ARP-STATISTICS {
    description "IP ARP Statistics information";
    leaf requests-received {
      type uint32;
      description "Total ARP requests received";
    }
    leaf replies-received {
      type uint32;
      description "Total ARP replies received";
    }
    leaf requests-sent {
      type uint32;
      description "Total ARP requests sent";
    }
    leaf replies-sent {
      type uint32;
      description "Total ARP replies sent";
    }
    leaf proxy-replies-sent {
      type uint32;
      description "Total Proxy ARP replies sent";
    }
    leaf subscr-requests-received {
      type uint32;
      description
        "Total ARP requests received over subscriber
        interface";
    }
    leaf subscr-replies-sent {
      type uint32;
      description
        "Total ARP replies sent over subscriber interface";
    }
    leaf subscr-replies-gratg-sent {
      type uint32;
      description
        "Total ARP grat replies sent over subscriber
        interface";
    }
    leaf local-proxy-replies-sent {
      type uint32;
      description "Total Local Proxy ARP replies sent";
    }
    leaf gratuitous-replies-sent {
      type uint32;
      description "Total Gratuituous ARP replies sent";
    }
    leaf resolution-requests-received {
      type uint32;
      description "Total ARP resolution requests received";
    }
    leaf resolution-replies-received {
      type uint32;
      description "Total ARP resolution replies received";
    }
    leaf resolution-requests-dropped {
      type uint32;
      description "total ARP resolution requests dropped";
    }
    leaf out-of-memory-errors {
      type uint32;
      description "Total errors for out of memory";
    }
    leaf no-buffer-errors {
      type uint32;
      description "Total errors for no buffer";
    }
    leaf total-entries {
      type uint32;
      description "Total ARP entries in the cache";
    }
    leaf dynamic-entries {
      type uint32;
      description "Total dynamic entries in the cache";
    }
    leaf static-entries {
      type uint32;
      description "Total static entries in the cache";
    }
    leaf alias-entries {
      type uint32;
      description "Total alias entries in the cache";
    }
    leaf interface-entries {
      type uint32;
      description "Total interface entries in the cache";
    }
    leaf standby-entries {
      type uint32;
      description "Total standby entries in the cache";
    }
    leaf dhcp-entries {
      type uint32;
      description "Total DHCP entries in the cache";
    }
    leaf vxlan-entries {
      type uint32;
      description "Total VXLAN entries in the cache";
    }
    leaf drop-adjacency-entries {
      type uint32;
      description "Total drop adjacency entries in the cache";
    }
    leaf ip-packets-dropped-node {
      type uint32;
      description "Total ip packets droped on this node";
    }
    leaf arp-packet-node-out-of-subnet {
      type uint32;
      description "Total ARP packets on node due to out of subnet";
    }
    leaf ip-packets-dropped-interface {
      type uint32;
      description "Total ip packets droped on this interface";
    }
    leaf arp-packet-interface-out-of-subnet {
      type uint32;
      description
        "Total arp packets on interface due to out of
        subnet";
    }
    leaf arp-packet-unsolicited-packet {
      type uint32;
      description "Total unsolicited arp packets dropped";
    }
    leaf idb-structures {
      type uint32;
      description "Total idb structures on this node";
    }
  }

  grouping ARP-STATUS-INFO {
    description "ARP Status";
    leaf process-start-time {
      type uint64;
      units "nanosecond";
      description
        "Timestamp for the process start time in
        nanoseconds since Epoch, i.e. since 00:00:00 UTC
        , January 1, 1970";
    }
    leaf issu-sync-complete-time {
      type uint64;
      units "nanosecond";
      description
        "Timestamp for the ISSU sync complete in
        nanoseconds since Epoch, i.e. since 00:00:00 UTC
        , January 1, 1970";
    }
    leaf issu-ready-time {
      type uint64;
      units "nanosecond";
      description
        "Timestamp for the ISSU ready declaration in
        nanoseconds since Epoch, i.e. since 00:00:00 UTC
        , January 1, 1970";
    }
    leaf big-bang-time {
      type uint64;
      units "nanosecond";
      description
        "Timestamp for the Big Bang notification time in
        nanoseconds since Epoch, i.e. since 00:00:00 UTC
        , January 1, 1970";
    }
    leaf primary-role-time {
      type uint64;
      units "nanosecond";
      description
        "Timestamp for the change to Primary role
        notification time in nanoseconds since Epoch, i
        .e. since 00:00:00 UTC, January 1, 1970";
    }
    leaf role {
      type Arp-issu-role;
      description "The current role of the ARP process";
    }
    leaf phase {
      type Arp-issu-phase;
      description "The current ISSU phase of the ARP process";
    }
    leaf version {
      type Arp-issu-version;
      description
        "The current version of the ARP process in the
        context of an ISSU";
    }
    leaf dynamic-entries-recovered-count {
      type uint32;
      description
        "The number of entries that have been recovered
        during ISSU V1 and V2 synchronisation";
    }
    leaf non-operational-entries-count {
      type uint32;
      description
        "The number of entries that are currently
        non-operational in the shadow database";
    }
    leaf interface-handle-translation-failure-count {
      type uint32;
      description
        "The number of interface handle translation
        failures that occurred during the ISSU V1 and V2
        synchronisation";
    }
    leaf issu-ready-issu-mgr-connection {
      type boolean;
      description
        "Whether or not ARP is currently connected to
        ISSU Manager during the ISSU Load Phase";
    }
    leaf issu-ready-im {
      type boolean;
      description
        "Whether or not ARP is in sync with IM during the
        ISSU Load Phase";
    }
    leaf issu-ready-dagr-rib {
      type boolean;
      description
        "Whether or not the ARP DAGR system is in sync
        with the RIB during the ISSU Load Phase";
    }
    leaf issu-ready-entries-replicate {
      type boolean;
      description
        "Whether or not ARP has received all replicated
        entries during the ISSU Load Phase";
    }
  }

  grouping ARP-RESHIST-ENTRY {
    description "ARP resolution history entry";
    leaf nsec-timestamp {
      type uint64;
      units "nanosecond";
      description
        "Timestamp for entry in nanoseconds since Epoch,
        i.e. since 00:00:00 UTC, January 1, 1970";
    }
    leaf idb-interface-name {
      type xr:Interface-name;
      description "Interface";
    }
    leaf ipv4-address {
      type inet:ipv4-address;
      description "IPv4 address";
    }
    leaf mac-address {
      type yang:mac-address;
      description "MAC address";
    }
    leaf status {
      type Arp-resolution-history-status;
      description "Resolution status";
    }
    leaf client-id {
      type int32;
      description "Resolving Client ID";
    }
    leaf entry-state {
      type int32;
      description "ARP entry state";
    }
    leaf resolution-request-count {
      type uint32;
      description "Resolution Request count";
    }
  }

  grouping ARP-RESHIST {
    description "ARP Resolution History";

    list arp-entry {
      description "Resolution history array";
      uses ARP-RESHIST-ENTRY;
    }
  }
}
