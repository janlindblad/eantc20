module Cisco-IOS-XR-sysmgr-act {

    namespace "http://cisco.com/ns/yang/Cisco-IOS-XR-sysmgr-act";
    
    prefix "Cisco-IOS-XR-sysmgr-act";
    
    organization "Cisco Systems, Inc.";
    
    contact
    "Cisco Systems, Inc.
     Customer Service

     Postal: 170 West Tasman Drive
     San Jose, CA 95134

     Tel: +1 800 553-NETS

     E-mail: cs-yang@cisco.com";
    
    description 
    "This module contains a collection of YANG definitions
     for Cisco IOS-XR sysmgr action package configuration.

     Copyright (c) 2016-2017 by Cisco Systems, Inc.
     All rights reserved.";
    
    revision "2017-03-03" {
        description
            "IOS XR 6.3.1 revision.";
    } 
    
    rpc sysmgr-process-restart {
        description "Restart an XR process";
        input {
                leaf process-name {
                    description "XR process name or Job Id e.g. bgp, ospf";
                    type string;
                    mandatory true;
                }
                leaf location {
                    description "XR node identifier e.g. 0/RP0/CPU0, 0/0/CPU0";
                    type string;
                }
        }
    }

}
