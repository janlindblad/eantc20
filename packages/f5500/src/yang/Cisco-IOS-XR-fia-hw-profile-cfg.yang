module Cisco-IOS-XR-fia-hw-profile-cfg {

  /*** NAMESPACE / PREFIX DEFINITION ***/

  namespace "http://cisco.com/ns"+
    "/yang/Cisco-IOS-XR-fia-hw-profile-cfg";


  prefix "Cisco-IOS-XR-fia-hw-profile-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR fia-hw-profile package configuration.

     This module contains definitions
     for the following management objects:
       hw-module-profile-config: none

     Copyright (c) 2013-2018 by Cisco Systems, Inc.
     All rights reserved.";

  revision "2016-06-22" {
    description
      "Schema added.";
  }

  revision "2015-11-09" {
    description
      "IOS XR 6.0 revision.";
  }

  typedef Srv6-profile {
    type enumeration {
      enum enable {
        value 1;
        description
          "Enable with default behavior for traffic-class";
      }
      enum enable-with-traffic-class-propagation {
        value 2;
        description "Enable with traffic-class propagation";
      }
      enum enable-with-traffic-class-value {
        value 3;
        description "Enable with traffic-class set";
      }
    }
    description "Srv6 profile";
  }
  typedef Plane-rack {
    type uint32 {
      range "0..15";
    }
    description "Plane rack";
  }
  typedef Srv6-traffic-class-value {
    type uint32 {
      range "0..255";
    }
    description "Srv6 traffic class value";
  }

  container hw-module-profile-config {
    description "none";

    container profile {
      description "Configure profile.";

      container tcam-table {
        description "Configure profile for TCAM LC cards";

        container fib-table {
          description "FIB table for TCAM LC cards";

          container ipv4-address {
            description "IPv4 table for TCAM LC cards";

            container ipv4-unicast {
              description "Unicast table for TCAM LC cards";

              container ipv4-unicast-prefix-lengths {
                description "IPv4 Unicast prefix ";

                list ipv4-unicast-prefix-length {
                  key "prefix-length";
                  description "IPv4 Unicast prefix length";
                  leaf ipv4-unicast-prefix-percent {
                    type string;
                    units "percentage";
                    description
                      "curve out percentage of TCAM table
                      entries";
                  }
                  leaf prefix-length {
                    type uint32 {
                      range "0..32";
                    }
                    description "prefix length";
                  }
                }
              }
              leaf ipv4-unicast-percent {
                type uint32 {
                  range "0..100";
                }
                units "percentage";
                description
                  "curve out percentage of TCAM table entries";
              }
            }
          }

          container ipv6-address {
            description "IPv6 table for TCAM LC cards";

            container ipv6-unicast {
              description "Unicast table for TCAM LC cards";

              container ipv6-unicast-prefix-lengths {
                description "IPv6 Unicast prefix ";

                list ipv6-unicast-prefix-length {
                  key "prefix-length";
                  description "IPv6 Unicast prefix length";
                  leaf ipv6-unicast-prefix-percent {
                    type string;
                    units "percentage";
                    description
                      "curve out percentage of TCAM table
                      entries";
                  }
                  leaf prefix-length {
                    type uint32 {
                      range "0..128";
                    }
                    description "prefix length";
                  }
                }
              }
              leaf ipv6-unicast-percent {
                type uint32 {
                  range "0..100";
                }
                units "percentage";
                description
                  "curve out percentage of TCAM table entries";
              }
            }
          }
        }
      }

      container netflow {
        description "Configure Netflow profile.";

        container netflow-locations {
          description "none";

          list netflow-location {
            key "location-string";
            description "none";
            leaf location-string {
              type xr:Cisco-ios-xr-string;
              description "Location of NETFLOW config";
            }

            list netflow-location-leaf {
              key "location-id";
              description "none";
              leaf location-id {
                type uint32;
                description "Location ID";
              }
              leaf enable-val {
                type uint32;
                mandatory true;
                description "If Enabled set value to 65535";
              }
            }
          }
        }

        container location-all {
          description "IPFIX315 Location All";
          leaf location-all-leaf {
            type uint32;
            description "If Enabled set value to 65535";
          }
        }
      }

      container flowspec-table {
        description "Configure Flowspec profile.";

        container flowspecs {
          description "Configure v6 enable on Flowspec profile.";

          list flowspec {
            key "location-string location-id";
            description "none";
            leaf location-string {
              type xr:Cisco-ios-xr-string;
              description "Location of FLOWSPEC config";
            }
            leaf location-id {
              type uint32;
              description "Location ID hex to Decimal 65535";
            }
            leaf enable-val {
              type uint32;
              mandatory true;
              description "If Enabled set value to 1";
            }
          }
        }
      }

      container load-balance {
        description "Configure load balance parameters";
        leaf load-balance-profile {
          type uint32;
          description "Configure load balance parameters";
        }
      }

      container stats {
        description "Configure stats";

        container stats-profile-modes {
          description
            "Configure stats for qos-enhanced, acl-permit
            and ingress-sr";

          list stats-profile-mode {
            key "counter-profile";
            description "Stats mode";
            leaf mode {
              type uint32;
              mandatory true;
              description "Stats Mode";
            }
            leaf counter-profile {
              type uint32;
              description "none";
            }
          }
        }
      }

      container segment-routing {
        description "Configure Segment Routing profile.";

        container srv6 {
          description "Enable SRv6 profile";
          leaf profile-type {
            type Srv6-profile;
            description "Profile type";
          }
          leaf traffic-class-value {
            when "../profile-type ="+
              " 'enable-with-traffic-class-value'" {
                description
                  "../ProfileType =
                  EnableWithTrafficClassValue";
            }
            type Srv6-traffic-class-value;
            description "Traffic-class value";
          }
        }
      }

      container profile-acl {
        description "Configure acl profile";
        leaf egress {
          type boolean;
          description "Enabled or disabled";
        }
      }

      container sr-policies {
        description
          "Configure IPV6 NULL label autopush for SR
          policy.";

        list sr-policy {
          key "null-label-autopush";
          description "none";
          leaf null-label-autopush {
            type xr:Cisco-ios-xr-string;
            description "none";
          }
          leaf enable-val {
            type uint32;
            mandatory true;
            description "If Enabled set value to 1";
          }
        }
      }

      container bundle-scale {
        description "Configure Bundle profile.";
        leaf trunk-size {
          type uint32;
          description "Configure Max Trunk Size";
        }
      }

      container profile-tcam {
        description "Configure Tcam Profile";

        container key-format {
          description "none";

          container key-format-acl-table {
            description "Configure acl profile";

            container ipv6-acl-tables {
              description "Configure ipv6 acl profile";

              list ipv6-acl-table {
                key "location-string location-id";
                description "Configure format for ipv6 acl profile";
                leaf location-string {
                  type xr:Cisco-ios-xr-string;
                  description
                    "Location string (all) if for all LCs";
                }
                leaf location-id {
                  type uint32;
                  description
                    "Location ID hex to Decimal 0xffff for all";
                }
                leaf source-addr {
                  type uint32;
                  description "Source Address";
                }
                leaf source-port {
                  type uint32;
                  description "Source Port";
                }
                leaf destination-addr {
                  type uint32;
                  description "Destination Address";
                }
                leaf dest-port {
                  type uint32;
                  description "Destination Port";
                }
                leaf prot-type {
                  type uint32;
                  description "Next Header Type";
                }
                leaf tcp-flag {
                  type uint32;
                  description "TCP Flags";
                }
                leaf pack-len {
                  type uint32;
                  description "Packet Length";
                }
                leaf precedence {
                  type uint32;
                  description "Precedence";
                }
                leaf udf1 {
                  type string;
                  description "UDF name";
                }
                leaf udf2 {
                  type string;
                  description "UDF name";
                }
                leaf udf3 {
                  type string;
                  description "UDF name";
                }
                leaf udf4 {
                  type string;
                  description "UDF name";
                }
                leaf udf5 {
                  type string;
                  description "UDF name";
                }
                leaf udf6 {
                  type string;
                  description "UDF name";
                }
                leaf udf7 {
                  type string;
                  description "UDF name";
                }
                leaf udf8 {
                  type string;
                  description "UDF name";
                }
                leaf en-capture {
                  type uint32;
                  description "Enable Capture";
                }
                leaf en-ttl {
                  type uint32;
                  description "Enable Setting TTL";
                }
                leaf en-match {
                  type uint32;
                  description "Enable Matching TTL";
                }
                leaf en-share-acl {
                  type uint32;
                  description "Enable Non Shared Interface ACL";
                }
              }
            }

            container ipv4-acl-tables {
              description "Configure ipv4 acl profile";

              list ipv4-acl-table {
                key "location-string location-id";
                description "Configure format for ipv4 acl profile";
                leaf location-string {
                  type xr:Cisco-ios-xr-string;
                  description
                    "Location string (all) if for all LCs";
                }
                leaf location-id {
                  type uint32;
                  description
                    "Location ID hex to Decimal 0xffff for all";
                }
                leaf source-addr {
                  type uint32;
                  description "Source Address";
                }
                leaf destination-addr {
                  type uint32;
                  description "Destination Address";
                }
                leaf source-port {
                  type uint32;
                  description "Source Port";
                }
                leaf dest-port {
                  type uint32;
                  description "Destination Port";
                }
                leaf prot-type {
                  type uint32;
                  description "Protocol Type";
                }
                leaf tcp-flag {
                  type uint32;
                  description "TCP Flags";
                }
                leaf pack-len {
                  type uint32;
                  description "Packet Length";
                }
                leaf frag-bit {
                  type uint32;
                  description "Fragment Bit";
                }
                leaf precedence {
                  type uint32;
                  description "Precedence";
                }
                leaf port-range {
                  type uint32;
                  description "PortRange";
                }
                leaf udf1 {
                  type string;
                  description "UDF name";
                }
                leaf udf2 {
                  type string;
                  description "UDF name";
                }
                leaf udf3 {
                  type string;
                  description "UDF name";
                }
                leaf udf4 {
                  type string;
                  description "UDF name";
                }
                leaf udf5 {
                  type string;
                  description "UDF name";
                }
                leaf udf6 {
                  type string;
                  description "UDF name";
                }
                leaf udf7 {
                  type string;
                  description "UDF name";
                }
                leaf udf8 {
                  type string;
                  description "UDF name";
                }
                leaf en-capture {
                  type uint32;
                  description "Enable Capture";
                }
                leaf en-ttl {
                  type uint32;
                  description "Enable Setting TTL";
                }
                leaf en-match {
                  type uint32;
                  description "Enable Matching TTL";
                }
                leaf en-share-acl {
                  type uint32;
                  description "Enable Non Shared Interface ACL";
                }
              }
            }
          }
        }
      }

      container offload {
        description "Configure offload profile for NCS5501-SE";
        leaf offload-profile {
          type uint32;
          description "Configure offload profile for NCS5501-SE";
        }
      }

      container qos {
        description "Configure profile.";

        container hqos-enable-all {
          description "Configure Hqos profile";
          leaf hqos-enable {
            type uint32;
            description " Hqos profile value";
          }
        }

        container ingress-model-root-def {
          description "Configure Ingress Model Default";
          leaf ingress-model-leaf-def {
            type uint32;
            description "Ingress Model Default";
          }
        }

        container ingress-models {
          description "Configure Ingress Model Root";

          list ingress-model {
            key "node-name";
            description "Configure Ingress Model";
            leaf node-name {
              type xr:Cisco-ios-xr-string;
              description "NodeName";
            }

            list ingress-model-leaf {
              key "location";
              description "Configure Ingress Model Leaf";
              leaf ingress-model-leaf {
                type uint32;
                mandatory true;
                description "IngressModelLeaf";
              }
              leaf location {
                type uint32;
                description "Location";
              }
            }
          }
        }

        container class-maps-root-def {
          description "Configure Class Maps Default";
          leaf class-map-size-def {
            type uint32;
            description "Class Map Size Default";
          }
        }

        container class-maps {
          description "Configure Class Map Root";

          list class-map {
            key "node-name";
            description "Configure Class Maps";
            leaf node-name {
              type xr:Cisco-ios-xr-string;
              description "NodeName";
            }

            list class-map-size {
              key "location";
              description "Class Map Size";
              leaf class-map-size {
                type uint32;
                mandatory true;
                description "ClassMapSize";
              }
              leaf location {
                type uint32;
                description "Location";
              }
            }
          }
        }
      }
    }

    container fib-scale {
      description "Configure Fib for Scale for noTcam LC.";

      container ipv6-unicast-scale-no-tcam {
        description "IPv6 table for NOTCAM LC Scale.";

        container scale-ipv6-no-tcam {
          description "Scale for IPv6 table for NoTCAM LC.";
          leaf internet-optimized-ipv6-no-tcam {
            type string;
            description
              "Internet-optimized Scale for IPv6 table for
              NoTCAM LC.";
          }
        }
      }

      container ipv4-unicast-scale-no-tcam {
        description "IPv4 table for NOTCAM LC Scale.";

        container scale-ipv4-no-tcam {
          description "Scale for IPv4 table for NoTCAM LC.";
          leaf optimized-ipv4-no-tcam {
            type string;
            description
              "Optimized Scale for IPv4 table for NoTCAM LC.";
          }
        }
      }
    }

    container orchestrated-linecard-reload {
      description "Configure OLR.";

      container plane-table-entries {
        description "Plane type";

        list plane-table-entry {
          key "plane-name";
          description "Plane : A or B";

          container rack-table-entries {
            description "Rack Information";

            list rack-table-entry {
              key "rack-num";
              description "Rack Number";
              leaf nodes-list {
                type string;
                description
                  "Please enter linecards separated via comma
                  eg 0,3,6,11,13";
              }
              leaf rack-num {
                type Plane-rack;
                description "Rack Number";
              }
            }
          }
          leaf plane-name {
            type xr:Cisco-ios-xr-string;
            description "Plane Name";
          }
        }
      }
    }

    container tcam {
      description "Configure Tcam.";

      container fib-tcam-scale {
        description "Configure Fib scale for Tcam.";

        container ipv4-unicast-scale {
          description "IPv4 table for TCAM LC Scale.";
          leaf ipv4-scale {
            type boolean;
            description "Scale for IPv4 table for TCAM LC.";
          }
        }
      }
    }

    container qosqppb {
      description "Configure profile.";

      container ipv6-scale {
        description "Configure IPv6 destination short profile";
        leaf ipv6-short {
          type boolean;
          description "ipv6 short profile value";
        }
      }
    }
  }
}
