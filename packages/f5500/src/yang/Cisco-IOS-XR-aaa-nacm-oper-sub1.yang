submodule Cisco-IOS-XR-aaa-nacm-oper-sub1 {

  belongs-to Cisco-IOS-XR-aaa-nacm-oper {
    prefix Cisco-IOS-XR-aaa-nacm-oper-sub1;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR aaa-nacm package operational data.

     Copyright (c) 2013-2018 by Cisco Systems, Inc.
     All rights reserved.";

  revision "2015-11-09" {
    description
      "IOS XR 6.0 revision.";
  }


  grouping NACM-GROUP-DETAIL {
    description "Nacm Group detail";
    leaf group-name {
      type string {
        length "0..256";
      }
      description "Group Name";
    }

    list user-name {
      description "Users Name List";
      uses LIST-NODE;
    }

    list rule-name {
      description "Rules Name List";
      uses LIST-NODE;
    }
  }

  grouping NACM-RULE-DETAIL {
    description "Nacm Rule Detail";
    leaf rule-name {
      type string {
        length "0..512";
      }
      description "Rule Name";
    }
    leaf rule-index {
      type string {
        length "0..16";
      }
      description "Rule Index";
    }
    leaf rulelist-index {
      type string {
        length "0..16";
      }
      description "Rulelist Index";
    }
    leaf module-name {
      type string {
        length "0..512";
      }
      description "Module Name";
    }
    leaf action {
      type string {
        length "0..256";
      }
      description "Action";
    }
    leaf rule-type {
      type string {
        length "0..256";
      }
      description "Rule Type";
    }
    leaf comment {
      type string {
        length "0..256";
      }
      description "Comment";
    }
    leaf access-operations {
      type string {
        length "0..256";
      }
      description "Access Operations";
    }
    leaf rule-value {
      type string {
        length "0..512";
      }
      description "Rule Value";
    }
    leaf hit-count {
      type int32;
      description "Hit Count";
    }
  }

  grouping NACM-SUMMARY {
    description "Nacm Summary";
    leaf groups {
      type int32;
      description "Groups";
    }
    leaf users {
      type int32;
      description "Users";
    }
    leaf rulelist {
      type int32;
      description "Rulelist";
    }
    leaf rules {
      type int32;
      description "Rules";
    }
    leaf read-default {
      type string {
        length "0..16";
      }
      description "Read Default";
    }
    leaf write-default {
      type string {
        length "0..16";
      }
      description "Write Default";
    }
    leaf exec-default {
      type string {
        length "0..16";
      }
      description "Exec Default";
    }
    leaf enable-nacm {
      type string {
        length "0..16";
      }
      description "Enable Nacm";
    }
    leaf enable-external-groups {
      type string {
        length "0..16";
      }
      description "Enable External Groups";
    }
  }

  grouping LIST-NODE {
    description "List Node";
    leaf name {
      type string {
        length "0..256";
      }
      description "Name";
    }
  }

  grouping NACM-USER-DETAIL {
    description "Nacm User detail";
    leaf user-name {
      type string {
        length "0..256";
      }
      description "User Name";
    }

    list group-name {
      description "Group Name List";
      uses LIST-NODE;
    }
  }

  grouping NACM-COUNTERS {
    description "Nacm Counters";
    leaf denied-operations {
      type int32;
      description "Denied Operations";
    }
    leaf denied-data-writes {
      type int32;
      description "Denied Data Writes";
    }
    leaf denied-notifications {
      type int32;
      description "Denied Notifications";
    }
  }
}
