module Cisco-IOS-XR-sysadmin-entity-state-mib {
  // Generated by yanger -t ncs
  tailf:mount-id f5500-nc-1.0:f5500-nc-1.0;
  tailf:ncs-device-type "netconf";

  namespace "http://www.cisco.com/ns/yang/Cisco-IOS-XR-sysadmin-entity-state-mib";
  // NCS drop tailf:id
  prefix Cisco-IOS-XR-sysadmin-entity-state-mib;
  tailf:snmp-mib-module-name ENTITY-STATE-MIB;

  import ietf-yang-types {
    prefix yang;
  }
  import tailf-common {
    prefix tailf;
  }
  import Cisco-IOS-XR-sysadmin-entity-state-tc-mib {
    prefix ENTITY-STATE-TC-MIB;
  }
  import Cisco-IOS-XR-sysadmin-entity-mib {
    prefix ENTITY-MIB;
  }
  import "f5500-nc-1.0" {
    prefix "f5500-nc-1.0";
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains a collection of YANG
     definitions for Cisco IOS-XR SysAdmin configuration.

     Copyright(c) 2015-2017 by Cisco Systems, Inc.
     All rights reserved.";

  revision 2017-04-12 {
    description
      "Changed namespace and module name";
  }
  revision 2005-11-22 {
    description
      "";
  }

  augment "/ncs:devices/ncs:device/ncs:config" {
    container ENTITY-STATE-MIB {
      tailf:ncs-device-type "netconf";
      tailf:display-when "not(../../ncs:module) or ../../ncs:module[ncs:name='Cisco-IOS-XR-sysadmin-entity-state-mib']";
      // NCS drop config false container entStateTable
    }
  }
  augment "/ncs:devices/ncs:device/ncs:live-status" {
    container ENTITY-STATE-MIB {
      tailf:ncs-device-type "netconf";
      tailf:display-when "not(../../ncs:module) or ../../ncs:module[ncs:name='Cisco-IOS-XR-sysadmin-entity-state-mib'] or (../../ncs:live-status-protocol[not(ncs:capability)]) or (../../ncs:live-status-protocol/ncs:capability/ncs:module[.='Cisco-IOS-XR-sysadmin-entity-state-mib'])";
      container entStateTable {
        // NCS drop tailf:callpoint
        list entStateEntry {
          key "entPhysicalIndex";
          tailf:sort-order snmp;
          tailf:snmp-oid "1.3.6.1.2.1.131.1.1";
          leaf entPhysicalIndex {
            type ENTITY-MIB:PhysicalIndex;
            tailf:snmp-oid "1.3.6.1.2.1.47.1.1.1.1.1";
          }
          leaf entStateLastChanged {
            type yang:date-and-time;
            tailf:snmp-oid "1.3.6.1.2.1.131.1.1.1.1";
          }
          leaf entStateAdmin {
            type ENTITY-STATE-TC-MIB:EntityAdminState;
            tailf:snmp-oid "1.3.6.1.2.1.131.1.1.1.2";
          }
          leaf entStateOper {
            type ENTITY-STATE-TC-MIB:EntityOperState;
            tailf:snmp-oid "1.3.6.1.2.1.131.1.1.1.3";
          }
          leaf entStateUsage {
            type ENTITY-STATE-TC-MIB:EntityUsageState;
            tailf:snmp-oid "1.3.6.1.2.1.131.1.1.1.4";
          }
          leaf entStateAlarm {
            type ENTITY-STATE-TC-MIB:EntityAlarmStatus;
            tailf:snmp-oid "1.3.6.1.2.1.131.1.1.1.5";
          }
          leaf entStateStandby {
            type ENTITY-STATE-TC-MIB:EntityStandbyStatus;
            tailf:snmp-oid "1.3.6.1.2.1.131.1.1.1.6";
          }
        }
      }
    }
  }
  augment "/ncs:devices/ncs:template/ncs:ned-id/ncs:config" {
    container ENTITY-STATE-MIB {
      // NCS drop config false container entStateTable
    }
  }
}
