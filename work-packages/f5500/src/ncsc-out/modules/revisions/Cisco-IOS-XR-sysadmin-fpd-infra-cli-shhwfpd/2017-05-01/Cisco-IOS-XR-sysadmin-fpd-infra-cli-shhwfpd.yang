module Cisco-IOS-XR-sysadmin-fpd-infra-cli-shhwfpd {
  // Generated by yanger -t ncs
  tailf:mount-id f5500-nc-1.0:f5500-nc-1.0;
  tailf:ncs-device-type "netconf";

  namespace "http://www.cisco.com/ns/yang/Cisco-IOS-XR-sysadmin-fpd-infra-cli-shhwfpd";
  prefix Cisco-IOS-XR-sysadmin-fpd-infra-cli-shhwfpd;

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains definitions
     for the Calvados model objects.

     Copyright (c) 2012-2018 by Cisco Systems, Inc.
     All rights reserved.";

  revision 2017-05-01 {
    description
      "Namespace change to comply with Cisco guidelines on namespace";
  }

  grouping ncs_template_hw-module-oper-group {
    // NCS drop config false container shhwfpd
  }

  grouping ncs_rpc_notif_hw-module-oper-group {
    container shhwfpd {
      config false;
      list alocation {
        key "locs";
        leaf locs {
          type string;
        }
        list fpd {
          key "fpdname";
          leaf fpdname {
            type string;
          }
          leaf state {
            type string;
            description
              "Status";
          }
          leaf hwver {
            type string;
            description
              "HWver";
          }
          leaf fpdver {
            type string;
            description
              "FPD ver";
          }
          leaf cardname {
            type string;
            description
              "Card type";
          }
          leaf attr {
            type string;
            description
              "Attribute";
          }
          leaf fpddnld {
            type string;
            description
              "FPD Programed";
          }
        }
      }
      list fpd {
        key "fpdname";
        leaf fpdname {
          type string;
        }
      }
    }
  }

  grouping live_ncs_hw-module-oper-group {
    container shhwfpd {
      list alocation {
        key "locs";
        leaf locs {
          type string;
        }
        list fpd {
          key "fpdname";
          leaf fpdname {
            type string;
          }
          leaf state {
            type string;
            description
              "Status";
          }
          leaf hwver {
            type string;
            description
              "HWver";
          }
          leaf fpdver {
            type string;
            description
              "FPD ver";
          }
          leaf cardname {
            type string;
            description
              "Card type";
          }
          leaf attr {
            type string;
            description
              "Attribute";
          }
          leaf fpddnld {
            type string;
            description
              "FPD Programed";
          }
        }
      }
      list fpd {
        key "fpdname";
        leaf fpdname {
          type string;
        }
      }
    }
  }

  grouping hw-module-oper-group {
    // NCS drop config false container shhwfpd
  }
}
