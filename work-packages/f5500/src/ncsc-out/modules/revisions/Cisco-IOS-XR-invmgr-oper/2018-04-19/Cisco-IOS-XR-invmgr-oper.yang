module Cisco-IOS-XR-invmgr-oper {
  // Generated by yanger -t ncs
  tailf:mount-id f5500-nc-1.0:f5500-nc-1.0;
  tailf:ncs-device-type "netconf";

  namespace "http://cisco.com/ns/yang/Cisco-IOS-XR-invmgr-oper";
  prefix Cisco-IOS-XR-invmgr-oper;

  import Cisco-IOS-XR-types {
    prefix xr;
  }
  include Cisco-IOS-XR-invmgr-oper-sub4 {
    revision-date 2018-04-19;
  }
  include Cisco-IOS-XR-invmgr-oper-sub3 {
    revision-date 2018-04-19;
  }
  include Cisco-IOS-XR-invmgr-oper-sub2 {
    revision-date 2018-04-19;
  }
  include Cisco-IOS-XR-invmgr-oper-sub1 {
    revision-date 2018-04-19;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR invmgr package operational data.

     This module contains definitions
     for the following management objects:
       inventory: Inventory information

     Copyright (c) 2013-2018 by Cisco Systems, Inc.
     All rights reserved.";

  revision 2018-04-19 {
    description
      "Added additional bags";
  }
  revision 2017-09-07 {
    description
      "Fixed type translation error.";
  }
  revision 2017-05-01 {
    description
      "Fixing backward compatibility error in module.";
  }
  revision 2015-11-09 {
    description
      "IOS XR 6.0 revision.";
  }

  grouping ncs_template_THRESH-BAG {
    description
      "Common node of minor-lo, minor-hi, major-lo,
       major-hi, critical-lo, critical-hi";
    container thresh-bag {
      description
        "Environment threshold info";
      uses ncs_template_ENVMON-THRESHOLD-INFO;
    }
  }

  grouping ncs_template_INVMGR-EXT1-OPER-THRESH-BAG {
    description
      "Common node of minor-lo, minor-hi, major-lo,
       major-hi, critical-lo, critical-hiCommon node of
       minor-lo, minor-hi, major-lo, major-hi,
       critical-lo, critical-hi";
    container thresh-bag {
      description
        "Environment threshold info";
      uses ncs_template_ENVMON-THRESHOLD-INFO;
    }
  }

  grouping ncs_template_ATTRIBUTES {
    description
      "Common node of rack, slot, tsi1, tsi2, tsi3, tsi4
       , tsi5, tsi6, tsi7, tsi8, tsi9, tsi10, tsi11";
    container attributes {
      description
        "Attributes";
      container inv-basic-bag {
        description
          "Inventory Basic Bag";
        uses ncs_template_INV-PHY-ENTITY-BASIC-INFO;
      }
      container env-sensor-info {
        description
          "Environment sensor info";
        uses ncs_template_ENVMON-SENSOR-INFO;
      }
      container pwg-info {
        description
          "Inventory EDM PWG info";
        uses ncs_template_INV-PWG-INFO;
      }
      container env-sensor-info-xml {
        description
          "Environment sensor info XML";
        uses ncs_template_ENVMON-SENSOR-INFO-XML;
      }
      container inv-asset-bag {
        description
          "Inventory Asset Bag";
        uses ncs_template_INV-PHY-ENTITY-ASSET-INFO;
      }
      container threshold {
        description
          "Threshold";
        container major-lo {
          description
            "Major Low";
          uses ncs_template_THRESH-BAG;
        }
        container critical-hi {
          description
            "Critical High";
          uses ncs_template_THRESH-BAG;
        }
        container minor-hi {
          description
            "Minor High";
          uses ncs_template_THRESH-BAG;
        }
        container major-hi {
          description
            "Major High";
          uses ncs_template_THRESH-BAG;
        }
        container critical-lo {
          description
            "Critical Low";
          uses ncs_template_THRESH-BAG;
        }
        container minor-lo {
          description
            "Minor Low";
          uses ncs_template_THRESH-BAG;
        }
      }
      container fru-info {
        description
          "Inventory EDM FRU info";
        uses ncs_template_INV-CARD-FRU-INFO;
      }
      container inv-eeprom-info {
        description
          "Inventory EDM EEPROM Information Bag";
        uses ncs_template_INVMGR-EEPROM-OPAQUE-DATA;
      }
    }
  }

  grouping ncs_template_SLOT {
    description
      "Common node of powershelf, fantray, entity";
    list slot {
      // NCS patched for predictable order
      ordered-by user;
      key "name";
      description
        "Slot number";
      container tsi1s {
        description
          "Entity Level 1";
        list tsi1 {
          // NCS patched for predictable order
          ordered-by user;
          key "name";
          description
            "TSI1";
          container tsi2s {
            description
              "Entity Level 2";
            list tsi2 {
              // NCS patched for predictable order
              ordered-by user;
              key "name";
              description
                "TSI2";
              container tsi3s {
                description
                  "Entity Level 3";
                list tsi3 {
                  // NCS patched for predictable order
                  ordered-by user;
                  key "name";
                  description
                    "TSI3";
                  container tsi4s {
                    description
                      "Entity Level 4";
                    list tsi4 {
                      // NCS patched for predictable order
                      ordered-by user;
                      key "name";
                      description
                        "TSI4";
                      container tsi5s {
                        description
                          "Entity Level 5";
                        list tsi5 {
                          // NCS patched for predictable order
                          ordered-by user;
                          key "name";
                          description
                            "TSI5";
                          container tsi6s {
                            description
                              "Entity Level 6";
                            list tsi6 {
                              // NCS patched for predictable order
                              ordered-by user;
                              key "name";
                              description
                                "TSI6";
                              container tsi7s {
                                description
                                  "Entity Level 7";
                                list tsi7 {
                                  // NCS patched for predictable order
                                  ordered-by user;
                                  key "name";
                                  description
                                    "TSI7";
                                  container tsi8s {
                                    description
                                      "Entity Level 8";
                                    list tsi8 {
                                      // NCS patched for predictable order
                                      ordered-by user;
                                      key "name";
                                      description
                                        "TSI8";
                                      container tsi9s {
                                        description
                                          "Entity Level 9";
                                        list tsi9 {
                                          // NCS patched for predictable order
                                          ordered-by user;
                                          key "name";
                                          description
                                            "TSI9";
                                          container tsi10s {
                                            description
                                              "Entity Level 10";
                                            list tsi10 {
                                              // NCS patched for predictable order
                                              ordered-by user;
                                              key "name";
                                              description
                                                "TSI10";
                                              container tsi11s {
                                                description
                                                  "Entity Level 11";
                                                list tsi11 {
                                                  // NCS patched for predictable order
                                                  ordered-by user;
                                                  key "name";
                                                  description
                                                    "TSI11";
                                                  leaf name {
                                                    type string;
                                                    description
                                                      "TSI11";
                                                  }
                                                  uses ncs_template_ATTRIBUTES;
                                                }
                                              }
                                              leaf name {
                                                type string;
                                                description
                                                  "TSI10";
                                              }
                                              uses ncs_template_ATTRIBUTES;
                                            }
                                          }
                                          leaf name {
                                            type string;
                                            description
                                              "TSI9";
                                          }
                                          uses ncs_template_ATTRIBUTES;
                                        }
                                      }
                                      leaf name {
                                        type string;
                                        description
                                          "TSI8";
                                      }
                                      uses ncs_template_ATTRIBUTES;
                                    }
                                  }
                                  leaf name {
                                    type string;
                                    description
                                      "TSI7";
                                  }
                                  uses ncs_template_ATTRIBUTES;
                                }
                              }
                              leaf name {
                                type string;
                                description
                                  "TSI6";
                              }
                              uses ncs_template_ATTRIBUTES;
                            }
                          }
                          leaf name {
                            type string;
                            description
                              "TSI5";
                          }
                          uses ncs_template_ATTRIBUTES;
                        }
                      }
                      leaf name {
                        type string;
                        description
                          "TSI4";
                      }
                      uses ncs_template_ATTRIBUTES;
                    }
                  }
                  leaf name {
                    type string;
                    description
                      "TSI3";
                  }
                  uses ncs_template_ATTRIBUTES;
                }
              }
              leaf name {
                type string;
                description
                  "TSI2";
              }
              uses ncs_template_ATTRIBUTES;
            }
          }
          leaf name {
            type string;
            description
              "TSI1";
          }
          uses ncs_template_ATTRIBUTES;
        }
      }
      leaf name {
        type string;
        description
          "Slot name";
      }
      uses ncs_template_ATTRIBUTES;
    }
  }

  grouping ncs_rpc_notif_THRESH-BAG {
    description
      "Common node of minor-lo, minor-hi, major-lo,
       major-hi, critical-lo, critical-hi";
    container thresh-bag {
      description
        "Environment threshold info";
      uses ncs_rpc_notif_ENVMON-THRESHOLD-INFO;
    }
  }

  grouping ncs_rpc_notif_INVMGR-EXT1-OPER-THRESH-BAG {
    description
      "Common node of minor-lo, minor-hi, major-lo,
       major-hi, critical-lo, critical-hiCommon node of
       minor-lo, minor-hi, major-lo, major-hi,
       critical-lo, critical-hi";
    container thresh-bag {
      description
        "Environment threshold info";
      uses ncs_rpc_notif_ENVMON-THRESHOLD-INFO;
    }
  }

  grouping ncs_rpc_notif_ATTRIBUTES {
    description
      "Common node of rack, slot, tsi1, tsi2, tsi3, tsi4
       , tsi5, tsi6, tsi7, tsi8, tsi9, tsi10, tsi11";
    container attributes {
      description
        "Attributes";
      container inv-basic-bag {
        description
          "Inventory Basic Bag";
        uses ncs_rpc_notif_INV-PHY-ENTITY-BASIC-INFO;
      }
      container env-sensor-info {
        description
          "Environment sensor info";
        uses ncs_rpc_notif_ENVMON-SENSOR-INFO;
      }
      container pwg-info {
        description
          "Inventory EDM PWG info";
        uses ncs_rpc_notif_INV-PWG-INFO;
      }
      container env-sensor-info-xml {
        description
          "Environment sensor info XML";
        uses ncs_rpc_notif_ENVMON-SENSOR-INFO-XML;
      }
      container inv-asset-bag {
        description
          "Inventory Asset Bag";
        uses ncs_rpc_notif_INV-PHY-ENTITY-ASSET-INFO;
      }
      container threshold {
        description
          "Threshold";
        container major-lo {
          description
            "Major Low";
          uses ncs_rpc_notif_THRESH-BAG;
        }
        container critical-hi {
          description
            "Critical High";
          uses ncs_rpc_notif_THRESH-BAG;
        }
        container minor-hi {
          description
            "Minor High";
          uses ncs_rpc_notif_THRESH-BAG;
        }
        container major-hi {
          description
            "Major High";
          uses ncs_rpc_notif_THRESH-BAG;
        }
        container critical-lo {
          description
            "Critical Low";
          uses ncs_rpc_notif_THRESH-BAG;
        }
        container minor-lo {
          description
            "Minor Low";
          uses ncs_rpc_notif_THRESH-BAG;
        }
      }
      container fru-info {
        description
          "Inventory EDM FRU info";
        uses ncs_rpc_notif_INV-CARD-FRU-INFO;
      }
      container inv-eeprom-info {
        description
          "Inventory EDM EEPROM Information Bag";
        uses ncs_rpc_notif_INVMGR-EEPROM-OPAQUE-DATA;
      }
    }
  }

  grouping ncs_rpc_notif_SLOT {
    description
      "Common node of powershelf, fantray, entity";
    list slot {
      key "name";
      description
        "Slot number";
      container tsi1s {
        description
          "Entity Level 1";
        list tsi1 {
          key "name";
          description
            "TSI1";
          container tsi2s {
            description
              "Entity Level 2";
            list tsi2 {
              key "name";
              description
                "TSI2";
              container tsi3s {
                description
                  "Entity Level 3";
                list tsi3 {
                  key "name";
                  description
                    "TSI3";
                  container tsi4s {
                    description
                      "Entity Level 4";
                    list tsi4 {
                      key "name";
                      description
                        "TSI4";
                      container tsi5s {
                        description
                          "Entity Level 5";
                        list tsi5 {
                          key "name";
                          description
                            "TSI5";
                          container tsi6s {
                            description
                              "Entity Level 6";
                            list tsi6 {
                              key "name";
                              description
                                "TSI6";
                              container tsi7s {
                                description
                                  "Entity Level 7";
                                list tsi7 {
                                  key "name";
                                  description
                                    "TSI7";
                                  container tsi8s {
                                    description
                                      "Entity Level 8";
                                    list tsi8 {
                                      key "name";
                                      description
                                        "TSI8";
                                      container tsi9s {
                                        description
                                          "Entity Level 9";
                                        list tsi9 {
                                          key "name";
                                          description
                                            "TSI9";
                                          container tsi10s {
                                            description
                                              "Entity Level 10";
                                            list tsi10 {
                                              key "name";
                                              description
                                                "TSI10";
                                              container tsi11s {
                                                description
                                                  "Entity Level 11";
                                                list tsi11 {
                                                  key "name";
                                                  description
                                                    "TSI11";
                                                  leaf name {
                                                    type xr:Cisco-ios-xr-string;
                                                    description
                                                      "TSI11";
                                                  }
                                                  uses ncs_rpc_notif_ATTRIBUTES;
                                                }
                                              }
                                              leaf name {
                                                type xr:Cisco-ios-xr-string;
                                                description
                                                  "TSI10";
                                              }
                                              uses ncs_rpc_notif_ATTRIBUTES;
                                            }
                                          }
                                          leaf name {
                                            type xr:Cisco-ios-xr-string;
                                            description
                                              "TSI9";
                                          }
                                          uses ncs_rpc_notif_ATTRIBUTES;
                                        }
                                      }
                                      leaf name {
                                        type xr:Cisco-ios-xr-string;
                                        description
                                          "TSI8";
                                      }
                                      uses ncs_rpc_notif_ATTRIBUTES;
                                    }
                                  }
                                  leaf name {
                                    type xr:Cisco-ios-xr-string;
                                    description
                                      "TSI7";
                                  }
                                  uses ncs_rpc_notif_ATTRIBUTES;
                                }
                              }
                              leaf name {
                                type xr:Cisco-ios-xr-string;
                                description
                                  "TSI6";
                              }
                              uses ncs_rpc_notif_ATTRIBUTES;
                            }
                          }
                          leaf name {
                            type xr:Cisco-ios-xr-string;
                            description
                              "TSI5";
                          }
                          uses ncs_rpc_notif_ATTRIBUTES;
                        }
                      }
                      leaf name {
                        type xr:Cisco-ios-xr-string;
                        description
                          "TSI4";
                      }
                      uses ncs_rpc_notif_ATTRIBUTES;
                    }
                  }
                  leaf name {
                    type xr:Cisco-ios-xr-string;
                    description
                      "TSI3";
                  }
                  uses ncs_rpc_notif_ATTRIBUTES;
                }
              }
              leaf name {
                type xr:Cisco-ios-xr-string;
                description
                  "TSI2";
              }
              uses ncs_rpc_notif_ATTRIBUTES;
            }
          }
          leaf name {
            type xr:Cisco-ios-xr-string;
            description
              "TSI1";
          }
          uses ncs_rpc_notif_ATTRIBUTES;
        }
      }
      leaf name {
        type xr:Cisco-ios-xr-string;
        description
          "Slot name";
      }
      uses ncs_rpc_notif_ATTRIBUTES;
    }
  }

  grouping live_ncs_THRESH-BAG {
    description
      "Common node of minor-lo, minor-hi, major-lo,
       major-hi, critical-lo, critical-hi";
    container thresh-bag {
      description
        "Environment threshold info";
      uses live_ncs_ENVMON-THRESHOLD-INFO;
    }
  }

  grouping live_ncs_INVMGR-EXT1-OPER-THRESH-BAG {
    description
      "Common node of minor-lo, minor-hi, major-lo,
       major-hi, critical-lo, critical-hiCommon node of
       minor-lo, minor-hi, major-lo, major-hi,
       critical-lo, critical-hi";
    container thresh-bag {
      description
        "Environment threshold info";
      uses live_ncs_ENVMON-THRESHOLD-INFO;
    }
  }

  grouping live_ncs_ATTRIBUTES {
    description
      "Common node of rack, slot, tsi1, tsi2, tsi3, tsi4
       , tsi5, tsi6, tsi7, tsi8, tsi9, tsi10, tsi11";
    container attributes {
      description
        "Attributes";
      container inv-basic-bag {
        description
          "Inventory Basic Bag";
        uses live_ncs_INV-PHY-ENTITY-BASIC-INFO;
      }
      container env-sensor-info {
        description
          "Environment sensor info";
        uses live_ncs_ENVMON-SENSOR-INFO;
      }
      container pwg-info {
        description
          "Inventory EDM PWG info";
        uses live_ncs_INV-PWG-INFO;
      }
      container env-sensor-info-xml {
        description
          "Environment sensor info XML";
        uses live_ncs_ENVMON-SENSOR-INFO-XML;
      }
      container inv-asset-bag {
        description
          "Inventory Asset Bag";
        uses live_ncs_INV-PHY-ENTITY-ASSET-INFO;
      }
      container threshold {
        description
          "Threshold";
        container major-lo {
          description
            "Major Low";
          uses live_ncs_THRESH-BAG;
        }
        container critical-hi {
          description
            "Critical High";
          uses live_ncs_THRESH-BAG;
        }
        container minor-hi {
          description
            "Minor High";
          uses live_ncs_THRESH-BAG;
        }
        container major-hi {
          description
            "Major High";
          uses live_ncs_THRESH-BAG;
        }
        container critical-lo {
          description
            "Critical Low";
          uses live_ncs_THRESH-BAG;
        }
        container minor-lo {
          description
            "Minor Low";
          uses live_ncs_THRESH-BAG;
        }
      }
      container fru-info {
        description
          "Inventory EDM FRU info";
        uses live_ncs_INV-CARD-FRU-INFO;
      }
      container inv-eeprom-info {
        description
          "Inventory EDM EEPROM Information Bag";
        uses live_ncs_INVMGR-EEPROM-OPAQUE-DATA;
      }
    }
  }

  grouping live_ncs_SLOT {
    description
      "Common node of powershelf, fantray, entity";
    list slot {
      key "name";
      description
        "Slot number";
      container tsi1s {
        description
          "Entity Level 1";
        list tsi1 {
          key "name";
          description
            "TSI1";
          container tsi2s {
            description
              "Entity Level 2";
            list tsi2 {
              key "name";
              description
                "TSI2";
              container tsi3s {
                description
                  "Entity Level 3";
                list tsi3 {
                  key "name";
                  description
                    "TSI3";
                  container tsi4s {
                    description
                      "Entity Level 4";
                    list tsi4 {
                      key "name";
                      description
                        "TSI4";
                      container tsi5s {
                        description
                          "Entity Level 5";
                        list tsi5 {
                          key "name";
                          description
                            "TSI5";
                          container tsi6s {
                            description
                              "Entity Level 6";
                            list tsi6 {
                              key "name";
                              description
                                "TSI6";
                              container tsi7s {
                                description
                                  "Entity Level 7";
                                list tsi7 {
                                  key "name";
                                  description
                                    "TSI7";
                                  container tsi8s {
                                    description
                                      "Entity Level 8";
                                    list tsi8 {
                                      key "name";
                                      description
                                        "TSI8";
                                      container tsi9s {
                                        description
                                          "Entity Level 9";
                                        list tsi9 {
                                          key "name";
                                          description
                                            "TSI9";
                                          container tsi10s {
                                            description
                                              "Entity Level 10";
                                            list tsi10 {
                                              key "name";
                                              description
                                                "TSI10";
                                              container tsi11s {
                                                description
                                                  "Entity Level 11";
                                                list tsi11 {
                                                  key "name";
                                                  description
                                                    "TSI11";
                                                  leaf name {
                                                    type xr:Cisco-ios-xr-string;
                                                    description
                                                      "TSI11";
                                                  }
                                                  uses live_ncs_ATTRIBUTES;
                                                }
                                              }
                                              leaf name {
                                                type xr:Cisco-ios-xr-string;
                                                description
                                                  "TSI10";
                                              }
                                              uses live_ncs_ATTRIBUTES;
                                            }
                                          }
                                          leaf name {
                                            type xr:Cisco-ios-xr-string;
                                            description
                                              "TSI9";
                                          }
                                          uses live_ncs_ATTRIBUTES;
                                        }
                                      }
                                      leaf name {
                                        type xr:Cisco-ios-xr-string;
                                        description
                                          "TSI8";
                                      }
                                      uses live_ncs_ATTRIBUTES;
                                    }
                                  }
                                  leaf name {
                                    type xr:Cisco-ios-xr-string;
                                    description
                                      "TSI7";
                                  }
                                  uses live_ncs_ATTRIBUTES;
                                }
                              }
                              leaf name {
                                type xr:Cisco-ios-xr-string;
                                description
                                  "TSI6";
                              }
                              uses live_ncs_ATTRIBUTES;
                            }
                          }
                          leaf name {
                            type xr:Cisco-ios-xr-string;
                            description
                              "TSI5";
                          }
                          uses live_ncs_ATTRIBUTES;
                        }
                      }
                      leaf name {
                        type xr:Cisco-ios-xr-string;
                        description
                          "TSI4";
                      }
                      uses live_ncs_ATTRIBUTES;
                    }
                  }
                  leaf name {
                    type xr:Cisco-ios-xr-string;
                    description
                      "TSI3";
                  }
                  uses live_ncs_ATTRIBUTES;
                }
              }
              leaf name {
                type xr:Cisco-ios-xr-string;
                description
                  "TSI2";
              }
              uses live_ncs_ATTRIBUTES;
            }
          }
          leaf name {
            type xr:Cisco-ios-xr-string;
            description
              "TSI1";
          }
          uses live_ncs_ATTRIBUTES;
        }
      }
      leaf name {
        type xr:Cisco-ios-xr-string;
        description
          "Slot name";
      }
      uses live_ncs_ATTRIBUTES;
    }
  }

  grouping THRESH-BAG {
    description
      "Common node of minor-lo, minor-hi, major-lo,
       major-hi, critical-lo, critical-hi";
    container thresh-bag {
      description
        "Environment threshold info";
      uses ENVMON-THRESHOLD-INFO;
    }
  }

  grouping INVMGR-EXT1-OPER-THRESH-BAG {
    description
      "Common node of minor-lo, minor-hi, major-lo,
       major-hi, critical-lo, critical-hiCommon node of
       minor-lo, minor-hi, major-lo, major-hi,
       critical-lo, critical-hi";
    container thresh-bag {
      description
        "Environment threshold info";
      uses ENVMON-THRESHOLD-INFO;
    }
  }

  grouping ATTRIBUTES {
    description
      "Common node of rack, slot, tsi1, tsi2, tsi3, tsi4
       , tsi5, tsi6, tsi7, tsi8, tsi9, tsi10, tsi11";
    container attributes {
      description
        "Attributes";
      container inv-basic-bag {
        description
          "Inventory Basic Bag";
        uses INV-PHY-ENTITY-BASIC-INFO;
      }
      container env-sensor-info {
        description
          "Environment sensor info";
        uses ENVMON-SENSOR-INFO;
      }
      container pwg-info {
        description
          "Inventory EDM PWG info";
        uses INV-PWG-INFO;
      }
      container env-sensor-info-xml {
        description
          "Environment sensor info XML";
        uses ENVMON-SENSOR-INFO-XML;
      }
      container inv-asset-bag {
        description
          "Inventory Asset Bag";
        uses INV-PHY-ENTITY-ASSET-INFO;
      }
      container threshold {
        description
          "Threshold";
        container major-lo {
          description
            "Major Low";
          uses THRESH-BAG;
        }
        container critical-hi {
          description
            "Critical High";
          uses THRESH-BAG;
        }
        container minor-hi {
          description
            "Minor High";
          uses THRESH-BAG;
        }
        container major-hi {
          description
            "Major High";
          uses THRESH-BAG;
        }
        container critical-lo {
          description
            "Critical Low";
          uses THRESH-BAG;
        }
        container minor-lo {
          description
            "Minor Low";
          uses THRESH-BAG;
        }
      }
      container fru-info {
        description
          "Inventory EDM FRU info";
        uses INV-CARD-FRU-INFO;
      }
      container inv-eeprom-info {
        description
          "Inventory EDM EEPROM Information Bag";
        uses INVMGR-EEPROM-OPAQUE-DATA;
      }
    }
  }

  grouping SLOT {
    description
      "Common node of powershelf, fantray, entity";
    list slot {
      key "name";
      description
        "Slot number";
      container tsi1s {
        description
          "Entity Level 1";
        list tsi1 {
          key "name";
          description
            "TSI1";
          container tsi2s {
            description
              "Entity Level 2";
            list tsi2 {
              key "name";
              description
                "TSI2";
              container tsi3s {
                description
                  "Entity Level 3";
                list tsi3 {
                  key "name";
                  description
                    "TSI3";
                  container tsi4s {
                    description
                      "Entity Level 4";
                    list tsi4 {
                      key "name";
                      description
                        "TSI4";
                      container tsi5s {
                        description
                          "Entity Level 5";
                        list tsi5 {
                          key "name";
                          description
                            "TSI5";
                          container tsi6s {
                            description
                              "Entity Level 6";
                            list tsi6 {
                              key "name";
                              description
                                "TSI6";
                              container tsi7s {
                                description
                                  "Entity Level 7";
                                list tsi7 {
                                  key "name";
                                  description
                                    "TSI7";
                                  container tsi8s {
                                    description
                                      "Entity Level 8";
                                    list tsi8 {
                                      key "name";
                                      description
                                        "TSI8";
                                      container tsi9s {
                                        description
                                          "Entity Level 9";
                                        list tsi9 {
                                          key "name";
                                          description
                                            "TSI9";
                                          container tsi10s {
                                            description
                                              "Entity Level 10";
                                            list tsi10 {
                                              key "name";
                                              description
                                                "TSI10";
                                              container tsi11s {
                                                description
                                                  "Entity Level 11";
                                                list tsi11 {
                                                  key "name";
                                                  description
                                                    "TSI11";
                                                  leaf name {
                                                    type xr:Cisco-ios-xr-string;
                                                    description
                                                      "TSI11";
                                                  }
                                                  uses ATTRIBUTES;
                                                }
                                              }
                                              leaf name {
                                                type xr:Cisco-ios-xr-string;
                                                description
                                                  "TSI10";
                                              }
                                              uses ATTRIBUTES;
                                            }
                                          }
                                          leaf name {
                                            type xr:Cisco-ios-xr-string;
                                            description
                                              "TSI9";
                                          }
                                          uses ATTRIBUTES;
                                        }
                                      }
                                      leaf name {
                                        type xr:Cisco-ios-xr-string;
                                        description
                                          "TSI8";
                                      }
                                      uses ATTRIBUTES;
                                    }
                                  }
                                  leaf name {
                                    type xr:Cisco-ios-xr-string;
                                    description
                                      "TSI7";
                                  }
                                  uses ATTRIBUTES;
                                }
                              }
                              leaf name {
                                type xr:Cisco-ios-xr-string;
                                description
                                  "TSI6";
                              }
                              uses ATTRIBUTES;
                            }
                          }
                          leaf name {
                            type xr:Cisco-ios-xr-string;
                            description
                              "TSI5";
                          }
                          uses ATTRIBUTES;
                        }
                      }
                      leaf name {
                        type xr:Cisco-ios-xr-string;
                        description
                          "TSI4";
                      }
                      uses ATTRIBUTES;
                    }
                  }
                  leaf name {
                    type xr:Cisco-ios-xr-string;
                    description
                      "TSI3";
                  }
                  uses ATTRIBUTES;
                }
              }
              leaf name {
                type xr:Cisco-ios-xr-string;
                description
                  "TSI2";
              }
              uses ATTRIBUTES;
            }
          }
          leaf name {
            type xr:Cisco-ios-xr-string;
            description
              "TSI1";
          }
          uses ATTRIBUTES;
        }
      }
      leaf name {
        type xr:Cisco-ios-xr-string;
        description
          "Slot name";
      }
      uses ATTRIBUTES;
    }
  }

  augment "/ncs:devices/ncs:device/ncs:config" {
    // NCS drop config false container inventory
  }
  augment "/ncs:devices/ncs:device/ncs:live-status" {
    container inventory {
      tailf:ncs-device-type "netconf";
      tailf:display-when "not(../../ncs:module) or ../../ncs:module[ncs:name='Cisco-IOS-XR-invmgr-oper'] or (../../ncs:live-status-protocol[not(ncs:capability)]) or (../../ncs:live-status-protocol/ncs:capability/ncs:module[.='Cisco-IOS-XR-invmgr-oper'])";
      description
        "Inventory information";
      container entities {
        description
          "Entities Table";
        list entity {
          key "name";
          description
            "Entity name";
          container subentities {
            description
              "SubEntities Table";
            list subentity {
              key "name";
              description
                "Subentity Bag";
              leaf name {
                type string;
                description
                  "Subentity name";
              }
              uses live_ncs_SUBENTITY-INFO;
            }
          }
          container attributes {
            description
              "Attributes";
            container inv-basic-bag {
              description
                "Inventory Basic Bag";
              uses live_ncs_INV-PHY-ENTITY-BASIC-INFO;
            }
            container vm-node-id {
              description
                "VM Node ID Tuple";
              uses live_ncs_VM-NODEID-INFO;
            }
            container threshold {
              description
                "Threshold";
              container minor-hi {
                description
                  "Minor High";
                uses live_ncs_INVMGR-EXT1-OPER-THRESH-BAG;
              }
              container major-hi {
                description
                  "Major High";
                uses live_ncs_INVMGR-EXT1-OPER-THRESH-BAG;
              }
              container minor-lo {
                description
                  "Minor Low";
                uses live_ncs_INVMGR-EXT1-OPER-THRESH-BAG;
              }
              container major-lo {
                description
                  "Major Low";
                uses live_ncs_INVMGR-EXT1-OPER-THRESH-BAG;
              }
              container critical-hi {
                description
                  "Critical High";
                uses live_ncs_INVMGR-EXT1-OPER-THRESH-BAG;
              }
              container critical-lo {
                description
                  "Critical Low";
                uses live_ncs_INVMGR-EXT1-OPER-THRESH-BAG;
              }
            }
            container vm-done {
              description
                "VM Done Tuple";
              uses live_ncs_VMDONE-INFO;
            }
            container fru-info {
              description
                "Inventory EDM FRU info";
              uses live_ncs_INV-CARD-FRU-INFO;
            }
            container env-sensor-info-xml {
              description
                "Environment sensor info XML";
              uses live_ncs_ENVMON-SENSOR-INFO-XML;
            }
            container inv-asset-bag {
              description
                "Inventory Asset Bag";
              uses live_ncs_INV-PHY-ENTITY-ASSET-INFO;
            }
            container env-sensor-info {
              description
                "Environment sensor info";
              uses live_ncs_ENVMON-SENSOR-INFO;
            }
            container node-id {
              description
                "Node ID Tuple";
              uses live_ncs_NODEID-INFO;
            }
            container inv-eeprom-info {
              description
                "Inventory EDM EEPROM Information Bag";
              uses live_ncs_INVMGR-EEPROM-OPAQUE-DATA;
            }
          }
          leaf name {
            type string;
            description
              "Entity name";
          }
        }
      }
      container racks {
        description
          "RackTable";
        list rack {
          key "name";
          description
            "Rack name";
          container entity {
            description
              "Entity information";
            uses live_ncs_SLOT;
          }
          container powershelf {
            description
              "Powershelf information";
            uses live_ncs_SLOT;
          }
          container fantray {
            description
              "Fantray information";
            uses live_ncs_SLOT;
          }
          leaf name {
            type xr:Cisco-ios-xr-string;
            description
              "Rack name";
          }
          uses live_ncs_ATTRIBUTES;
        }
      }
    }
  }
  augment "/ncs:devices/ncs:template/ncs:ned-id/ncs:config" {
    // NCS drop config false container inventory
  }
}
