module Cisco-IOS-XR-mpls-static-oper {
  // Generated by yanger -t ncs
  tailf:mount-id f5500-nc-1.0:f5500-nc-1.0;
  tailf:ncs-device-type "netconf";

  namespace "http://cisco.com/ns/yang/Cisco-IOS-XR-mpls-static-oper";
  prefix Cisco-IOS-XR-mpls-static-oper;

  import Cisco-IOS-XR-types {
    prefix xr;
  }
  include Cisco-IOS-XR-mpls-static-oper-sub1 {
    revision-date 2017-05-01;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR mpls-static package operational data.

     This module contains definitions
     for the following management objects:
       mpls-static: MPLS STATIC operational data

     Copyright (c) 2013-2018 by Cisco Systems, Inc.
     All rights reserved.";

  revision 2017-05-01 {
    description
      "Fixing backward compatibility error in module.";
  }
  revision 2015-11-09 {
    description
      "IOS XR 6.0 revision.";
  }

  grouping ncs_template_LOCAL-LABEL-TABLE {
    description
      "Common node of mpls-static, vrf";
    container local-labels {
      description
        "data for static local-label table";
      list local-label {
        // NCS patched for predictable order
        ordered-by user;
        key "local-label-id";
        description
          "Data for static label";
        leaf local-label-id {
          type string;
          description
            "Local Label";
        }
        uses ncs_template_MPLS-STATIC-LBL-INFO;
      }
    }
  }

  grouping ncs_rpc_notif_LOCAL-LABEL-TABLE {
    description
      "Common node of mpls-static, vrf";
    container local-labels {
      description
        "data for static local-label table";
      list local-label {
        key "local-label-id";
        description
          "Data for static label";
        leaf local-label-id {
          type uint32 {
            range "16..1048575";
          }
          description
            "Local Label";
        }
        uses ncs_rpc_notif_MPLS-STATIC-LBL-INFO;
      }
    }
  }

  grouping live_ncs_LOCAL-LABEL-TABLE {
    description
      "Common node of mpls-static, vrf";
    container local-labels {
      description
        "data for static local-label table";
      list local-label {
        key "local-label-id";
        description
          "Data for static label";
        leaf local-label-id {
          type uint32 {
            range "16..1048575";
          }
          description
            "Local Label";
        }
        uses live_ncs_MPLS-STATIC-LBL-INFO;
      }
    }
  }

  grouping LOCAL-LABEL-TABLE {
    description
      "Common node of mpls-static, vrf";
    container local-labels {
      description
        "data for static local-label table";
      list local-label {
        key "local-label-id";
        description
          "Data for static label";
        leaf local-label-id {
          type uint32 {
            range "16..1048575";
          }
          description
            "Local Label";
        }
        uses MPLS-STATIC-LBL-INFO;
      }
    }
  }

  augment "/ncs:devices/ncs:device/ncs:config" {
    // NCS drop config false container 'mpls-static'
  }
  augment "/ncs:devices/ncs:device/ncs:live-status" {
    container mpls-static {
      tailf:ncs-device-type "netconf";
      tailf:display-when "not(../../ncs:module) or ../../ncs:module[ncs:name='Cisco-IOS-XR-mpls-static-oper'] or (../../ncs:live-status-protocol[not(ncs:capability)]) or (../../ncs:live-status-protocol/ncs:capability/ncs:module[.='Cisco-IOS-XR-mpls-static-oper'])";
      description
        "MPLS STATIC operational data";
      container vrfs {
        description
          "VRF table";
        list vrf {
          key "vrf-name";
          description
            "VRF Name";
          container lsps {
            description
              "data for static lsp table";
            list lsp {
              key "lsp-name";
              description
                "Data for static lsp";
              leaf lsp-name {
                type xr:Cisco-ios-xr-string;
                description
                  "LSP Name";
              }
              uses live_ncs_MPLS-STATIC-LSP-INFO;
            }
          }
          leaf vrf-name {
            type xr:Cisco-ios-xr-string;
            description
              "VRF Name";
          }
          uses live_ncs_LOCAL-LABEL-TABLE;
        }
      }
      container summary {
        description
          "MPLS STATIC summary data";
        uses live_ncs_MPLS-STATIC-SUMMARY;
      }
      uses live_ncs_LOCAL-LABEL-TABLE;
    }
  }
  augment "/ncs:devices/ncs:template/ncs:ned-id/ncs:config" {
    // NCS drop config false container 'mpls-static'
  }
}
