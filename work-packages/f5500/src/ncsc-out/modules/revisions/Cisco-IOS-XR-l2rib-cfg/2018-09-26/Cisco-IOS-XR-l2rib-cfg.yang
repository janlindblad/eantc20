module Cisco-IOS-XR-l2rib-cfg {
  // Generated by yanger -t ncs
  tailf:mount-id f5500-nc-1.0:f5500-nc-1.0;
  tailf:ncs-device-type "netconf";

  namespace "http://cisco.com/ns/yang/Cisco-IOS-XR-l2rib-cfg";
  prefix Cisco-IOS-XR-l2rib-cfg;

  import Cisco-IOS-XR-l2vpn-cfg {
    prefix a1;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR l2rib package configuration.

     This YANG module augments the
       Cisco-IOS-XR-l2vpn-cfg
     module with configuration data.

     Copyright (c) 2013-2018 by Cisco Systems, Inc.
     All rights reserved.";

  revision 2018-09-26 {
    description
      "Duplicate detection parameters config moved from l2vpn to l2rib.";
  }
  revision 2015-11-09 {
    description
      "IOS XR 6.0 revision.";
  }

  grouping ncs_template_DUPLICATE-DETECTION {
    description
      "Common node of mac, ipv4, ipv6";
    container duplicate-detection {
      description
        "EVPN HOST [MAC/IPv4/IPv6] DUP-DETECT
         Configuration";
      leaf move-count {
        type string;
        // NCS drop default statement
        description
          "Number of moves to occur within the
           MoveInterval before a MAC/IPv4/IPv6 address is
           marked as duplicate";
      }
      leaf retry-count {
        type string;
        // NCS drop default statement
        description
          "Number of times to automatically clear the
           duplicate flag on a MAC/IPV4/IPV6 route before
           permanently freezing it";
      }
      leaf freeze-time {
        type string;
        // NCS drop default statement
        description
          "Length of time to lock the MAC/IPv4/IPv6 after
           a MAC/IPv4/IPv6 has been marked as duplicate";
      }
      leaf move-interval {
        type string;
        // NCS drop default statement
        description
          "Interval within which MoveCount number of moves
           need to happen before a MAC/IPv4/IPv6 route is
           marked as duplicate";
      }
      leaf disable {
        type empty;
        description
          "Set to disable duplicate detection";
      }
    }
  }

  grouping ncs_rpc_notif_DUPLICATE-DETECTION {
    description
      "Common node of mac, ipv4, ipv6";
    container duplicate-detection {
      description
        "EVPN HOST [MAC/IPv4/IPv6] DUP-DETECT
         Configuration";
      leaf move-count {
        type uint32 {
          range "1..1000";
        }
        default "5";
        description
          "Number of moves to occur within the
           MoveInterval before a MAC/IPv4/IPv6 address is
           marked as duplicate";
      }
      leaf retry-count {
        type uint32 {
          range "0..1000";
        }
        default "3";
        description
          "Number of times to automatically clear the
           duplicate flag on a MAC/IPV4/IPV6 route before
           permanently freezing it";
      }
      leaf freeze-time {
        type uint32 {
          range "5..3600";
        }
        default "30";
        description
          "Length of time to lock the MAC/IPv4/IPv6 after
           a MAC/IPv4/IPv6 has been marked as duplicate";
      }
      leaf move-interval {
        type uint32 {
          range "5..3600";
        }
        default "180";
        description
          "Interval within which MoveCount number of moves
           need to happen before a MAC/IPv4/IPv6 route is
           marked as duplicate";
      }
      leaf disable {
        type empty;
        description
          "Set to disable duplicate detection";
      }
    }
  }

  grouping live_ncs_DUPLICATE-DETECTION {
    description
      "Common node of mac, ipv4, ipv6";
    container duplicate-detection {
      description
        "EVPN HOST [MAC/IPv4/IPv6] DUP-DETECT
         Configuration";
      leaf move-count {
        type uint32 {
          range "1..1000";
        }
        // NCS drop default statement
        description
          "Number of moves to occur within the
           MoveInterval before a MAC/IPv4/IPv6 address is
           marked as duplicate";
      }
      leaf retry-count {
        type uint32 {
          range "0..1000";
        }
        // NCS drop default statement
        description
          "Number of times to automatically clear the
           duplicate flag on a MAC/IPV4/IPV6 route before
           permanently freezing it";
      }
      leaf freeze-time {
        type uint32 {
          range "5..3600";
        }
        // NCS drop default statement
        description
          "Length of time to lock the MAC/IPv4/IPv6 after
           a MAC/IPv4/IPv6 has been marked as duplicate";
      }
      leaf move-interval {
        type uint32 {
          range "5..3600";
        }
        // NCS drop default statement
        description
          "Interval within which MoveCount number of moves
           need to happen before a MAC/IPv4/IPv6 route is
           marked as duplicate";
      }
      leaf disable {
        type empty;
        description
          "Set to disable duplicate detection";
      }
    }
  }

  grouping DUPLICATE-DETECTION {
    description
      "Common node of mac, ipv4, ipv6";
    container duplicate-detection {
      description
        "EVPN HOST [MAC/IPv4/IPv6] DUP-DETECT
         Configuration";
      leaf move-count {
        type uint32 {
          range "1..1000";
        }
        default "5";
        description
          "Number of moves to occur within the
           MoveInterval before a MAC/IPv4/IPv6 address is
           marked as duplicate";
      }
      leaf retry-count {
        type uint32 {
          range "0..1000";
        }
        default "3";
        description
          "Number of times to automatically clear the
           duplicate flag on a MAC/IPV4/IPV6 route before
           permanently freezing it";
      }
      leaf freeze-time {
        type uint32 {
          range "5..3600";
        }
        default "30";
        description
          "Length of time to lock the MAC/IPv4/IPv6 after
           a MAC/IPv4/IPv6 has been marked as duplicate";
      }
      leaf move-interval {
        type uint32 {
          range "5..3600";
        }
        default "180";
        description
          "Interval within which MoveCount number of moves
           need to happen before a MAC/IPv4/IPv6 route is
           marked as duplicate";
      }
      leaf disable {
        type empty;
        description
          "Set to disable duplicate detection";
      }
    }
  }

  augment "/ncs:devices/ncs:template/ncs:ned-id/ncs:config/a1:evpn/a1:evpn-tables" {
    container host {
      description
        "EVPN HOST Configuration";
      container ipv6 {
        description
          "EVPN HOST IPV6-ADDR Configuration";
        uses ncs_template_DUPLICATE-DETECTION;
      }
      container ipv4 {
        description
          "EVPN HOST IPV4-ADDR Configuration";
        uses ncs_template_DUPLICATE-DETECTION;
      }
      container mac {
        description
          "EVPN HOST MAC-ADDR Configuration";
        uses ncs_template_DUPLICATE-DETECTION;
      }
    }
    description
      "This augment extends the configuration data of
       'Cisco-IOS-XR-l2vpn-cfg'";
  }
  augment "/ncs:devices/ncs:device/ncs:live-status/a1:evpn/a1:evpn-tables" {
    container host {
      tailf:ncs-device-type "netconf";
      tailf:display-when "not(../../../../ncs:module) or ../../../../ncs:module[ncs:name='Cisco-IOS-XR-l2rib-cfg'] or (../../../../ncs:live-status-protocol[not(ncs:capability)]) or (../../../../ncs:live-status-protocol/ncs:capability/ncs:module[.='Cisco-IOS-XR-l2rib-cfg'])";
      description
        "EVPN HOST Configuration";
      container ipv6 {
        description
          "EVPN HOST IPV6-ADDR Configuration";
        uses live_ncs_DUPLICATE-DETECTION;
      }
      container ipv4 {
        description
          "EVPN HOST IPV4-ADDR Configuration";
        uses live_ncs_DUPLICATE-DETECTION;
      }
      container mac {
        description
          "EVPN HOST MAC-ADDR Configuration";
        uses live_ncs_DUPLICATE-DETECTION;
      }
    }
    description
      "This augment extends the configuration data of
       'Cisco-IOS-XR-l2vpn-cfg'";
  }
  augment "/ncs:devices/ncs:device/ncs:config/a1:evpn/a1:evpn-tables" {
    container host {
      tailf:ncs-device-type "netconf";
      tailf:display-when "not(../../../../ncs:module) or ../../../../ncs:module[ncs:name='Cisco-IOS-XR-l2rib-cfg']";
      description
        "EVPN HOST Configuration";
      container ipv6 {
        description
          "EVPN HOST IPV6-ADDR Configuration";
        uses DUPLICATE-DETECTION;
      }
      container ipv4 {
        description
          "EVPN HOST IPV4-ADDR Configuration";
        uses DUPLICATE-DETECTION;
      }
      container mac {
        description
          "EVPN HOST MAC-ADDR Configuration";
        uses DUPLICATE-DETECTION;
      }
    }
    description
      "This augment extends the configuration data of
       'Cisco-IOS-XR-l2vpn-cfg'";
  }
}
