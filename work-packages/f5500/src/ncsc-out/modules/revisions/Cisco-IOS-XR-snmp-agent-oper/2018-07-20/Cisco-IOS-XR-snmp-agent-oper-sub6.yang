submodule Cisco-IOS-XR-snmp-agent-oper-sub6 {
  // Generated by yanger -t ncs
  tailf:mount-id f5500-nc-1.0:f5500-nc-1.0;

  belongs-to Cisco-IOS-XR-snmp-agent-oper {
    prefix Cisco-IOS-XR-snmp-agent-oper-sub6;
  }

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR snmp-agent package operational data.

     Copyright (c) 2013-2018 by Cisco Systems, Inc.
     All rights reserved.";

  revision 2018-07-20 {
    description
      "Fixed English plural name transformation error.";
  }
  revision 2017-09-07 {
    description
      "Fixed type translation error.";
  }
  revision 2017-05-01 {
    description
      "Fixing backward compatibility error in module.";
  }
  revision 2016-06-01 {
    description
      "IOS XR 6.0.1 revision.";
  }
  revision 2015-01-07 {
    description
      "IOS XR 5.3.1 revision.";
  }

  typedef Nms-ip {
    type string;
    description
      "Nms ip";
  }

  grouping ncs_template_SNMP-OID-STATS-B {
    description
      "SNMP incomming/processing queue statistics";
    leaf nms-count {
      type string;
      description
        " Managment station count";
    }
    leaf-list nms {
      // NCS patched for predictable order
      ordered-by user;
      type string;
      // NCS drop max-elements statement
      description
        "Network Managment station ipadress";
    }
    leaf-list request-count {
      // NCS patched for predictable order
      ordered-by user;
      type string;
      // NCS drop max-elements statement
      description
        "OID request count for each Managment station ";
    }
  }

  grouping ncs_rpc_notif_SNMP-OID-STATS-B {
    description
      "SNMP incomming/processing queue statistics";
    leaf nms-count {
      type uint32;
      description
        " Managment station count";
    }
    leaf-list nms {
      type Nms-ip;
      max-elements 15;
      description
        "Network Managment station ipadress";
    }
    leaf-list request-count {
      type uint32;
      max-elements 15;
      description
        "OID request count for each Managment station ";
    }
  }

  grouping live_ncs_SNMP-OID-STATS-B {
    description
      "SNMP incomming/processing queue statistics";
    leaf nms-count {
      type uint32;
      description
        " Managment station count";
    }
    leaf-list nms {
      type Nms-ip;
      // NCS drop max-elements statement
      description
        "Network Managment station ipadress";
    }
    leaf-list request-count {
      type uint32;
      // NCS drop max-elements statement
      description
        "OID request count for each Managment station ";
    }
  }

  grouping SNMP-OID-STATS-B {
    description
      "SNMP incomming/processing queue statistics";
    leaf nms-count {
      type uint32;
      description
        " Managment station count";
    }
    leaf-list nms {
      type Nms-ip;
      max-elements 15;
      description
        "Network Managment station ipadress";
    }
    leaf-list request-count {
      type uint32;
      max-elements 15;
      description
        "OID request count for each Managment station ";
    }
  }
}
