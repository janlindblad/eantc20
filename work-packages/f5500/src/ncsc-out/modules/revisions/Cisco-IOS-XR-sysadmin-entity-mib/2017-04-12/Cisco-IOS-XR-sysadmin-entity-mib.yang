module Cisco-IOS-XR-sysadmin-entity-mib {
  // Generated by yanger -t ncs
  tailf:mount-id f5500-nc-1.0:f5500-nc-1.0;
  tailf:ncs-device-type "netconf";

  namespace "http://www.cisco.com/ns/yang/Cisco-IOS-XR-sysadmin-entity-mib";
  // NCS drop tailf:id
  prefix Cisco-IOS-XR-sysadmin-entity-mib;
  tailf:snmp-mib-module-name ENTITY-MIB;

  import ietf-yang-types {
    prefix yang;
  }
  import tailf-common {
    prefix tailf;
  }
  import SNMPv2-TC {
    prefix SNMPv2-TC;
  }
  import SNMP-FRAMEWORK-MIB {
    prefix SNMP-FRAMEWORK-MIB;
  }
  import "f5500-nc-1.0" {
    prefix "f5500-nc-1.0";
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains a collection of YANG
     definitions for Cisco IOS-XR SysAdmin configuration.

     Copyright(c) 2015-2017 by Cisco Systems, Inc.
     All rights reserved.";

  revision 2017-04-12 {
    description
      "Changed namespace and module name";
  }
  revision 1999-12-07 {
    description
      "";
  }

  typedef entAliasLogicalIndexOrZeroType {
    type int32 {
      range "0 .. 2147483647";
    }
  }

  typedef entLogicalCommunityType {
    type tailf:hex-list {
      tailf:value-length "min .. 255";
    }
  }

  typedef entLogicalIndexType {
    type int32 {
      range "1 .. 2147483647";
    }
  }

  typedef entPhysicalAssetIDType {
    type string {
      length "min .. 32";
    }
  }

  typedef entPhysicalAliasType {
    type string {
      length "min .. 32";
    }
  }

  typedef entPhysicalSerialNumType {
    type string {
      length "min .. 32";
    }
  }

  typedef entPhysicalParentRelPosType {
    type int32 {
      range "-1 .. 2147483647";
    }
  }

  typedef entPhysicalContainedInType {
    type int32 {
      range "0 .. 2147483647";
    }
  }

  typedef SnmpEngineIdOrNone {
    type tailf:hex-list {
      tailf:value-length "min .. 32";
    }
  }

  typedef PhysicalClass {
    type enumeration {
      enum "other" {
        value 1;
      }
      enum "unknown" {
        value 2;
      }
      enum "chassis" {
        value 3;
      }
      enum "backplane" {
        value 4;
      }
      enum "container" {
        value 5;
      }
      enum "powerSupply" {
        value 6;
      }
      enum "fan" {
        value 7;
      }
      enum "sensor" {
        value 8;
      }
      enum "module" {
        value 9;
      }
      enum "port" {
        value 10;
      }
      enum "stack" {
        value 11;
      }
    }
  }

  typedef PhysicalIndex {
    type int32 {
      range "1 .. 2147483647";
    }
  }

  augment "/ncs:devices/ncs:device/ncs:config" {
    container ENTITY-MIB {
      tailf:ncs-device-type "netconf";
      tailf:display-when "not(../../ncs:module) or ../../ncs:module[ncs:name='Cisco-IOS-XR-sysadmin-entity-mib']";
      // NCS drop config false container entityGeneral
      // NCS drop config false container entPhysicalTable
      // NCS drop config false container entLogicalTable
      // NCS drop config false container entLPMappingTable
      // NCS drop config false container entAliasMappingTable
      // NCS drop config false container entPhysicalContainsTable
    }
  }
  augment "/ncs:devices/ncs:device/ncs:live-status" {
    container ENTITY-MIB {
      tailf:ncs-device-type "netconf";
      tailf:display-when "not(../../ncs:module) or ../../ncs:module[ncs:name='Cisco-IOS-XR-sysadmin-entity-mib'] or (../../ncs:live-status-protocol[not(ncs:capability)]) or (../../ncs:live-status-protocol/ncs:capability/ncs:module[.='Cisco-IOS-XR-sysadmin-entity-mib'])";
      container entityGeneral {
        tailf:snmp-oid "1.3.6.1.2.1.47.1.4";
        leaf entLastChangeTime {
          type yang:timestamp;
          tailf:snmp-oid "1.3.6.1.2.1.47.1.4.1";
        }
      }
      container entPhysicalTable {
        // NCS drop tailf:callpoint
        list entPhysicalEntry {
          key "entPhysicalIndex";
          tailf:sort-order snmp;
          tailf:snmp-oid "1.3.6.1.2.1.47.1.1.1";
          leaf entPhysicalIndex {
            type PhysicalIndex;
            tailf:snmp-oid "1.3.6.1.2.1.47.1.1.1.1.1";
          }
          leaf entPhysicalDescr {
            type SNMP-FRAMEWORK-MIB:SnmpAdminString;
            tailf:snmp-oid "1.3.6.1.2.1.47.1.1.1.1.2";
          }
          leaf entPhysicalVendorType {
            type SNMPv2-TC:AutonomousType;
            tailf:snmp-oid "1.3.6.1.2.1.47.1.1.1.1.3";
          }
          leaf entPhysicalContainedIn {
            type entPhysicalContainedInType;
            tailf:snmp-oid "1.3.6.1.2.1.47.1.1.1.1.4";
          }
          leaf entPhysicalClass {
            type PhysicalClass;
            tailf:snmp-oid "1.3.6.1.2.1.47.1.1.1.1.5";
          }
          leaf entPhysicalParentRelPos {
            type entPhysicalParentRelPosType;
            tailf:snmp-oid "1.3.6.1.2.1.47.1.1.1.1.6";
          }
          leaf entPhysicalName {
            type SNMP-FRAMEWORK-MIB:SnmpAdminString;
            tailf:snmp-oid "1.3.6.1.2.1.47.1.1.1.1.7";
          }
          leaf entPhysicalHardwareRev {
            type SNMP-FRAMEWORK-MIB:SnmpAdminString;
            tailf:snmp-oid "1.3.6.1.2.1.47.1.1.1.1.8";
          }
          leaf entPhysicalFirmwareRev {
            type SNMP-FRAMEWORK-MIB:SnmpAdminString;
            tailf:snmp-oid "1.3.6.1.2.1.47.1.1.1.1.9";
          }
          leaf entPhysicalSoftwareRev {
            type SNMP-FRAMEWORK-MIB:SnmpAdminString;
            tailf:snmp-oid "1.3.6.1.2.1.47.1.1.1.1.10";
          }
          leaf entPhysicalSerialNum {
            type entPhysicalSerialNumType;
            tailf:snmp-oid "1.3.6.1.2.1.47.1.1.1.1.11";
          }
          leaf entPhysicalMfgName {
            type SNMP-FRAMEWORK-MIB:SnmpAdminString;
            tailf:snmp-oid "1.3.6.1.2.1.47.1.1.1.1.12";
          }
          leaf entPhysicalModelName {
            type SNMP-FRAMEWORK-MIB:SnmpAdminString;
            tailf:snmp-oid "1.3.6.1.2.1.47.1.1.1.1.13";
          }
          leaf entPhysicalAlias {
            type entPhysicalAliasType;
            tailf:snmp-oid "1.3.6.1.2.1.47.1.1.1.1.14";
          }
          leaf entPhysicalAssetID {
            type entPhysicalAssetIDType;
            tailf:snmp-oid "1.3.6.1.2.1.47.1.1.1.1.15";
          }
          leaf entPhysicalIsFRU {
            type SNMPv2-TC:TruthValue;
            tailf:snmp-oid "1.3.6.1.2.1.47.1.1.1.1.16";
          }
        }
      }
      container entLogicalTable {
        list entLogicalEntry {
          key "entLogicalIndex";
          tailf:sort-order snmp;
          tailf:snmp-oid "1.3.6.1.2.1.47.1.2.1";
          leaf entLogicalIndex {
            type entLogicalIndexType;
            tailf:snmp-oid "1.3.6.1.2.1.47.1.2.1.1.1";
          }
          leaf entLogicalDescr {
            type SNMP-FRAMEWORK-MIB:SnmpAdminString;
            tailf:snmp-oid "1.3.6.1.2.1.47.1.2.1.1.2";
          }
          leaf entLogicalType {
            type SNMPv2-TC:AutonomousType;
            tailf:snmp-oid "1.3.6.1.2.1.47.1.2.1.1.3";
          }
          leaf entLogicalCommunity {
            type entLogicalCommunityType;
            tailf:snmp-oid "1.3.6.1.2.1.47.1.2.1.1.4";
          }
          leaf entLogicalTAddress {
            type SNMPv2-TC:TAddress;
            tailf:snmp-oid "1.3.6.1.2.1.47.1.2.1.1.5";
          }
          leaf entLogicalTDomain {
            type SNMPv2-TC:TDomain;
            tailf:snmp-oid "1.3.6.1.2.1.47.1.2.1.1.6";
          }
          leaf entLogicalContextEngineID {
            type SnmpEngineIdOrNone;
            tailf:snmp-oid "1.3.6.1.2.1.47.1.2.1.1.7";
          }
          leaf entLogicalContextName {
            type SNMP-FRAMEWORK-MIB:SnmpAdminString;
            tailf:snmp-oid "1.3.6.1.2.1.47.1.2.1.1.8";
          }
        }
      }
      container entLPMappingTable {
        list entLPMappingEntry {
          key "entLogicalIndex entLPPhysicalIndex";
          tailf:sort-order snmp;
          tailf:snmp-oid "1.3.6.1.2.1.47.1.3.1";
          leaf entLogicalIndex {
            type entLogicalIndexType;
            tailf:snmp-oid "1.3.6.1.2.1.47.1.2.1.1.1";
          }
          leaf entLPPhysicalIndex {
            type PhysicalIndex;
            tailf:snmp-oid "1.3.6.1.2.1.47.1.3.1.1.1";
          }
        }
      }
      container entAliasMappingTable {
        list entAliasMappingEntry {
          key "entPhysicalIndex entAliasLogicalIndexOrZero";
          tailf:sort-order snmp;
          tailf:snmp-oid "1.3.6.1.2.1.47.1.3.2";
          leaf entPhysicalIndex {
            type PhysicalIndex;
            tailf:snmp-oid "1.3.6.1.2.1.47.1.1.1.1.1";
          }
          leaf entAliasLogicalIndexOrZero {
            type entAliasLogicalIndexOrZeroType;
            tailf:snmp-oid "1.3.6.1.2.1.47.1.3.2.1.1";
          }
          leaf entAliasMappingIdentifier {
            type SNMPv2-TC:RowPointer;
            tailf:snmp-oid "1.3.6.1.2.1.47.1.3.2.1.2";
          }
        }
      }
      container entPhysicalContainsTable {
        list entPhysicalContainsEntry {
          key "entPhysicalIndex entPhysicalChildIndex";
          tailf:sort-order snmp;
          tailf:snmp-oid "1.3.6.1.2.1.47.1.3.3";
          leaf entPhysicalIndex {
            type PhysicalIndex;
            tailf:snmp-oid "1.3.6.1.2.1.47.1.1.1.1.1";
          }
          leaf entPhysicalChildIndex {
            type PhysicalIndex;
            tailf:snmp-oid "1.3.6.1.2.1.47.1.3.3.1.1";
          }
        }
      }
    }
  }
  augment "/ncs:devices/ncs:template/ncs:ned-id/ncs:config" {
    container ENTITY-MIB {
      // NCS drop config false container entityGeneral
      // NCS drop config false container entPhysicalTable
      // NCS drop config false container entLogicalTable
      // NCS drop config false container entLPMappingTable
      // NCS drop config false container entAliasMappingTable
      // NCS drop config false container entPhysicalContainsTable
    }
  }
}
