module Cisco-IOS-XR-ipv4-filesystems-cfg {
  // Generated by yanger -t ncs
  tailf:mount-id f5500-nc-1.0:f5500-nc-1.0;
  tailf:ncs-device-type "netconf";

  namespace "http://cisco.com/ns/yang/Cisco-IOS-XR-ipv4-filesystems-cfg";
  prefix Cisco-IOS-XR-ipv4-filesystems-cfg;

  import Cisco-IOS-XR-types {
    prefix xr;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ipv4-filesystems package configuration.

     This module contains definitions
     for the following management objects:
       rcp: RCP configuration
       ftp: ftp
       tftp: tftp

     Copyright (c) 2013-2018 by Cisco Systems, Inc.
     All rights reserved.";

  revision 2017-11-28 {
    description
      "IOS XR 6.4.1 revision.";
  }
  revision 2015-11-09 {
    description
      "IOS XR 6.0 revision.";
  }

  grouping ncs_template_USERNAME {
    description
      "Common node of ftp-client, rcp-client";
    leaf username {
      type string;
      description
        "Specify username for connections";
    }
  }

  grouping ncs_template_SOURCE-INTERFACE {
    description
      "Common node of ftp-client, tftp-client,
       rcp-client";
    leaf source-interface {
      type string;
      description
        "Specify interface for source address in
         connections";
    }
  }

  grouping ncs_rpc_notif_USERNAME {
    description
      "Common node of ftp-client, rcp-client";
    leaf username {
      type string;
      description
        "Specify username for connections";
    }
  }

  grouping ncs_rpc_notif_SOURCE-INTERFACE {
    description
      "Common node of ftp-client, tftp-client,
       rcp-client";
    leaf source-interface {
      type xr:Interface-name;
      description
        "Specify interface for source address in
         connections";
    }
  }

  grouping live_ncs_USERNAME {
    description
      "Common node of ftp-client, rcp-client";
    leaf username {
      type string;
      description
        "Specify username for connections";
    }
  }

  grouping live_ncs_SOURCE-INTERFACE {
    description
      "Common node of ftp-client, tftp-client,
       rcp-client";
    leaf source-interface {
      type xr:Interface-name;
      description
        "Specify interface for source address in
         connections";
    }
  }

  grouping USERNAME {
    description
      "Common node of ftp-client, rcp-client";
    leaf username {
      type string;
      description
        "Specify username for connections";
    }
  }

  grouping SOURCE-INTERFACE {
    description
      "Common node of ftp-client, tftp-client,
       rcp-client";
    leaf source-interface {
      type xr:Interface-name;
      description
        "Specify interface for source address in
         connections";
    }
  }

  augment "/ncs:devices/ncs:device/ncs:config" {
    container rcp {
      tailf:ncs-device-type "netconf";
      tailf:display-when "not(../../ncs:module) or ../../ncs:module[ncs:name='Cisco-IOS-XR-ipv4-filesystems-cfg']";
      description
        "RCP configuration";
      container rcp-client {
        description
          "RCP client configuration";
        uses USERNAME;
        uses SOURCE-INTERFACE;
      }
    }
    container ftp {
      tailf:ncs-device-type "netconf";
      tailf:display-when "not(../../ncs:module) or ../../ncs:module[ncs:name='Cisco-IOS-XR-ipv4-filesystems-cfg']";
      description
        "ftp";
      container ftp-client {
        description
          "FTP client configuration";
        container vrfs {
          description
            "VRF table";
          list vrf {
            key "vrf-name";
            description
              "VRF specific data";
            leaf source-interface {
              type xr:Interface-name;
              description
                "Specify interface for source address in
                 connections";
            }
            leaf username {
              type string;
              description
                "Specify username for connections";
            }
            leaf anonymous-password {
              type string;
              description
                "Password for anonymous user (ftp server
                 dependent)";
            }
            leaf password {
              type xr:Proprietary-password;
              description
                "Specify password for ftp connnection";
            }
            leaf passive {
              type empty;
              description
                "Enable connect using passive mode";
            }
            leaf vrf-name {
              type xr:Cisco-ios-xr-string;
              description
                "Name of the VRF instance";
            }
          }
        }
        leaf passive {
          type empty;
          description
            "Enable connect using passive mode";
        }
        leaf password {
          type xr:Proprietary-password;
          description
            "Specify password for ftp connnection";
        }
        leaf anonymous-password {
          type string;
          description
            "Password for anonymous user (ftp server
             dependent)";
        }
        uses USERNAME;
        uses SOURCE-INTERFACE;
      }
    }
    container tftp {
      tailf:ncs-device-type "netconf";
      tailf:display-when "not(../../ncs:module) or ../../ncs:module[ncs:name='Cisco-IOS-XR-ipv4-filesystems-cfg']";
      description
        "tftp";
      container tftp-client {
        description
          "TFTP client configuration";
        container vrfs {
          description
            "VRF table";
          list vrf {
            key "vrf-name";
            description
              "VRF specific data";
            leaf source-interface {
              type xr:Interface-name;
              description
                "Specify interface for source address in
                 connections";
            }
            leaf retry {
              type uint32 {
                range "0..256";
              }
              description
                "Specify the number of retries when client
                 requests TFTP connections";
            }
            leaf timeout {
              type uint32 {
                range "0..256";
              }
              units "second";
              description
                "Specify the timeout for every TFTP connection
                 in seconds";
            }
            leaf vrf-name {
              type xr:Cisco-ios-xr-string;
              description
                "Name of the VRF instance";
            }
          }
        }
        leaf retry {
          type uint32 {
            range "0..256";
          }
          description
            "Specify the number of retries when client
             requests TFTP connections";
        }
        leaf timeout {
          type uint32 {
            range "0..256";
          }
          units "second";
          description
            "Specify the timeout for every TFTP connection
             in seconds";
        }
        uses SOURCE-INTERFACE;
      }
    }
  }
  augment "/ncs:devices/ncs:device/ncs:live-status" {
    container rcp {
      tailf:ncs-device-type "netconf";
      tailf:display-when "not(../../ncs:module) or ../../ncs:module[ncs:name='Cisco-IOS-XR-ipv4-filesystems-cfg'] or (../../ncs:live-status-protocol[not(ncs:capability)]) or (../../ncs:live-status-protocol/ncs:capability/ncs:module[.='Cisco-IOS-XR-ipv4-filesystems-cfg'])";
      description
        "RCP configuration";
      container rcp-client {
        description
          "RCP client configuration";
        uses live_ncs_USERNAME;
        uses live_ncs_SOURCE-INTERFACE;
      }
    }
    container ftp {
      tailf:ncs-device-type "netconf";
      tailf:display-when "not(../../ncs:module) or ../../ncs:module[ncs:name='Cisco-IOS-XR-ipv4-filesystems-cfg'] or (../../ncs:live-status-protocol[not(ncs:capability)]) or (../../ncs:live-status-protocol/ncs:capability/ncs:module[.='Cisco-IOS-XR-ipv4-filesystems-cfg'])";
      description
        "ftp";
      container ftp-client {
        description
          "FTP client configuration";
        container vrfs {
          description
            "VRF table";
          list vrf {
            key "vrf-name";
            description
              "VRF specific data";
            leaf source-interface {
              type xr:Interface-name;
              description
                "Specify interface for source address in
                 connections";
            }
            leaf username {
              type string;
              description
                "Specify username for connections";
            }
            leaf anonymous-password {
              type string;
              description
                "Password for anonymous user (ftp server
                 dependent)";
            }
            leaf password {
              type xr:Proprietary-password;
              description
                "Specify password for ftp connnection";
            }
            leaf passive {
              type empty;
              description
                "Enable connect using passive mode";
            }
            leaf vrf-name {
              type xr:Cisco-ios-xr-string;
              description
                "Name of the VRF instance";
            }
          }
        }
        leaf passive {
          type empty;
          description
            "Enable connect using passive mode";
        }
        leaf password {
          type xr:Proprietary-password;
          description
            "Specify password for ftp connnection";
        }
        leaf anonymous-password {
          type string;
          description
            "Password for anonymous user (ftp server
             dependent)";
        }
        uses live_ncs_USERNAME;
        uses live_ncs_SOURCE-INTERFACE;
      }
    }
    container tftp {
      tailf:ncs-device-type "netconf";
      tailf:display-when "not(../../ncs:module) or ../../ncs:module[ncs:name='Cisco-IOS-XR-ipv4-filesystems-cfg'] or (../../ncs:live-status-protocol[not(ncs:capability)]) or (../../ncs:live-status-protocol/ncs:capability/ncs:module[.='Cisco-IOS-XR-ipv4-filesystems-cfg'])";
      description
        "tftp";
      container tftp-client {
        description
          "TFTP client configuration";
        container vrfs {
          description
            "VRF table";
          list vrf {
            key "vrf-name";
            description
              "VRF specific data";
            leaf source-interface {
              type xr:Interface-name;
              description
                "Specify interface for source address in
                 connections";
            }
            leaf retry {
              type uint32 {
                range "0..256";
              }
              description
                "Specify the number of retries when client
                 requests TFTP connections";
            }
            leaf timeout {
              type uint32 {
                range "0..256";
              }
              units "second";
              description
                "Specify the timeout for every TFTP connection
                 in seconds";
            }
            leaf vrf-name {
              type xr:Cisco-ios-xr-string;
              description
                "Name of the VRF instance";
            }
          }
        }
        leaf retry {
          type uint32 {
            range "0..256";
          }
          description
            "Specify the number of retries when client
             requests TFTP connections";
        }
        leaf timeout {
          type uint32 {
            range "0..256";
          }
          units "second";
          description
            "Specify the timeout for every TFTP connection
             in seconds";
        }
        uses live_ncs_SOURCE-INTERFACE;
      }
    }
  }
  augment "/ncs:devices/ncs:template/ncs:ned-id/ncs:config" {
    container rcp {
      description
        "RCP configuration";
      container rcp-client {
        description
          "RCP client configuration";
        uses ncs_template_USERNAME;
        uses ncs_template_SOURCE-INTERFACE;
      }
    }
    container ftp {
      description
        "ftp";
      container ftp-client {
        description
          "FTP client configuration";
        container vrfs {
          description
            "VRF table";
          list vrf {
            // NCS patched for predictable order
            ordered-by user;
            key "vrf-name";
            description
              "VRF specific data";
            leaf source-interface {
              type string;
              description
                "Specify interface for source address in
                 connections";
            }
            leaf username {
              type string;
              description
                "Specify username for connections";
            }
            leaf anonymous-password {
              type string;
              description
                "Password for anonymous user (ftp server
                 dependent)";
            }
            leaf password {
              type string;
              description
                "Specify password for ftp connnection";
            }
            leaf passive {
              type empty;
              description
                "Enable connect using passive mode";
            }
            leaf vrf-name {
              type string;
              description
                "Name of the VRF instance";
            }
          }
        }
        leaf passive {
          type empty;
          description
            "Enable connect using passive mode";
        }
        leaf password {
          type string;
          description
            "Specify password for ftp connnection";
        }
        leaf anonymous-password {
          type string;
          description
            "Password for anonymous user (ftp server
             dependent)";
        }
        uses ncs_template_USERNAME;
        uses ncs_template_SOURCE-INTERFACE;
      }
    }
    container tftp {
      description
        "tftp";
      container tftp-client {
        description
          "TFTP client configuration";
        container vrfs {
          description
            "VRF table";
          list vrf {
            // NCS patched for predictable order
            ordered-by user;
            key "vrf-name";
            description
              "VRF specific data";
            leaf source-interface {
              type string;
              description
                "Specify interface for source address in
                 connections";
            }
            leaf retry {
              type string;
              description
                "Specify the number of retries when client
                 requests TFTP connections";
            }
            leaf timeout {
              type string;
              units "second";
              description
                "Specify the timeout for every TFTP connection
                 in seconds";
            }
            leaf vrf-name {
              type string;
              description
                "Name of the VRF instance";
            }
          }
        }
        leaf retry {
          type string;
          description
            "Specify the number of retries when client
             requests TFTP connections";
        }
        leaf timeout {
          type string;
          units "second";
          description
            "Specify the timeout for every TFTP connection
             in seconds";
        }
        uses ncs_template_SOURCE-INTERFACE;
      }
    }
  }
}
