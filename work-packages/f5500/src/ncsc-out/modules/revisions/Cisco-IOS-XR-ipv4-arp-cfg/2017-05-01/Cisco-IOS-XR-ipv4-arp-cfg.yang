module Cisco-IOS-XR-ipv4-arp-cfg {
  // Generated by yanger -t ncs
  tailf:mount-id f5500-nc-1.0:f5500-nc-1.0;
  tailf:ncs-device-type "netconf";

  namespace "http://cisco.com/ns/yang/Cisco-IOS-XR-ipv4-arp-cfg";
  prefix Cisco-IOS-XR-ipv4-arp-cfg;

  import ietf-inet-types {
    prefix inet;
  }
  import ietf-yang-types {
    prefix yang;
  }
  import Cisco-IOS-XR-types {
    prefix xr;
  }
  import Cisco-IOS-XR-ifmgr-cfg {
    prefix a1;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ipv4-arp package configuration.

     This module contains definitions
     for the following management objects:
       arp: ARP configuraiton
       iedge-cfg: iedge cfg
       arpgmp: arpgmp
       arp-redundancy: arp redundancy

     This YANG module augments the
       Cisco-IOS-XR-ifmgr-cfg
     module with configuration data.

     Copyright (c) 2013-2018 by Cisco Systems, Inc.
     All rights reserved.";

  revision 2017-05-01 {
    description
      "Fixing backward compatibility error in module.";
  }
  revision 2015-11-09 {
    description
      "IOS XR 6.0 revision.";
  }

  typedef Arp-encap {
    type enumeration {
      enum "arpa" {
        value 1;
        description
          "Encapsulation type ARPA";
      }
      enum "srp" {
        value 4;
        description
          "Encapsulation type SRP";
      }
      enum "srpa" {
        value 5;
        description
          "Encapsulation type SRPA";
      }
      enum "srpb" {
        value 6;
        description
          "Encapsulation type SRPB";
      }
    }
    description
      "Arp encap";
  }

  typedef Arp-entry {
    type enumeration {
      enum "static" {
        value 0;
        description
          "Static ARP entry type";
      }
      enum "alias" {
        value 1;
        description
          "Alias ARP entry type";
      }
    }
    description
      "Arp entry";
  }

  augment "/ncs:devices/ncs:device/ncs:config" {
    container arp {
      tailf:ncs-device-type "netconf";
      tailf:display-when "not(../../ncs:module) or ../../ncs:module[ncs:name='Cisco-IOS-XR-ipv4-arp-cfg']";
      description
        "ARP configuraiton";
      leaf max-entries {
        type uint32 {
          range "1..256000";
        }
        description
          "Configure maximum number of safe ARP entries per
           line card";
      }
      leaf inner-cos {
        type uint32 {
          range "0..7";
        }
        description
          "Configure inner cos values for arp packets";
      }
      leaf outer-cos {
        type uint32 {
          range "0..7";
        }
        description
          "Configure outer cos values for arp packets";
      }
    }
    container iedge-cfg {
      tailf:ncs-device-type "netconf";
      tailf:display-when "not(../../ncs:module) or ../../ncs:module[ncs:name='Cisco-IOS-XR-ipv4-arp-cfg']";
      description
        "iedge cfg";
      leaf subscriber-uncond-proxy {
        type empty;
        description
          "ARP Subscriber Enable Unconditional Proxy ARP";
      }
      leaf subscriber-scale-mode {
        type empty;
        description
          "ARP Subscriber Scale Mode Configuration";
      }
    }
    container arpgmp {
      tailf:ncs-device-type "netconf";
      tailf:display-when "not(../../ncs:module) or ../../ncs:module[ncs:name='Cisco-IOS-XR-ipv4-arp-cfg']";
      description
        "arpgmp";
      list vrf {
        key "vrf-name";
        description
          "Per VRF configuration, for the default VRF use
           'default'";
        container entries {
          description
            "ARP static and alias entry configuration";
          list entry {
            key "address";
            description
              "ARP static and alias entry configuration item";
            leaf address {
              type inet:ipv4-address-no-zone;
              description
                "IP Address";
            }
            leaf mac-address {
              type yang:mac-address;
              description
                "MAC Address";
            }
            leaf encapsulation {
              type Arp-encap;
              description
                "Encapsulation type";
            }
            leaf entry-type {
              type Arp-entry;
              description
                "Entry type";
            }
            leaf interface {
              type xr:Interface-name;
              description
                "Interface name";
            }
          }
        }
        leaf vrf-name {
          type xr:Cisco-ios-xr-string;
          description
            "VRF name";
        }
      }
    }
    container arp-redundancy {
      tailf:ncs-device-type "netconf";
      tailf:display-when "not(../../ncs:module) or ../../ncs:module[ncs:name='Cisco-IOS-XR-ipv4-arp-cfg']";
      description
        "arp redundancy";
      container redundancy {
        presence "Indicates a redundancy node is configured.";
        description
          "Configure parameter for ARP Geo redundancy";
        container groups {
          description
            "Table of Group";
          list group {
            key "group-id";
            description
              "None";
            container peers {
              description
                "Table of Peer";
              list peer {
                key "prefix-string";
                description
                  "None";
                leaf prefix-string {
                  type inet:ip-address-no-zone;
                  description
                    "Neighbor IPv4 address";
                }
              }
            }
            container interface-list {
              presence "Indicates a interface-list node is configured.";
              description
                "List of Interfaces for this Group";
              container interfaces {
                description
                  "Table of Interface";
                list interface {
                  key "interface-name";
                  description
                    "Interface for this Group";
                  leaf interface-name {
                    type xr:Interface-name;
                    description
                      "Interface name";
                  }
                  leaf interface-id {
                    type uint32 {
                      range "1..65535";
                    }
                    mandatory true;
                    description
                      "Interface Id for the interface";
                  }
                }
              }
              leaf enable {
                type empty;
                mandatory true;
                description
                  "Enable List of Interfaces for this Group.
                   Deletion of this object also causes deletion
                   of all associated objects under
                   InterfaceList.";
              }
            }
            leaf source-interface {
              type xr:Interface-name;
              description
                "Interface name";
            }
            leaf group-id {
              type uint32 {
                range "1..32";
              }
              description
                "Group ID";
            }
          }
        }
        leaf enable {
          type empty;
          mandatory true;
          description
            "Enable Configure parameter for ARP Geo
             redundancy. Deletion of this object also causes
             deletion of all associated objects under
             ArpRedundancy.";
        }
      }
    }
  }
  augment "/ncs:devices/ncs:device/ncs:live-status" {
    container arp {
      tailf:ncs-device-type "netconf";
      tailf:display-when "not(../../ncs:module) or ../../ncs:module[ncs:name='Cisco-IOS-XR-ipv4-arp-cfg'] or (../../ncs:live-status-protocol[not(ncs:capability)]) or (../../ncs:live-status-protocol/ncs:capability/ncs:module[.='Cisco-IOS-XR-ipv4-arp-cfg'])";
      description
        "ARP configuraiton";
      leaf max-entries {
        type uint32 {
          range "1..256000";
        }
        description
          "Configure maximum number of safe ARP entries per
           line card";
      }
      leaf inner-cos {
        type uint32 {
          range "0..7";
        }
        description
          "Configure inner cos values for arp packets";
      }
      leaf outer-cos {
        type uint32 {
          range "0..7";
        }
        description
          "Configure outer cos values for arp packets";
      }
    }
    container iedge-cfg {
      tailf:ncs-device-type "netconf";
      tailf:display-when "not(../../ncs:module) or ../../ncs:module[ncs:name='Cisco-IOS-XR-ipv4-arp-cfg'] or (../../ncs:live-status-protocol[not(ncs:capability)]) or (../../ncs:live-status-protocol/ncs:capability/ncs:module[.='Cisco-IOS-XR-ipv4-arp-cfg'])";
      description
        "iedge cfg";
      leaf subscriber-uncond-proxy {
        type empty;
        description
          "ARP Subscriber Enable Unconditional Proxy ARP";
      }
      leaf subscriber-scale-mode {
        type empty;
        description
          "ARP Subscriber Scale Mode Configuration";
      }
    }
    container arpgmp {
      tailf:ncs-device-type "netconf";
      tailf:display-when "not(../../ncs:module) or ../../ncs:module[ncs:name='Cisco-IOS-XR-ipv4-arp-cfg'] or (../../ncs:live-status-protocol[not(ncs:capability)]) or (../../ncs:live-status-protocol/ncs:capability/ncs:module[.='Cisco-IOS-XR-ipv4-arp-cfg'])";
      description
        "arpgmp";
      list vrf {
        key "vrf-name";
        description
          "Per VRF configuration, for the default VRF use
           'default'";
        container entries {
          description
            "ARP static and alias entry configuration";
          list entry {
            key "address";
            description
              "ARP static and alias entry configuration item";
            leaf address {
              type inet:ipv4-address-no-zone;
              description
                "IP Address";
            }
            leaf mac-address {
              type yang:mac-address;
              description
                "MAC Address";
            }
            leaf encapsulation {
              type Arp-encap;
              description
                "Encapsulation type";
            }
            leaf entry-type {
              type Arp-entry;
              description
                "Entry type";
            }
            leaf interface {
              type xr:Interface-name;
              description
                "Interface name";
            }
          }
        }
        leaf vrf-name {
          type xr:Cisco-ios-xr-string;
          description
            "VRF name";
        }
      }
    }
    container arp-redundancy {
      tailf:ncs-device-type "netconf";
      tailf:display-when "not(../../ncs:module) or ../../ncs:module[ncs:name='Cisco-IOS-XR-ipv4-arp-cfg'] or (../../ncs:live-status-protocol[not(ncs:capability)]) or (../../ncs:live-status-protocol/ncs:capability/ncs:module[.='Cisco-IOS-XR-ipv4-arp-cfg'])";
      description
        "arp redundancy";
      container redundancy {
        presence "Indicates a redundancy node is configured.";
        description
          "Configure parameter for ARP Geo redundancy";
        container groups {
          description
            "Table of Group";
          list group {
            key "group-id";
            description
              "None";
            container peers {
              description
                "Table of Peer";
              list peer {
                key "prefix-string";
                description
                  "None";
                leaf prefix-string {
                  type inet:ip-address-no-zone;
                  description
                    "Neighbor IPv4 address";
                }
              }
            }
            container interface-list {
              presence "Indicates a interface-list node is configured.";
              description
                "List of Interfaces for this Group";
              container interfaces {
                description
                  "Table of Interface";
                list interface {
                  key "interface-name";
                  description
                    "Interface for this Group";
                  leaf interface-name {
                    type xr:Interface-name;
                    description
                      "Interface name";
                  }
                  leaf interface-id {
                    type uint32 {
                      range "1..65535";
                    }
                    // NCS drop mandatory statement
                    description
                      "Interface Id for the interface";
                  }
                }
              }
              leaf enable {
                type empty;
                // NCS drop mandatory statement
                description
                  "Enable List of Interfaces for this Group.
                   Deletion of this object also causes deletion
                   of all associated objects under
                   InterfaceList.";
              }
            }
            leaf source-interface {
              type xr:Interface-name;
              description
                "Interface name";
            }
            leaf group-id {
              type uint32 {
                range "1..32";
              }
              description
                "Group ID";
            }
          }
        }
        leaf enable {
          type empty;
          // NCS drop mandatory statement
          description
            "Enable Configure parameter for ARP Geo
             redundancy. Deletion of this object also causes
             deletion of all associated objects under
             ArpRedundancy.";
        }
      }
    }
  }
  augment "/ncs:devices/ncs:template/ncs:ned-id/ncs:config" {
    container arp {
      description
        "ARP configuraiton";
      leaf max-entries {
        type string;
        description
          "Configure maximum number of safe ARP entries per
           line card";
      }
      leaf inner-cos {
        type string;
        description
          "Configure inner cos values for arp packets";
      }
      leaf outer-cos {
        type string;
        description
          "Configure outer cos values for arp packets";
      }
    }
    container iedge-cfg {
      description
        "iedge cfg";
      leaf subscriber-uncond-proxy {
        type empty;
        description
          "ARP Subscriber Enable Unconditional Proxy ARP";
      }
      leaf subscriber-scale-mode {
        type empty;
        description
          "ARP Subscriber Scale Mode Configuration";
      }
    }
    container arpgmp {
      description
        "arpgmp";
      list vrf {
        // NCS patched for predictable order
        ordered-by user;
        key "vrf-name";
        description
          "Per VRF configuration, for the default VRF use
           'default'";
        container entries {
          description
            "ARP static and alias entry configuration";
          list entry {
            // NCS patched for predictable order
            ordered-by user;
            key "address";
            description
              "ARP static and alias entry configuration item";
            leaf address {
              type string;
              description
                "IP Address";
            }
            leaf mac-address {
              type string;
              description
                "MAC Address";
            }
            leaf encapsulation {
              type string;
              description
                "Encapsulation type";
            }
            leaf entry-type {
              type string;
              description
                "Entry type";
            }
            leaf interface {
              type string;
              description
                "Interface name";
            }
          }
        }
        leaf vrf-name {
          type string;
          description
            "VRF name";
        }
      }
    }
    container arp-redundancy {
      description
        "arp redundancy";
      container redundancy {
        presence "Indicates a redundancy node is configured.";
        description
          "Configure parameter for ARP Geo redundancy";
        container groups {
          description
            "Table of Group";
          list group {
            // NCS patched for predictable order
            ordered-by user;
            key "group-id";
            description
              "None";
            container peers {
              description
                "Table of Peer";
              list peer {
                // NCS patched for predictable order
                ordered-by user;
                key "prefix-string";
                description
                  "None";
                leaf prefix-string {
                  type string;
                  description
                    "Neighbor IPv4 address";
                }
              }
            }
            container interface-list {
              presence "Indicates a interface-list node is configured.";
              description
                "List of Interfaces for this Group";
              container interfaces {
                description
                  "Table of Interface";
                list interface {
                  // NCS patched for predictable order
                  ordered-by user;
                  key "interface-name";
                  description
                    "Interface for this Group";
                  leaf interface-name {
                    type string;
                    description
                      "Interface name";
                  }
                  leaf interface-id {
                    type string;
                    // NCS drop mandatory statement
                    description
                      "Interface Id for the interface";
                  }
                }
              }
              leaf enable {
                type empty;
                // NCS drop mandatory statement
                description
                  "Enable List of Interfaces for this Group.
                   Deletion of this object also causes deletion
                   of all associated objects under
                   InterfaceList.";
              }
            }
            leaf source-interface {
              type string;
              description
                "Interface name";
            }
            leaf group-id {
              type string;
              description
                "Group ID";
            }
          }
        }
        leaf enable {
          type empty;
          // NCS drop mandatory statement
          description
            "Enable Configure parameter for ARP Geo
             redundancy. Deletion of this object also causes
             deletion of all associated objects under
             ArpRedundancy.";
        }
      }
    }
  }
  augment "/ncs:devices/ncs:template/ncs:ned-id/ncs:config/a1:interface-configurations/a1:interface-configuration" {
    container dagrs {
      description
        "Direct-Attached Gateway Redundancy configuration";
      list dagr {
        // NCS patched for predictable order
        ordered-by user;
        key "ip-addr";
        description
          "The DAGR entry being configured";
        container sub {
          description
            "DAGR Submode configuration";
          container metric {
            description
              "Set Route Metric";
            leaf metric-norm {
              type string;
              // NCS drop default statement
              description
                "Normal Route Metric";
            }
            leaf metric-prio {
              type string;
              // NCS drop default statement
              description
                "Priority Route Metric";
            }
          }
          container timers {
            description
              "Set Query Timers";
            leaf query-time {
              type string;
              // NCS drop default statement
              description
                "Query Timeout";
            }
            leaf sby-time {
              type string;
              // NCS drop default statement
              description
                "Standby Query Timeout";
            }
          }
          container distance {
            description
              "Set Route Distance";
            leaf dist-norm {
              type string;
              // NCS drop default statement
              description
                "Normal Route Distance";
            }
            leaf dist-prio {
              type string;
              // NCS drop default statement
              description
                "Priority Route Distance";
            }
          }
          leaf priority-timeout {
            type string;
            // NCS drop default statement
            description
              "Priority Timeout value";
          }
        }
        leaf enter {
          type empty;
          description
            "DAGR Group Enter item";
        }
        leaf ip-addr {
          type string;
          description
            "DAGR Peer IPv4 address";
        }
      }
    }
    description
      "This augment extends the configuration data of
       'Cisco-IOS-XR-ifmgr-cfg'";
  }
  augment "/ncs:devices/ncs:device/ncs:live-status/a1:interface-configurations/a1:interface-configuration" {
    container dagrs {
      tailf:ncs-device-type "netconf";
      tailf:display-when "not(../../../../ncs:module) or ../../../../ncs:module[ncs:name='Cisco-IOS-XR-ipv4-arp-cfg'] or (../../../../ncs:live-status-protocol[not(ncs:capability)]) or (../../../../ncs:live-status-protocol/ncs:capability/ncs:module[.='Cisco-IOS-XR-ipv4-arp-cfg'])";
      description
        "Direct-Attached Gateway Redundancy configuration";
      list dagr {
        key "ip-addr";
        description
          "The DAGR entry being configured";
        container sub {
          description
            "DAGR Submode configuration";
          container metric {
            description
              "Set Route Metric";
            leaf metric-norm {
              type uint32 {
                range "0..256";
              }
              // NCS drop default statement
              description
                "Normal Route Metric";
            }
            leaf metric-prio {
              type uint32 {
                range "0..256";
              }
              // NCS drop default statement
              description
                "Priority Route Metric";
            }
          }
          container timers {
            description
              "Set Query Timers";
            leaf query-time {
              type uint32 {
                range "1..10000";
              }
              // NCS drop default statement
              description
                "Query Timeout";
            }
            leaf sby-time {
              type uint32 {
                range "1..10000";
              }
              // NCS drop default statement
              description
                "Standby Query Timeout";
            }
          }
          container distance {
            description
              "Set Route Distance";
            leaf dist-norm {
              type uint32 {
                range "0..256";
              }
              // NCS drop default statement
              description
                "Normal Route Distance";
            }
            leaf dist-prio {
              type uint32 {
                range "0..256";
              }
              // NCS drop default statement
              description
                "Priority Route Distance";
            }
          }
          leaf priority-timeout {
            type uint32 {
              range "1..10000";
            }
            // NCS drop default statement
            description
              "Priority Timeout value";
          }
        }
        leaf enter {
          type empty;
          description
            "DAGR Group Enter item";
        }
        leaf ip-addr {
          type inet:ipv4-address-no-zone;
          description
            "DAGR Peer IPv4 address";
        }
      }
    }
    description
      "This augment extends the configuration data of
       'Cisco-IOS-XR-ifmgr-cfg'";
  }
  augment "/ncs:devices/ncs:device/ncs:config/a1:interface-configurations/a1:interface-configuration" {
    container dagrs {
      tailf:ncs-device-type "netconf";
      tailf:display-when "not(../../../../ncs:module) or ../../../../ncs:module[ncs:name='Cisco-IOS-XR-ipv4-arp-cfg']";
      description
        "Direct-Attached Gateway Redundancy configuration";
      list dagr {
        key "ip-addr";
        description
          "The DAGR entry being configured";
        container sub {
          description
            "DAGR Submode configuration";
          container metric {
            description
              "Set Route Metric";
            leaf metric-norm {
              type uint32 {
                range "0..256";
              }
              default "100";
              description
                "Normal Route Metric";
            }
            leaf metric-prio {
              type uint32 {
                range "0..256";
              }
              default "90";
              description
                "Priority Route Metric";
            }
          }
          container timers {
            description
              "Set Query Timers";
            leaf query-time {
              type uint32 {
                range "1..10000";
              }
              default "1";
              description
                "Query Timeout";
            }
            leaf sby-time {
              type uint32 {
                range "1..10000";
              }
              default "20";
              description
                "Standby Query Timeout";
            }
          }
          container distance {
            description
              "Set Route Distance";
            leaf dist-norm {
              type uint32 {
                range "0..256";
              }
              default "150";
              description
                "Normal Route Distance";
            }
            leaf dist-prio {
              type uint32 {
                range "0..256";
              }
              default "5";
              description
                "Priority Route Distance";
            }
          }
          leaf priority-timeout {
            type uint32 {
              range "1..10000";
            }
            default "20";
            description
              "Priority Timeout value";
          }
        }
        leaf enter {
          type empty;
          description
            "DAGR Group Enter item";
        }
        leaf ip-addr {
          type inet:ipv4-address-no-zone;
          description
            "DAGR Peer IPv4 address";
        }
      }
    }
    description
      "This augment extends the configuration data of
       'Cisco-IOS-XR-ifmgr-cfg'";
  }
  augment "/ncs:devices/ncs:template/ncs:ned-id/ncs:config/a1:interface-configurations/a1:interface-configuration" {
    container ipv4arp {
      description
        "Configure Address Resolution Protocol";
      leaf learning-local {
        type empty;
        description
          "Enable the dynamic learning of ARP entries(for
           local subnet) on the interface";
      }
      leaf drop-adj-timeout {
        type string;
        units "second";
        // NCS drop default statement
        description
          "Number of seconds for ARP drop adjacency
           timeout";
      }
      leaf learning-solicited {
        type empty;
        description
          "ARP learning solicited configuration";
      }
      leaf gratuitous-ignore {
        type empty;
        description
          "Ignore the receipt of Gratuitous ARP packets on
           the interface";
      }
      leaf proxy-arp {
        type empty;
        description
          "Proxy ARP configuration";
      }
      leaf purge-delay {
        type string;
        description
          "Time to delay purging arp entries when the
           interface goes down";
      }
      leaf learning-disable {
        type empty;
        description
          "Disable the dynamic learning of ARP entries on
           the interface";
      }
      leaf local-proxy-arp {
        type empty;
        description
          "Local Proxy ARP configuration";
      }
      leaf timeout {
        type string;
        units "second";
        description
          "Number of seconds for ARP cache timeout";
      }
    }
    description
      "This augment extends the configuration data of
       'Cisco-IOS-XR-ifmgr-cfg'";
  }
  augment "/ncs:devices/ncs:device/ncs:live-status/a1:interface-configurations/a1:interface-configuration" {
    container ipv4arp {
      tailf:ncs-device-type "netconf";
      tailf:display-when "not(../../../../ncs:module) or ../../../../ncs:module[ncs:name='Cisco-IOS-XR-ipv4-arp-cfg'] or (../../../../ncs:live-status-protocol[not(ncs:capability)]) or (../../../../ncs:live-status-protocol/ncs:capability/ncs:module[.='Cisco-IOS-XR-ipv4-arp-cfg'])";
      description
        "Configure Address Resolution Protocol";
      leaf learning-local {
        type empty;
        description
          "Enable the dynamic learning of ARP entries(for
           local subnet) on the interface";
      }
      leaf drop-adj-timeout {
        type uint32 {
          range "900..7200";
        }
        units "second";
        // NCS drop default statement
        description
          "Number of seconds for ARP drop adjacency
           timeout";
      }
      leaf learning-solicited {
        type empty;
        description
          "ARP learning solicited configuration";
      }
      leaf gratuitous-ignore {
        type empty;
        description
          "Ignore the receipt of Gratuitous ARP packets on
           the interface";
      }
      leaf proxy-arp {
        type empty;
        description
          "Proxy ARP configuration";
      }
      leaf purge-delay {
        type uint32 {
          range "1..65535";
        }
        description
          "Time to delay purging arp entries when the
           interface goes down";
      }
      leaf learning-disable {
        type empty;
        description
          "Disable the dynamic learning of ARP entries on
           the interface";
      }
      leaf local-proxy-arp {
        type empty;
        description
          "Local Proxy ARP configuration";
      }
      leaf timeout {
        type uint32 {
          range "30..2144448000";
        }
        units "second";
        description
          "Number of seconds for ARP cache timeout";
      }
    }
    description
      "This augment extends the configuration data of
       'Cisco-IOS-XR-ifmgr-cfg'";
  }
  augment "/ncs:devices/ncs:device/ncs:config/a1:interface-configurations/a1:interface-configuration" {
    container ipv4arp {
      tailf:ncs-device-type "netconf";
      tailf:display-when "not(../../../../ncs:module) or ../../../../ncs:module[ncs:name='Cisco-IOS-XR-ipv4-arp-cfg']";
      description
        "Configure Address Resolution Protocol";
      leaf learning-local {
        type empty;
        description
          "Enable the dynamic learning of ARP entries(for
           local subnet) on the interface";
      }
      leaf drop-adj-timeout {
        type uint32 {
          range "900..7200";
        }
        units "second";
        default "3600";
        description
          "Number of seconds for ARP drop adjacency
           timeout";
      }
      leaf learning-solicited {
        type empty;
        description
          "ARP learning solicited configuration";
      }
      leaf gratuitous-ignore {
        type empty;
        description
          "Ignore the receipt of Gratuitous ARP packets on
           the interface";
      }
      leaf proxy-arp {
        type empty;
        description
          "Proxy ARP configuration";
      }
      leaf purge-delay {
        type uint32 {
          range "1..65535";
        }
        description
          "Time to delay purging arp entries when the
           interface goes down";
      }
      leaf learning-disable {
        type empty;
        description
          "Disable the dynamic learning of ARP entries on
           the interface";
      }
      leaf local-proxy-arp {
        type empty;
        description
          "Local Proxy ARP configuration";
      }
      leaf timeout {
        type uint32 {
          range "30..2144448000";
        }
        units "second";
        description
          "Number of seconds for ARP cache timeout";
      }
    }
    description
      "This augment extends the configuration data of
       'Cisco-IOS-XR-ifmgr-cfg'";
  }
}
