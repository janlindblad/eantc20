module Cisco-IOS-XR-dot1x-cfg {
  // Generated by yanger -t ncs
  tailf:mount-id f5500-nc-1.0:f5500-nc-1.0;
  tailf:ncs-device-type "netconf";

  namespace "http://cisco.com/ns/yang/Cisco-IOS-XR-dot1x-cfg";
  prefix Cisco-IOS-XR-dot1x-cfg;

  import Cisco-IOS-XR-types {
    prefix xr;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR dot1x package configuration.

     This module contains definitions
     for the following management objects:
       dot1x: Global Dot1x Configuration
       eap: eap

     Copyright (c) 2013-2018 by Cisco Systems, Inc.
     All rights reserved.";

  revision 2015-11-09 {
    description
      "IOS XR 6.0 revision.";
  }

  typedef Dot1x-server-dead-action {
    type enumeration {
      enum "auth-fail" {
        value 0;
        description
          "server dead action auth-fail";
      }
      enum "auth-retry" {
        value 1;
        description
          "server dead action auth-retry";
      }
    }
    description
      "Dot1x server dead action";
  }

  typedef Dot1x-reauth-local-interval {
    type uint32 {
      range "60..5184000";
    }
    description
      "Dot1x reauth local interval";
  }

  typedef Dot1xpae {
    type string {
      pattern '(supplicant)|(authenticator)|(both)';
    }
    description
      "supplicant:PAE Type as Supplicant, authenticator:
       PAE type as Authenticator, both: PAE type as
       Supplicant & Authenticator";
  }

  augment "/ncs:devices/ncs:device/ncs:config" {
    container dot1x {
      tailf:ncs-device-type "netconf";
      tailf:display-when "not(../../ncs:module) or ../../ncs:module[ncs:name='Cisco-IOS-XR-dot1x-cfg']";
      description
        "Global Dot1x Configuration";
      list dot1x-profile {
        key "profile-name";
        description
          "Global Dot1x Profile Name";
        container supplicant {
          description
            "Dot1x Supplicant Related Configuration";
          leaf eap-profile {
            type string {
              length "1..63";
            }
            description
              "EAP Profile for Supplicant";
          }
        }
        container authenticator {
          description
            "Dot1x Authenticator Related Configuration";
          container timers {
            description
              "Timers for Authenticator";
            container reauth-time {
              description
                "After this time ReAuthentication will be
                 trigerred";
              leaf server {
                type boolean;
                description
                  "Reauth will be triggerred based on the EAP
                   server configuration";
              }
              leaf local {
                type Dot1x-reauth-local-interval;
                units "second";
                description
                  "Reauth will be triggerred based on the
                   configuration in box";
              }
            }
          }
          leaf eap-profile {
            type string {
              length "1..63";
            }
            description
              "EAP Profile for Local EAP Server";
          }
          leaf server-dead {
            type Dot1x-server-dead-action;
            description
              "dot1x authenticator action on AAA server
               unreachability";
          }
        }
        leaf pae {
          type Dot1xpae;
          description
            "Dot1x PAE (Port Access Entity) Role";
        }
        leaf profile-name {
          type xr:Cisco-ios-xr-string {
            length "1..63";
          }
          description
            "Name of the Dot1x Profile";
        }
      }
    }
    container eap {
      tailf:ncs-device-type "netconf";
      tailf:display-when "not(../../ncs:module) or ../../ncs:module[ncs:name='Cisco-IOS-XR-dot1x-cfg']";
      description
        "eap";
      list eap-profile {
        key "profile-name";
        description
          "Global EAP Profile Configuration";
        container eaptls {
          description
            "EAP TLS Configuration";
          leaf pki-trustpoint {
            type xr:Cisco-ios-xr-string {
              length "1..63";
            }
            description
              "Configure PKI Trustpoint";
          }
        }
        leaf allow-eap-tls1-0 {
          type empty;
          description
            "Configure backward compatibility for TLS 1.0";
        }
        leaf identity {
          type string {
            length "1..63";
          }
          description
            "Configure EAP Identity/UserName";
        }
        leaf profile-name {
          type xr:Cisco-ios-xr-string {
            length "1..63";
          }
          description
            "Name of the EAP Profile";
        }
      }
    }
  }
  augment "/ncs:devices/ncs:device/ncs:live-status" {
    container dot1x {
      tailf:ncs-device-type "netconf";
      tailf:display-when "not(../../ncs:module) or ../../ncs:module[ncs:name='Cisco-IOS-XR-dot1x-cfg'] or (../../ncs:live-status-protocol[not(ncs:capability)]) or (../../ncs:live-status-protocol/ncs:capability/ncs:module[.='Cisco-IOS-XR-dot1x-cfg'])";
      description
        "Global Dot1x Configuration";
      list dot1x-profile {
        key "profile-name";
        description
          "Global Dot1x Profile Name";
        container supplicant {
          description
            "Dot1x Supplicant Related Configuration";
          leaf eap-profile {
            type string {
              length "1..63";
            }
            description
              "EAP Profile for Supplicant";
          }
        }
        container authenticator {
          description
            "Dot1x Authenticator Related Configuration";
          container timers {
            description
              "Timers for Authenticator";
            container reauth-time {
              description
                "After this time ReAuthentication will be
                 trigerred";
              leaf server {
                type boolean;
                description
                  "Reauth will be triggerred based on the EAP
                   server configuration";
              }
              leaf local {
                type Dot1x-reauth-local-interval;
                units "second";
                description
                  "Reauth will be triggerred based on the
                   configuration in box";
              }
            }
          }
          leaf eap-profile {
            type string {
              length "1..63";
            }
            description
              "EAP Profile for Local EAP Server";
          }
          leaf server-dead {
            type Dot1x-server-dead-action;
            description
              "dot1x authenticator action on AAA server
               unreachability";
          }
        }
        leaf pae {
          type Dot1xpae;
          description
            "Dot1x PAE (Port Access Entity) Role";
        }
        leaf profile-name {
          type xr:Cisco-ios-xr-string {
            length "1..63";
          }
          description
            "Name of the Dot1x Profile";
        }
      }
    }
    container eap {
      tailf:ncs-device-type "netconf";
      tailf:display-when "not(../../ncs:module) or ../../ncs:module[ncs:name='Cisco-IOS-XR-dot1x-cfg'] or (../../ncs:live-status-protocol[not(ncs:capability)]) or (../../ncs:live-status-protocol/ncs:capability/ncs:module[.='Cisco-IOS-XR-dot1x-cfg'])";
      description
        "eap";
      list eap-profile {
        key "profile-name";
        description
          "Global EAP Profile Configuration";
        container eaptls {
          description
            "EAP TLS Configuration";
          leaf pki-trustpoint {
            type xr:Cisco-ios-xr-string {
              length "1..63";
            }
            description
              "Configure PKI Trustpoint";
          }
        }
        leaf allow-eap-tls1-0 {
          type empty;
          description
            "Configure backward compatibility for TLS 1.0";
        }
        leaf identity {
          type string {
            length "1..63";
          }
          description
            "Configure EAP Identity/UserName";
        }
        leaf profile-name {
          type xr:Cisco-ios-xr-string {
            length "1..63";
          }
          description
            "Name of the EAP Profile";
        }
      }
    }
  }
  augment "/ncs:devices/ncs:template/ncs:ned-id/ncs:config" {
    container dot1x {
      description
        "Global Dot1x Configuration";
      list dot1x-profile {
        // NCS patched for predictable order
        ordered-by user;
        key "profile-name";
        description
          "Global Dot1x Profile Name";
        container supplicant {
          description
            "Dot1x Supplicant Related Configuration";
          leaf eap-profile {
            type string;
            description
              "EAP Profile for Supplicant";
          }
        }
        container authenticator {
          description
            "Dot1x Authenticator Related Configuration";
          container timers {
            description
              "Timers for Authenticator";
            container reauth-time {
              description
                "After this time ReAuthentication will be
                 trigerred";
              leaf server {
                type string;
                description
                  "Reauth will be triggerred based on the EAP
                   server configuration";
              }
              leaf local {
                type string;
                units "second";
                description
                  "Reauth will be triggerred based on the
                   configuration in box";
              }
            }
          }
          leaf eap-profile {
            type string;
            description
              "EAP Profile for Local EAP Server";
          }
          leaf server-dead {
            type string;
            description
              "dot1x authenticator action on AAA server
               unreachability";
          }
        }
        leaf pae {
          type string;
          description
            "Dot1x PAE (Port Access Entity) Role";
        }
        leaf profile-name {
          type string;
          description
            "Name of the Dot1x Profile";
        }
      }
    }
    container eap {
      description
        "eap";
      list eap-profile {
        // NCS patched for predictable order
        ordered-by user;
        key "profile-name";
        description
          "Global EAP Profile Configuration";
        container eaptls {
          description
            "EAP TLS Configuration";
          leaf pki-trustpoint {
            type string;
            description
              "Configure PKI Trustpoint";
          }
        }
        leaf allow-eap-tls1-0 {
          type empty;
          description
            "Configure backward compatibility for TLS 1.0";
        }
        leaf identity {
          type string;
          description
            "Configure EAP Identity/UserName";
        }
        leaf profile-name {
          type string;
          description
            "Name of the EAP Profile";
        }
      }
    }
  }
}
