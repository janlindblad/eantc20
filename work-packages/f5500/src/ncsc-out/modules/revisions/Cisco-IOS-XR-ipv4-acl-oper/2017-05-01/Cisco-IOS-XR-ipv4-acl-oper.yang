module Cisco-IOS-XR-ipv4-acl-oper {
  // Generated by yanger -t ncs
  tailf:mount-id f5500-nc-1.0:f5500-nc-1.0;
  tailf:ncs-device-type "netconf";

  namespace "http://cisco.com/ns/yang/Cisco-IOS-XR-ipv4-acl-oper";
  prefix Cisco-IOS-XR-ipv4-acl-oper;

  import Cisco-IOS-XR-types {
    prefix xr;
  }
  import Cisco-IOS-XR-common-acl-datatypes {
    prefix dt1;
  }
  include Cisco-IOS-XR-ipv4-acl-oper-sub1 {
    revision-date 2017-05-01;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ipv4-acl package operational data.

     This module contains definitions
     for the following management objects:
       ipv4-acl-and-prefix-list: Root class of IPv4 Oper schema tree

     Copyright (c) 2013-2018 by Cisco Systems, Inc.
     All rights reserved.";

  revision 2017-05-01 {
    description
      "Fixing backward compatibility error in module.";
  }
  revision 2015-11-09 {
    description
      "IOS XR 6.0 revision.";
  }

  augment "/ncs:devices/ncs:device/ncs:config" {
    // NCS drop config false container 'ipv4-acl-and-prefix-list'
  }
  augment "/ncs:devices/ncs:device/ncs:live-status" {
    container ipv4-acl-and-prefix-list {
      tailf:ncs-device-type "netconf";
      tailf:display-when "not(../../ncs:module) or ../../ncs:module[ncs:name='Cisco-IOS-XR-ipv4-acl-oper'] or (../../ncs:live-status-protocol[not(ncs:capability)]) or (../../ncs:live-status-protocol/ncs:capability/ncs:module[.='Cisco-IOS-XR-ipv4-acl-oper'])";
      description
        "Root class of IPv4 Oper schema tree";
      container access-list-manager {
        description
          "Access list manager containing access lists and
           prefix lists";
        container prefixes {
          description
            "Table of prefix lists";
          list prefix {
            key "prefix-list-name";
            description
              "Name of the prefix list";
            container prefix-list-sequences {
              description
                "Table of all the SequenceNumbers per prefix
                 list";
              list prefix-list-sequence {
                key "sequence-number";
                description
                  "Sequence Number of a prefix list entry";
                leaf sequence-number {
                  type dt1:Acl-sequence-number-range;
                  description
                    "Sequence Number of the prefix list entry";
                }
                uses live_ncs_IPV4-PFX-EDM-ACE;
              }
            }
            leaf prefix-list-name {
              type string;
              description
                "Name of the prefix list";
            }
          }
        }
        container accesses {
          description
            "Access listL class displaying Usage and Entries";
          list access {
            key "access-list-name";
            description
              "Name of the Access List";
            container access-list-sequences {
              description
                "Table of all the SequenceNumbers per access
                 list";
              list access-list-sequence {
                key "sequence-number";
                description
                  "Sequence Number of an access list entry";
                leaf sequence-number {
                  type dt1:Acl-sequence-number-range;
                  description
                    "ACLEntry Sequence Number";
                }
                uses live_ncs_IPV4-ACL-EDM-ACE;
              }
            }
            container object-group {
              description
                "Object Group in an Access list";
              uses live_ncs_IPV4-ACL-EDM-OBJGRP;
            }
            leaf access-list-name {
              type string;
              description
                "Name of the Access List";
            }
          }
        }
        container usages {
          description
            "Table of Usage statistics of access lists at
             different nodes";
          list usage {
            description
              "Usage statistics of an access list at a node";
            leaf node-name {
              type xr:Node-id;
              description
                "Node where access list is applied";
            }
            leaf application-id {
              type dt1:Acl-usage-app-id-enum;
              description
                "Application ID";
            }
            leaf access-list-name {
              type string;
              description
                "Name of the access list";
            }
            leaf usage-details {
              type string;
              // NCS drop mandatory statement
              description
                "Usage Statistics Details";
            }
          }
        }
      }
      container oor {
        description
          "Out Of Resources, Limits to the resources
           allocatable";
        container details {
          description
            "Details of the Overall Out Of Resources Limits";
          uses live_ncs_IPV4-ACL-EDM-OOR-DETAIL;
        }
        container oor-prefixes {
          description
            "Resource occupation details for prefix lists";
          list oor-prefix {
            key "prefix-list-name";
            description
              "Resource occupation details for a particular
               prefix list";
            leaf prefix-list-name {
              type string;
              description
                "Name of a prefix list";
            }
            uses live_ncs_IPV4-ACL-EDM-OOR-DETAIL;
          }
        }
        container oor-accesses {
          description
            "Resource occupation details for access lists";
          list oor-access {
            key "access-list-name";
            description
              "Resource occupation details for a particular
               access list";
            leaf access-list-name {
              type string;
              description
                "Name of the Access List";
            }
            uses live_ncs_IPV4-ACL-EDM-OOR-DETAIL;
          }
        }
        container access-list-summary {
          description
            "Resource limits pertaining to access lists only";
          container details {
            description
              "Details containing the resource limits of the
               access lists";
            uses live_ncs_IPV4-ACL-EDM-OOR-DETAIL;
          }
        }
        container prefix-list-summary {
          description
            "Summary of the prefix Lists resource
             utilization";
          container details {
            description
              "Summary Detail of the prefix list Resource
               Utilisation";
            uses live_ncs_IPV4-ACL-EDM-OOR-DETAIL;
          }
        }
      }
    }
  }
  augment "/ncs:devices/ncs:template/ncs:ned-id/ncs:config" {
    // NCS drop config false container 'ipv4-acl-and-prefix-list'
  }
}
