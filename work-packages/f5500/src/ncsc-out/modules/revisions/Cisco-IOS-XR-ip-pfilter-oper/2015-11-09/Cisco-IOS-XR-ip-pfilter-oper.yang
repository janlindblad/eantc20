module Cisco-IOS-XR-ip-pfilter-oper {
  // Generated by yanger -t ncs
  tailf:mount-id f5500-nc-1.0:f5500-nc-1.0;
  tailf:ncs-device-type "netconf";

  namespace "http://cisco.com/ns/yang/Cisco-IOS-XR-ip-pfilter-oper";
  prefix Cisco-IOS-XR-ip-pfilter-oper;

  import Cisco-IOS-XR-types {
    prefix xr;
  }
  include Cisco-IOS-XR-ip-pfilter-oper-sub1 {
    revision-date 2015-11-09;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ip-pfilter package operational data.

     This module contains definitions
     for the following management objects:
       pfilter-ma: Root class of PfilterMa Oper schema

     Copyright (c) 2013-2018 by Cisco Systems, Inc.
     All rights reserved.";

  revision 2015-11-09 {
    description
      "IOS XR 6.0 revision.";
  }

  grouping ncs_template_ACL-INFO-TABLE {
    description
      "Common node of ipv4, ipv6";
    container acl-info-table {
      description
        "Operational data for pfilter";
      container interface-infos {
        description
          "Operational data for pfilter";
        list interface-info {
          // NCS patched for predictable order
          ordered-by user;
          key "interface-name";
          description
            "Operational data for pfilter in bag";
          leaf interface-name {
            type string;
            description
              "Name of the interface";
          }
          uses ncs_template_PFILTER-INTF-ACL-INFO;
        }
      }
    }
  }

  grouping ncs_rpc_notif_ACL-INFO-TABLE {
    description
      "Common node of ipv4, ipv6";
    container acl-info-table {
      description
        "Operational data for pfilter";
      container interface-infos {
        description
          "Operational data for pfilter";
        list interface-info {
          key "interface-name";
          description
            "Operational data for pfilter in bag";
          leaf interface-name {
            type xr:Interface-name;
            description
              "Name of the interface";
          }
          uses ncs_rpc_notif_PFILTER-INTF-ACL-INFO;
        }
      }
    }
  }

  grouping live_ncs_ACL-INFO-TABLE {
    description
      "Common node of ipv4, ipv6";
    container acl-info-table {
      description
        "Operational data for pfilter";
      container interface-infos {
        description
          "Operational data for pfilter";
        list interface-info {
          key "interface-name";
          description
            "Operational data for pfilter in bag";
          leaf interface-name {
            type xr:Interface-name;
            description
              "Name of the interface";
          }
          uses live_ncs_PFILTER-INTF-ACL-INFO;
        }
      }
    }
  }

  grouping ACL-INFO-TABLE {
    description
      "Common node of ipv4, ipv6";
    container acl-info-table {
      description
        "Operational data for pfilter";
      container interface-infos {
        description
          "Operational data for pfilter";
        list interface-info {
          key "interface-name";
          description
            "Operational data for pfilter in bag";
          leaf interface-name {
            type xr:Interface-name;
            description
              "Name of the interface";
          }
          uses PFILTER-INTF-ACL-INFO;
        }
      }
    }
  }

  augment "/ncs:devices/ncs:device/ncs:config" {
    // NCS drop config false container 'pfilter-ma'
  }
  augment "/ncs:devices/ncs:device/ncs:live-status" {
    container pfilter-ma {
      tailf:ncs-device-type "netconf";
      tailf:display-when "not(../../ncs:module) or ../../ncs:module[ncs:name='Cisco-IOS-XR-ip-pfilter-oper'] or (../../ncs:live-status-protocol[not(ncs:capability)]) or (../../ncs:live-status-protocol/ncs:capability/ncs:module[.='Cisco-IOS-XR-ip-pfilter-oper'])";
      description
        "Root class of PfilterMa Oper schema";
      container nodes {
        description
          "Node-specific operational data";
        list node {
          key "node-name";
          description
            "PfilterMa operational data for a particular
             node";
          container process {
            description
              "Operational data for pfilter";
            container ipv6 {
              description
                "Operational data for pfilter";
              uses live_ncs_ACL-INFO-TABLE;
            }
            container ipv4 {
              description
                "Operational data for pfilter";
              uses live_ncs_ACL-INFO-TABLE;
            }
          }
          leaf node-name {
            type xr:Node-id;
            description
              "The node";
          }
        }
      }
    }
  }
  augment "/ncs:devices/ncs:template/ncs:ned-id/ncs:config" {
    // NCS drop config false container 'pfilter-ma'
  }
}
