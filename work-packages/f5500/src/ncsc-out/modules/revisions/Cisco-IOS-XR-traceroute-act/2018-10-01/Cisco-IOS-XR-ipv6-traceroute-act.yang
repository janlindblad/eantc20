submodule Cisco-IOS-XR-ipv6-traceroute-act {
  // Generated by yanger -t ncs
  tailf:mount-id f5500-nc-1.0:f5500-nc-1.0;

  belongs-to Cisco-IOS-XR-traceroute-act {
    prefix Cisco-IOS-XR-ipv6-traceroute-act;
  }

  include Cisco-IOS-XR-ipv4-traceroute-act;
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR IPv6 traceroute action package configuration.

     Copyright (c) 2016 by Cisco Systems, Inc.
     All rights reserved.";

  revision 2016-09-17 {
    description
      "IOS XR 6.2.1 revision.";
  }

  grouping ncs_template_IPV6-SPECIFIC-OPTIONS {
    leaf priority {
      description
        "Priority of hte packet";
      type string;
    }
    leaf outgoing-interface {
      description
        "Outgoing interface, needed in case of traceroute to link local address";
      type string;
    }
  }

  grouping ncs_template_IPV6-TRACEROUTE-INPUT {
    uses ncs_template_TRACEROUTE-OPTIONS;
    uses ncs_template_IPV6-SPECIFIC-OPTIONS;
  }

  grouping ncs_rpc_notif_IPV6-SPECIFIC-OPTIONS {
    leaf priority {
      description
        "Priority of hte packet";
      type uint16 {
        range "0..15";
      }
    }
    leaf outgoing-interface {
      description
        "Outgoing interface, needed in case of traceroute to link local address";
      type string;
    }
  }

  grouping ncs_rpc_notif_IPV6-TRACEROUTE-INPUT {
    uses ncs_rpc_notif_TRACEROUTE-OPTIONS;
    uses ncs_rpc_notif_IPV6-SPECIFIC-OPTIONS;
  }

  grouping live_ncs_IPV6-SPECIFIC-OPTIONS {
    leaf priority {
      description
        "Priority of hte packet";
      type uint16 {
        range "0..15";
      }
    }
    leaf outgoing-interface {
      description
        "Outgoing interface, needed in case of traceroute to link local address";
      type string;
    }
  }

  grouping live_ncs_IPV6-TRACEROUTE-INPUT {
    uses live_ncs_TRACEROUTE-OPTIONS;
    uses live_ncs_IPV6-SPECIFIC-OPTIONS;
  }

  grouping IPV6-SPECIFIC-OPTIONS {
    leaf priority {
      description
        "Priority of hte packet";
      type uint16 {
        range "0..15";
      }
    }
    leaf outgoing-interface {
      description
        "Outgoing interface, needed in case of traceroute to link local address";
      type string;
    }
  }

  grouping IPV6-TRACEROUTE-INPUT {
    uses TRACEROUTE-OPTIONS;
    uses IPV6-SPECIFIC-OPTIONS;
  }
}
