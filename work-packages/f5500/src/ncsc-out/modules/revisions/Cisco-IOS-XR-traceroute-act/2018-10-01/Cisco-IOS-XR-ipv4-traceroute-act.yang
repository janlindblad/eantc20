submodule Cisco-IOS-XR-ipv4-traceroute-act {
  // Generated by yanger -t ncs
  tailf:mount-id f5500-nc-1.0:f5500-nc-1.0;

  belongs-to Cisco-IOS-XR-traceroute-act {
    prefix Cisco-IOS-XR-ipv4-traceroute-act;
  }

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR IPv4 traceroute action package configuration.

     Copyright (c) 2016-2018 by Cisco Systems, Inc.
     All rights reserved.";

  revision 2016-09-17 {
    description
      "IOS XR 6.2.1 revision.";
  }

  grouping ncs_template_TRACEROUTE-OPTIONS {
    leaf destination {
      description
        "Destination address or hostname";
      type string;
      // NCS drop mandatory statement
    }
    leaf source {
      description
        "Source address or interface";
      type string;
    }
    leaf timeout {
      description
        "Timeout in seconds";
      type string;
      // NCS drop default statement
    }
    leaf probe {
      description
        "Probe count";
      type string;
      // NCS drop default statement
    }
    leaf numeric {
      description
        "Numeric display only";
      type string;
    }
    leaf vrf-name {
      description
        "VRF name";
      type string;
    }
    leaf min-ttl {
      description
        "minimum time to live";
      type string;
      // NCS drop default statement
    }
    leaf max-ttl {
      description
        "maximum time to live";
      type string;
      // NCS drop default statement
    }
    leaf port {
      description
        "Port numbe";
      type string;
    }
    leaf verbose {
      description
        "verbose output";
      type string;
    }
    leaf srv6-header {
      description
        "srv6 header";
      type string;
    }
  }

  grouping ncs_template_TRACEROUTE-OUTPUT {
    leaf destination {
      description
        "Destination address or hostname";
      type string;
    }
    container hops {
      list hop {
        // NCS patched for predictable order
        ordered-by user;
        key "hop-index";
        leaf hop-index {
          description
            "Index of the hop";
          type string;
        }
        leaf hop-address {
          description
            "Address of the hop";
          type string;
        }
        leaf hop-hostname {
          description
            "Hostname of the hop";
          type string;
        }
        container probes {
          list probe {
            // NCS patched for predictable order
            ordered-by user;
            key "probe-index";
            leaf probe-index {
              description
                "Index of the probe";
              type string;
            }
            leaf result {
              description
                "Response for each probe";
              type string;
            }
            leaf delta-time {
              description
                "Delta time in seconds";
              type string;
            }
            leaf hop-address {
              description
                "Address of the hop";
              type string;
            }
            leaf hop-hostname {
              description
                "Hostname of the hop";
              type string;
            }
            container srv6-header {
              leaf destination-address {
                description
                  "Destination address for srv6 header";
                type string;
              }
              leaf segments-left {
                description
                  "Number of segments left";
                type string;
              }
              container segments {
                leaf-list segment {
                  // NCS patched for predictable order
                  ordered-by user;
                  description
                    "sid in sidlist";
                  type string;
                }
              }
            }
          }
        }
      }
    }
    leaf verbose-output {
      description
        "Verbose output";
      type string;
    }
  }

  grouping ncs_rpc_notif_TRACEROUTE-OPTIONS {
    leaf destination {
      description
        "Destination address or hostname";
      type string;
      mandatory true;
    }
    leaf source {
      description
        "Source address or interface";
      type string;
    }
    leaf timeout {
      description
        "Timeout in seconds";
      type uint32 {
        range "0..36";
      }
      default "3";
    }
    leaf probe {
      description
        "Probe count";
      type uint16 {
        range "1..64";
      }
      default "3";
    }
    leaf numeric {
      description
        "Numeric display only";
      type boolean;
    }
    leaf vrf-name {
      description
        "VRF name";
      type string;
    }
    leaf min-ttl {
      description
        "minimum time to live";
      type uint16 {
        range "0..255";
      }
      default "1";
    }
    leaf max-ttl {
      description
        "maximum time to live";
      type uint16 {
        range "0..255";
      }
      default "30";
    }
    leaf port {
      description
        "Port numbe";
      type uint32 {
        range "0..65535";
      }
    }
    leaf verbose {
      description
        "verbose output";
      type boolean;
    }
    leaf srv6-header {
      description
        "srv6 header";
      type boolean;
    }
  }

  grouping ncs_rpc_notif_TRACEROUTE-OUTPUT {
    leaf destination {
      description
        "Destination address or hostname";
      type string;
    }
    container hops {
      list hop {
        key "hop-index";
        leaf hop-index {
          description
            "Index of the hop";
          type uint32;
        }
        leaf hop-address {
          description
            "Address of the hop";
          type string;
        }
        leaf hop-hostname {
          description
            "Hostname of the hop";
          type string;
        }
        container probes {
          list probe {
            key "probe-index";
            leaf probe-index {
              description
                "Index of the probe";
              type uint32;
            }
            leaf result {
              description
                "Response for each probe";
              type string;
            }
            leaf delta-time {
              description
                "Delta time in seconds";
              type uint32;
            }
            leaf hop-address {
              description
                "Address of the hop";
              type string;
            }
            leaf hop-hostname {
              description
                "Hostname of the hop";
              type string;
            }
            container srv6-header {
              leaf destination-address {
                description
                  "Destination address for srv6 header";
                type uint32;
              }
              leaf segments-left {
                description
                  "Number of segments left";
                type uint32;
              }
              container segments {
                leaf-list segment {
                  description
                    "sid in sidlist";
                  type string;
                }
              }
            }
          }
        }
      }
    }
    leaf verbose-output {
      description
        "Verbose output";
      type string;
    }
  }

  grouping live_ncs_TRACEROUTE-OPTIONS {
    leaf destination {
      description
        "Destination address or hostname";
      type string;
      // NCS drop mandatory statement
    }
    leaf source {
      description
        "Source address or interface";
      type string;
    }
    leaf timeout {
      description
        "Timeout in seconds";
      type uint32 {
        range "0..36";
      }
      // NCS drop default statement
    }
    leaf probe {
      description
        "Probe count";
      type uint16 {
        range "1..64";
      }
      // NCS drop default statement
    }
    leaf numeric {
      description
        "Numeric display only";
      type boolean;
    }
    leaf vrf-name {
      description
        "VRF name";
      type string;
    }
    leaf min-ttl {
      description
        "minimum time to live";
      type uint16 {
        range "0..255";
      }
      // NCS drop default statement
    }
    leaf max-ttl {
      description
        "maximum time to live";
      type uint16 {
        range "0..255";
      }
      // NCS drop default statement
    }
    leaf port {
      description
        "Port numbe";
      type uint32 {
        range "0..65535";
      }
    }
    leaf verbose {
      description
        "verbose output";
      type boolean;
    }
    leaf srv6-header {
      description
        "srv6 header";
      type boolean;
    }
  }

  grouping live_ncs_TRACEROUTE-OUTPUT {
    leaf destination {
      description
        "Destination address or hostname";
      type string;
    }
    container hops {
      list hop {
        key "hop-index";
        leaf hop-index {
          description
            "Index of the hop";
          type uint32;
        }
        leaf hop-address {
          description
            "Address of the hop";
          type string;
        }
        leaf hop-hostname {
          description
            "Hostname of the hop";
          type string;
        }
        container probes {
          list probe {
            key "probe-index";
            leaf probe-index {
              description
                "Index of the probe";
              type uint32;
            }
            leaf result {
              description
                "Response for each probe";
              type string;
            }
            leaf delta-time {
              description
                "Delta time in seconds";
              type uint32;
            }
            leaf hop-address {
              description
                "Address of the hop";
              type string;
            }
            leaf hop-hostname {
              description
                "Hostname of the hop";
              type string;
            }
            container srv6-header {
              leaf destination-address {
                description
                  "Destination address for srv6 header";
                type uint32;
              }
              leaf segments-left {
                description
                  "Number of segments left";
                type uint32;
              }
              container segments {
                leaf-list segment {
                  description
                    "sid in sidlist";
                  type string;
                }
              }
            }
          }
        }
      }
    }
    leaf verbose-output {
      description
        "Verbose output";
      type string;
    }
  }

  grouping TRACEROUTE-OPTIONS {
    leaf destination {
      description
        "Destination address or hostname";
      type string;
      mandatory true;
    }
    leaf source {
      description
        "Source address or interface";
      type string;
    }
    leaf timeout {
      description
        "Timeout in seconds";
      type uint32 {
        range "0..36";
      }
      default "3";
    }
    leaf probe {
      description
        "Probe count";
      type uint16 {
        range "1..64";
      }
      default "3";
    }
    leaf numeric {
      description
        "Numeric display only";
      type boolean;
    }
    leaf vrf-name {
      description
        "VRF name";
      type string;
    }
    leaf min-ttl {
      description
        "minimum time to live";
      type uint16 {
        range "0..255";
      }
      default "1";
    }
    leaf max-ttl {
      description
        "maximum time to live";
      type uint16 {
        range "0..255";
      }
      default "30";
    }
    leaf port {
      description
        "Port numbe";
      type uint32 {
        range "0..65535";
      }
    }
    leaf verbose {
      description
        "verbose output";
      type boolean;
    }
    leaf srv6-header {
      description
        "srv6 header";
      type boolean;
    }
  }

  grouping TRACEROUTE-OUTPUT {
    leaf destination {
      description
        "Destination address or hostname";
      type string;
    }
    container hops {
      list hop {
        key "hop-index";
        leaf hop-index {
          description
            "Index of the hop";
          type uint32;
        }
        leaf hop-address {
          description
            "Address of the hop";
          type string;
        }
        leaf hop-hostname {
          description
            "Hostname of the hop";
          type string;
        }
        container probes {
          list probe {
            key "probe-index";
            leaf probe-index {
              description
                "Index of the probe";
              type uint32;
            }
            leaf result {
              description
                "Response for each probe";
              type string;
            }
            leaf delta-time {
              description
                "Delta time in seconds";
              type uint32;
            }
            leaf hop-address {
              description
                "Address of the hop";
              type string;
            }
            leaf hop-hostname {
              description
                "Hostname of the hop";
              type string;
            }
            container srv6-header {
              leaf destination-address {
                description
                  "Destination address for srv6 header";
                type uint32;
              }
              leaf segments-left {
                description
                  "Number of segments left";
                type uint32;
              }
              container segments {
                leaf-list segment {
                  description
                    "sid in sidlist";
                  type string;
                }
              }
            }
          }
        }
      }
    }
    leaf verbose-output {
      description
        "Verbose output";
      type string;
    }
  }
}
