module Cisco-IOS-XR-traceroute-act {
  // Generated by yanger -t ncs
  tailf:mount-id f5500-nc-1.0:f5500-nc-1.0;
  tailf:ncs-device-type "netconf";

  namespace "http://cisco.com/ns/yang/Cisco-IOS-XR-traceroute-act";
  prefix Cisco-IOS-XR-traceroute-act;

  include Cisco-IOS-XR-ipv4-traceroute-act;
  include Cisco-IOS-XR-ipv6-traceroute-act;
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ping action package configuration.

     Copyright (c) 2016, 2018 by Cisco Systems, Inc.
     All rights reserved.";

  revision 2018-10-01 {
    description
      "IOS XR 6.2.1 revision.";
  }

  augment "/ncs:devices/ncs:device/ncs:rpc" {
    container rpc-traceroute {
      tailf:ncs-device-type "netconf";
      tailf:display-when "not(../../ncs:module) or ../../ncs:module[ncs:name='Cisco-IOS-XR-traceroute-act']";
      tailf:action traceroute {
        tailf:actionpoint ncsproxy {
          tailf:internal;
        }
        description
          "Trace route to destination";
        input {
          container destination {
            presence "traceroute input";
            uses ncs_rpc_notif_TRACEROUTE-OPTIONS;
            uses ncs_rpc_notif_IPV6-SPECIFIC-OPTIONS;
          }
          container ipv4 {
            presence "ipv4 traceroute input";
            uses ncs_rpc_notif_TRACEROUTE-OPTIONS;
          }
          container ipv6 {
            presence "ipv6 traceroute input";
            uses ncs_rpc_notif_IPV6-TRACEROUTE-INPUT;
          }
        }
        output {
          container traceroute-response {
            container ipv4 {
              presence "ipv4 traceroute output";
              uses ncs_rpc_notif_TRACEROUTE-OUTPUT;
            }
            container ipv6 {
              presence "ipv6 traceroute output";
              uses ncs_rpc_notif_TRACEROUTE-OUTPUT;
            }
          }
        }
      }
    }
  }
  augment "/ncs:devices/ncs:device-group/ncs:ned-id/ncs:rpc" {
    container rpc-traceroute {
      tailf:ncs-device-type "netconf";
      tailf:display-when "/ncs:devices/ncs:device[ncs:name=current()/../../../ncs:member]/ncs:module[ncs:name='Cisco-IOS-XR-traceroute-act']";
      tailf:action traceroute {
        tailf:actionpoint ncsproxy {
          tailf:internal;
        }
        description
          "Trace route to destination";
        input {
          container destination {
            presence "traceroute input";
            uses ncs_rpc_notif_TRACEROUTE-OPTIONS;
            uses ncs_rpc_notif_IPV6-SPECIFIC-OPTIONS;
          }
          container ipv4 {
            presence "ipv4 traceroute input";
            uses ncs_rpc_notif_TRACEROUTE-OPTIONS;
          }
          container ipv6 {
            presence "ipv6 traceroute input";
            uses ncs_rpc_notif_IPV6-TRACEROUTE-INPUT;
          }
        }
        output {
          container "device" {
            leaf "name" {
              type string;
            }
            leaf "info" {
              type string;
            }
            container "result" {
              container traceroute-response {
                container ipv4 {
                  presence "ipv4 traceroute output";
                  uses ncs_rpc_notif_TRACEROUTE-OUTPUT;
                }
                container ipv6 {
                  presence "ipv6 traceroute output";
                  uses ncs_rpc_notif_TRACEROUTE-OUTPUT;
                }
              }
            }
          }
        }
      }
    }
  }
}
