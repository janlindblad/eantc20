module Cisco-IOS-XR-sysadmin-show-diag {
  // Generated by yanger -t ncs
  tailf:mount-id f5500-nc-1.0:f5500-nc-1.0;
  tailf:ncs-device-type "netconf";

  namespace "http://www.cisco.com/ns/yang/Cisco-IOS-XR-sysadmin-show-diag";
  prefix Cisco-IOS-XR-sysadmin-show-diag;

  import "f5500-nc-1.0" {
    prefix "f5500-nc-1.0";
  }
  import tailf-ncs {
    prefix ncs;
  }
  import tailf-common {
    prefix tailf;
  }

  organization
    "Cisco Systems Inc.";
  contact
    "Cisco Systems, Inc.
     Customer Service

     Postal: 170 West Tasman Drive
     San Jose, CA 95134

     Tel: +1 800 553-NETS

     E-mail: cs-yang@cisco.com";
  description
    "This module contains definitions
     for the Calvados model objects.

     This module contains a collection of YANG
     definitions for Cisco IOS-XR SysAdmin configuration.

     This module holds diag data for chassis, card, fan, power.

     Copyright(c) 2012-2017 by Cisco Systems, Inc.
     All rights reserved.

     Copyright (c) 2012-2018 by Cisco Systems, Inc.
     All rights reserved.";

  revision 2017-04-12 {
    description
      "Changed namespace and module name";
  }

  grouping ncs_template_diag-default-data {
    container default {
      list default_list {
        // NCS patched for predictable order
        ordered-by user;
        key "location";
        leaf location {
          type string;
        }
        container default-data {
          leaf-list default_out_list {
            // NCS patched for predictable order
            ordered-by user;
            type string;
          }
        }
      }
    }
    container fans {
      list fans_list {
        // NCS patched for predictable order
        ordered-by user;
        key "location";
        leaf location {
          type string;
        }
        container default-data {
          leaf-list default_out_list {
            // NCS patched for predictable order
            ordered-by user;
            type string;
          }
        }
      }
    }
    container power-supply {
      list pwr_list {
        // NCS patched for predictable order
        ordered-by user;
        key "location";
        leaf location {
          type string;
        }
        container default-data {
          leaf-list default_out_list {
            // NCS patched for predictable order
            ordered-by user;
            type string;
          }
        }
      }
    }

    grouping chassis_eeprom_grp {
      container chassis_eeprom_cnt {
        list chassis_eeprom_list {
          // NCS patched for predictable order
          ordered-by user;
          key "location";
          leaf location {
            type string;
          }
          container eeprom-data {
            leaf-list raw_list {
              // NCS patched for predictable order
              ordered-by user;
              type string;
            }
          }
        }
      }
    }

    grouping chassis_grp {
      container chassis_cnt {
        list chassis_list {
          // NCS patched for predictable order
          ordered-by user;
          key "location";
          leaf location {
            type string;
          }
          container default-data {
            leaf-list default_out_list {
              // NCS patched for predictable order
              ordered-by user;
              type string;
            }
          }
        }
      }
    }
    container chassis {
      uses chassis_grp;
      uses chassis_eeprom_grp;
    }
  }

  grouping ncs_template_diag-summary-data {
    container summary {
      list summary_list {
        // NCS patched for predictable order
        ordered-by user;
        key "location";
        leaf location {
          type string;
        }
        container summary-data {
          leaf-list summary_out_list {
            // NCS patched for predictable order
            ordered-by user;
            type string;
          }
        }
      }
    }
  }

  grouping ncs_template_diag-detail-data {
    container detail {
      list detail_list {
        // NCS patched for predictable order
        ordered-by user;
        key "location";
        leaf location {
          type string;
        }
        container detail-data {
          leaf-list detail_out_list {
            // NCS patched for predictable order
            ordered-by user;
            type string;
          }
        }
      }
    }
  }

  grouping ncs_template_diag-eeprom-location-data {
    container eeprom {
      list eeprom_list {
        // NCS patched for predictable order
        ordered-by user;
        key "location";
        leaf location {
          type string;
        }
        container eeprom-data {
          leaf-list raw_list {
            // NCS patched for predictable order
            ordered-by user;
            type string;
          }
        }
      }
    }
  }

  grouping ncs_rpc_notif_diag-default-data {
    container default {
      list default_list {
        key "location";
        leaf location {
          type string;
        }
        container default-data {
          leaf-list default_out_list {
            type string;
          }
        }
      }
    }
    container fans {
      list fans_list {
        key "location";
        leaf location {
          type string;
        }
        container default-data {
          leaf-list default_out_list {
            type string;
          }
        }
      }
    }
    container power-supply {
      list pwr_list {
        key "location";
        leaf location {
          type string;
        }
        container default-data {
          leaf-list default_out_list {
            type string;
          }
        }
      }
    }

    grouping chassis_eeprom_grp {
      container chassis_eeprom_cnt {
        list chassis_eeprom_list {
          key "location";
          leaf location {
            type string;
          }
          container eeprom-data {
            leaf-list raw_list {
              type string;
            }
          }
        }
      }
    }

    grouping chassis_grp {
      container chassis_cnt {
        list chassis_list {
          key "location";
          leaf location {
            type string;
          }
          container default-data {
            leaf-list default_out_list {
              type string;
            }
          }
        }
      }
    }
    container chassis {
      uses chassis_grp;
      uses chassis_eeprom_grp;
    }
  }

  grouping ncs_rpc_notif_diag-summary-data {
    container summary {
      list summary_list {
        key "location";
        leaf location {
          type string;
        }
        container summary-data {
          leaf-list summary_out_list {
            type string;
          }
        }
      }
    }
  }

  grouping ncs_rpc_notif_diag-detail-data {
    container detail {
      list detail_list {
        key "location";
        leaf location {
          type string;
        }
        container detail-data {
          leaf-list detail_out_list {
            type string;
          }
        }
      }
    }
  }

  grouping ncs_rpc_notif_diag-eeprom-location-data {
    container eeprom {
      list eeprom_list {
        key "location";
        leaf location {
          type string;
        }
        container eeprom-data {
          leaf-list raw_list {
            type string;
          }
        }
      }
    }
  }

  grouping live_ncs_diag-default-data {
    container default {
      list default_list {
        key "location";
        leaf location {
          type string;
        }
        container default-data {
          leaf-list default_out_list {
            type string;
          }
        }
      }
    }
    container fans {
      list fans_list {
        key "location";
        leaf location {
          type string;
        }
        container default-data {
          leaf-list default_out_list {
            type string;
          }
        }
      }
    }
    container power-supply {
      list pwr_list {
        key "location";
        leaf location {
          type string;
        }
        container default-data {
          leaf-list default_out_list {
            type string;
          }
        }
      }
    }

    grouping chassis_eeprom_grp {
      container chassis_eeprom_cnt {
        list chassis_eeprom_list {
          key "location";
          leaf location {
            type string;
          }
          container eeprom-data {
            leaf-list raw_list {
              type string;
            }
          }
        }
      }
    }

    grouping chassis_grp {
      container chassis_cnt {
        list chassis_list {
          key "location";
          leaf location {
            type string;
          }
          container default-data {
            leaf-list default_out_list {
              type string;
            }
          }
        }
      }
    }
    container chassis {
      uses chassis_grp;
      uses chassis_eeprom_grp;
    }
  }

  grouping live_ncs_diag-summary-data {
    container summary {
      list summary_list {
        key "location";
        leaf location {
          type string;
        }
        container summary-data {
          leaf-list summary_out_list {
            type string;
          }
        }
      }
    }
  }

  grouping live_ncs_diag-detail-data {
    container detail {
      list detail_list {
        key "location";
        leaf location {
          type string;
        }
        container detail-data {
          leaf-list detail_out_list {
            type string;
          }
        }
      }
    }
  }

  grouping live_ncs_diag-eeprom-location-data {
    container eeprom {
      list eeprom_list {
        key "location";
        leaf location {
          type string;
        }
        container eeprom-data {
          leaf-list raw_list {
            type string;
          }
        }
      }
    }
  }

  grouping diag-default-data {
    container default {
      list default_list {
        key "location";
        leaf location {
          type string;
        }
        container default-data {
          leaf-list default_out_list {
            type string;
          }
        }
      }
    }
    container fans {
      list fans_list {
        key "location";
        leaf location {
          type string;
        }
        container default-data {
          leaf-list default_out_list {
            type string;
          }
        }
      }
    }
    container power-supply {
      list pwr_list {
        key "location";
        leaf location {
          type string;
        }
        container default-data {
          leaf-list default_out_list {
            type string;
          }
        }
      }
    }

    grouping chassis_eeprom_grp {
      container chassis_eeprom_cnt {
        list chassis_eeprom_list {
          key "location";
          leaf location {
            type string;
          }
          container eeprom-data {
            leaf-list raw_list {
              type string;
            }
          }
        }
      }
    }

    grouping chassis_grp {
      container chassis_cnt {
        list chassis_list {
          key "location";
          leaf location {
            type string;
          }
          container default-data {
            leaf-list default_out_list {
              type string;
            }
          }
        }
      }
    }
    container chassis {
      uses chassis_grp;
      uses chassis_eeprom_grp;
    }
  }

  grouping diag-summary-data {
    container summary {
      list summary_list {
        key "location";
        leaf location {
          type string;
        }
        container summary-data {
          leaf-list summary_out_list {
            type string;
          }
        }
      }
    }
  }

  grouping diag-detail-data {
    container detail {
      list detail_list {
        key "location";
        leaf location {
          type string;
        }
        container detail-data {
          leaf-list detail_out_list {
            type string;
          }
        }
      }
    }
  }

  grouping diag-eeprom-location-data {
    container eeprom {
      list eeprom_list {
        key "location";
        leaf location {
          type string;
        }
        container eeprom-data {
          leaf-list raw_list {
            type string;
          }
        }
      }
    }
  }

  augment "/ncs:devices/ncs:device/ncs:config" {
    // NCS drop config false container diag
  }
  augment "/ncs:devices/ncs:device/ncs:live-status" {
    container diag {
      tailf:ncs-device-type "netconf";
      tailf:display-when "not(../../ncs:module) or ../../ncs:module[ncs:name='Cisco-IOS-XR-sysadmin-show-diag'] or (../../ncs:live-status-protocol[not(ncs:capability)]) or (../../ncs:live-status-protocol/ncs:capability/ncs:module[.='Cisco-IOS-XR-sysadmin-show-diag'])";
      description
        "diag data";
      uses live_ncs_diag-default-data;
      uses live_ncs_diag-summary-data;
      uses live_ncs_diag-eeprom-location-data;
      uses live_ncs_diag-detail-data;
    }
  }
  augment "/ncs:devices/ncs:template/ncs:ned-id/ncs:config" {
    // NCS drop config false container diag
  }
}
