module Cisco-IOS-XR-telemetry-model-driven-oper {
  // Generated by yanger -t ncs
  tailf:mount-id f5500-nc-1.0:f5500-nc-1.0;
  tailf:ncs-device-type "netconf";

  namespace "http://cisco.com/ns/yang/Cisco-IOS-XR-telemetry-model-driven-oper";
  prefix Cisco-IOS-XR-telemetry-model-driven-oper;

  import Cisco-IOS-XR-types {
    prefix xr;
  }
  include Cisco-IOS-XR-telemetry-model-driven-oper-sub2 {
    revision-date 2017-09-27;
  }
  include Cisco-IOS-XR-telemetry-model-driven-oper-sub1 {
    revision-date 2017-09-27;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR telemetry-model-driven package operational data.

     This module contains definitions
     for the following management objects:
       telemetry-model-driven: Telemetry operational data

     Copyright (c) 2013-2018 by Cisco Systems, Inc.
     All rights reserved.";

  revision 2017-09-27 {
    description
      "Summary container added";
  }
  revision 2017-05-05 {
    description
      "Modified the type for the state variables";
  }
  revision 2017-05-01 {
    description
      "Fixing backward compatibility error in module.";
  }
  revision 2017-02-09 {
    description
      "Added DSCP";
  }
  revision 2017-01-30 {
    description
      "Initial 6.2.1 revision";
  }
  revision 2015-11-09 {
    description
      "IOS XR 6.0 revision.";
  }

  augment "/ncs:devices/ncs:device/ncs:config" {
    // NCS drop config false container 'telemetry-model-driven'
  }
  augment "/ncs:devices/ncs:device/ncs:live-status" {
    container telemetry-model-driven {
      tailf:ncs-device-type "netconf";
      tailf:display-when "not(../../ncs:module) or ../../ncs:module[ncs:name='Cisco-IOS-XR-telemetry-model-driven-oper'] or (../../ncs:live-status-protocol[not(ncs:capability)]) or (../../ncs:live-status-protocol/ncs:capability/ncs:module[.='Cisco-IOS-XR-telemetry-model-driven-oper'])";
      description
        "Telemetry operational data";
      container destinations {
        description
          "Telemetry Destinations";
        list destination {
          key "destination-id";
          description
            "Telemetry Destination";
          leaf destination-id {
            type xr:Cisco-ios-xr-string;
            description
              "Id of the destination";
          }
          uses live_ncs_MDT-DESTINATION-GROUP-DETAIL;
        }
      }
      container subscriptions {
        description
          "Telemetry Subscriptions";
        list subscription {
          key "subscription-id";
          description
            "Telemetry Subscription";
          leaf subscription-id {
            type xr:Cisco-ios-xr-string;
            description
              "Id of the subscription";
          }
          uses live_ncs_MDT-SUBSCRIPTION-DETAILS;
        }
      }
      container sensor-groups {
        description
          "Telemetry Sensor Groups";
        list sensor-group {
          key "sensor-group-id";
          description
            "Telemetry Sensor Groups";
          leaf sensor-group-id {
            type xr:Cisco-ios-xr-string;
            description
              "Id of the sensor group";
          }
          uses live_ncs_MDT-SENSOR-GROUP;
        }
      }
      container summary {
        description
          "Telemetry Summary info";
        uses live_ncs_TELEMETRY-SHOW-SUMMARY;
      }
    }
  }
  augment "/ncs:devices/ncs:template/ncs:ned-id/ncs:config" {
    // NCS drop config false container 'telemetry-model-driven'
  }
}
