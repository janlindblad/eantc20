module Cisco-IOS-XR-nto-misc-oper {
  // Generated by yanger -t ncs
  tailf:mount-id f5500-nc-1.0:f5500-nc-1.0;
  tailf:ncs-device-type "netconf";

  namespace "http://cisco.com/ns/yang/Cisco-IOS-XR-nto-misc-oper";
  prefix Cisco-IOS-XR-nto-misc-oper;

  import Cisco-IOS-XR-types {
    prefix xr;
  }
  include Cisco-IOS-XR-nto-misc-oper-sub1 {
    revision-date 2015-11-09;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR nto-misc package operational data.

     This module contains definitions
     for the following management objects:
       memory-summary: Memory summary information

     Copyright (c) 2013-2018 by Cisco Systems, Inc.
     All rights reserved.";

  revision 2015-11-09 {
    description
      "IOS XR 6.0 revision.";
  }

  augment "/ncs:devices/ncs:device/ncs:config" {
    // NCS drop config false container 'memory-summary'
  }
  augment "/ncs:devices/ncs:device/ncs:live-status" {
    container memory-summary {
      tailf:ncs-device-type "netconf";
      tailf:display-when "not(../../ncs:module) or ../../ncs:module[ncs:name='Cisco-IOS-XR-nto-misc-oper'] or (../../ncs:live-status-protocol[not(ncs:capability)]) or (../../ncs:live-status-protocol/ncs:capability/ncs:module[.='Cisco-IOS-XR-nto-misc-oper'])";
      description
        "Memory summary information";
      container nodes {
        description
          "List of nodes";
        list node {
          key "node-name";
          description
            "Name of nodes";
          container summary {
            description
              "Memory summary information for a specific node";
            uses live_ncs_NODE-MEM-INFO;
          }
          container detail {
            description
              "Detail Memory summary information for a
               specific node";
            uses live_ncs_NODE-MEM-INFO-DETAIL;
          }
          leaf node-name {
            type xr:Node-id;
            description
              "Node name";
          }
        }
      }
    }
  }
  augment "/ncs:devices/ncs:template/ncs:ned-id/ncs:config" {
    // NCS drop config false container 'memory-summary'
  }
}
