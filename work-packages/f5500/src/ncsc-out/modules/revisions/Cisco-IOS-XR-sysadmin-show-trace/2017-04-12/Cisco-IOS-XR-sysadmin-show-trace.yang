module Cisco-IOS-XR-sysadmin-show-trace {
  // Generated by yanger -t ncs
  tailf:mount-id f5500-nc-1.0:f5500-nc-1.0;
  tailf:ncs-device-type "netconf";

  namespace "http://www.cisco.com/ns/yang/Cisco-IOS-XR-sysadmin-show-trace";
  prefix Cisco-IOS-XR-sysadmin-show-trace;

  import "f5500-nc-1.0" {
    prefix "f5500-nc-1.0";
  }
  import tailf-ncs {
    prefix ncs;
  }
  import tailf-common {
    prefix tailf;
  }

  organization
    "Cisco Systems Inc.";
  contact
    "Cisco Systems, Inc.
     Customer Service

     Postal: 170 West Tasman Drive
     San Jose, CA 95134

     Tel: +1 800 553-NETS

     E-mail: cs-yang@cisco.com";
  description
    "This module contains definitions
     for the Calvados model objects.

     This module contains a collection of YANG
     definitions for Cisco IOS-XR SysAdmin configuration.

     Copyright(c) 2012-2017 by Cisco Systems, Inc.
     All rights reserved.

     Copyright (c) 2012-2018 by Cisco Systems, Inc.
     All rights reserved.";

  revision 2017-04-12 {
    description
      "Changed namespace and module name";
  }

  grouping ncs_template_traceable {
    // NCS drop config false list trace
  }

  grouping ncs_template_traceable_process {
    // NCS drop config false list instance
  }

  grouping ncs_template_traceable_with_keypath_location {
    // NCS drop config false list trace
  }

  grouping ncs_rpc_notif_traceable {
    list trace {
      description
        "show traceable processes";
      config false;
      key "buffer";
      leaf buffer {
        type string;
      }
      list location {
        key "location_name";
        leaf location_name {
          type string;
        }
        list all-options {
          key "option";
          leaf option {
            type string;
          }
          list trace-blocks {
            leaf data {
              type string;
              description
                "Trace output block";
            }
          }
        }
      }
    }
  }

  grouping ncs_rpc_notif_traceable_process {
    list instance {
      description
        "show traceable process instance names";
      config false;
      key "process_name";
      leaf process_name {
        type string;
      }
      list trace {
        description
          "show traceable processes";
        config false;
        key "buffer";
        leaf buffer {
          type string;
        }
        list location {
          key "location_name";
          leaf location_name {
            type string;
          }
          list all-options {
            key "option";
            leaf option {
              type string;
            }
            list trace-blocks {
              leaf data {
                type string;
                description
                  "Trace output block";
              }
            }
          }
        }
      }
    }
  }

  grouping ncs_rpc_notif_traceable_with_keypath_location {
    list trace {
      config false;
      key "buffer";
      leaf buffer {
        type string;
      }
      list all-options {
        key "option";
        leaf option {
          type string;
        }
        list trace-blocks {
          leaf data {
            type string;
          }
        }
      }
    }
  }

  grouping live_ncs_traceable {
    list trace {
      description
        "show traceable processes";
      key "buffer";
      leaf buffer {
        type string;
      }
      list location {
        key "location_name";
        leaf location_name {
          type string;
        }
        list all-options {
          key "option";
          leaf option {
            type string;
          }
          list trace-blocks {
            leaf data {
              type string;
              description
                "Trace output block";
            }
          }
        }
      }
    }
  }

  grouping live_ncs_traceable_process {
    list instance {
      description
        "show traceable process instance names";
      key "process_name";
      leaf process_name {
        type string;
      }
      list trace {
        description
          "show traceable processes";
        key "buffer";
        leaf buffer {
          type string;
        }
        list location {
          key "location_name";
          leaf location_name {
            type string;
          }
          list all-options {
            key "option";
            leaf option {
              type string;
            }
            list trace-blocks {
              leaf data {
                type string;
                description
                  "Trace output block";
              }
            }
          }
        }
      }
    }
  }

  grouping live_ncs_traceable_with_keypath_location {
    list trace {
      key "buffer";
      leaf buffer {
        type string;
      }
      list all-options {
        key "option";
        leaf option {
          type string;
        }
        list trace-blocks {
          leaf data {
            type string;
          }
        }
      }
    }
  }

  grouping traceable {
    // NCS drop config false list trace
  }

  grouping traceable_process {
    // NCS drop config false list instance
  }

  grouping traceable_with_keypath_location {
    // NCS drop config false list trace
  }
}
