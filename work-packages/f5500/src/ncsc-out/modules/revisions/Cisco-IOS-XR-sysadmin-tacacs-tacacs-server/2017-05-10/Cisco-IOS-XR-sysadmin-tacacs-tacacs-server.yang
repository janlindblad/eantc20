module Cisco-IOS-XR-sysadmin-tacacs-tacacs-server {
  // Generated by yanger -t ncs
  tailf:mount-id f5500-nc-1.0:f5500-nc-1.0;
  tailf:ncs-device-type "netconf";

  namespace "http://www.cisco.com/ns/yang/Cisco-IOS-XR-sysadmin-tacacs-tacacs-server";
  prefix Cisco-IOS-XR-sysadmin-tacacs-tacacs-server;

  import tailf-common {
    prefix tailf;
  }
  import ietf-inet-types {
    prefix inet;
  }
  import "f5500-nc-1.0" {
    prefix "f5500-nc-1.0";
  }
  import tailf-ncs {
    prefix ncs;
  }

  organization
    "Cisco Systems";
  contact
    "aaa-ng-tacacs-dev@cisco.com";
  description
    "This module contains definitions
     for the Calvados model objects.

     This module defines the TACACS+ data model.

     Copyright (c) 2012-2018 by Cisco Systems, Inc.
     All rights reserved.";

  revision 2017-05-10 {
    description
      "Namespace changed from tacacs to Cisco-IOS-XR-sysadmin-tacacs-tacacs-server";
  }

  typedef passwdStr {
    type tailf:aes-cfb-128-encrypted-string;
  }

  augment "/ncs:devices/ncs:device/ncs:config" {
    container tacacs-server {
      tailf:ncs-device-type "netconf";
      tailf:display-when "not(../../ncs:module) or ../../ncs:module[ncs:name='Cisco-IOS-XR-sysadmin-tacacs-tacacs-server']";
      list host {
        max-elements 10;
        key "ip port";
        ordered-by user;
        leaf ip {
          type inet:ip-address;
        }
        leaf port {
          type inet:port-number {
            range "1 .. 65535";
          }
        }
        leaf timeout {
          type uint32 {
            range "1 .. 1000";
          }
        }
        leaf key {
          type passwdStr;
        }
      }
      leaf timeout {
        type uint32 {
          range "1 .. 1000";
        }
      }
      leaf key {
        type passwdStr;
      }
    }
  }
  augment "/ncs:devices/ncs:device/ncs:live-status" {
    container tacacs-server {
      tailf:ncs-device-type "netconf";
      tailf:display-when "not(../../ncs:module) or ../../ncs:module[ncs:name='Cisco-IOS-XR-sysadmin-tacacs-tacacs-server'] or (../../ncs:live-status-protocol[not(ncs:capability)]) or (../../ncs:live-status-protocol/ncs:capability/ncs:module[.='Cisco-IOS-XR-sysadmin-tacacs-tacacs-server'])";
      list host {
        // NCS drop max-elements statement
        key "ip port";
        ordered-by user;
        leaf ip {
          type inet:ip-address;
        }
        leaf port {
          type inet:port-number {
            range "1 .. 65535";
          }
        }
        leaf timeout {
          type uint32 {
            range "1 .. 1000";
          }
        }
        leaf key {
          type passwdStr;
        }
      }
      leaf timeout {
        type uint32 {
          range "1 .. 1000";
        }
      }
      leaf key {
        type passwdStr;
      }
    }
  }
  augment "/ncs:devices/ncs:template/ncs:ned-id/ncs:config" {
    container tacacs-server {
      list host {
        // NCS patched for predictable order
        ordered-by user;
        // NCS drop max-elements statement
        key "ip port";
        leaf ip {
          type string;
        }
        leaf port {
          type string;
        }
        leaf timeout {
          type string;
        }
        leaf key {
          type string;
        }
      }
      leaf timeout {
        type string;
      }
      leaf key {
        type string;
      }
    }
  }
}
