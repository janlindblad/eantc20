module Cisco-IOS-XR-traffmon-netflow-cfg {
  // Generated by yanger -t ncs
  tailf:mount-id f5500-nc-1.0:f5500-nc-1.0;
  tailf:ncs-device-type "netconf";

  namespace "http://cisco.com/ns/yang/Cisco-IOS-XR-traffmon-netflow-cfg";
  prefix Cisco-IOS-XR-traffmon-netflow-cfg;

  import ietf-inet-types {
    prefix inet;
  }
  import Cisco-IOS-XR-types {
    prefix xr;
  }
  import Cisco-IOS-XR-ifmgr-cfg {
    prefix a1;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR traffmon-netflow package configuration.

     This module contains definitions
     for the following management objects:
       net-flow: NetFlow Configuration

     This YANG module augments the
       Cisco-IOS-XR-ifmgr-cfg
     module with configuration data.

     Copyright (c) 2013-2018 by Cisco Systems, Inc.
     All rights reserved.";

  revision 2018-06-15 {
    description
      "Changed type of version node from range to enum and made it mandatory.";
  }
  revision 2018-06-15 {
    description
      "Allow min..max in range when min == max.";
  }
  revision 2018-05-28 {
    description
      "Changed some schema paths for commit check functionality.";
  }
  revision 2018-04-01 {
    description
      "Changed some schema paths for commit replace functionality.";
  }
  revision 2017-05-01 {
    description
      "Fixing backward compatibility error in module.";
  }
  revision 2015-11-09 {
    description
      "IOS XR 6.0 revision.";
  }

  typedef Nf-flow-protocol {
    type enumeration {
      enum "ipv4" {
        value 0;
        description
          "Netflow flow protocol ipv4";
      }
      enum "ipv6" {
        value 1;
        description
          "Netflow flow protocol ipv6";
      }
      enum "mpls" {
        value 2;
        description
          "Netflow flow protocol mpls";
      }
      enum "data-link-frame-section" {
        value 13;
        description
          "Netflow flow protocol data-link-frame-section";
      }
    }
    description
      "Nf flow protocol";
  }

  typedef Nf-flow-direction {
    type enumeration {
      enum "ingress" {
        value 0;
        description
          "Netflow flow direction ingress";
      }
      enum "egress" {
        value 1;
        description
          "Netflow flow direction egress";
      }
    }
    description
      "Nf flow direction";
  }

  typedef Nf-cache-timeout-rate-limit {
    type uint32 {
      range "1..1000000";
    }
    description
      "Nf cache timeout rate limit";
  }

  typedef Nf-export-version {
    type enumeration {
      enum "v9" {
        value 9;
        description
          "Version v9";
      }
      enum "ipfix" {
        value 10;
        description
          "Version ipfix";
      }
    }
    description
      "Nf export version";
  }

  typedef Nf-sampling-mode {
    type enumeration {
      enum "random" {
        value 2;
        description
          "Random sampling";
      }
    }
    description
      "Nf sampling mode";
  }

  typedef Nf-update-cache-aging-timeout {
    type uint32 {
      range "1..604800";
    }
    description
      "Nf update cache aging timeout";
  }

  typedef Nf-cache-entry {
    type uint32 {
      range "4096..1000000";
    }
    description
      "Nf cache entry";
  }

  typedef Nf-cache-aging-mode {
    type enumeration {
      enum "normal" {
        value 0;
        description
          "Normal, caches age";
      }
      enum "permanent" {
        value 1;
        description
          "Permanent, caches never age";
      }
      enum "immediate" {
        value 2;
        description
          "Immediate, caches age immediately";
      }
    }
    description
      "Nf cache aging mode";
  }

  typedef Nf-map-name {
    type string {
      length "1..32";
    }
    description
      "Nf map name";
  }

  typedef Nf-template-timeout {
    type uint32 {
      range "1..604800";
    }
    description
      "Nf template timeout";
  }

  typedef Nf-record-format {
    type enumeration {
      enum "datalinkframesections-any" {
        value 0;
        description
          "Record Format datalinkframesections_any";
      }
      enum "default-mdi" {
        value 1;
        description
          "Record Format default_mdi";
      }
      enum "default-rtp" {
        value 2;
        description
          "Record Format default_rtp";
      }
      enum "ipv4-as-agg" {
        value 3;
        description
          "Record Format ipv4_as_agg";
      }
      enum "ipv4-as-tos-agg" {
        value 4;
        description
          "Record Format ipv4_as_tos_agg";
      }
      enum "ipv4-bgp-nexthop-tos-agg" {
        value 5;
        description
          "Record Format ipv4_bgp_nexthop_tos_agg";
      }
      enum "ipv4-destination" {
        value 6;
        description
          "Record Format ipv4_destination";
      }
      enum "ipv4-destination-tos-agg" {
        value 7;
        description
          "Record Format ipv4_destination_tos_agg";
      }
      enum "ipv4-destination-prefix-agg" {
        value 8;
        description
          "Record Format ipv4_destination_prefix_agg";
      }
      enum "ipv4-destination-prefix-tos-agg" {
        value 9;
        description
          "Record Format ipv4_destination_prefix_tos_agg";
      }
      enum "ipv4-peer-as" {
        value 10;
        description
          "Record Format ipv4_peer_as";
      }
      enum "ipv4-prefix-agg" {
        value 11;
        description
          "Record Format ipv4_prefix_agg";
      }
      enum "ipv4-prefix-port-agg" {
        value 12;
        description
          "Record Format ipv4_prefix_port_agg";
      }
      enum "ipv4-prefix-tos-agg" {
        value 13;
        description
          "Record Format ipv4_prefix_tos_agg";
      }
      enum "ipv4-protocol-port-agg" {
        value 14;
        description
          "Record Format ipv4_protocol_port_agg";
      }
      enum "ipv4-protocol-port-tos-agg" {
        value 15;
        description
          "Record Format ipv4_protocol_port_tos_agg";
      }
      enum "ipv4-raw" {
        value 16;
        description
          "Record Format ipv4_raw";
      }
      enum "ipv4-source-prefix-agg" {
        value 17;
        description
          "Record Format ipv4_source_prefix_agg";
      }
      enum "ipv4-source-prefix-tos-agg" {
        value 18;
        description
          "Record Format ipv4_source_prefix_tos_agg";
      }
      enum "ipv6" {
        value 19;
        description
          "Record Format ipv6";
      }
      enum "ipv6-destination" {
        value 20;
        description
          "Record Format ipv6_destination";
      }
      enum "ipv6-peer-as" {
        value 21;
        description
          "Record Format ipv6_peer_as";
      }
      enum "mpls" {
        value 22;
        description
          "Record Format mpls";
      }
      enum "mpls-ipv4" {
        value 23;
        description
          "Record Format mpls_ipv4";
      }
      enum "mpls-ipv4-ipv6" {
        value 24;
        description
          "Record Format mpls_ipv4_ipv6";
      }
      enum "mpls-ipv6" {
        value 25;
        description
          "Record Format mpls_ipv6";
      }
    }
    description
      "Nf record format";
  }

  typedef Nf-sample-number {
    type uint32 {
      range "1";
    }
    description
      "Nf sample number";
  }

  typedef Nf-sample-interval {
    type uint32 {
      range "1..65535";
    }
    description
      "Nf sample interval";
  }

  typedef Nf-inactive-cache-aging-timeout {
    type uint32 {
      range "0..604800";
    }
    description
      "Nf inactive cache aging timeout";
  }

  typedef Nf-active-cache-aging-timeout {
    type uint32 {
      range "1..604800";
    }
    description
      "Nf active cache aging timeout";
  }

  typedef Nf-export-timeout {
    type uint32 {
      range "0..604800";
    }
    description
      "Nf export timeout";
  }

  grouping ncs_template_FLOW-MONITOR-MAP {
    description
      "Common node of flow-monitor-map-table,
       flow-monitor-map-performance-table";
    list flow-monitor-map {
      // NCS patched for predictable order
      ordered-by user;
      key "monitor-map-name";
      description
        "Monitor map name";
      container option {
        description
          "Specify an option for the flow cache";
        leaf filtered {
          type empty;
          description
            "Specify whether data should be filtered";
        }
        leaf out-bundle-member {
          type empty;
          description
            "Specify whether to export physical ifh for
             bundle interface";
        }
        leaf out-phys-int {
          type empty;
          description
            "Specify whether it exports the physical output
             interface";
        }
        leaf bgp-attr {
          type empty;
          description
            "Specify if BGP Attributes AS_PATH STD_COMM
             should be exported";
        }
      }
      container exporters {
        description
          "Configure exporters to be used by the
           monitor-map";
        list exporter {
          // NCS patched for predictable order
          ordered-by user;
          key "exporter-name";
          description
            "Configure exporter to be used by the
             monitor-map";
          leaf exporter-name {
            type string;
            description
              "Exporter name";
          }
        }
      }
      container record {
        presence "Indicates a record node is configured.";
        description
          "Specify a flow record format";
        leaf record-format {
          type string;
          // NCS drop mandatory statement
          description
            "Flow record format";
        }
        leaf label {
          type string;
          description
            "Enter label value for MPLS record type";
        }
      }
      leaf cache-update-aging-timeout {
        type string;
        units "second";
        description
          "Specify the update flow cache aging timeout";
      }
      leaf cache-entries {
        type string;
        description
          "Specify the number of entries in the flow cache";
      }
      leaf cache-inactive-aging-timeout {
        type string;
        units "second";
        description
          "Specify the inactive flow cache aging timeout";
      }
      leaf cache-active-aging-timeout {
        type string;
        units "second";
        description
          "Specify the active flow cache aging timeout";
      }
      leaf cache-timeout-rate-limit {
        type string;
        description
          "Specify the maximum number of entries to age
           each second";
      }
      leaf cache-aging-mode {
        type string;
        description
          "Specify the flow cache aging mode";
      }
      leaf monitor-map-name {
        type string;
        description
          "Monitor map name";
      }
    }
  }

  grouping ncs_rpc_notif_FLOW-MONITOR-MAP {
    description
      "Common node of flow-monitor-map-table,
       flow-monitor-map-performance-table";
    list flow-monitor-map {
      key "monitor-map-name";
      description
        "Monitor map name";
      container option {
        description
          "Specify an option for the flow cache";
        leaf filtered {
          type empty;
          description
            "Specify whether data should be filtered";
        }
        leaf out-bundle-member {
          type empty;
          description
            "Specify whether to export physical ifh for
             bundle interface";
        }
        leaf out-phys-int {
          type empty;
          description
            "Specify whether it exports the physical output
             interface";
        }
        leaf bgp-attr {
          type empty;
          description
            "Specify if BGP Attributes AS_PATH STD_COMM
             should be exported";
        }
      }
      container exporters {
        description
          "Configure exporters to be used by the
           monitor-map";
        list exporter {
          key "exporter-name";
          description
            "Configure exporter to be used by the
             monitor-map";
          leaf exporter-name {
            type Nf-map-name;
            description
              "Exporter name";
          }
        }
      }
      container record {
        presence "Indicates a record node is configured.";
        description
          "Specify a flow record format";
        leaf record-format {
          type Nf-record-format;
          mandatory true;
          description
            "Flow record format";
        }
        leaf label {
          type uint32 {
            range "1..6";
          }
          description
            "Enter label value for MPLS record type";
        }
      }
      leaf cache-update-aging-timeout {
        type Nf-update-cache-aging-timeout;
        units "second";
        description
          "Specify the update flow cache aging timeout";
      }
      leaf cache-entries {
        type Nf-cache-entry;
        description
          "Specify the number of entries in the flow cache";
      }
      leaf cache-inactive-aging-timeout {
        type Nf-inactive-cache-aging-timeout;
        units "second";
        description
          "Specify the inactive flow cache aging timeout";
      }
      leaf cache-active-aging-timeout {
        type Nf-active-cache-aging-timeout;
        units "second";
        description
          "Specify the active flow cache aging timeout";
      }
      leaf cache-timeout-rate-limit {
        type Nf-cache-timeout-rate-limit;
        description
          "Specify the maximum number of entries to age
           each second";
      }
      leaf cache-aging-mode {
        type Nf-cache-aging-mode;
        description
          "Specify the flow cache aging mode";
      }
      leaf monitor-map-name {
        type Nf-map-name;
        description
          "Monitor map name";
      }
    }
  }

  grouping live_ncs_FLOW-MONITOR-MAP {
    description
      "Common node of flow-monitor-map-table,
       flow-monitor-map-performance-table";
    list flow-monitor-map {
      key "monitor-map-name";
      description
        "Monitor map name";
      container option {
        description
          "Specify an option for the flow cache";
        leaf filtered {
          type empty;
          description
            "Specify whether data should be filtered";
        }
        leaf out-bundle-member {
          type empty;
          description
            "Specify whether to export physical ifh for
             bundle interface";
        }
        leaf out-phys-int {
          type empty;
          description
            "Specify whether it exports the physical output
             interface";
        }
        leaf bgp-attr {
          type empty;
          description
            "Specify if BGP Attributes AS_PATH STD_COMM
             should be exported";
        }
      }
      container exporters {
        description
          "Configure exporters to be used by the
           monitor-map";
        list exporter {
          key "exporter-name";
          description
            "Configure exporter to be used by the
             monitor-map";
          leaf exporter-name {
            type Nf-map-name;
            description
              "Exporter name";
          }
        }
      }
      container record {
        presence "Indicates a record node is configured.";
        description
          "Specify a flow record format";
        leaf record-format {
          type Nf-record-format;
          // NCS drop mandatory statement
          description
            "Flow record format";
        }
        leaf label {
          type uint32 {
            range "1..6";
          }
          description
            "Enter label value for MPLS record type";
        }
      }
      leaf cache-update-aging-timeout {
        type Nf-update-cache-aging-timeout;
        units "second";
        description
          "Specify the update flow cache aging timeout";
      }
      leaf cache-entries {
        type Nf-cache-entry;
        description
          "Specify the number of entries in the flow cache";
      }
      leaf cache-inactive-aging-timeout {
        type Nf-inactive-cache-aging-timeout;
        units "second";
        description
          "Specify the inactive flow cache aging timeout";
      }
      leaf cache-active-aging-timeout {
        type Nf-active-cache-aging-timeout;
        units "second";
        description
          "Specify the active flow cache aging timeout";
      }
      leaf cache-timeout-rate-limit {
        type Nf-cache-timeout-rate-limit;
        description
          "Specify the maximum number of entries to age
           each second";
      }
      leaf cache-aging-mode {
        type Nf-cache-aging-mode;
        description
          "Specify the flow cache aging mode";
      }
      leaf monitor-map-name {
        type Nf-map-name;
        description
          "Monitor map name";
      }
    }
  }

  grouping FLOW-MONITOR-MAP {
    description
      "Common node of flow-monitor-map-table,
       flow-monitor-map-performance-table";
    list flow-monitor-map {
      key "monitor-map-name";
      description
        "Monitor map name";
      container option {
        description
          "Specify an option for the flow cache";
        leaf filtered {
          type empty;
          description
            "Specify whether data should be filtered";
        }
        leaf out-bundle-member {
          type empty;
          description
            "Specify whether to export physical ifh for
             bundle interface";
        }
        leaf out-phys-int {
          type empty;
          description
            "Specify whether it exports the physical output
             interface";
        }
        leaf bgp-attr {
          type empty;
          description
            "Specify if BGP Attributes AS_PATH STD_COMM
             should be exported";
        }
      }
      container exporters {
        description
          "Configure exporters to be used by the
           monitor-map";
        list exporter {
          key "exporter-name";
          description
            "Configure exporter to be used by the
             monitor-map";
          leaf exporter-name {
            type Nf-map-name;
            description
              "Exporter name";
          }
        }
      }
      container record {
        presence "Indicates a record node is configured.";
        description
          "Specify a flow record format";
        leaf record-format {
          type Nf-record-format;
          mandatory true;
          description
            "Flow record format";
        }
        leaf label {
          type uint32 {
            range "1..6";
          }
          description
            "Enter label value for MPLS record type";
        }
      }
      leaf cache-update-aging-timeout {
        type Nf-update-cache-aging-timeout;
        units "second";
        description
          "Specify the update flow cache aging timeout";
      }
      leaf cache-entries {
        type Nf-cache-entry;
        description
          "Specify the number of entries in the flow cache";
      }
      leaf cache-inactive-aging-timeout {
        type Nf-inactive-cache-aging-timeout;
        units "second";
        description
          "Specify the inactive flow cache aging timeout";
      }
      leaf cache-active-aging-timeout {
        type Nf-active-cache-aging-timeout;
        units "second";
        description
          "Specify the active flow cache aging timeout";
      }
      leaf cache-timeout-rate-limit {
        type Nf-cache-timeout-rate-limit;
        description
          "Specify the maximum number of entries to age
           each second";
      }
      leaf cache-aging-mode {
        type Nf-cache-aging-mode;
        description
          "Specify the flow cache aging mode";
      }
      leaf monitor-map-name {
        type Nf-map-name;
        description
          "Monitor map name";
      }
    }
  }

  augment "/ncs:devices/ncs:device/ncs:config" {
    container net-flow {
      tailf:ncs-device-type "netconf";
      tailf:display-when "not(../../ncs:module) or ../../ncs:module[ncs:name='Cisco-IOS-XR-traffmon-netflow-cfg']";
      description
        "NetFlow Configuration";
      container flow-exporter-maps {
        description
          "Configure a flow exporter map";
        list flow-exporter-map {
          key "exporter-map-name";
          description
            "Exporter map name";
          container udp {
            description
              "Use UDP as transport protocol";
            leaf destination-port {
              type uint32 {
                range "1024..65535";
              }
              description
                "Configure Destination UDP port";
            }
          }
          container destination {
            description
              "Configure export destination (collector)";
            leaf ip-address {
              type inet:ipv4-address-no-zone;
              description
                "Destination IPv4 address";
            }
            leaf ipv6-address {
              type inet:ipv6-address-no-zone;
              description
                "IPV6 address of the tunnel destination";
            }
            leaf vrf-name {
              type xr:Cisco-ios-xr-string {
                length "1..32";
              }
              description
                "VRF name";
            }
          }
          container version {
            presence "Indicates a version node is configured.";
            description
              "Specify export version parameters";
            container options {
              description
                "Specify options for exporting templates";
              leaf interface-table-export-timeout {
                type Nf-export-timeout;
                units "second";
                description
                  "Specify timeout for exporting interface
                   table";
              }
              leaf sampler-table-export-timeout {
                type Nf-export-timeout;
                units "second";
                description
                  "Specify timeout for exporting sampler table";
              }
              leaf vrf-table-export-timeout {
                type Nf-export-timeout;
                units "second";
                description
                  "Specify timeout for exporting vrf table";
              }
            }
            leaf version-type {
              type Nf-export-version;
              mandatory true;
              description
                "Export version number";
            }
            leaf options-template-timeout {
              type Nf-template-timeout;
              units "second";
              default "1800";
              description
                "Option template configuration options";
            }
            leaf common-template-timeout {
              type Nf-template-timeout;
              units "second";
              default "1800";
              description
                "Specify custom timeout for the template";
            }
            leaf data-template-timeout {
              type Nf-template-timeout;
              units "second";
              default "1800";
              description
                "Data template configuration options";
            }
          }
          leaf source-interface {
            type xr:Interface-name;
            description
              "Configure source interface for collector";
          }
          leaf dscp {
            type uint32 {
              range "0..63";
            }
            description
              "Specify DSCP value for export packets";
          }
          leaf packet-length {
            type uint32 {
              range "512..1468";
            }
            description
              "Configure Maximum Value for Export Packet size";
          }
          leaf exporter-map-name {
            type Nf-map-name;
            description
              "Exporter map name";
          }
        }
      }
      container flow-sampler-maps {
        description
          "Flow sampler map configuration";
        list flow-sampler-map {
          key "sampler-map-name";
          description
            "Sampler map name";
          container sampling-modes {
            description
              "Configure packet sampling mode";
            list sampling-mode {
              key "mode";
              description
                "Configure sampling mode";
              leaf mode {
                type Nf-sampling-mode;
                description
                  "Sampling mode";
              }
              leaf sample-number {
                type Nf-sample-number;
                mandatory true;
                description
                  "Number of packets to be sampled in the
                   sampling interval";
              }
              leaf interval {
                type Nf-sample-interval;
                mandatory true;
                description
                  "Sampling interval in units of packets";
              }
            }
          }
          leaf sampler-map-name {
            type Nf-map-name;
            description
              "Sampler map name";
          }
        }
      }
      container flow-monitor-map-table {
        description
          "Flow monitor map configuration";
        uses FLOW-MONITOR-MAP;
      }
      container flow-monitor-map-performance-table {
        description
          "Configure a performance traffic flow monitor map";
        uses FLOW-MONITOR-MAP;
      }
    }
  }
  augment "/ncs:devices/ncs:device/ncs:live-status" {
    container net-flow {
      tailf:ncs-device-type "netconf";
      tailf:display-when "not(../../ncs:module) or ../../ncs:module[ncs:name='Cisco-IOS-XR-traffmon-netflow-cfg'] or (../../ncs:live-status-protocol[not(ncs:capability)]) or (../../ncs:live-status-protocol/ncs:capability/ncs:module[.='Cisco-IOS-XR-traffmon-netflow-cfg'])";
      description
        "NetFlow Configuration";
      container flow-exporter-maps {
        description
          "Configure a flow exporter map";
        list flow-exporter-map {
          key "exporter-map-name";
          description
            "Exporter map name";
          container udp {
            description
              "Use UDP as transport protocol";
            leaf destination-port {
              type uint32 {
                range "1024..65535";
              }
              description
                "Configure Destination UDP port";
            }
          }
          container destination {
            description
              "Configure export destination (collector)";
            leaf ip-address {
              type inet:ipv4-address-no-zone;
              description
                "Destination IPv4 address";
            }
            leaf ipv6-address {
              type inet:ipv6-address-no-zone;
              description
                "IPV6 address of the tunnel destination";
            }
            leaf vrf-name {
              type xr:Cisco-ios-xr-string {
                length "1..32";
              }
              description
                "VRF name";
            }
          }
          container version {
            presence "Indicates a version node is configured.";
            description
              "Specify export version parameters";
            container options {
              description
                "Specify options for exporting templates";
              leaf interface-table-export-timeout {
                type Nf-export-timeout;
                units "second";
                description
                  "Specify timeout for exporting interface
                   table";
              }
              leaf sampler-table-export-timeout {
                type Nf-export-timeout;
                units "second";
                description
                  "Specify timeout for exporting sampler table";
              }
              leaf vrf-table-export-timeout {
                type Nf-export-timeout;
                units "second";
                description
                  "Specify timeout for exporting vrf table";
              }
            }
            leaf version-type {
              type Nf-export-version;
              // NCS drop mandatory statement
              description
                "Export version number";
            }
            leaf options-template-timeout {
              type Nf-template-timeout;
              units "second";
              // NCS drop default statement
              description
                "Option template configuration options";
            }
            leaf common-template-timeout {
              type Nf-template-timeout;
              units "second";
              // NCS drop default statement
              description
                "Specify custom timeout for the template";
            }
            leaf data-template-timeout {
              type Nf-template-timeout;
              units "second";
              // NCS drop default statement
              description
                "Data template configuration options";
            }
          }
          leaf source-interface {
            type xr:Interface-name;
            description
              "Configure source interface for collector";
          }
          leaf dscp {
            type uint32 {
              range "0..63";
            }
            description
              "Specify DSCP value for export packets";
          }
          leaf packet-length {
            type uint32 {
              range "512..1468";
            }
            description
              "Configure Maximum Value for Export Packet size";
          }
          leaf exporter-map-name {
            type Nf-map-name;
            description
              "Exporter map name";
          }
        }
      }
      container flow-sampler-maps {
        description
          "Flow sampler map configuration";
        list flow-sampler-map {
          key "sampler-map-name";
          description
            "Sampler map name";
          container sampling-modes {
            description
              "Configure packet sampling mode";
            list sampling-mode {
              key "mode";
              description
                "Configure sampling mode";
              leaf mode {
                type Nf-sampling-mode;
                description
                  "Sampling mode";
              }
              leaf sample-number {
                type Nf-sample-number;
                // NCS drop mandatory statement
                description
                  "Number of packets to be sampled in the
                   sampling interval";
              }
              leaf interval {
                type Nf-sample-interval;
                // NCS drop mandatory statement
                description
                  "Sampling interval in units of packets";
              }
            }
          }
          leaf sampler-map-name {
            type Nf-map-name;
            description
              "Sampler map name";
          }
        }
      }
      container flow-monitor-map-table {
        description
          "Flow monitor map configuration";
        uses live_ncs_FLOW-MONITOR-MAP;
      }
      container flow-monitor-map-performance-table {
        description
          "Configure a performance traffic flow monitor map";
        uses live_ncs_FLOW-MONITOR-MAP;
      }
    }
  }
  augment "/ncs:devices/ncs:template/ncs:ned-id/ncs:config" {
    container net-flow {
      description
        "NetFlow Configuration";
      container flow-exporter-maps {
        description
          "Configure a flow exporter map";
        list flow-exporter-map {
          // NCS patched for predictable order
          ordered-by user;
          key "exporter-map-name";
          description
            "Exporter map name";
          container udp {
            description
              "Use UDP as transport protocol";
            leaf destination-port {
              type string;
              description
                "Configure Destination UDP port";
            }
          }
          container destination {
            description
              "Configure export destination (collector)";
            leaf ip-address {
              type string;
              description
                "Destination IPv4 address";
            }
            leaf ipv6-address {
              type string;
              description
                "IPV6 address of the tunnel destination";
            }
            leaf vrf-name {
              type string;
              description
                "VRF name";
            }
          }
          container version {
            presence "Indicates a version node is configured.";
            description
              "Specify export version parameters";
            container options {
              description
                "Specify options for exporting templates";
              leaf interface-table-export-timeout {
                type string;
                units "second";
                description
                  "Specify timeout for exporting interface
                   table";
              }
              leaf sampler-table-export-timeout {
                type string;
                units "second";
                description
                  "Specify timeout for exporting sampler table";
              }
              leaf vrf-table-export-timeout {
                type string;
                units "second";
                description
                  "Specify timeout for exporting vrf table";
              }
            }
            leaf version-type {
              type string;
              // NCS drop mandatory statement
              description
                "Export version number";
            }
            leaf options-template-timeout {
              type string;
              units "second";
              // NCS drop default statement
              description
                "Option template configuration options";
            }
            leaf common-template-timeout {
              type string;
              units "second";
              // NCS drop default statement
              description
                "Specify custom timeout for the template";
            }
            leaf data-template-timeout {
              type string;
              units "second";
              // NCS drop default statement
              description
                "Data template configuration options";
            }
          }
          leaf source-interface {
            type string;
            description
              "Configure source interface for collector";
          }
          leaf dscp {
            type string;
            description
              "Specify DSCP value for export packets";
          }
          leaf packet-length {
            type string;
            description
              "Configure Maximum Value for Export Packet size";
          }
          leaf exporter-map-name {
            type string;
            description
              "Exporter map name";
          }
        }
      }
      container flow-sampler-maps {
        description
          "Flow sampler map configuration";
        list flow-sampler-map {
          // NCS patched for predictable order
          ordered-by user;
          key "sampler-map-name";
          description
            "Sampler map name";
          container sampling-modes {
            description
              "Configure packet sampling mode";
            list sampling-mode {
              // NCS patched for predictable order
              ordered-by user;
              key "mode";
              description
                "Configure sampling mode";
              leaf mode {
                type string;
                description
                  "Sampling mode";
              }
              leaf sample-number {
                type string;
                // NCS drop mandatory statement
                description
                  "Number of packets to be sampled in the
                   sampling interval";
              }
              leaf interval {
                type string;
                // NCS drop mandatory statement
                description
                  "Sampling interval in units of packets";
              }
            }
          }
          leaf sampler-map-name {
            type string;
            description
              "Sampler map name";
          }
        }
      }
      container flow-monitor-map-table {
        description
          "Flow monitor map configuration";
        uses ncs_template_FLOW-MONITOR-MAP;
      }
      container flow-monitor-map-performance-table {
        description
          "Configure a performance traffic flow monitor map";
        uses ncs_template_FLOW-MONITOR-MAP;
      }
    }
  }
  augment "/ncs:devices/ncs:template/ncs:ned-id/ncs:config/a1:interface-configurations/a1:interface-configuration" {
    container flow-protocols {
      description
        "Interface netflow configuration";
      list flow-protocol {
        // NCS patched for predictable order
        ordered-by user;
        key "flow-protocol";
        description
          "Configure netflow flow protocol";
        leaf flow-protocol {
          type string;
          description
            "Netflow Flow Protocol";
        }
        list direction {
          // NCS patched for predictable order
          ordered-by user;
          list monitor-info {
            // NCS patched for predictable order
            ordered-by user;
            key "monitor-map";
            description
              "Specify a sampler for a flow monitor";
            leaf monitor-map {
              type string;
              description
                "Flow monitor map name";
            }
          }
          list monitor-info-sampler-map {
            // NCS patched for predictable order
            ordered-by user;
            key "sampler-map monitor-map";
            description
              "Specify a sampler for a flow monitor";
            leaf sampler-map {
              type string;
              description
                "Sampler map name";
            }
            leaf monitor-map {
              type string;
              description
                "Flow monitor map name";
            }
          }
          key "flow-direction";
          description
            "Configure netflow flow direction";
          leaf flow-direction {
            type string;
            description
              "Netflow Flow Direction";
          }
        }
      }
    }
    description
      "This augment extends the configuration data of
       'Cisco-IOS-XR-ifmgr-cfg'";
  }
  augment "/ncs:devices/ncs:device/ncs:live-status/a1:interface-configurations/a1:interface-configuration" {
    container flow-protocols {
      tailf:ncs-device-type "netconf";
      tailf:display-when "not(../../../../ncs:module) or ../../../../ncs:module[ncs:name='Cisco-IOS-XR-traffmon-netflow-cfg'] or (../../../../ncs:live-status-protocol[not(ncs:capability)]) or (../../../../ncs:live-status-protocol/ncs:capability/ncs:module[.='Cisco-IOS-XR-traffmon-netflow-cfg'])";
      description
        "Interface netflow configuration";
      list flow-protocol {
        key "flow-protocol";
        description
          "Configure netflow flow protocol";
        leaf flow-protocol {
          type Nf-flow-protocol;
          description
            "Netflow Flow Protocol";
        }
        list direction {
          list monitor-info {
            key "monitor-map";
            description
              "Specify a sampler for a flow monitor";
            leaf monitor-map {
              type xr:Cisco-ios-xr-string;
              description
                "Flow monitor map name";
            }
          }
          list monitor-info-sampler-map {
            key "sampler-map monitor-map";
            description
              "Specify a sampler for a flow monitor";
            leaf sampler-map {
              type xr:Cisco-ios-xr-string;
              description
                "Sampler map name";
            }
            leaf monitor-map {
              type xr:Cisco-ios-xr-string;
              description
                "Flow monitor map name";
            }
          }
          key "flow-direction";
          description
            "Configure netflow flow direction";
          leaf flow-direction {
            type Nf-flow-direction;
            description
              "Netflow Flow Direction";
          }
        }
      }
    }
    description
      "This augment extends the configuration data of
       'Cisco-IOS-XR-ifmgr-cfg'";
  }
  augment "/ncs:devices/ncs:device/ncs:config/a1:interface-configurations/a1:interface-configuration" {
    container flow-protocols {
      tailf:ncs-device-type "netconf";
      tailf:display-when "not(../../../../ncs:module) or ../../../../ncs:module[ncs:name='Cisco-IOS-XR-traffmon-netflow-cfg']";
      description
        "Interface netflow configuration";
      list flow-protocol {
        key "flow-protocol";
        description
          "Configure netflow flow protocol";
        leaf flow-protocol {
          type Nf-flow-protocol;
          description
            "Netflow Flow Protocol";
        }
        list direction {
          list monitor-info {
            key "monitor-map";
            description
              "Specify a sampler for a flow monitor";
            leaf monitor-map {
              type xr:Cisco-ios-xr-string;
              description
                "Flow monitor map name";
            }
          }
          list monitor-info-sampler-map {
            key "sampler-map monitor-map";
            description
              "Specify a sampler for a flow monitor";
            leaf sampler-map {
              type xr:Cisco-ios-xr-string;
              description
                "Sampler map name";
            }
            leaf monitor-map {
              type xr:Cisco-ios-xr-string;
              description
                "Flow monitor map name";
            }
          }
          key "flow-direction";
          description
            "Configure netflow flow direction";
          leaf flow-direction {
            type Nf-flow-direction;
            description
              "Netflow Flow Direction";
          }
        }
      }
    }
    description
      "This augment extends the configuration data of
       'Cisco-IOS-XR-ifmgr-cfg'";
  }
}
