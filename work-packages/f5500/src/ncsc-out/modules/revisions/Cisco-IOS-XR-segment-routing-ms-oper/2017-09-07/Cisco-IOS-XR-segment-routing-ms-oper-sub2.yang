submodule Cisco-IOS-XR-segment-routing-ms-oper-sub2 {
  // Generated by yanger -t ncs
  tailf:mount-id f5500-nc-1.0:f5500-nc-1.0;

  belongs-to Cisco-IOS-XR-segment-routing-ms-oper {
    prefix Cisco-IOS-XR-segment-routing-ms-oper-sub2;
  }

  import ietf-inet-types {
    prefix inet;
  }
  include Cisco-IOS-XR-segment-routing-ms-oper-sub3 {
    revision-date 2017-09-07;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR segment-routing-ms package operational data.

     Copyright (c) 2013-2018 by Cisco Systems, Inc.
     All rights reserved.";

  revision 2017-09-07 {
    description
      "Fixed type translation error.";
  }
  revision 2015-11-09 {
    description
      "IOS XR 6.0 revision.";
  }

  typedef Srms-af {
    type enumeration {
      enum "none" {
        value 0;
        description
          "None";
      }
      enum "ipv4" {
        value 1;
        description
          "IPv4";
      }
      enum "ipv6" {
        value 2;
        description
          "IPv6";
      }
    }
    description
      "Srms af";
  }

  grouping ncs_template_ADDR1 {
    description
      "ADDR1";
    leaf af {
      type string;
      description
        "AF";
    }
    leaf ipv4 {
      // NCS drop when statement
      type string;
      description
        "IPv4";
    }
    leaf ipv6 {
      // NCS drop when statement
      type string;
      description
        "IPv6";
    }
  }

  grouping ncs_template_SRMS-L2-ADJ-T-B {
    description
      "SRMA show bag";
    container nexthop-address {
      description
        "Nexthop address";
      uses ncs_template_ADDR1;
    }
    leaf interface-name {
      type string;
      description
        "Interface name";
    }
    leaf sid-value-xr {
      type string;
      description
        "SID Value";
    }
    leaf sid-type-xr {
      type string;
      description
        "SID type";
    }
    leaf address-family {
      type string;
      description
        "Interface address family";
    }
    leaf has-nexthop {
      type string;
      description
        "Has nexthop";
    }
    leaf interface-count {
      type string;
      description
        "Interface count";
    }
    leaf interface-delete-count {
      type string;
      description
        "Interface delete count";
    }
  }

  grouping ncs_rpc_notif_ADDR1 {
    description
      "ADDR1";
    leaf af {
      type Srms-af;
      description
        "AF";
    }
    leaf ipv4 {
      when "../af = 'ipv4'" {
        tailf:xpath-root 3;
        description
          "../AF = 'IPv4'";
      }
      type inet:ipv4-address;
      description
        "IPv4";
    }
    leaf ipv6 {
      when "../af = 'ipv6'" {
        tailf:xpath-root 3;
        description
          "../AF = 'IPv6'";
      }
      type In6-addr-t-b;
      description
        "IPv6";
    }
  }

  grouping ncs_rpc_notif_SRMS-L2-ADJ-T-B {
    description
      "SRMA show bag";
    container nexthop-address {
      description
        "Nexthop address";
      uses ncs_rpc_notif_ADDR1;
    }
    leaf interface-name {
      type string {
        length "0..64";
      }
      description
        "Interface name";
    }
    leaf sid-value-xr {
      type uint32;
      description
        "SID Value";
    }
    leaf sid-type-xr {
      type uint32;
      description
        "SID type";
    }
    leaf address-family {
      type uint32;
      description
        "Interface address family";
    }
    leaf has-nexthop {
      type boolean;
      description
        "Has nexthop";
    }
    leaf interface-count {
      type int32;
      description
        "Interface count";
    }
    leaf interface-delete-count {
      type int32;
      description
        "Interface delete count";
    }
  }

  grouping live_ncs_ADDR1 {
    description
      "ADDR1";
    leaf af {
      type Srms-af;
      description
        "AF";
    }
    leaf ipv4 {
      // NCS drop when statement
      type inet:ipv4-address;
      description
        "IPv4";
    }
    leaf ipv6 {
      // NCS drop when statement
      type In6-addr-t-b;
      description
        "IPv6";
    }
  }

  grouping live_ncs_SRMS-L2-ADJ-T-B {
    description
      "SRMA show bag";
    container nexthop-address {
      description
        "Nexthop address";
      uses live_ncs_ADDR1;
    }
    leaf interface-name {
      type string {
        length "0..64";
      }
      description
        "Interface name";
    }
    leaf sid-value-xr {
      type uint32;
      description
        "SID Value";
    }
    leaf sid-type-xr {
      type uint32;
      description
        "SID type";
    }
    leaf address-family {
      type uint32;
      description
        "Interface address family";
    }
    leaf has-nexthop {
      type boolean;
      description
        "Has nexthop";
    }
    leaf interface-count {
      type int32;
      description
        "Interface count";
    }
    leaf interface-delete-count {
      type int32;
      description
        "Interface delete count";
    }
  }

  grouping ADDR1 {
    description
      "ADDR1";
    leaf af {
      type Srms-af;
      description
        "AF";
    }
    leaf ipv4 {
      when "../af = 'ipv4'" {
        tailf:xpath-root 3;
        description
          "../AF = 'IPv4'";
      }
      type inet:ipv4-address;
      description
        "IPv4";
    }
    leaf ipv6 {
      when "../af = 'ipv6'" {
        tailf:xpath-root 3;
        description
          "../AF = 'IPv6'";
      }
      type In6-addr-t-b;
      description
        "IPv6";
    }
  }

  grouping SRMS-L2-ADJ-T-B {
    description
      "SRMA show bag";
    container nexthop-address {
      description
        "Nexthop address";
      uses ADDR1;
    }
    leaf interface-name {
      type string {
        length "0..64";
      }
      description
        "Interface name";
    }
    leaf sid-value-xr {
      type uint32;
      description
        "SID Value";
    }
    leaf sid-type-xr {
      type uint32;
      description
        "SID type";
    }
    leaf address-family {
      type uint32;
      description
        "Interface address family";
    }
    leaf has-nexthop {
      type boolean;
      description
        "Has nexthop";
    }
    leaf interface-count {
      type int32;
      description
        "Interface count";
    }
    leaf interface-delete-count {
      type int32;
      description
        "Interface delete count";
    }
  }
}
