module Cisco-IOS-XR-sysadmin-sm-hw-mod {
  // Generated by yanger -t ncs
  tailf:mount-id f5500-nc-1.0:f5500-nc-1.0;
  tailf:ncs-device-type "netconf";

  namespace "http://www.cisco.com/ns/yang/Cisco-IOS-XR-sysadmin-sm-hw-mod";
  prefix Cisco-IOS-XR-sysadmin-sm-hw-mod;

  import tailf-common {
    prefix tailf;
  }
  import Cisco-IOS-XR-sysadmin-types {
    prefix calvados;
  }
  import "f5500-nc-1.0" {
    prefix "f5500-nc-1.0";
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains definitions
     for the Calvados model objects.

     This module contains a collection of YANG
     definitions for Cisco IOS-XR SysAdmin configuration.

     This module holds Shelf Management HW module data.

     Copyright(c) 2012-2017 by Cisco Systems, Inc.
     All rights reserved.

     Copyright (c) 2012-2018 by Cisco Systems, Inc.
     All rights reserved.";

  revision 2017-04-12 {
    description
      "Changed namespace and module name";
  }

  grouping ncs_template_hw-module-config-group {
    uses ncs_template_hw-module-shutdown-config-group;
    uses ncs_template_hw-module-reset-auto-disable-config-group;
    uses ncs_template_hw-module-offline-config-group;
  }

  grouping ncs_template_hw-module-shutdown-config-group {
    container shutdown {
      list location {
        // NCS patched for predictable order
        ordered-by user;
        key "location";
        leaf location {
          type string;
          // NCS drop mandatory statement
        }
      }
    }
  }

  grouping ncs_template_hw-module-reset-auto-disable-config-group {
    container reset {
      container auto {
        container disable {
          list location {
            // NCS patched for predictable order
            ordered-by user;
            key "location";
            leaf location {
              type string;
              // NCS drop mandatory statement
            }
          }
        }
      }
    }
  }

  grouping ncs_template_hw-module-offline-config-group {
    container offline {
      list location {
        // NCS patched for predictable order
        ordered-by user;
        key "location";
        leaf location {
          type string;
          // NCS drop mandatory statement
        }
      }
    }
  }

  grouping ncs_template_hw-module-action-group {
    uses ncs_template_hw-module-reload-action-group;
    uses ncs_template_hw-module-bootmedia-action-group;
    uses ncs_template_hw-module-shutdown-action-group;
    uses ncs_template_hw-module-offline-action-group;
    uses ncs_template_hw-module-online-action-group;
  }

  grouping ncs_template_hw-module-bootmedia-action-group {
    // NCS drop config false container cbootmedia
  }

  grouping ncs_template_hw-module-reload-action-group;

  grouping ncs_template_hw-module-shutdown-action-group;

  grouping ncs_template_hw-module-offline-action-group;

  grouping ncs_template_hw-module-online-action-group;

  grouping ncs_rpc_notif_hw-module-config-group {
    uses ncs_rpc_notif_hw-module-shutdown-config-group;
    uses ncs_rpc_notif_hw-module-reset-auto-disable-config-group;
    uses ncs_rpc_notif_hw-module-offline-config-group;
  }

  grouping ncs_rpc_notif_hw-module-shutdown-config-group {
    container shutdown {
      list location {
        key "location";
        leaf location {
          type calvados:location-id;
          mandatory true;
        }
      }
    }
  }

  grouping ncs_rpc_notif_hw-module-reset-auto-disable-config-group {
    container reset {
      container auto {
        container disable {
          list location {
            key "location";
            leaf location {
              type calvados:location-id;
              mandatory true;
            }
          }
        }
      }
    }
  }

  grouping ncs_rpc_notif_hw-module-offline-config-group {
    container offline {
      list location {
        key "location";
        leaf location {
          type calvados:location-id;
          mandatory true;
        }
      }
    }
  }

  grouping ncs_rpc_notif_hw-module-action-group {
    uses ncs_rpc_notif_hw-module-reload-action-group;
    uses ncs_rpc_notif_hw-module-bootmedia-action-group;
    uses ncs_rpc_notif_hw-module-shutdown-action-group;
    uses ncs_rpc_notif_hw-module-offline-action-group;
    uses ncs_rpc_notif_hw-module-online-action-group;
  }

  grouping ncs_rpc_notif_hw-module-bootmedia-action-group {
    container cbootmedia {
      config false;
      list bootmedia {
        key "bootmedium";
        config false;
        leaf bootmedium {
          type string;
        }
        // NCS drop tailf:action
      }
    }
  }

  grouping ncs_rpc_notif_hw-module-reload-action-group {
    // NCS drop tailf:action
  }

  grouping ncs_rpc_notif_hw-module-shutdown-action-group {
    // NCS drop tailf:action
  }

  grouping ncs_rpc_notif_hw-module-offline-action-group {
    // NCS drop tailf:action
  }

  grouping ncs_rpc_notif_hw-module-online-action-group {
    // NCS drop tailf:action
  }

  grouping live_ncs_hw-module-config-group {
    uses live_ncs_hw-module-shutdown-config-group;
    uses live_ncs_hw-module-reset-auto-disable-config-group;
    uses live_ncs_hw-module-offline-config-group;
  }

  grouping live_ncs_hw-module-shutdown-config-group {
    container shutdown {
      list location {
        key "location";
        leaf location {
          type calvados:location-id;
          // NCS drop mandatory statement
        }
      }
    }
  }

  grouping live_ncs_hw-module-reset-auto-disable-config-group {
    container reset {
      container auto {
        container disable {
          list location {
            key "location";
            leaf location {
              type calvados:location-id;
              // NCS drop mandatory statement
            }
          }
        }
      }
    }
  }

  grouping live_ncs_hw-module-offline-config-group {
    container offline {
      list location {
        key "location";
        leaf location {
          type calvados:location-id;
          // NCS drop mandatory statement
        }
      }
    }
  }

  grouping live_ncs_hw-module-action-group {
    uses live_ncs_hw-module-reload-action-group;
    uses live_ncs_hw-module-bootmedia-action-group;
    uses live_ncs_hw-module-shutdown-action-group;
    uses live_ncs_hw-module-offline-action-group;
    uses live_ncs_hw-module-online-action-group;
  }

  grouping live_ncs_hw-module-bootmedia-action-group {
    container cbootmedia {
      list bootmedia {
        key "bootmedium";
        leaf bootmedium {
          type string;
        }
        tailf:action reload {
          tailf:actionpoint ncsproxy {
            tailf:internal;
          }
          output {
            leaf result {
              type string;
              mandatory true;
            }
          }
        }
      }
    }
  }

  grouping live_ncs_hw-module-reload-action-group {
    tailf:action reload {
      tailf:actionpoint ncsproxy {
        tailf:internal;
      }
      input {
        leaf force {
          type empty;
          mandatory false;
        }
        leaf noprompt {
          type empty;
          mandatory false;
        }
        leaf warm {
          type empty;
          mandatory false;
        }
      }
      output {
        leaf result {
          type string;
          mandatory true;
        }
      }
    }
  }

  grouping live_ncs_hw-module-shutdown-action-group {
    tailf:action shutdown {
      tailf:actionpoint ncsproxy {
        tailf:internal;
      }
      input {
        choice shutdown_polarity {
          mandatory false;
          case shutdown {
            leaf force {
              type empty;
              mandatory false;
            }
          }
          case powerup {
            leaf disable {
              type empty;
              mandatory false;
            }
          }
        }
      }
      output {
        leaf result {
          type string;
          mandatory true;
        }
      }
    }
  }

  grouping live_ncs_hw-module-offline-action-group {
    tailf:action offline {
      tailf:actionpoint ncsproxy {
        tailf:internal;
      }
      output {
        leaf result {
          type string;
          mandatory true;
        }
      }
    }
  }

  grouping live_ncs_hw-module-online-action-group {
    tailf:action online {
      tailf:actionpoint ncsproxy {
        tailf:internal;
      }
      output {
        leaf result {
          type string;
          mandatory true;
        }
      }
    }
  }

  grouping hw-module-config-group {
    uses hw-module-shutdown-config-group;
    uses hw-module-reset-auto-disable-config-group;
    uses hw-module-offline-config-group;
  }

  grouping hw-module-shutdown-config-group {
    container shutdown {
      list location {
        key "location";
        leaf location {
          type calvados:location-id;
          mandatory true;
        }
      }
    }
  }

  grouping hw-module-reset-auto-disable-config-group {
    container reset {
      container auto {
        container disable {
          list location {
            key "location";
            leaf location {
              type calvados:location-id;
              mandatory true;
            }
          }
        }
      }
    }
  }

  grouping hw-module-offline-config-group {
    container offline {
      list location {
        key "location";
        leaf location {
          type calvados:location-id;
          mandatory true;
        }
      }
    }
  }

  grouping hw-module-action-group {
    uses hw-module-reload-action-group;
    uses hw-module-bootmedia-action-group;
    uses hw-module-shutdown-action-group;
    uses hw-module-offline-action-group;
    uses hw-module-online-action-group;
  }

  grouping hw-module-bootmedia-action-group {
    // NCS drop config false container cbootmedia
  }

  grouping hw-module-reload-action-group {
    tailf:action reload {
      tailf:actionpoint ncsproxy {
        tailf:internal;
      }
      input {
        leaf force {
          type empty;
          mandatory false;
        }
        leaf noprompt {
          type empty;
          mandatory false;
        }
        leaf warm {
          type empty;
          mandatory false;
        }
      }
      output {
        leaf result {
          type string;
          mandatory true;
        }
      }
    }
  }

  grouping hw-module-shutdown-action-group {
    tailf:action shutdown {
      tailf:actionpoint ncsproxy {
        tailf:internal;
      }
      input {
        choice shutdown_polarity {
          mandatory false;
          case shutdown {
            leaf force {
              type empty;
              mandatory false;
            }
          }
          case powerup {
            leaf disable {
              type empty;
              mandatory false;
            }
          }
        }
      }
      output {
        leaf result {
          type string;
          mandatory true;
        }
      }
    }
  }

  grouping hw-module-offline-action-group {
    tailf:action offline {
      tailf:actionpoint ncsproxy {
        tailf:internal;
      }
      output {
        leaf result {
          type string;
          mandatory true;
        }
      }
    }
  }

  grouping hw-module-online-action-group {
    tailf:action online {
      tailf:actionpoint ncsproxy {
        tailf:internal;
      }
      output {
        leaf result {
          type string;
          mandatory true;
        }
      }
    }
  }
}
