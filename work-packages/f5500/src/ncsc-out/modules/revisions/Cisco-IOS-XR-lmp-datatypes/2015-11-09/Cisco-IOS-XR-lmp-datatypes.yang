module Cisco-IOS-XR-lmp-datatypes {
  // Generated by yanger -t ncs
  tailf:mount-id f5500-nc-1.0:f5500-nc-1.0;
  tailf:ncs-device-type "netconf";

  namespace "http://cisco.com/ns/yang/Cisco-IOS-XR-lmp-datatypes";
  prefix Cisco-IOS-XR-lmp-datatypes;

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of generally useful
     derived YANG data types.

     Copyright (c) 2013-2018 by Cisco Systems, Inc.
     All rights reserved.";

  revision 2015-11-09 {
    description
      "IOS XR 6.0 revision.";
  }

  typedef Olm-switching-cap {
    type enumeration {
      enum "lsc" {
        value 150;
        description
          "Lambda switch capable";
      }
      enum "fsc" {
        value 200;
        description
          "Fiber switch capable";
      }
    }
    description
      "Olm switching cap";
  }

  typedef Olm-addr {
    type enumeration {
      enum "ipv4" {
        value 101;
        description
          "IPv4 address";
      }
      enum "ipv6" {
        value 102;
        description
          "IPv6 address";
      }
      enum "unnumbered" {
        value 103;
        description
          "Unnumbered address";
      }
      enum "nsap" {
        value 104;
        description
          "NSAP address";
      }
    }
    description
      "Olm addr";
  }
}
