module Cisco-IOS-XR-gnss-cfg {
  // Generated by yanger -t ncs
  tailf:mount-id f5500-nc-1.0:f5500-nc-1.0;
  tailf:ncs-device-type "netconf";

  namespace "http://cisco.com/ns/yang/Cisco-IOS-XR-gnss-cfg";
  prefix Cisco-IOS-XR-gnss-cfg;

  import Cisco-IOS-XR-config-mda-cfg {
    prefix node;
  }
  import Cisco-IOS-XR-freqsync-datatypes {
    prefix dt1;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR gnss package configuration.

     This YANG module augments the
       Cisco-IOS-XR-config-mda-cfg
     module with configuration data.

     Copyright (c) 2013-2018 by Cisco Systems, Inc.
     All rights reserved.";

  revision 2017-09-07 {
    description
      "Fixed type translation error.";
  }
  revision 2015-11-09 {
    description
      "IOS XR 6.0 revision.";
  }

  grouping ncs_template_NODE-CFG {
    description
      "active/preconfigured nodes configuration";
    container gnss-receivers {
      description
        "Configuration for a GNSS receiver";
      list gnss-receiver {
        // NCS patched for predictable order
        ordered-by user;
        key "number";
        description
          "Configuration for a GNSS receiver";
        container frequency-synchronization {
          description
            "Frequency Synchronization clock configuraiton";
          container output-quality-level {
            description
              "Set the output quality level";
            leaf quality-level-option {
              type string;
              // NCS drop must statement
              description
                "Quality level option";
            }
            leaf exact-quality-level-value {
              type string;
              // NCS drop must statement
              description
                "Exact quality level value";
            }
            leaf min-quality-level-value {
              type string;
              // NCS drop must statement
              description
                "Minimum quality level value";
            }
            leaf max-quality-level-value {
              type string;
              // NCS drop must statement
              description
                "Maximum quality level value";
            }
          }
          container input-quality-level {
            description
              "Set the input quality level";
            leaf quality-level-option {
              type string;
              // NCS drop must statement
              description
                "Quality level option";
            }
            leaf exact-quality-level-value {
              type string;
              // NCS drop must statement
              description
                "Exact quality level value";
            }
            leaf min-quality-level-value {
              type string;
              // NCS drop must statement
              description
                "Minimum quality level value";
            }
            leaf max-quality-level-value {
              type string;
              // NCS drop must statement
              description
                "Maximum quality level value";
            }
          }
          leaf ssm-disable {
            type empty;
            description
              "Disable SSM on this source";
          }
          leaf priority {
            type string;
            // NCS drop default statement
            description
              "Set the priority of this source";
          }
          leaf selection-input {
            type empty;
            description
              "Assign this source as a selection input";
          }
          leaf wait-to-restore-time {
            type string;
            // NCS drop default statement
            description
              "Set the wait-to-restore time for this source";
          }
          leaf time-of-day-priority {
            type string;
            // NCS drop default statement
            description
              "Set the time-of-day priority of this source";
          }
        }
        leaf enable {
          type empty;
          description
            "Enable the GNSS receiver";
        }
        leaf snr-threshold {
          type string;
          // NCS drop default statement
          description
            "Set the satellite SNR threshold, in dB-Hz";
        }
        leaf traim-threshold {
          type string;
          units "microsecond";
          // NCS drop default statement
          description
            "Set the satellite TRAIM threshold, in
             microseconds";
        }
        leaf polarity1pps {
          type string;
          // NCS drop default statement
          description
            "Set the GNSS receiver 1PPS polarity";
        }
        leaf cable-delay-compensation {
          type string;
          units "nanosecond";
          // NCS drop default statement
          description
            "Set the cable-delay compensation, in
             nanoseconds";
        }
        leaf anti-jam-disable {
          type empty;
          description
            "Stop running the GNSS receiver in anti-jam
             mode";
        }
        leaf pdop-threshold {
          type string;
          // NCS drop default statement
          description
            "Set the satellite PDOP threshold";
        }
        leaf elevation-threshold {
          type string;
          // NCS drop default statement
          description
            "Set the satellite elevation threshold, in
             degrees";
        }
        leaf shutdown {
          type empty;
          description
            "Shutdown the GNSS receiver";
        }
        leaf constellation {
          type string;
          // NCS drop default statement
          description
            "Set the constellation to be used by the GNSS
             receiver";
        }
        leaf number {
          type string;
          description
            "Receiver number";
        }
      }
    }
  }

  grouping ncs_rpc_notif_NODE-CFG {
    description
      "active/preconfigured nodes configuration";
    container gnss-receivers {
      description
        "Configuration for a GNSS receiver";
      list gnss-receiver {
        key "number";
        description
          "Configuration for a GNSS receiver";
        container frequency-synchronization {
          description
            "Frequency Synchronization clock configuraiton";
          container output-quality-level {
            description
              "Set the output quality level";
            leaf quality-level-option {
              type dt1:Fsync-ql-option;
              must '../exact-quality-level-value or ../min-quality-level-value or ../max-quality-level-value' {
                tailf:xpath-root 3;
              }
              description
                "Quality level option";
            }
            leaf exact-quality-level-value {
              type dt1:Fsync-ql-value;
              must '../quality-level-option and not(../min-quality-level-value or ../max-quality-level-value)' {
                tailf:xpath-root 3;
              }
              description
                "Exact quality level value";
            }
            leaf min-quality-level-value {
              type dt1:Fsync-ql-value;
              must '../quality-level-option and not(../exact-quality-level-value)' {
                tailf:xpath-root 3;
              }
              description
                "Minimum quality level value";
            }
            leaf max-quality-level-value {
              type dt1:Fsync-ql-value;
              must '../quality-level-option and not(../exact-quality-level-value)' {
                tailf:xpath-root 3;
              }
              description
                "Maximum quality level value";
            }
          }
          container input-quality-level {
            description
              "Set the input quality level";
            leaf quality-level-option {
              type dt1:Fsync-ql-option;
              must '../exact-quality-level-value or ../min-quality-level-value or ../max-quality-level-value' {
                tailf:xpath-root 3;
              }
              description
                "Quality level option";
            }
            leaf exact-quality-level-value {
              type dt1:Fsync-ql-value;
              must '../quality-level-option and not(../min-quality-level-value or ../max-quality-level-value)' {
                tailf:xpath-root 3;
              }
              description
                "Exact quality level value";
            }
            leaf min-quality-level-value {
              type dt1:Fsync-ql-value;
              must '../quality-level-option and not(../exact-quality-level-value)' {
                tailf:xpath-root 3;
              }
              description
                "Minimum quality level value";
            }
            leaf max-quality-level-value {
              type dt1:Fsync-ql-value;
              must '../quality-level-option and not(../exact-quality-level-value)' {
                tailf:xpath-root 3;
              }
              description
                "Maximum quality level value";
            }
          }
          leaf ssm-disable {
            type empty;
            description
              "Disable SSM on this source";
          }
          leaf priority {
            type uint32 {
              range "1..254";
            }
            default "100";
            description
              "Set the priority of this source";
          }
          leaf selection-input {
            type empty;
            description
              "Assign this source as a selection input";
          }
          leaf wait-to-restore-time {
            type uint32 {
              range "0..12";
            }
            default "5";
            description
              "Set the wait-to-restore time for this source";
          }
          leaf time-of-day-priority {
            type uint32 {
              range "1..254";
            }
            default "100";
            description
              "Set the time-of-day priority of this source";
          }
        }
        leaf enable {
          type empty;
          description
            "Enable the GNSS receiver";
        }
        leaf snr-threshold {
          type uint32 {
            range "0..40";
          }
          default "0";
          description
            "Set the satellite SNR threshold, in dB-Hz";
        }
        leaf traim-threshold {
          type uint32 {
            range "0..2";
          }
          units "microsecond";
          default "0";
          description
            "Set the satellite TRAIM threshold, in
             microseconds";
        }
        leaf polarity1pps {
          type dt1:Gnss1pps-polarity;
          default "positive";
          description
            "Set the GNSS receiver 1PPS polarity";
        }
        leaf cable-delay-compensation {
          type int32 {
            range "-1000000..1000000";
          }
          units "nanosecond";
          default "0";
          description
            "Set the cable-delay compensation, in
             nanoseconds";
        }
        leaf anti-jam-disable {
          type empty;
          description
            "Stop running the GNSS receiver in anti-jam
             mode";
        }
        leaf pdop-threshold {
          type uint32 {
            range "0..10";
          }
          default "0";
          description
            "Set the satellite PDOP threshold";
        }
        leaf elevation-threshold {
          type uint32 {
            range "0..40";
          }
          default "0";
          description
            "Set the satellite elevation threshold, in
             degrees";
        }
        leaf shutdown {
          type empty;
          description
            "Shutdown the GNSS receiver";
        }
        leaf constellation {
          type dt1:Gnss-constellation;
          default "auto";
          description
            "Set the constellation to be used by the GNSS
             receiver";
        }
        leaf number {
          type uint32;
          description
            "Receiver number";
        }
      }
    }
  }

  grouping live_ncs_NODE-CFG {
    description
      "active/preconfigured nodes configuration";
    container gnss-receivers {
      description
        "Configuration for a GNSS receiver";
      list gnss-receiver {
        key "number";
        description
          "Configuration for a GNSS receiver";
        container frequency-synchronization {
          description
            "Frequency Synchronization clock configuraiton";
          container output-quality-level {
            description
              "Set the output quality level";
            leaf quality-level-option {
              type dt1:Fsync-ql-option;
              // NCS drop must statement
              description
                "Quality level option";
            }
            leaf exact-quality-level-value {
              type dt1:Fsync-ql-value;
              // NCS drop must statement
              description
                "Exact quality level value";
            }
            leaf min-quality-level-value {
              type dt1:Fsync-ql-value;
              // NCS drop must statement
              description
                "Minimum quality level value";
            }
            leaf max-quality-level-value {
              type dt1:Fsync-ql-value;
              // NCS drop must statement
              description
                "Maximum quality level value";
            }
          }
          container input-quality-level {
            description
              "Set the input quality level";
            leaf quality-level-option {
              type dt1:Fsync-ql-option;
              // NCS drop must statement
              description
                "Quality level option";
            }
            leaf exact-quality-level-value {
              type dt1:Fsync-ql-value;
              // NCS drop must statement
              description
                "Exact quality level value";
            }
            leaf min-quality-level-value {
              type dt1:Fsync-ql-value;
              // NCS drop must statement
              description
                "Minimum quality level value";
            }
            leaf max-quality-level-value {
              type dt1:Fsync-ql-value;
              // NCS drop must statement
              description
                "Maximum quality level value";
            }
          }
          leaf ssm-disable {
            type empty;
            description
              "Disable SSM on this source";
          }
          leaf priority {
            type uint32 {
              range "1..254";
            }
            // NCS drop default statement
            description
              "Set the priority of this source";
          }
          leaf selection-input {
            type empty;
            description
              "Assign this source as a selection input";
          }
          leaf wait-to-restore-time {
            type uint32 {
              range "0..12";
            }
            // NCS drop default statement
            description
              "Set the wait-to-restore time for this source";
          }
          leaf time-of-day-priority {
            type uint32 {
              range "1..254";
            }
            // NCS drop default statement
            description
              "Set the time-of-day priority of this source";
          }
        }
        leaf enable {
          type empty;
          description
            "Enable the GNSS receiver";
        }
        leaf snr-threshold {
          type uint32 {
            range "0..40";
          }
          // NCS drop default statement
          description
            "Set the satellite SNR threshold, in dB-Hz";
        }
        leaf traim-threshold {
          type uint32 {
            range "0..2";
          }
          units "microsecond";
          // NCS drop default statement
          description
            "Set the satellite TRAIM threshold, in
             microseconds";
        }
        leaf polarity1pps {
          type dt1:Gnss1pps-polarity;
          // NCS drop default statement
          description
            "Set the GNSS receiver 1PPS polarity";
        }
        leaf cable-delay-compensation {
          type int32 {
            range "-1000000..1000000";
          }
          units "nanosecond";
          // NCS drop default statement
          description
            "Set the cable-delay compensation, in
             nanoseconds";
        }
        leaf anti-jam-disable {
          type empty;
          description
            "Stop running the GNSS receiver in anti-jam
             mode";
        }
        leaf pdop-threshold {
          type uint32 {
            range "0..10";
          }
          // NCS drop default statement
          description
            "Set the satellite PDOP threshold";
        }
        leaf elevation-threshold {
          type uint32 {
            range "0..40";
          }
          // NCS drop default statement
          description
            "Set the satellite elevation threshold, in
             degrees";
        }
        leaf shutdown {
          type empty;
          description
            "Shutdown the GNSS receiver";
        }
        leaf constellation {
          type dt1:Gnss-constellation;
          // NCS drop default statement
          description
            "Set the constellation to be used by the GNSS
             receiver";
        }
        leaf number {
          type uint32;
          description
            "Receiver number";
        }
      }
    }
  }

  grouping NODE-CFG {
    description
      "active/preconfigured nodes configuration";
    container gnss-receivers {
      description
        "Configuration for a GNSS receiver";
      list gnss-receiver {
        key "number";
        description
          "Configuration for a GNSS receiver";
        container frequency-synchronization {
          description
            "Frequency Synchronization clock configuraiton";
          container output-quality-level {
            description
              "Set the output quality level";
            leaf quality-level-option {
              type dt1:Fsync-ql-option;
              must '../exact-quality-level-value or ../min-quality-level-value or ../max-quality-level-value' {
                tailf:xpath-root 3;
              }
              description
                "Quality level option";
            }
            leaf exact-quality-level-value {
              type dt1:Fsync-ql-value;
              must '../quality-level-option and not(../min-quality-level-value or ../max-quality-level-value)' {
                tailf:xpath-root 3;
              }
              description
                "Exact quality level value";
            }
            leaf min-quality-level-value {
              type dt1:Fsync-ql-value;
              must '../quality-level-option and not(../exact-quality-level-value)' {
                tailf:xpath-root 3;
              }
              description
                "Minimum quality level value";
            }
            leaf max-quality-level-value {
              type dt1:Fsync-ql-value;
              must '../quality-level-option and not(../exact-quality-level-value)' {
                tailf:xpath-root 3;
              }
              description
                "Maximum quality level value";
            }
          }
          container input-quality-level {
            description
              "Set the input quality level";
            leaf quality-level-option {
              type dt1:Fsync-ql-option;
              must '../exact-quality-level-value or ../min-quality-level-value or ../max-quality-level-value' {
                tailf:xpath-root 3;
              }
              description
                "Quality level option";
            }
            leaf exact-quality-level-value {
              type dt1:Fsync-ql-value;
              must '../quality-level-option and not(../min-quality-level-value or ../max-quality-level-value)' {
                tailf:xpath-root 3;
              }
              description
                "Exact quality level value";
            }
            leaf min-quality-level-value {
              type dt1:Fsync-ql-value;
              must '../quality-level-option and not(../exact-quality-level-value)' {
                tailf:xpath-root 3;
              }
              description
                "Minimum quality level value";
            }
            leaf max-quality-level-value {
              type dt1:Fsync-ql-value;
              must '../quality-level-option and not(../exact-quality-level-value)' {
                tailf:xpath-root 3;
              }
              description
                "Maximum quality level value";
            }
          }
          leaf ssm-disable {
            type empty;
            description
              "Disable SSM on this source";
          }
          leaf priority {
            type uint32 {
              range "1..254";
            }
            default "100";
            description
              "Set the priority of this source";
          }
          leaf selection-input {
            type empty;
            description
              "Assign this source as a selection input";
          }
          leaf wait-to-restore-time {
            type uint32 {
              range "0..12";
            }
            default "5";
            description
              "Set the wait-to-restore time for this source";
          }
          leaf time-of-day-priority {
            type uint32 {
              range "1..254";
            }
            default "100";
            description
              "Set the time-of-day priority of this source";
          }
        }
        leaf enable {
          type empty;
          description
            "Enable the GNSS receiver";
        }
        leaf snr-threshold {
          type uint32 {
            range "0..40";
          }
          default "0";
          description
            "Set the satellite SNR threshold, in dB-Hz";
        }
        leaf traim-threshold {
          type uint32 {
            range "0..2";
          }
          units "microsecond";
          default "0";
          description
            "Set the satellite TRAIM threshold, in
             microseconds";
        }
        leaf polarity1pps {
          type dt1:Gnss1pps-polarity;
          default "positive";
          description
            "Set the GNSS receiver 1PPS polarity";
        }
        leaf cable-delay-compensation {
          type int32 {
            range "-1000000..1000000";
          }
          units "nanosecond";
          default "0";
          description
            "Set the cable-delay compensation, in
             nanoseconds";
        }
        leaf anti-jam-disable {
          type empty;
          description
            "Stop running the GNSS receiver in anti-jam
             mode";
        }
        leaf pdop-threshold {
          type uint32 {
            range "0..10";
          }
          default "0";
          description
            "Set the satellite PDOP threshold";
        }
        leaf elevation-threshold {
          type uint32 {
            range "0..40";
          }
          default "0";
          description
            "Set the satellite elevation threshold, in
             degrees";
        }
        leaf shutdown {
          type empty;
          description
            "Shutdown the GNSS receiver";
        }
        leaf constellation {
          type dt1:Gnss-constellation;
          default "auto";
          description
            "Set the constellation to be used by the GNSS
             receiver";
        }
        leaf number {
          type uint32;
          description
            "Receiver number";
        }
      }
    }
  }

  augment "/ncs:devices/ncs:template/ncs:ned-id/ncs:config/node:active-nodes/node:active-node" {
    uses ncs_template_NODE-CFG;
    description
      "This augment extends active nodes configuration";
  }
  augment "/ncs:devices/ncs:device/ncs:live-status/node:active-nodes/node:active-node" {
    uses live_ncs_NODE-CFG {
      refine gnss-receivers {
        tailf:ncs-device-type "netconf";
        tailf:display-when "not(../../../../ncs:module) or ../../../../ncs:module[ncs:name='Cisco-IOS-XR-gnss-cfg'] or (../../../../ncs:live-status-protocol[not(ncs:capability)]) or (../../../../ncs:live-status-protocol/ncs:capability/ncs:module[.='Cisco-IOS-XR-gnss-cfg'])";
      }
    }
    description
      "This augment extends active nodes configuration";
  }
  augment "/ncs:devices/ncs:device/ncs:config/node:active-nodes/node:active-node" {
    uses NODE-CFG {
      refine gnss-receivers {
        tailf:ncs-device-type "netconf";
        tailf:display-when "not(../../../../ncs:module) or ../../../../ncs:module[ncs:name='Cisco-IOS-XR-gnss-cfg']";
      }
    }
    description
      "This augment extends active nodes configuration";
  }
  augment "/ncs:devices/ncs:template/ncs:ned-id/ncs:config/node:preconfigured-nodes/node:preconfigured-node" {
    uses ncs_template_NODE-CFG;
    description
      "This augment extends preconfigured nodes
       configuration";
  }
  augment "/ncs:devices/ncs:device/ncs:live-status/node:preconfigured-nodes/node:preconfigured-node" {
    uses live_ncs_NODE-CFG {
      refine gnss-receivers {
        tailf:ncs-device-type "netconf";
        tailf:display-when "not(../../../../ncs:module) or ../../../../ncs:module[ncs:name='Cisco-IOS-XR-gnss-cfg'] or (../../../../ncs:live-status-protocol[not(ncs:capability)]) or (../../../../ncs:live-status-protocol/ncs:capability/ncs:module[.='Cisco-IOS-XR-gnss-cfg'])";
      }
    }
    description
      "This augment extends preconfigured nodes
       configuration";
  }
  augment "/ncs:devices/ncs:device/ncs:config/node:preconfigured-nodes/node:preconfigured-node" {
    uses NODE-CFG {
      refine gnss-receivers {
        tailf:ncs-device-type "netconf";
        tailf:display-when "not(../../../../ncs:module) or ../../../../ncs:module[ncs:name='Cisco-IOS-XR-gnss-cfg']";
      }
    }
    description
      "This augment extends preconfigured nodes
       configuration";
  }
}
