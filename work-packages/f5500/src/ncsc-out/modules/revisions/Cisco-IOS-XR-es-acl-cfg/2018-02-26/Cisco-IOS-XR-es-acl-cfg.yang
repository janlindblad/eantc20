module Cisco-IOS-XR-es-acl-cfg {
  // Generated by yanger -t ncs
  tailf:mount-id f5500-nc-1.0:f5500-nc-1.0;
  tailf:ncs-device-type "netconf";

  namespace "http://cisco.com/ns/yang/Cisco-IOS-XR-es-acl-cfg";
  prefix Cisco-IOS-XR-es-acl-cfg;

  import Cisco-IOS-XR-types {
    prefix xr;
  }
  import Cisco-IOS-XR-common-acl-datatypes {
    prefix dt1;
  }
  include Cisco-IOS-XR-es-ace-cfg {
    revision-date 2018-02-26;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR es-acl package configuration.

     This module contains definitions
     for the following management objects:
       es-acl: Layer 2 ACL configuration data

     Copyright (c) 2013-2018 by Cisco Systems, Inc.
     All rights reserved.";

  revision 2018-02-26 {
    description
      "6.5.1 revision. Fixed datatypes for below leaves: - vlan1, vlan2 - inner-vlan1, inner-vlan2 - cos, inner-cos - dei, inner-dei - log-option.";
  }
  revision 2018-02-21 {
    description
      "Changed ether-type-number to type Hex-integer-16.";
  }
  revision 2018-01-03 {
    description
      "6.4.1 revision. Fixed a few typos in the description.";
  }
  revision 2015-11-09 {
    description
      "IOS XR 6.0 revision.";
  }

  typedef Es-acl-name {
    type xr:Cisco-ios-xr-string {
      length "1..64";
    }
    description
      "Es acl name";
  }

  augment "/ncs:devices/ncs:device/ncs:config" {
    container es-acl {
      tailf:ncs-device-type "netconf";
      tailf:display-when "not(../../ncs:module) or ../../ncs:module[ncs:name='Cisco-IOS-XR-es-acl-cfg']";
      description
        "Layer 2 ACL configuration data";
      container accesses {
        description
          "Table of access lists";
        list access {
          key "name";
          description
            "An ACL";
          container access-list-entries {
            description
              "ACL entry table; contains list of access list
               entries";
            list access-list-entry {
              key "sequence-number";
              description
                "An ACL entry; either a description (remark)
                 or anAccess List Entry to match against";
              leaf sequence-number {
                type dt1:Acl-sequence-number-range;
                description
                  "Sequence number of access list entry";
              }
              uses ES-ACL-CONFIG-ACE;
            }
          }
          leaf name {
            type Es-acl-name;
            description
              "Name of the access list";
          }
        }
      }
    }
  }
  augment "/ncs:devices/ncs:device/ncs:live-status" {
    container es-acl {
      tailf:ncs-device-type "netconf";
      tailf:display-when "not(../../ncs:module) or ../../ncs:module[ncs:name='Cisco-IOS-XR-es-acl-cfg'] or (../../ncs:live-status-protocol[not(ncs:capability)]) or (../../ncs:live-status-protocol/ncs:capability/ncs:module[.='Cisco-IOS-XR-es-acl-cfg'])";
      description
        "Layer 2 ACL configuration data";
      container accesses {
        description
          "Table of access lists";
        list access {
          key "name";
          description
            "An ACL";
          container access-list-entries {
            description
              "ACL entry table; contains list of access list
               entries";
            list access-list-entry {
              key "sequence-number";
              description
                "An ACL entry; either a description (remark)
                 or anAccess List Entry to match against";
              leaf sequence-number {
                type dt1:Acl-sequence-number-range;
                description
                  "Sequence number of access list entry";
              }
              uses live_ncs_ES-ACL-CONFIG-ACE;
            }
          }
          leaf name {
            type Es-acl-name;
            description
              "Name of the access list";
          }
        }
      }
    }
  }
  augment "/ncs:devices/ncs:template/ncs:ned-id/ncs:config" {
    container es-acl {
      description
        "Layer 2 ACL configuration data";
      container accesses {
        description
          "Table of access lists";
        list access {
          // NCS patched for predictable order
          ordered-by user;
          key "name";
          description
            "An ACL";
          container access-list-entries {
            description
              "ACL entry table; contains list of access list
               entries";
            list access-list-entry {
              // NCS patched for predictable order
              ordered-by user;
              key "sequence-number";
              description
                "An ACL entry; either a description (remark)
                 or anAccess List Entry to match against";
              leaf sequence-number {
                type string;
                description
                  "Sequence number of access list entry";
              }
              uses ncs_template_ES-ACL-CONFIG-ACE;
            }
          }
          leaf name {
            type string;
            description
              "Name of the access list";
          }
        }
      }
    }
  }
}
