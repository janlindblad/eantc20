module Cisco-IOS-XR-pmengine-oper {
  // Generated by yanger -t ncs
  tailf:mount-id f5500-nc-1.0:f5500-nc-1.0;
  tailf:ncs-device-type "netconf";

  namespace "http://cisco.com/ns/yang/Cisco-IOS-XR-pmengine-oper";
  prefix Cisco-IOS-XR-pmengine-oper;

  import Cisco-IOS-XR-types {
    prefix xr;
  }
  include Cisco-IOS-XR-pmengine-oper-sub1 {
    revision-date 2017-09-07;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR pmengine package operational data.

     This module contains definitions
     for the following management objects:
       performance-management: performace data
       performance-management-history: performance management history

     Copyright (c) 2013-2018 by Cisco Systems, Inc.
     All rights reserved.";

  revision 2017-09-07 {
    description
      "Fixed type translation error.";
  }
  revision 2017-05-01 {
    description
      "Fixing backward compatibility error in module.";
  }
  revision 2017-03-30 {
    description
      "OTU PRBS Stats Added";
  }
  revision 2015-11-09 {
    description
      "IOS XR 6.0 revision.";
  }

  augment "/ncs:devices/ncs:device/ncs:config" {
    // NCS drop config false container 'performance-management'
    // NCS drop config false container 'performance-management-history'
  }
  augment "/ncs:devices/ncs:device/ncs:live-status" {
    container performance-management {
      tailf:ncs-device-type "netconf";
      tailf:display-when "not(../../ncs:module) or ../../ncs:module[ncs:name='Cisco-IOS-XR-pmengine-oper'] or (../../ncs:live-status-protocol[not(ncs:capability)]) or (../../ncs:live-status-protocol/ncs:capability/ncs:module[.='Cisco-IOS-XR-pmengine-oper'])";
      description
        "performace data";
      container macsec {
        description
          "MACSEC controller performance data";
        container macsec-ports {
          description
            "Port performance data";
          list macsec-port {
            key "name";
            description
              "Port performance data";
            container macsec-current {
              description
                "port current performance data";
              container macsec-minute15 {
                description
                  "port current performance data";
                container macsec-minute15secyifs {
                  description
                    "port current performance data";
                  list macsec-minute15secyif {
                    key "number";
                    description
                      "port 15-minute secy-if performance data";
                    leaf number {
                      type uint32;
                      description
                        "channel number";
                    }
                    uses live_ncs_PM-SECY-IF-PARAS;
                  }
                }
                container macsec-minute15secyrxes {
                  description
                    "port current performance data";
                  list macsec-minute15secyrx {
                    key "number";
                    description
                      "port 15-minute secy-rx performance data";
                    leaf number {
                      type uint32;
                      description
                        "channel number";
                    }
                    uses live_ncs_PM-SECY-RX-PARAS;
                  }
                }
                container macsec-minute15secytxes {
                  description
                    "port current performance data";
                  list macsec-minute15secytx {
                    key "number";
                    description
                      "port 15-minute secy-tx performance data";
                    leaf number {
                      type uint32;
                      description
                        "channel number";
                    }
                    uses live_ncs_PM-SECY-TX-PARAS;
                  }
                }
                container macsec-minute15-ether-s {
                  description
                    "port current performance data";
                  list macsec-minute15-ether {
                    key "number";
                    description
                      "port 15-minute ether performance data";
                    leaf number {
                      type uint32;
                      description
                        "channel number";
                    }
                    uses live_ncs_PM-ETHERNET-PARAS;
                  }
                }
              }
              container macsec-second30 {
                description
                  "port current performance data";
                container macsec-second30secyifs {
                  description
                    "port current performance data";
                  list macsec-second30secyif {
                    key "number";
                    description
                      "port 30-sec secy-if performance data";
                    leaf number {
                      type uint32;
                      description
                        "channel number";
                    }
                    uses live_ncs_PM-SECY-IF-PARAS;
                  }
                }
                container macsec-second30secyrxes {
                  description
                    "port current performance data";
                  list macsec-second30secyrx {
                    key "number";
                    description
                      "port 30-sec secy-rx performance data";
                    leaf number {
                      type uint32;
                      description
                        "channel number";
                    }
                    uses live_ncs_PM-SECY-RX-PARAS;
                  }
                }
                container macsec-second30-ether-s {
                  description
                    "port current performance data";
                  list macsec-second30-ether {
                    key "number";
                    description
                      "port 30-sec ether performance data";
                    leaf number {
                      type uint32;
                      description
                        "channel number";
                    }
                    uses live_ncs_PM-ETHERNET-PARAS;
                  }
                }
                container macsec-second30secytxes {
                  description
                    "port current performance data";
                  list macsec-second30secytx {
                    key "number";
                    description
                      "port 30-sec secy-tx performance data";
                    leaf number {
                      type uint32;
                      description
                        "channel number";
                    }
                    uses live_ncs_PM-SECY-TX-PARAS;
                  }
                }
              }
              container macsec-hour24 {
                description
                  "port current performance data";
                container macsec-hour24-ether-s {
                  description
                    "port current performance data";
                  list macsec-hour24-ether {
                    key "number";
                    description
                      "port 24 hour ether performance data";
                    leaf number {
                      type uint32;
                      description
                        "channel number";
                    }
                    uses live_ncs_PM-ETHERNET-PARAS;
                  }
                }
                container macsec-hour24secyifs {
                  description
                    "port current performance data";
                  list macsec-hour24secyif {
                    key "number";
                    description
                      "port 24 hour secy-if performance data";
                    leaf number {
                      type uint32;
                      description
                        "channel number";
                    }
                    uses live_ncs_PM-SECY-IF-PARAS;
                  }
                }
                container macsec-hour24secyrxes {
                  description
                    "port current performance data";
                  list macsec-hour24secyrx {
                    key "number";
                    description
                      "port 24 hour secy-rx performance data";
                    leaf number {
                      type uint32;
                      description
                        "channel number";
                    }
                    uses live_ncs_PM-SECY-RX-PARAS;
                  }
                }
                container macsec-hour24secytxes {
                  description
                    "port current performance data";
                  list macsec-hour24secytx {
                    key "number";
                    description
                      "port 24 hour secy-tx performance data";
                    leaf number {
                      type uint32;
                      description
                        "channel number";
                    }
                    uses live_ncs_PM-SECY-TX-PARAS;
                  }
                }
              }
            }
            leaf name {
              type xr:Interface-name;
              description
                "Port name";
            }
          }
        }
      }
      container ho-vc {
        description
          "HO_VC controller performance data";
        container ho-vc-ports {
          description
            "Port performance data";
          list ho-vc-port {
            key "name";
            description
              "Port performance data";
            container ho-vc-current {
              description
                "port current performance data";
              container ho-vc-hour24 {
                description
                  "port current performance data";
                container ho-vc-hour24-paths {
                  description
                    "port current performance data";
                  list ho-vc-hour24-path {
                    key "number";
                    description
                      "port 24 hour Path performance data";
                    leaf number {
                      type uint32;
                      description
                        "channel number";
                    }
                    uses live_ncs_PM-HO-VC-PARAS;
                  }
                }
              }
              container ho-vc-minute15 {
                description
                  "port current performance data";
                container ho-vc-minute15-paths {
                  description
                    "port current performance data";
                  list ho-vc-minute15-path {
                    key "number";
                    description
                      "port 15-minute Path performance data";
                    leaf number {
                      type uint32;
                      description
                        "channel number";
                    }
                    uses live_ncs_PM-HO-VC-PARAS;
                  }
                }
              }
            }
            leaf name {
              type xr:Interface-name;
              description
                "Port name";
            }
          }
        }
      }
      container odu {
        description
          "ODU controller performance data";
        container odu-ports {
          description
            "Port performance data";
          list odu-port {
            key "name";
            description
              "Port performance data";
            container odu-current {
              description
                "port current performance data";
              container odu-minute15 {
                description
                  "port current performance data";
                container odu-minute15gfps {
                  description
                    "port current performance data";
                  list odu-minute15gfp {
                    key "number";
                    description
                      "port 15-minute otn performance data";
                    leaf number {
                      type uint32;
                      description
                        "channel number";
                    }
                    uses live_ncs_PM-GFP-PARAS;
                  }
                }
                container odu-minute15prbses {
                  description
                    "port current performance data";
                  list odu-minute15prbs {
                    key "number";
                    description
                      "port 15-minute prbs performance data";
                    leaf number {
                      type uint32;
                      description
                        "channel number";
                    }
                    uses live_ncs_PM-PRBS-PARAS;
                  }
                }
                container odu-minute15otns {
                  description
                    "port current performance data";
                  list odu-minute15otn {
                    key "number";
                    description
                      "port 15-minute otn performance data";
                    leaf number {
                      type uint32;
                      description
                        "channel number";
                    }
                    uses live_ncs_PM-OTN-PARAS;
                  }
                }
              }
              container odu-hour24 {
                description
                  "port current performance data";
                container odu-hour24prbses {
                  description
                    "port 24 hour performance data";
                  list odu-hour24prbs {
                    key "number";
                    description
                      "port 24 hour otn performance data";
                    leaf number {
                      type uint32;
                      description
                        "channel number";
                    }
                    uses live_ncs_PM-PRBS-PARAS;
                  }
                }
                container odu-hour24gfps {
                  description
                    "port 24 hour performance data";
                  list odu-hour24gfp {
                    key "number";
                    description
                      "port 24 hour otn performance data";
                    leaf number {
                      type uint32;
                      description
                        "channel number";
                    }
                    uses live_ncs_PM-GFP-PARAS;
                  }
                }
                container odu-hour24otns {
                  description
                    "port 24 hour performance data";
                  list odu-hour24otn {
                    key "number";
                    description
                      "port 24 hour otn performance data";
                    leaf number {
                      type uint32;
                      description
                        "channel number";
                    }
                    uses live_ncs_PM-OTN-PARAS;
                  }
                }
              }
            }
            leaf name {
              type xr:Interface-name;
              description
                "Port name";
            }
          }
        }
      }
      container otu {
        description
          "OTU controller performance data";
        container otu-ports {
          description
            "Port performance data";
          list otu-port {
            key "name";
            description
              "Port performance data";
            container otu-current {
              description
                "port current performance data";
              container otu-minute15 {
                description
                  "port current performance data";
                container otu-minute15fecs {
                  description
                    "port current performance data";
                  list otu-minute15fec {
                    key "number";
                    description
                      "port 15-minute fec performance data";
                    leaf number {
                      type uint32;
                      description
                        "channel number";
                    }
                    uses live_ncs_PM-FEC-PARAS;
                  }
                }
                container otu-minute15otns {
                  description
                    "port current performance data";
                  list otu-minute15otn {
                    key "number";
                    description
                      "port 15-minute otn performance data";
                    leaf number {
                      type uint32;
                      description
                        "channel number";
                    }
                    uses live_ncs_PM-OTN-PARAS;
                  }
                }
                container otu-minute15prbses {
                  description
                    "port current performance data";
                  list otu-minute15prbs {
                    key "number";
                    description
                      "port 15-minute prbs performance data";
                    leaf number {
                      type uint32;
                      description
                        "channel number";
                    }
                    uses live_ncs_PM-PRBS-PARAS;
                  }
                }
              }
              container otu-second30 {
                description
                  "port current performance data";
                container otu-second30fecs {
                  description
                    "port current performance data";
                  list otu-second30fec {
                    key "number";
                    description
                      "port 30-sec fec performance data";
                    leaf number {
                      type uint32;
                      description
                        "channel number";
                    }
                    uses live_ncs_PM-FEC-PARAS;
                  }
                }
                container otu-second30otns {
                  description
                    "port current performance data";
                  list otu-second30otn {
                    key "number";
                    description
                      "port 30-sec otn performance data";
                    leaf number {
                      type uint32;
                      description
                        "channel number";
                    }
                    uses live_ncs_PM-OTN-PARAS;
                  }
                }
              }
              container otu-hour24 {
                description
                  "port current performance data";
                container otu-hour24fecs {
                  description
                    "port current performance data";
                  list otu-hour24fec {
                    key "number";
                    description
                      "port 24 hour fec performance data";
                    leaf number {
                      type uint32;
                      description
                        "channel number";
                    }
                    uses live_ncs_PM-FEC-PARAS;
                  }
                }
                container otu-hour24prbses {
                  description
                    "port 24 hour performance data";
                  list otu-hour24prbs {
                    key "number";
                    description
                      "port 24 hour otn performance data";
                    leaf number {
                      type uint32;
                      description
                        "channel number";
                    }
                    uses live_ncs_PM-PRBS-PARAS;
                  }
                }
                container otu-hour24otns {
                  description
                    "port 24 hour performance data";
                  list otu-hour24otn {
                    key "number";
                    description
                      "port 24 hour otn performance data";
                    leaf number {
                      type uint32;
                      description
                        "channel number";
                    }
                    uses live_ncs_PM-OTN-PARAS;
                  }
                }
              }
            }
            leaf name {
              type xr:Interface-name;
              description
                "Port name";
            }
          }
        }
      }
      container stm {
        description
          "STM controller performance data";
        container stm-ports {
          description
            "Port performance data";
          list stm-port {
            key "name";
            description
              "Port performance data";
            container stm-current {
              description
                "port current performance data";
              container stm-hour24 {
                description
                  "port current performance data";
                container stm-hour24stms {
                  description
                    "port current performance data";
                  list stm-hour24stm {
                    key "number";
                    description
                      "port 24 hour stm performance data";
                    leaf number {
                      type uint32;
                      description
                        "channel number";
                    }
                    uses live_ncs_PM-STM-PARAS;
                  }
                }
              }
              container stm-minute15 {
                description
                  "port current performance data";
                container stm-minute15stms {
                  description
                    "port current performance data";
                  list stm-minute15stm {
                    key "number";
                    description
                      "port 15-minute stm performance data";
                    leaf number {
                      type uint32;
                      description
                        "channel number";
                    }
                    uses live_ncs_PM-STM-PARAS;
                  }
                }
              }
            }
            leaf name {
              type xr:Interface-name;
              description
                "Port name";
            }
          }
        }
      }
      container sonet {
        description
          "SONET controller performance data";
        container sonet-ports {
          description
            "Port performance data";
          list sonet-port {
            key "name";
            description
              "Port performance data";
            container sonet-current {
              description
                "port current performance data";
              container sonet-minute15 {
                description
                  "port current performance data";
                container sonet-minute15-paths {
                  description
                    "port current performance data";
                  list sonet-minute15-path {
                    key "number";
                    description
                      "port 15-minute Path performance data";
                    leaf number {
                      type uint32;
                      description
                        "channel number";
                    }
                    uses live_ncs_PM-SONET-PATH-PARAS;
                  }
                }
                container sonet-minute15ocns {
                  description
                    "port current performance data";
                  list sonet-minute15ocn {
                    key "number";
                    description
                      "port 15-minute ocn performance data";
                    leaf number {
                      type uint32;
                      description
                        "channel number";
                    }
                    uses live_ncs_PM-SONET-PARAS;
                  }
                }
              }
              container sonet-hour24 {
                description
                  "port current performance data";
                container sonet-hour24ocns {
                  description
                    "port current performance data";
                  list sonet-hour24ocn {
                    key "number";
                    description
                      "port 24 hour ocn performance data";
                    leaf number {
                      type uint32;
                      description
                        "channel number";
                    }
                    uses live_ncs_PM-SONET-PARAS;
                  }
                }
                container sonet-hour24-paths {
                  description
                    "port current performance data";
                  list sonet-hour24-path {
                    key "number";
                    description
                      "port 24 hour Path performance data";
                    leaf number {
                      type uint32;
                      description
                        "channel number";
                    }
                    uses live_ncs_PM-SONET-PATH-PARAS;
                  }
                }
              }
            }
            leaf name {
              type xr:Interface-name;
              description
                "Port name";
            }
          }
        }
      }
      container optics {
        description
          "OPTICS controller performance data";
        container optics-ports {
          description
            "Port performance data";
          list optics-port {
            key "name";
            description
              "Port performance data";
            container optics-current {
              description
                "port current performance data";
              container optics-hour24 {
                description
                  "port current performance data";
                container optics-hour24-optics {
                  description
                    "port 24 hour performance data";
                  list optics-hour24-optic {
                    key "number";
                    description
                      "port 24 hour optics performance data";
                    leaf number {
                      type uint32;
                      description
                        "channel number";
                    }
                    uses live_ncs_PM-OPTICS-PARAS;
                  }
                }
                container optics-hour24fecs {
                  description
                    "port current performance data";
                  list optics-hour24fec {
                    key "number";
                    description
                      "port 24 hour fec performance data";
                    leaf number {
                      type uint32;
                      description
                        "channel number";
                    }
                    uses live_ncs_PM-FEC-PARAS;
                  }
                }
              }
              container optics-minute15 {
                description
                  "port current performance data";
                container optics-minute15-optics {
                  description
                    "port current performance data";
                  list optics-minute15-optic {
                    key "number";
                    description
                      "port 15-minute optics performance data";
                    leaf number {
                      type uint32;
                      description
                        "channel number";
                    }
                    uses live_ncs_PM-OPTICS-PARAS;
                  }
                }
                container optics-minute15fecs {
                  description
                    "port current performance data";
                  list optics-minute15fec {
                    key "number";
                    description
                      "port 15-minute fec performance data";
                    leaf number {
                      type uint32;
                      description
                        "channel number";
                    }
                    uses live_ncs_PM-FEC-PARAS;
                  }
                }
              }
              container optics-second30 {
                description
                  "port current performance data";
                container optics-second30fecs {
                  description
                    "port current performance data";
                  list optics-second30fec {
                    key "number";
                    description
                      "port 30-second fec performance data";
                    leaf number {
                      type uint32;
                      description
                        "channel number";
                    }
                    uses live_ncs_PM-FEC-PARAS;
                  }
                }
                container optics-second30-optics {
                  description
                    "port current performance data";
                  list optics-second30-optic {
                    key "number";
                    description
                      "port 30-second optics performance data";
                    leaf number {
                      type uint32;
                      description
                        "channel number";
                    }
                    uses live_ncs_PM-OPTICS-PARAS;
                  }
                }
              }
            }
            leaf name {
              type xr:Interface-name;
              description
                "Port name";
            }
          }
        }
      }
      container sts {
        description
          "STS controller performance data";
        container sts-ports {
          description
            "Port performance data";
          list sts-port {
            key "name";
            description
              "Port performance data";
            container sts-current {
              description
                "port current performance data";
              container sts-minute15 {
                description
                  "port current performance data";
                container sts-minute15-paths {
                  description
                    "port current performance data";
                  list sts-minute15-path {
                    key "number";
                    description
                      "port 15-minute Path performance data";
                    leaf number {
                      type uint32;
                      description
                        "channel number";
                    }
                    uses live_ncs_PM-SONET-PATH-PARAS;
                  }
                }
              }
              container sts-hour24 {
                description
                  "port current performance data";
                container sts-hour24-paths {
                  description
                    "port current performance data";
                  list sts-hour24-path {
                    key "number";
                    description
                      "port 24 hour Path performance data";
                    leaf number {
                      type uint32;
                      description
                        "channel number";
                    }
                    uses live_ncs_PM-SONET-PATH-PARAS;
                  }
                }
              }
            }
            leaf name {
              type xr:Interface-name;
              description
                "Port name";
            }
          }
        }
      }
      container dwdm {
        description
          "DWDM controller performance data";
        container dwdm-ports {
          description
            "Port performance data";
          list dwdm-port {
            key "name";
            description
              "Port performance data";
            container dwdm-current {
              description
                "port current performance data";
              container dwdm-minute15 {
                description
                  "port current performance data";
                container dwdm-minute15fecs {
                  description
                    "port current performance data";
                  list dwdm-minute15fec {
                    key "number";
                    description
                      "port 15-minute fec performance data";
                    leaf number {
                      type uint32;
                      description
                        "channel number";
                    }
                    uses live_ncs_PM-FEC-PARAS;
                  }
                }
                container dwdm-minute15-optics {
                  description
                    "port current performance data";
                  list dwdm-minute15-optic {
                    key "number";
                    description
                      "port 15-minute optics performance data";
                    leaf number {
                      type uint32;
                      description
                        "channel number";
                    }
                    uses live_ncs_PM-OPTICS-PARAS;
                  }
                }
                container dwdm-minute15otns {
                  description
                    "port current performance data";
                  list dwdm-minute15otn {
                    key "number";
                    description
                      "port 15-minute otn performance data";
                    leaf number {
                      type uint32;
                      description
                        "channel number";
                    }
                    uses live_ncs_PM-OTN-PARAS;
                  }
                }
              }
              container dwdm-hour24 {
                description
                  "port current performance data";
                container dwdm-hour24-optics {
                  description
                    "port 24 hour performance data";
                  list dwdm-hour24-optic {
                    key "number";
                    description
                      "port 24 hour optics performance data";
                    leaf number {
                      type uint32;
                      description
                        "channel number";
                    }
                    uses live_ncs_PM-OPTICS-PARAS;
                  }
                }
                container dwdm-hour24fecs {
                  description
                    "port current performance data";
                  list dwdm-hour24fec {
                    key "number";
                    description
                      "port 24 hour fec performance data";
                    leaf number {
                      type uint32;
                      description
                        "channel number";
                    }
                    uses live_ncs_PM-FEC-PARAS;
                  }
                }
                container dwdm-hour24otns {
                  description
                    "port 24 hour performance data";
                  list dwdm-hour24otn {
                    key "number";
                    description
                      "port 24 hour otn performance data";
                    leaf number {
                      type uint32;
                      description
                        "channel number";
                    }
                    uses live_ncs_PM-OTN-PARAS;
                  }
                }
              }
            }
            leaf name {
              type xr:Interface-name;
              description
                "Port name";
            }
          }
        }
      }
      container oc {
        description
          "OC controller performance data";
        container oc-ports {
          description
            "Port performance data";
          list oc-port {
            key "name";
            description
              "Port performance data";
            container oc-current {
              description
                "port current performance data";
              container oc-hour24 {
                description
                  "port current performance data";
                container oc-hour24ocns {
                  description
                    "port current performance data";
                  list oc-hour24ocn {
                    key "number";
                    description
                      "port 24 hour ocn performance data";
                    leaf number {
                      type uint32;
                      description
                        "channel number";
                    }
                    uses live_ncs_PM-SONET-PARAS;
                  }
                }
              }
              container oc-minute15 {
                description
                  "port current performance data";
                container oc-minute15ocns {
                  description
                    "port current performance data";
                  list oc-minute15ocn {
                    key "number";
                    description
                      "port 15-minute ocn performance data";
                    leaf number {
                      type uint32;
                      description
                        "channel number";
                    }
                    uses live_ncs_PM-SONET-PARAS;
                  }
                }
              }
            }
            leaf name {
              type xr:Interface-name;
              description
                "Port name";
            }
          }
        }
      }
      container ethernet {
        description
          "EHERNET controller performance data";
        container ethernet-ports {
          description
            "Port performance data";
          list ethernet-port {
            key "name";
            description
              "Port performance data";
            container ethernet-current {
              description
                "port current performance data";
              container ethernet-second30 {
                description
                  "port current performance data";
                container second30-fecs {
                  description
                    "ETHERNET port interval performance data";
                  list second30-fec {
                    key "slot-number";
                    description
                      "ETHERNET port 30 second fec performance
                       data";
                    leaf slot-number {
                      type uint32;
                      description
                        "interval slot number";
                    }
                    uses live_ncs_PM-FEC-PARAS;
                  }
                }
                container second30pcses {
                  description
                    "ETHERNET port interval performance data";
                  list second30pcs {
                    key "slot-number";
                    description
                      "Ethernet port 30 second pcs  performance
                       data";
                    leaf slot-number {
                      type uint32;
                      description
                        "interval slot number";
                    }
                    uses live_ncs_PM-PCS-PARAS;
                  }
                }
                container second30-ethers {
                  description
                    "ETHERNET port interval performance data";
                  list second30-ether {
                    key "slot-number";
                    description
                      "ETHERNET port 30 second ether performance
                       data";
                    leaf slot-number {
                      type uint32;
                      description
                        "interval slot number";
                    }
                    uses live_ncs_PM-ETHERNET-PARAS;
                  }
                }
              }
              container ethernet-hour24 {
                description
                  "port current performance data";
                container ethernet-hour24-ether-s {
                  description
                    "port current performance data";
                  list ethernet-hour24-ether {
                    key "number";
                    description
                      "port 24 hour ethernet performance data";
                    leaf number {
                      type uint32;
                      description
                        "channel number";
                    }
                    uses live_ncs_PM-ETHERNET-PARAS;
                  }
                }
                container hour24pcses {
                  description
                    "port current performance data";
                  list hour24pcs {
                    key "number";
                    description
                      "Ethernet port 24 hour pcs performance data";
                    leaf number {
                      type uint32;
                      description
                        "channel number";
                    }
                    uses live_ncs_PM-PCS-PARAS;
                  }
                }
                container ethernet-hour24fecs {
                  description
                    "port current performance data";
                  list ethernet-hour24fec {
                    key "number";
                    description
                      "port 24 hour ethernet performance data";
                    leaf number {
                      type uint32;
                      description
                        "channel number";
                    }
                    uses live_ncs_PM-FEC-PARAS;
                  }
                }
              }
              container minute15 {
                description
                  "port current performance data";
                container minute15-fecs {
                  description
                    "ETHERNET port interval performance data";
                  list minute15-fec {
                    key "slot-number";
                    description
                      "ETHERNET port 15-minute fec performance
                       data";
                    leaf slot-number {
                      type uint32;
                      description
                        "interval slot number";
                    }
                    uses live_ncs_PM-FEC-PARAS;
                  }
                }
                container minute15pcses {
                  description
                    "ETHERNET port interval performance data";
                  list minute15pcs {
                    key "slot-number";
                    description
                      "ETHERNET port 15-minute pcs performance
                       data";
                    leaf slot-number {
                      type uint32;
                      description
                        "interval slot number";
                    }
                    uses live_ncs_PM-PCS-PARAS;
                  }
                }
                container minute15-ethers {
                  description
                    "ETHERNET port interval performance data";
                  list minute15-ether {
                    key "slot-number";
                    description
                      "ETHERNET port 15-minute ether performance
                       data";
                    leaf slot-number {
                      type uint32;
                      description
                        "interval slot number";
                    }
                    uses live_ncs_PM-ETHERNET-PARAS;
                  }
                }
              }
            }
            leaf name {
              type xr:Interface-name;
              description
                "Port name";
            }
          }
        }
      }
    }
    container performance-management-history {
      tailf:ncs-device-type "netconf";
      tailf:display-when "not(../../ncs:module) or ../../ncs:module[ncs:name='Cisco-IOS-XR-pmengine-oper'] or (../../ncs:live-status-protocol[not(ncs:capability)]) or (../../ncs:live-status-protocol/ncs:capability/ncs:module[.='Cisco-IOS-XR-pmengine-oper'])";
      description
        "performance management history";
      container global {
        description
          "global History performace data";
        container periodic {
          description
            "History performace data";
          container sonet-history {
            description
              "SONET controller History performance data";
            container sonet-port-histories {
              description
                "Port performance data";
              list sonet-port-history {
                key "name";
                description
                  "Port performance data";
                container sonet-minute15-history {
                  description
                    "port current performance data";
                  container sonet-minute15ocn-histories {
                    description
                      "port current performance data";
                    list sonet-minute15ocn-history {
                      key "number";
                      description
                        "port 15-minute ocn performance data";
                      container sonet-minute15ocn-time-line-instances {
                        description
                          "port current performance data";
                        list sonet-minute15ocn-time-line-instance {
                          key "number";
                          description
                            "port 15-minute otn performance data";
                          leaf number {
                            type uint32;
                            description
                              "History Index number";
                          }
                          uses live_ncs_PM-SONET-PARAS;
                        }
                      }
                      leaf number {
                        type uint32;
                        description
                          "channel number";
                      }
                    }
                  }
                  container sonet-minute15-path-histories {
                    description
                      "port current performance data";
                    list sonet-minute15-path-history {
                      key "number";
                      description
                        "port 15-minute Path performance data";
                      container sonet-minute15-path-time-line-instances {
                        description
                          "port current performance data";
                        list sonet-minute15-path-time-line-instance {
                          key "number";
                          description
                            "port 15-minute otn performance data";
                          leaf number {
                            type uint32;
                            description
                              "History Index number";
                          }
                          uses live_ncs_PM-SONET-PATH-PARAS;
                        }
                      }
                      leaf number {
                        type uint32;
                        description
                          "channel number";
                      }
                    }
                  }
                }
                container sonet-hour24-history {
                  description
                    "port current performance data";
                  container sonet-hour24-path-histories {
                    description
                      "port current performance data";
                    list sonet-hour24-path-history {
                      key "number";
                      description
                        "port 24 hour Path performance data";
                      container sonet-hour24-path-time-line-instances {
                        description
                          "port current performance data";
                        list sonet-hour24-path-time-line-instance {
                          key "number";
                          description
                            "port 15-minute otn performance data";
                          leaf number {
                            type uint32;
                            description
                              "History Index number";
                          }
                          uses live_ncs_PM-SONET-PATH-PARAS;
                        }
                      }
                      leaf number {
                        type uint32;
                        description
                          "channel number";
                      }
                    }
                  }
                  container sonet-hour24ocn-histories {
                    description
                      "port current performance data";
                    list sonet-hour24ocn-history {
                      key "number";
                      description
                        "port 24 hour ocn performance data";
                      container sonet-hour24ocn-time-line-instances {
                        description
                          "port current performance data";
                        list sonet-hour24ocn-time-line-instance {
                          key "number";
                          description
                            "port 15-minute otn performance data";
                          leaf number {
                            type uint32;
                            description
                              "History Index number";
                          }
                          uses live_ncs_PM-SONET-PARAS;
                        }
                      }
                      leaf number {
                        type uint32;
                        description
                          "channel number";
                      }
                    }
                  }
                }
                leaf name {
                  type xr:Interface-name;
                  description
                    "Port name";
                }
              }
            }
          }
          container sts-history {
            description
              "STS controller History performance data";
            container sts-port-histories {
              description
                "Port performance data";
              list sts-port-history {
                key "name";
                description
                  "Port performance data";
                container sts-minute15-history {
                  description
                    "port current performance data";
                  container sts-minute15-path-histories {
                    description
                      "port current performance data";
                    list sts-minute15-path-history {
                      key "number";
                      description
                        "port 15-minute Path performance data";
                      container sts-minute15-path-time-line-instances {
                        description
                          "port current performance data";
                        list sts-minute15-path-time-line-instance {
                          key "number";
                          description
                            "port 15-minute otn performance data";
                          leaf number {
                            type uint32;
                            description
                              "History Index number";
                          }
                          uses live_ncs_PM-SONET-PATH-PARAS;
                        }
                      }
                      leaf number {
                        type uint32;
                        description
                          "channel number";
                      }
                    }
                  }
                }
                container sts-hour24-history {
                  description
                    "port current performance data";
                  container sts-hour24-path-histories {
                    description
                      "port current performance data";
                    list sts-hour24-path-history {
                      key "number";
                      description
                        "port 24 hour Path performance data";
                      container sts-hour24-path-time-line-instances {
                        description
                          "port current performance data";
                        list sts-hour24-path-time-line-instance {
                          key "number";
                          description
                            "port 15-minute sts performance data";
                          leaf number {
                            type uint32;
                            description
                              "History Index number";
                          }
                          uses live_ncs_PM-SONET-PATH-PARAS;
                        }
                      }
                      leaf number {
                        type uint32;
                        description
                          "channel number";
                      }
                    }
                  }
                }
                leaf name {
                  type xr:Interface-name;
                  description
                    "Port name";
                }
              }
            }
          }
          container ethernet-history {
            description
              "EHERNET controller History performance data";
            container ethernet-port-histories {
              description
                "Port performance data";
              list ethernet-port-history {
                key "name";
                description
                  "Port performance data";
                container ethernet-second30-history {
                  description
                    "port current performance data";
                  container second30pcs-histories {
                    description
                      "ETHERNET port interval performance data";
                    list second30pcs-history {
                      key "slot-number";
                      description
                        "ETHERNET port 30 sec pcs performance data";
                      container second30pcs-time-line-instances {
                        description
                          "port current performance data";
                        list second30pcs-time-line-instance {
                          key "number";
                          description
                            "port 30 sec pcs performance data";
                          leaf number {
                            type uint32;
                            description
                              "History Index number";
                          }
                          uses live_ncs_PM-PCS-PARAS;
                        }
                      }
                      leaf slot-number {
                        type uint32;
                        description
                          "interval slot number";
                      }
                    }
                  }
                  container second30-ether-histories {
                    description
                      "ETHERNET port interval performance data";
                    list second30-ether-history {
                      key "slot-number";
                      description
                        "ETHERNET port 30 sec ether performance
                         data";
                      container second30-ether-time-line-instances {
                        description
                          "port current performance data";
                        list second30-ether-time-line-instance {
                          key "number";
                          description
                            "port 30 sec otn performance data";
                          leaf number {
                            type uint32;
                            description
                              "History Index number";
                          }
                          uses live_ncs_PM-ETHERNET-PARAS;
                        }
                      }
                      leaf slot-number {
                        type uint32;
                        description
                          "interval slot number";
                      }
                    }
                  }
                  container second30-fec-histories {
                    description
                      "ETHERNET port interval performance data";
                    list second30-fec-history {
                      key "slot-number";
                      description
                        "ETHERNET port 30 sec fec performance data";
                      container second30-fec-time-line-instances {
                        description
                          "port current performance data";
                        list second30-fec-time-line-instance {
                          key "number";
                          description
                            "port 30 sec fec performance data";
                          leaf number {
                            type uint32;
                            description
                              "History Index number";
                          }
                          uses live_ncs_PM-FEC-PARAS;
                        }
                      }
                      leaf slot-number {
                        type uint32;
                        description
                          "interval slot number";
                      }
                    }
                  }
                }
                container ethernet-hour24-history {
                  description
                    "port current performance data";
                  container hour24pcs-histories {
                    description
                      "port current performance data";
                    list hour24pcs-history {
                      key "number";
                      description
                        "port 24 hour ethernet performance data";
                      container hour24pcs-time-line-instances {
                        description
                          "port current performance data";
                        list hour24pcs-time-line-instance {
                          key "number";
                          description
                            "port 24-hour ethernet performance data";
                          leaf number {
                            type uint32;
                            description
                              "History Index number";
                          }
                          uses live_ncs_PM-PCS-PARAS;
                        }
                      }
                      leaf number {
                        type uint32;
                        description
                          "channel number";
                      }
                    }
                  }
                  container ethernet-hour24fec-histories {
                    description
                      "port current performance data";
                    list ethernet-hour24fec-history {
                      key "number";
                      description
                        "port 24 hour ethernet performance data";
                      container ethernet-hour24fec-time-line-instances {
                        description
                          "port current performance data";
                        list ethernet-hour24fec-time-line-instance {
                          key "number";
                          description
                            "port 24-hour ethernet performance data";
                          leaf number {
                            type uint32;
                            description
                              "History Index number";
                          }
                          uses live_ncs_PM-FEC-PARAS;
                        }
                      }
                      leaf number {
                        type uint32;
                        description
                          "channel number";
                      }
                    }
                  }
                  container ethernet-hour24-ether-histories {
                    description
                      "port current performance data";
                    list ethernet-hour24-ether-history {
                      key "number";
                      description
                        "port 24 hour ethernet performance data";
                      container ethernet-hour24-ether-time-line-instances {
                        description
                          "port current performance data";
                        list ethernet-hour24-ether-time-line-instance {
                          key "number";
                          description
                            "port 15-minute otn performance data";
                          leaf number {
                            type uint32;
                            description
                              "History Index number";
                          }
                          uses live_ncs_PM-ETHERNET-PARAS;
                        }
                      }
                      leaf number {
                        type uint32;
                        description
                          "channel number";
                      }
                    }
                  }
                }
                container ethernet-minute15-history {
                  description
                    "port current performance data";
                  container minute15pcs-histories {
                    description
                      "ETHERNET port interval performance data";
                    list minute15pcs-history {
                      key "slot-number";
                      description
                        "ETHERNET port 15-minute pcs performance
                         data";
                      container minute15pcs-time-line-instances {
                        description
                          "port current performance data";
                        list minute15pcs-time-line-instance {
                          key "number";
                          description
                            "port 15-minute pcs performance data";
                          leaf number {
                            type uint32;
                            description
                              "History Index number";
                          }
                          uses live_ncs_PM-PCS-PARAS;
                        }
                      }
                      leaf slot-number {
                        type uint32;
                        description
                          "interval slot number";
                      }
                    }
                  }
                  container minute15-ether-histories {
                    description
                      "ETHERNET port interval performance data";
                    list minute15-ether-history {
                      key "slot-number";
                      description
                        "ETHERNET port 15-minute ether performance
                         data";
                      container minute15-ether-time-line-instances {
                        description
                          "port current performance data";
                        list minute15-ether-time-line-instance {
                          key "number";
                          description
                            "port 15-minute otn performance data";
                          leaf number {
                            type uint32;
                            description
                              "History Index number";
                          }
                          uses live_ncs_PM-ETHERNET-PARAS;
                        }
                      }
                      leaf slot-number {
                        type uint32;
                        description
                          "interval slot number";
                      }
                    }
                  }
                  container minute15-fec-histories {
                    description
                      "ETHERNET port interval performance data";
                    list minute15-fec-history {
                      key "slot-number";
                      description
                        "ETHERNET port 15-minute fec performance
                         data";
                      container minute15-fec-time-line-instances {
                        description
                          "port current performance data";
                        list minute15-fec-time-line-instance {
                          key "number";
                          description
                            "port 15-minute fec performance data";
                          leaf number {
                            type uint32;
                            description
                              "History Index number";
                          }
                          uses live_ncs_PM-FEC-PARAS;
                        }
                      }
                      leaf slot-number {
                        type uint32;
                        description
                          "interval slot number";
                      }
                    }
                  }
                }
                leaf name {
                  type xr:Interface-name;
                  description
                    "Port name";
                }
              }
            }
          }
          container dwdm-history {
            description
              "DWDM controller History performance data";
            container dwdm-port-histories {
              description
                "Port performance data";
              list dwdm-port-history {
                key "name";
                description
                  "Port performance data";
                container dwdm-minute15-history {
                  description
                    "port current performance data";
                  container dwdm-minute15otn-histories {
                    description
                      "port current performance data";
                    list dwdm-minute15otn-history {
                      key "number";
                      description
                        "port 15-minute otn performance data";
                      container dwdm-minute15otn-time-line-instances {
                        description
                          "port current performance data";
                        list dwdm-minute15otn-time-line-instance {
                          key "number";
                          description
                            "port 15-minute otn performance data";
                          leaf number {
                            type uint32;
                            description
                              "History Index number";
                          }
                          uses live_ncs_PM-OTN-PARAS;
                        }
                      }
                      leaf number {
                        type uint32;
                        description
                          "channel number";
                      }
                    }
                  }
                  container dwdm-minute15fec-histories {
                    description
                      "port current performance data";
                    list dwdm-minute15fec-history {
                      key "number";
                      description
                        "port 15-minute fec performance data";
                      container dwdm-minute15fec-time-line-instances {
                        description
                          "port current performance data";
                        list dwdm-minute15fec-time-line-instance {
                          key "number";
                          description
                            "port 15-minute fec performance data by
                             index";
                          leaf number {
                            type uint32;
                            description
                              "History Index number";
                          }
                          uses live_ncs_PM-FEC-PARAS;
                        }
                      }
                      leaf number {
                        type uint32;
                        description
                          "channel number";
                      }
                    }
                  }
                  container dwdm-minute15-optics-histories {
                    description
                      "port current performance data";
                    list dwdm-minute15-optics-history {
                      key "number";
                      description
                        "port 15-minute optics performance data";
                      container dwdm-minute15-optics-time-line-instances {
                        description
                          "port current performance data";
                        list dwdm-minute15-optics-time-line-instance {
                          key "number";
                          description
                            "port 15-minute otn performance data";
                          leaf number {
                            type uint32;
                            description
                              "History Index number";
                          }
                          uses live_ncs_PM-OPTICS-PARAS;
                        }
                      }
                      leaf number {
                        type uint32;
                        description
                          "channel number";
                      }
                    }
                  }
                }
                container dwdm-hour24-history {
                  description
                    "port current performance data";
                  container dwdm-hour24otn-histories {
                    description
                      "port 24 hour performance data";
                    list dwdm-hour24otn-history {
                      key "number";
                      description
                        "port 24 hour otn performance data";
                      container dwdm-hour24otn-time-line-instances {
                        description
                          "port current performance data";
                        list dwdm-hour24otn-time-line-instance {
                          key "number";
                          description
                            "port 15-minute otn performance data";
                          leaf number {
                            type uint32;
                            description
                              "History Index number";
                          }
                          uses live_ncs_PM-OTN-PARAS;
                        }
                      }
                      leaf number {
                        type uint32;
                        description
                          "channel number";
                      }
                    }
                  }
                  container dwdm-hour24fec-histories {
                    description
                      "port current performance data";
                    list dwdm-hour24fec-history {
                      key "number";
                      description
                        "port 24 hour fec performance data";
                      container dwdm-hour24fec-time-line-instances {
                        description
                          "port current performance data";
                        list dwdm-hour24fec-time-line-instance {
                          key "number";
                          description
                            "port 15-minute fec performance data by
                             index";
                          leaf number {
                            type uint32;
                            description
                              "History Index number";
                          }
                          uses live_ncs_PM-FEC-PARAS;
                        }
                      }
                      leaf number {
                        type uint32;
                        description
                          "channel number";
                      }
                    }
                  }
                  container dwdm-hour24-optics-histories {
                    description
                      "port 24 hour performance data";
                    list dwdm-hour24-optics-history {
                      key "number";
                      description
                        "port 24 hour optics performance data";
                      container dwdm-hour24-optics-time-line-instances {
                        description
                          "port current performance data";
                        list dwdm-hour24-optics-time-line-instance {
                          key "number";
                          description
                            "port 15-minute otn performance data";
                          leaf number {
                            type uint32;
                            description
                              "History Index number";
                          }
                          uses live_ncs_PM-OPTICS-PARAS;
                        }
                      }
                      leaf number {
                        type uint32;
                        description
                          "channel number";
                      }
                    }
                  }
                }
                leaf name {
                  type xr:Interface-name;
                  description
                    "Port name";
                }
              }
            }
          }
          container stm-history {
            description
              "STM controller History performance data";
            container stm-port-histories {
              description
                "Port performance data";
              list stm-port-history {
                key "name";
                description
                  "Port performance data";
                container stm-hour24-history {
                  description
                    "port current performance data";
                  container stm-hour24stm-histories {
                    description
                      "port current performance data";
                    list stm-hour24stm-history {
                      key "number";
                      description
                        "port 24 hour stm performance data";
                      container stm-hour24stm-time-line-instances {
                        description
                          "port current performance data";
                        list stm-hour24stm-time-line-instance {
                          key "number";
                          description
                            "port 15-minute stm performance data";
                          leaf number {
                            type uint32;
                            description
                              "History Index number";
                          }
                          uses live_ncs_PM-STM-PARAS;
                        }
                      }
                      leaf number {
                        type uint32;
                        description
                          "channel number";
                      }
                    }
                  }
                }
                container stm-minute15-history {
                  description
                    "port current performance data";
                  container stm-minute15stm-histories {
                    description
                      "port current performance data";
                    list stm-minute15stm-history {
                      key "number";
                      description
                        "port 15-minute stm performance data";
                      container stm-minute15stm-time-line-instances {
                        description
                          "port current performance data";
                        list stm-minute15stm-time-line-instance {
                          key "number";
                          description
                            "port 15-minute stm performance data";
                          leaf number {
                            type uint32;
                            description
                              "History Index number";
                          }
                          uses live_ncs_PM-STM-PARAS;
                        }
                      }
                      leaf number {
                        type uint32;
                        description
                          "channel number";
                      }
                    }
                  }
                }
                leaf name {
                  type xr:Interface-name;
                  description
                    "Port name";
                }
              }
            }
          }
          container macsec-history {
            description
              "MACSEC controller History performance data";
            container macsec-port-histories {
              description
                "Port performance data";
              list macsec-port-history {
                key "name";
                description
                  "Port performance data";
                container macsec-minute15-history {
                  description
                    "port current performance data";
                  container macsec-minute15secyrx-histories {
                    description
                      "port current performance data";
                    list macsec-minute15secyrx-history {
                      key "number";
                      description
                        "port 15-minute secy_rx performance data";
                      container macsec-minute15secyrx-time-line-instances {
                        description
                          "port current performance data";
                        list macsec-minute15secyrx-time-line-instance {
                          key "number";
                          description
                            "port 15-minute secy_rx performance data
                             by index";
                          leaf number {
                            type uint32;
                            description
                              "History Index number";
                          }
                          uses live_ncs_PM-SECY-RX-PARAS;
                        }
                      }
                      leaf number {
                        type uint32;
                        description
                          "channel number";
                      }
                    }
                  }
                  container macsec-minute15-ether-histories {
                    description
                      "port current performance data";
                    list macsec-minute15-ether-history {
                      key "number";
                      description
                        "port 15-minute ether performance data";
                      container macsec-minute15-ether-time-line-instances {
                        description
                          "port current performance data";
                        list macsec-minute15-ether-time-line-instance {
                          key "number";
                          description
                            "port 15-minute ether performance data
                             by index";
                          leaf number {
                            type uint32;
                            description
                              "History Index number";
                          }
                          uses live_ncs_PM-ETHERNET-PARAS;
                        }
                      }
                      leaf number {
                        type uint32;
                        description
                          "channel number";
                      }
                    }
                  }
                  container macsec-minute15secytx-histories {
                    description
                      "port current performance data";
                    list macsec-minute15secytx-history {
                      key "number";
                      description
                        "port 15-minute secy_tx performance data";
                      container macsec-minute15secytx-time-line-instances {
                        description
                          "port current performance data";
                        list macsec-minute15secytx-time-line-instance {
                          key "number";
                          description
                            "port 15-minute secy_tx performance data
                             by index";
                          leaf number {
                            type uint32;
                            description
                              "History Index number";
                          }
                          uses live_ncs_PM-SECY-TX-PARAS;
                        }
                      }
                      leaf number {
                        type uint32;
                        description
                          "channel number";
                      }
                    }
                  }
                  container macsec-minute15secyif-histories {
                    description
                      "port current performance data";
                    list macsec-minute15secyif-history {
                      key "number";
                      description
                        "port 15-minute secy_if performance data";
                      container macsec-minute15secyif-time-line-instances {
                        description
                          "port current performance data";
                        list macsec-minute15secyif-time-line-instance {
                          key "number";
                          description
                            "port 15-minute secy_if performance data
                             by index";
                          leaf number {
                            type uint32;
                            description
                              "History Index number";
                          }
                          uses live_ncs_PM-SECY-IF-PARAS;
                        }
                      }
                      leaf number {
                        type uint32;
                        description
                          "channel number";
                      }
                    }
                  }
                }
                container macsec-hour24-history {
                  description
                    "port current performance data";
                  container macsec-hour24-ether-histories {
                    description
                      "port current performance data";
                    list macsec-hour24-ether-history {
                      key "number";
                      description
                        "port 24 hour ether performance data";
                      container macsec-hour24-ether-time-line-instances {
                        description
                          "port current performance data";
                        list macsec-hour24-ether-time-line-instance {
                          key "number";
                          description
                            "port 24 hour ether performance data";
                          leaf number {
                            type uint32;
                            description
                              "History Index number";
                          }
                          uses live_ncs_PM-ETHERNET-PARAS;
                        }
                      }
                      leaf number {
                        type uint32;
                        description
                          "channel number";
                      }
                    }
                  }
                  container macsec-hour24secytx-histories {
                    description
                      "port current performance data";
                    list macsec-hour24secytx-history {
                      key "number";
                      description
                        "port 24 hour secy_tx performance data";
                      container macsec-hour24secytx-time-line-instances {
                        description
                          "port current performance data";
                        list macsec-hour24secytx-time-line-instance {
                          key "number";
                          description
                            "port 24 hour secy_tx performance data";
                          leaf number {
                            type uint32;
                            description
                              "History Index number";
                          }
                          uses live_ncs_PM-SECY-TX-PARAS;
                        }
                      }
                      leaf number {
                        type uint32;
                        description
                          "channel number";
                      }
                    }
                  }
                  container macsec-hour24secyif-histories {
                    description
                      "port current performance data";
                    list macsec-hour24secyif-history {
                      key "number";
                      description
                        "port 24 hour secy_if performance data";
                      container macsec-hour24secyif-time-line-instances {
                        description
                          "port current performance data";
                        list macsec-hour24secyif-time-line-instance {
                          key "number";
                          description
                            "port 24 hour secy_if performance data";
                          leaf number {
                            type uint32;
                            description
                              "History Index number";
                          }
                          uses live_ncs_PM-SECY-IF-PARAS;
                        }
                      }
                      leaf number {
                        type uint32;
                        description
                          "channel number";
                      }
                    }
                  }
                  container macsec-hour24secyrx-histories {
                    description
                      "port current performance data";
                    list macsec-hour24secyrx-history {
                      key "number";
                      description
                        "port 24 hour secy_rx performance data";
                      container macsec-hour24secyrx-time-line-instances {
                        description
                          "port current performance data";
                        list macsec-hour24secyrx-time-line-instance {
                          key "number";
                          description
                            "port 24 hour secy_rx performance data";
                          leaf number {
                            type uint32;
                            description
                              "History Index number";
                          }
                          uses live_ncs_PM-SECY-RX-PARAS;
                        }
                      }
                      leaf number {
                        type uint32;
                        description
                          "channel number";
                      }
                    }
                  }
                }
                container macsec-second30-history {
                  description
                    "port current performance data";
                  container macsec-second30secyrx-histories {
                    description
                      "port current performance data";
                    list macsec-second30secyrx-history {
                      key "number";
                      description
                        "port 30-second secy_rx performance data";
                      container macsec-second30secyrx-time-line-instances {
                        description
                          "port current performance data";
                        list macsec-second30secyrx-time-line-instance {
                          key "number";
                          description
                            "port 30-second secy_rx performance data";
                          leaf number {
                            type uint32;
                            description
                              "History Index number";
                          }
                          uses live_ncs_PM-SECY-RX-PARAS;
                        }
                      }
                      leaf number {
                        type uint32;
                        description
                          "channel number";
                      }
                    }
                  }
                  container macsec-second30-ether-histories {
                    description
                      "port current performance data";
                    list macsec-second30-ether-history {
                      key "number";
                      description
                        "port 30-second ether performance data";
                      container macsec-second30-ether-time-line-instances {
                        description
                          "port current performance data";
                        list macsec-second30-ether-time-line-instance {
                          key "number";
                          description
                            "port 30-second ether performance data";
                          leaf number {
                            type uint32;
                            description
                              "History Index number";
                          }
                          uses live_ncs_PM-ETHERNET-PARAS;
                        }
                      }
                      leaf number {
                        type uint32;
                        description
                          "channel number";
                      }
                    }
                  }
                  container macsec-second30secytx-histories {
                    description
                      "port current performance data";
                    list macsec-second30secytx-history {
                      key "number";
                      description
                        "port 30-second secy_tx performance data";
                      container macsec-second30secytx-time-line-instances {
                        description
                          "port current performance data";
                        list macsec-second30secytx-time-line-instance {
                          key "number";
                          description
                            "port 30-second secy_tx performance data";
                          leaf number {
                            type uint32;
                            description
                              "History Index number";
                          }
                          uses live_ncs_PM-SECY-TX-PARAS;
                        }
                      }
                      leaf number {
                        type uint32;
                        description
                          "channel number";
                      }
                    }
                  }
                  container macsec-second30secyif-histories {
                    description
                      "port current performance data";
                    list macsec-second30secyif-history {
                      key "number";
                      description
                        "port 30-second secy_if performance data";
                      container macsec-second30secyif-time-line-instances {
                        description
                          "port current performance data";
                        list macsec-second30secyif-time-line-instance {
                          key "number";
                          description
                            "port 30-second secy_if performance data";
                          leaf number {
                            type uint32;
                            description
                              "History Index number";
                          }
                          uses live_ncs_PM-SECY-IF-PARAS;
                        }
                      }
                      leaf number {
                        type uint32;
                        description
                          "channel number";
                      }
                    }
                  }
                }
                leaf name {
                  type xr:Interface-name;
                  description
                    "Port name";
                }
              }
            }
          }
          container odu-history {
            description
              "ODU controller History performance data";
            container odu-port-histories {
              description
                "Port performance data";
              list odu-port-history {
                key "name";
                description
                  "Port performance data";
                container odu-hour24-history {
                  description
                    "port current performance data";
                  container odu-hour24gfp-histories {
                    description
                      "port 24 hour performance data";
                    list odu-hour24gfp-history {
                      key "number";
                      description
                        "port 24 hour otn performance data";
                      container odu-hour24gfp-time-line-instances {
                        description
                          "port current performance data";
                        list odu-hour24gfp-time-line-instance {
                          key "number";
                          description
                            "port 15-minute otn performance data";
                          leaf number {
                            type uint32;
                            description
                              "History Index number";
                          }
                          uses live_ncs_PM-GFP-PARAS;
                        }
                      }
                      leaf number {
                        type uint32;
                        description
                          "channel number";
                      }
                    }
                  }
                  container odu-hour24prbs-histories {
                    description
                      "port 24 hour performance data";
                    list odu-hour24prbs-history {
                      key "number";
                      description
                        "port 24 hour prbs performance data";
                      container odu-hour24prbs-time-line-instances {
                        description
                          "port current performance data";
                        list odu-hour24prbs-time-line-instance {
                          key "number";
                          description
                            "port 15-minute prbs performance data";
                          leaf number {
                            type uint32;
                            description
                              "History Index number";
                          }
                          uses live_ncs_PM-PRBS-PARAS;
                        }
                      }
                      leaf number {
                        type uint32;
                        description
                          "channel number";
                      }
                    }
                  }
                  container odu-hour24otn-histories {
                    description
                      "port 24 hour performance data";
                    list odu-hour24otn-history {
                      key "number";
                      description
                        "port 24 hour otn performance data";
                      container odu-hour24otn-time-line-instances {
                        description
                          "port current performance data";
                        list odu-hour24otn-time-line-instance {
                          key "number";
                          description
                            "port 15-minute otn performance data";
                          leaf number {
                            type uint32;
                            description
                              "History Index number";
                          }
                          uses live_ncs_PM-OTN-PARAS;
                        }
                      }
                      leaf number {
                        type uint32;
                        description
                          "channel number";
                      }
                    }
                  }
                }
                container odu-minute15-history {
                  description
                    "port current performance data";
                  container odu-minute15prbs-histories {
                    description
                      "port current performance data";
                    list odu-minute15prbs-history {
                      key "number";
                      description
                        "port 15-minute prbs performance data";
                      container odu-minute15prbs-time-line-instances {
                        description
                          "port current performance data";
                        list odu-minute15prbs-time-line-instance {
                          key "number";
                          description
                            "port 15-minute prbs performance data";
                          leaf number {
                            type uint32;
                            description
                              "History Index number";
                          }
                          uses live_ncs_PM-PRBS-PARAS;
                        }
                      }
                      leaf number {
                        type uint32;
                        description
                          "channel number";
                      }
                    }
                  }
                  container odu-minute15gfp-histories {
                    description
                      "port current performance data";
                    list odu-minute15gfp-history {
                      key "number";
                      description
                        "port 15-minute otn performance data";
                      container odu-minute15gfp-time-line-instances {
                        description
                          "port current performance data";
                        list odu-minute15gfp-time-line-instance {
                          key "number";
                          description
                            "port 15-minute otn performance data";
                          leaf number {
                            type uint32;
                            description
                              "History Index number";
                          }
                          uses live_ncs_PM-GFP-PARAS;
                        }
                      }
                      leaf number {
                        type uint32;
                        description
                          "channel number";
                      }
                    }
                  }
                  container odu-minute15otn-histories {
                    description
                      "port current performance data";
                    list odu-minute15otn-history {
                      key "number";
                      description
                        "port 15-minute otn performance data";
                      container odu-minute15otn-time-line-instances {
                        description
                          "port current performance data";
                        list odu-minute15otn-time-line-instance {
                          key "number";
                          description
                            "port 15-minute otn performance data";
                          leaf number {
                            type uint32;
                            description
                              "History Index number";
                          }
                          uses live_ncs_PM-OTN-PARAS;
                        }
                      }
                      leaf number {
                        type uint32;
                        description
                          "channel number";
                      }
                    }
                  }
                }
                leaf name {
                  type xr:Interface-name;
                  description
                    "Port name";
                }
              }
            }
          }
          container otu-history {
            description
              "OTU controller History performance data";
            container otu-port-histories {
              description
                "Port performance data";
              list otu-port-history {
                key "name";
                description
                  "Port performance data";
                container otu-second30-history {
                  description
                    "port current performance data";
                  container otu-second30fec-histories {
                    description
                      "port current performance data";
                    list otu-second30fec-history {
                      key "number";
                      description
                        "port 30-second fec performance data";
                      container otu-second30fec-time-line-instances {
                        description
                          "port current performance data";
                        list otu-second30fec-time-line-instance {
                          key "number";
                          description
                            "port 30-second fec performance data";
                          leaf number {
                            type uint32;
                            description
                              "History Index number";
                          }
                          uses live_ncs_PM-FEC-PARAS;
                        }
                      }
                      leaf number {
                        type uint32;
                        description
                          "channel number";
                      }
                    }
                  }
                  container otu-second30otn-histories {
                    description
                      "port current performance data";
                    list otu-second30otn-history {
                      key "number";
                      description
                        "port 30-second otn performance data";
                      container otu-second30otn-time-line-instances {
                        description
                          "port current performance data";
                        list otu-second30otn-time-line-instance {
                          key "number";
                          description
                            "port 30-second otn performance data";
                          leaf number {
                            type uint32;
                            description
                              "History Index number";
                          }
                          uses live_ncs_PM-OTN-PARAS;
                        }
                      }
                      leaf number {
                        type uint32;
                        description
                          "channel number";
                      }
                    }
                  }
                }
                container otu-minute15-history {
                  description
                    "port current performance data";
                  container otu-minute15fec-histories {
                    description
                      "port current performance data";
                    list otu-minute15fec-history {
                      key "number";
                      description
                        "port 15-minute fec performance data";
                      container otu-minute15fec-time-line-instances {
                        description
                          "port current performance data";
                        list otu-minute15fec-time-line-instance {
                          key "number";
                          description
                            "port 15-minute fec performance data";
                          leaf number {
                            type uint32;
                            description
                              "History Index number";
                          }
                          uses live_ncs_PM-FEC-PARAS;
                        }
                      }
                      leaf number {
                        type uint32;
                        description
                          "channel number";
                      }
                    }
                  }
                  container otu-minute15prbs-histories {
                    description
                      "port current performance data";
                    list otu-minute15prbs-history {
                      key "number";
                      description
                        "port 15-minute prbs performance data";
                      container otu-minute15prbs-time-line-instances {
                        description
                          "port current performance data";
                        list otu-minute15prbs-time-line-instance {
                          key "number";
                          description
                            "port 15-minute prbs performance data";
                          leaf number {
                            type uint32;
                            description
                              "History Index number";
                          }
                          uses live_ncs_PM-PRBS-PARAS;
                        }
                      }
                      leaf number {
                        type uint32;
                        description
                          "channel number";
                      }
                    }
                  }
                  container otu-minute15otn-histories {
                    description
                      "port current performance data";
                    list otu-minute15otn-history {
                      key "number";
                      description
                        "port 15-minute otn performance data";
                      container otu-minute15otn-time-line-instances {
                        description
                          "port current performance data";
                        list otu-minute15otn-time-line-instance {
                          key "number";
                          description
                            "port 15-minute otn performance data";
                          leaf number {
                            type uint32;
                            description
                              "History Index number";
                          }
                          uses live_ncs_PM-OTN-PARAS;
                        }
                      }
                      leaf number {
                        type uint32;
                        description
                          "channel number";
                      }
                    }
                  }
                }
                container otu-hour24-history {
                  description
                    "port current performance data";
                  container otu-hour24prbs-histories {
                    description
                      "port 24 hour performance data";
                    list otu-hour24prbs-history {
                      key "number";
                      description
                        "port 24 hour prbs performance data";
                      container otu-hour24prbs-time-line-instances {
                        description
                          "port current performance data";
                        list otu-hour24prbs-time-line-instance {
                          key "number";
                          description
                            "port 15-minute prbs performance data";
                          leaf number {
                            type uint32;
                            description
                              "History Index number";
                          }
                          uses live_ncs_PM-PRBS-PARAS;
                        }
                      }
                      leaf number {
                        type uint32;
                        description
                          "channel number";
                      }
                    }
                  }
                  container otu-hour24otn-histories {
                    description
                      "port 24 hour performance data";
                    list otu-hour24otn-history {
                      key "number";
                      description
                        "port 24 hour otn performance data";
                      container otu-hour24otn-time-line-instances {
                        description
                          "port current performance data";
                        list otu-hour24otn-time-line-instance {
                          key "number";
                          description
                            "port 15-minute otn performance data";
                          leaf number {
                            type uint32;
                            description
                              "History Index number";
                          }
                          uses live_ncs_PM-OTN-PARAS;
                        }
                      }
                      leaf number {
                        type uint32;
                        description
                          "channel number";
                      }
                    }
                  }
                  container otu-hour24fec-histories {
                    description
                      "port current performance data";
                    list otu-hour24fec-history {
                      key "number";
                      description
                        "port 24 hour fec performance data";
                      container otu-hour24fec-time-line-instances {
                        description
                          "port current performance data";
                        list otu-hour24fec-time-line-instance {
                          key "number";
                          description
                            "port 15-minute fec performance data";
                          leaf number {
                            type uint32;
                            description
                              "History Index number";
                          }
                          uses live_ncs_PM-FEC-PARAS;
                        }
                      }
                      leaf number {
                        type uint32;
                        description
                          "channel number";
                      }
                    }
                  }
                }
                leaf name {
                  type xr:Interface-name;
                  description
                    "Port name";
                }
              }
            }
          }
          container ho-vc-history {
            description
              "HO_VC controller History performance data";
            container ho-vc-port-histories {
              description
                "Port performance data";
              list ho-vc-port-history {
                key "name";
                description
                  "Port performance data";
                container ho-vc-minute15-history {
                  description
                    "port current performance data";
                  container ho-vc-minute15-path-histories {
                    description
                      "port current performance data";
                    list ho-vc-minute15-path-history {
                      key "number";
                      description
                        "port 15-minute Path performance data";
                      container ho-vc-minute15-path-time-line-instances {
                        description
                          "port current performance data";
                        list ho-vc-minute15-path-time-line-instance {
                          key "number";
                          description
                            "port 15-minute ho_vc performance data";
                          leaf number {
                            type uint32;
                            description
                              "History Index number";
                          }
                          uses live_ncs_PM-HO-VC-PARAS;
                        }
                      }
                      leaf number {
                        type uint32;
                        description
                          "channel number";
                      }
                    }
                  }
                }
                container ho-vc-hour24-history {
                  description
                    "port current performance data";
                  container ho-vc-hour24-path-histories {
                    description
                      "port current performance data";
                    list ho-vc-hour24-path-history {
                      key "number";
                      description
                        "port 24 hour Path performance data";
                      container ho-vc-hour24-path-time-line-instances {
                        description
                          "port current performance data";
                        list ho-vc-hour24-path-time-line-instance {
                          key "number";
                          description
                            "port 15-minute otn performance data";
                          leaf number {
                            type uint32;
                            description
                              "History Index number";
                          }
                          uses live_ncs_PM-HO-VC-PARAS;
                        }
                      }
                      leaf number {
                        type uint32;
                        description
                          "channel number";
                      }
                    }
                  }
                }
                leaf name {
                  type xr:Interface-name;
                  description
                    "Port name";
                }
              }
            }
          }
          container optics-history {
            description
              "OPTICS controller History performance data";
            container optics-port-histories {
              description
                "Port performance data";
              list optics-port-history {
                key "name";
                description
                  "Port performance data";
                container optics-hour24-history {
                  description
                    "port current performance data";
                  container optics-hour24-optics-histories {
                    description
                      "port 24 hour performance data";
                    list optics-hour24-optics-history {
                      key "number";
                      description
                        "port 24 hour optics performance data";
                      container optics-hour24-optics-time-line-instances {
                        description
                          "port current performance data";
                        list optics-hour24-optics-time-line-instance {
                          key "number";
                          description
                            "port 15-minute otn performance data";
                          leaf number {
                            type uint32;
                            description
                              "History Index number";
                          }
                          uses live_ncs_PM-OPTICS-PARAS;
                        }
                      }
                      leaf number {
                        type uint32;
                        description
                          "channel number";
                      }
                    }
                  }
                  container optics-hour24fec-histories {
                    description
                      "port current performance data";
                    list optics-hour24fec-history {
                      key "number";
                      description
                        "port 24 hour fec performance data";
                      container optics-hour24fec-time-line-instances {
                        description
                          "port current performance data";
                        list optics-hour24fec-time-line-instance {
                          key "number";
                          description
                            "port 15-minute fec performance data";
                          leaf number {
                            type uint32;
                            description
                              "History Index number";
                          }
                          uses live_ncs_PM-FEC-PARAS;
                        }
                      }
                      leaf number {
                        type uint32;
                        description
                          "channel number";
                      }
                    }
                  }
                }
                container optics-second30-history {
                  description
                    "port current performance data";
                  container optics-second30-optics-histories {
                    description
                      "port current performance data";
                    list optics-second30-optics-history {
                      key "number";
                      description
                        "port 30-second optics performance data";
                      container optics-second30-optics-time-line-instances {
                        description
                          "port current performance data";
                        list optics-second30-optics-time-line-instance {
                          key "number";
                          description
                            "port 30 second otn performance data";
                          leaf number {
                            type uint32;
                            description
                              "History Index number";
                          }
                          uses live_ncs_PM-OPTICS-PARAS;
                        }
                      }
                      leaf number {
                        type uint32;
                        description
                          "channel number";
                      }
                    }
                  }
                  container optics-second30fec-histories {
                    description
                      "port current performance data";
                    list optics-second30fec-history {
                      key "number";
                      description
                        "port 30-second fec performance data";
                      container optics-second30fec-time-line-instances {
                        description
                          "port current performance data";
                        list optics-second30fec-time-line-instance {
                          key "number";
                          description
                            "port sec-30 fec performance data";
                          leaf number {
                            type uint32;
                            description
                              "History Index number";
                          }
                          uses live_ncs_PM-FEC-PARAS;
                        }
                      }
                      leaf number {
                        type uint32;
                        description
                          "channel number";
                      }
                    }
                  }
                }
                container optics-minute15-history {
                  description
                    "port current performance data";
                  container optics-minute15-optics-histories {
                    description
                      "port current performance data";
                    list optics-minute15-optics-history {
                      key "number";
                      description
                        "port 15-minute optics performance data";
                      container optics-minute15-optics-time-line-instances {
                        description
                          "port current performance data";
                        list optics-minute15-optics-time-line-instance {
                          key "number";
                          description
                            "port 15-minute otn performance data";
                          leaf number {
                            type uint32;
                            description
                              "History Index number";
                          }
                          uses live_ncs_PM-OPTICS-PARAS;
                        }
                      }
                      leaf number {
                        type uint32;
                        description
                          "channel number";
                      }
                    }
                  }
                  container optics-minute15fec-histories {
                    description
                      "port current performance data";
                    list optics-minute15fec-history {
                      key "number";
                      description
                        "port 15-minute fec performance data";
                      container optics-minute15fec-time-line-instances {
                        description
                          "port current performance data";
                        list optics-minute15fec-time-line-instance {
                          key "number";
                          description
                            "port 15-minute fec performance data";
                          leaf number {
                            type uint32;
                            description
                              "History Index number";
                          }
                          uses live_ncs_PM-FEC-PARAS;
                        }
                      }
                      leaf number {
                        type uint32;
                        description
                          "channel number";
                      }
                    }
                  }
                }
                leaf name {
                  type xr:Interface-name;
                  description
                    "Port name";
                }
              }
            }
          }
          container oc-history {
            description
              "OC controller History performance data";
            container oc-port-histories {
              description
                "Port performance data";
              list oc-port-history {
                key "name";
                description
                  "Port performance data";
                container oc-hour24-history {
                  description
                    "port current performance data";
                  container oc-hour24ocn-histories {
                    description
                      "port current performance data";
                    list oc-hour24ocn-history {
                      key "number";
                      description
                        "port 24 hour ocn performance data";
                      container oc-hour24ocn-time-line-instances {
                        description
                          "port current performance data";
                        list oc-hour24ocn-time-line-instance {
                          key "number";
                          description
                            "port 15-minute otn performance data";
                          leaf number {
                            type uint32;
                            description
                              "History Index number";
                          }
                          uses live_ncs_PM-SONET-PARAS;
                        }
                      }
                      leaf number {
                        type uint32;
                        description
                          "channel number";
                      }
                    }
                  }
                }
                container oc-minute15-history {
                  description
                    "port current performance data";
                  container oc-minute15ocn-histories {
                    description
                      "port current performance data";
                    list oc-minute15ocn-history {
                      key "number";
                      description
                        "port 15-minute ocn performance data";
                      container oc-minute15ocn-time-line-instances {
                        description
                          "port current performance data";
                        list oc-minute15ocn-time-line-instance {
                          key "number";
                          description
                            "port 15-minute ocn performance data";
                          leaf number {
                            type uint32;
                            description
                              "History Index number";
                          }
                          uses live_ncs_PM-SONET-PARAS;
                        }
                      }
                      leaf number {
                        type uint32;
                        description
                          "channel number";
                      }
                    }
                  }
                }
                leaf name {
                  type xr:Interface-name;
                  description
                    "Port name";
                }
              }
            }
          }
        }
      }
    }
  }
  augment "/ncs:devices/ncs:template/ncs:ned-id/ncs:config" {
    // NCS drop config false container 'performance-management'
    // NCS drop config false container 'performance-management-history'
  }
}
