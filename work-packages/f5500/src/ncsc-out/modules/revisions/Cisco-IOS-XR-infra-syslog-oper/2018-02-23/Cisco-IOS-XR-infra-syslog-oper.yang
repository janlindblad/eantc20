module Cisco-IOS-XR-infra-syslog-oper {
  // Generated by yanger -t ncs
  tailf:mount-id f5500-nc-1.0:f5500-nc-1.0;
  tailf:ncs-device-type "netconf";

  namespace "http://cisco.com/ns/yang/Cisco-IOS-XR-infra-syslog-oper";
  prefix Cisco-IOS-XR-infra-syslog-oper;

  import ietf-yang-types {
    prefix yang;
  }
  include Cisco-IOS-XR-infra-syslog-oper-sub1 {
    revision-date 2018-02-22;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR infra-syslog package operational data.

     This module contains definitions
     for the following management objects:
       logging: Logging History data
       syslog: syslog

     Copyright (c) 2013-2018 by Cisco Systems, Inc.
     All rights reserved.";

  revision 2018-02-23 {
    description
      "Added a new rpc statement.";
  }
  revision 2018-02-22 {
    description
      "Fixed syslog message filter.";
  }
  revision 2017-09-07 {
    description
      "Fixed type translation error.";
  }
  revision 2016-06-24 {
    description
      "Schema added for Show logging files CLI";
  }
  revision 2015-01-07 {
    description
      "IOS XR 5.3.1 revision.";
  }

  augment "/ncs:devices/ncs:device/ncs:rpc" {
    container rpc-get-syslog {
      tailf:ncs-device-type "netconf";
      tailf:display-when "not(../../ncs:module) or ../../ncs:module[ncs:name='Cisco-IOS-XR-infra-syslog-oper']";
      tailf:action get-syslog {
        tailf:actionpoint ncsproxy {
          tailf:internal;
        }
        input {
          container filters {
            description
              "A set of filters of syslog messages to be returned";
            must 'start-time or end-time' {
              tailf:xpath-root 3;
              description
                "At least one of the filters must be specified.";
            }
            leaf start-time {
              type yang:date-and-time;
              description
                "Start timestamp of syslog messages to be returned";
            }
            leaf end-time {
              type yang:date-and-time;
              description
                "End timestamp of syslog messages to be returned";
            }
          }
        }
        output {
          container data {
            description
              "Output for RPC operation";
            container syslog {
              description
                "syslog";
              container messages {
                description
                  "Message table information";
                list message {
                  key "message-id";
                  description
                    "A system message";
                  leaf message-id {
                    type uint32;
                    description
                      "Message ID of the system message";
                  }
                  uses ncs_rpc_notif_SYSTEM-MESSAGE;
                }
              }
            }
          }
        }
      }
    }
  }
  augment "/ncs:devices/ncs:device-group/ncs:ned-id/ncs:rpc" {
    container rpc-get-syslog {
      tailf:ncs-device-type "netconf";
      tailf:display-when "/ncs:devices/ncs:device[ncs:name=current()/../../../ncs:member]/ncs:module[ncs:name='Cisco-IOS-XR-infra-syslog-oper']";
      tailf:action get-syslog {
        tailf:actionpoint ncsproxy {
          tailf:internal;
        }
        input {
          container filters {
            description
              "A set of filters of syslog messages to be returned";
            must 'start-time or end-time' {
              tailf:xpath-root 4;
              description
                "At least one of the filters must be specified.";
            }
            leaf start-time {
              type yang:date-and-time;
              description
                "Start timestamp of syslog messages to be returned";
            }
            leaf end-time {
              type yang:date-and-time;
              description
                "End timestamp of syslog messages to be returned";
            }
          }
        }
        output {
          container "device" {
            leaf "name" {
              type string;
            }
            leaf "info" {
              type string;
            }
            container "result" {
              container data {
                description
                  "Output for RPC operation";
                container syslog {
                  description
                    "syslog";
                  container messages {
                    description
                      "Message table information";
                    list message {
                      key "message-id";
                      description
                        "A system message";
                      leaf message-id {
                        type uint32;
                        description
                          "Message ID of the system message";
                      }
                      uses ncs_rpc_notif_SYSTEM-MESSAGE;
                    }
                  }
                }
              }
            }
          }
        }
      }
    }
  }
  augment "/ncs:devices/ncs:device/ncs:config" {
    // NCS drop config false container logging
    // NCS drop config false container syslog
  }
  augment "/ncs:devices/ncs:device/ncs:live-status" {
    container logging {
      tailf:ncs-device-type "netconf";
      tailf:display-when "not(../../ncs:module) or ../../ncs:module[ncs:name='Cisco-IOS-XR-infra-syslog-oper'] or (../../ncs:live-status-protocol[not(ncs:capability)]) or (../../ncs:live-status-protocol/ncs:capability/ncs:module[.='Cisco-IOS-XR-infra-syslog-oper'])";
      description
        "Logging History data";
      container history {
        description
          "Syslog Info ";
        leaf properties {
          type string;
          description
            "Syslog Properties";
        }
        leaf message {
          type string;
          description
            "Syslog Message";
        }
      }
    }
    container syslog {
      tailf:ncs-device-type "netconf";
      tailf:display-when "not(../../ncs:module) or ../../ncs:module[ncs:name='Cisco-IOS-XR-infra-syslog-oper'] or (../../ncs:live-status-protocol[not(ncs:capability)]) or (../../ncs:live-status-protocol/ncs:capability/ncs:module[.='Cisco-IOS-XR-infra-syslog-oper'])";
      description
        "syslog";
      container logging-files {
        description
          "Logging Files information";
        uses live_ncs_FILE-LOG-LIST-PATH;
      }
      container an-remote-servers {
        description
          "Logging AN remote servers information";
        uses live_ncs_AN-REMOTE-LOG-SERVERS;
      }
      container messages {
        description
          "Message table information";
        list message {
          key "message-id";
          description
            "A system message";
          leaf message-id {
            type uint32;
            description
              "Message ID of the system message";
          }
          uses live_ncs_SYSTEM-MESSAGE;
        }
      }
      container logging-statistics {
        description
          "Logging statistics information";
        uses live_ncs_SYSTEM-MESSAGE-STATISTICS;
      }
    }
  }
  augment "/ncs:devices/ncs:template/ncs:ned-id/ncs:config" {
    // NCS drop config false container logging
    // NCS drop config false container syslog
  }
}
