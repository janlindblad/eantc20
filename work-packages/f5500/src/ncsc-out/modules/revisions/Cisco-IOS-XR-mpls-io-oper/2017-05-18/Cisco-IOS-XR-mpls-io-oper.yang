module Cisco-IOS-XR-mpls-io-oper {
  // Generated by yanger -t ncs
  tailf:mount-id f5500-nc-1.0:f5500-nc-1.0;
  tailf:ncs-device-type "netconf";

  namespace "http://cisco.com/ns/yang/Cisco-IOS-XR-mpls-io-oper";
  prefix Cisco-IOS-XR-mpls-io-oper;

  import Cisco-IOS-XR-types {
    prefix xr;
  }
  include Cisco-IOS-XR-mpls-io-oper-sub1 {
    revision-date 2017-05-18;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR mpls-io package operational data.

     This module contains definitions
     for the following management objects:
       mpls-ea: MPLS IO EA operational data
       mpls-ma: mpls ma

     Copyright (c) 2013-2018 by Cisco Systems, Inc.
     All rights reserved.";

  revision 2017-05-18 {
    description
      "IOS XR 6.2.2 revision.";
  }
  revision 2015-11-09 {
    description
      "IOS XR 6.0 revision.";
  }

  augment "/ncs:devices/ncs:device/ncs:config" {
    // NCS drop config false container 'mpls-ea'
    // NCS drop config false container 'mpls-ma'
  }
  augment "/ncs:devices/ncs:device/ncs:live-status" {
    container mpls-ea {
      tailf:ncs-device-type "netconf";
      tailf:display-when "not(../../ncs:module) or ../../ncs:module[ncs:name='Cisco-IOS-XR-mpls-io-oper'] or (../../ncs:live-status-protocol[not(ncs:capability)]) or (../../ncs:live-status-protocol/ncs:capability/ncs:module[.='Cisco-IOS-XR-mpls-io-oper'])";
      description
        "MPLS IO EA operational data";
      container nodes {
        description
          "NODE container class for MPLS IO EA operational
           data";
        list node {
          key "node-name";
          description
            "Per node MPLS IO EA operational data";
          container interfaces {
            description
              "MPLS IO EA Interfaces information ";
            list interface {
              key "interface-name";
              description
                "MPLS IO EA NODE Interface data ";
              leaf interface-name {
                type xr:Interface-name;
                description
                  "Interface name";
              }
              uses live_ncs_MPLS-IO-SHOW-INTF-INFO;
            }
          }
          leaf node-name {
            type xr:Node-id;
            description
              "Node ID";
          }
        }
      }
    }
    container mpls-ma {
      tailf:ncs-device-type "netconf";
      tailf:display-when "not(../../ncs:module) or ../../ncs:module[ncs:name='Cisco-IOS-XR-mpls-io-oper'] or (../../ncs:live-status-protocol[not(ncs:capability)]) or (../../ncs:live-status-protocol/ncs:capability/ncs:module[.='Cisco-IOS-XR-mpls-io-oper'])";
      description
        "mpls ma";
      container nodes {
        description
          "NODE container class for MPLS IO MA operational
           data";
        list node {
          key "node-name";
          description
            "Per node MPLS IO MA operational data";
          container interfaces {
            description
              "MPLS IO MA Interfaces information ";
            list interface {
              key "interface-name";
              description
                "MPLS IO MA NODE Interface data ";
              leaf interface-name {
                type xr:Interface-name;
                description
                  "Interface name";
              }
              uses live_ncs_MPLS-IO-SHOW-INTF-INFO;
            }
          }
          leaf node-name {
            type xr:Node-id;
            description
              "Node ID";
          }
        }
      }
    }
  }
  augment "/ncs:devices/ncs:template/ncs:ned-id/ncs:config" {
    // NCS drop config false container 'mpls-ea'
    // NCS drop config false container 'mpls-ma'
  }
}
