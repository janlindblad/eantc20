submodule Cisco-IOS-XR-eigrp-oper-sub1 {
  // Generated by yanger -t ncs
  tailf:mount-id f5500-nc-1.0:f5500-nc-1.0;

  belongs-to Cisco-IOS-XR-eigrp-oper {
    prefix Cisco-IOS-XR-eigrp-oper-sub1;
  }

  import ietf-inet-types {
    prefix inet;
  }
  import ietf-yang-types {
    prefix yang;
  }
  import Cisco-IOS-XR-types {
    prefix xr;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR eigrp package operational data.

     Copyright (c) 2013-2018 by Cisco Systems, Inc.
     All rights reserved.";

  revision 2018-04-05 {
    description
      "Oper supported provided for oper data.";
  }
  revision 2015-11-09 {
    description
      "IOS XR 6.0 revision.";
  }

  typedef Eigrp-bd-metric-version {
    type enumeration {
      enum "metric-version32-bit" {
        value 0;
        description
          "Metric version is 32 bit";
      }
      enum "metric-version64-bit" {
        value 1;
        description
          "Metric version is 64 bit";
      }
    }
    description
      "EIGRP metric version";
  }

  typedef Eigrp-bd-path-send-flag {
    type enumeration {
      enum "no-send-pending" {
        value 0;
        description
          "No packet send pending";
      }
      enum "multicast-update-pending" {
        value 1;
        description
          "Multicast update pending";
      }
      enum "multicast-query-pending" {
        value 2;
        description
          "Multicast query pending";
      }
      enum "reply-pending" {
        value 3;
        description
          "Reply pending";
      }
      enum "sia-query-pending" {
        value 4;
        description
          "SIA Query pending";
      }
      enum "sia-reply-pending" {
        value 5;
        description
          "SIA Reply pending";
      }
    }
    description
      "EIGRP path send flag";
  }

  typedef Eigrp-bd-path-origin {
    type enumeration {
      enum "connected" {
        value 0;
        description
          "connected destination";
      }
      enum "static-redistributed" {
        value 1;
        description
          "static redistribution";
      }
      enum "connected-redistributed" {
        value 2;
        description
          "connected redistribution";
      }
      enum "subscriber-redistributed" {
        value 3;
        description
          "subscriber redistribution";
      }
      enum "redistributed" {
        value 4;
        description
          "redistributed destination";
      }
      enum "vpnv4-sourced" {
        value 5;
        description
          "vpnv4 destination";
      }
      enum "vpnv6-sourced" {
        value 6;
        description
          "vpnv6 destination";
      }
      enum "summary" {
        value 7;
        description
          "summary destination";
      }
      enum "dummy" {
        value 8;
        description
          "bogus drdb used for sia transmission";
      }
      enum "eigrp-destination" {
        value 9;
        description
          "igrp2 destination";
      }
      enum "origin-count" {
        value 10;
        description
          "Number of org types";
      }
    }
    description
      "EIGRP path origin";
  }

  typedef Eigrp-bd-delay-unit {
    type enumeration {
      enum "none" {
        value 0;
        description
          "No Delay configured";
      }
      enum "ten-microsecond" {
        value 1;
        description
          "Delay in 10's of Microseconds";
      }
      enum "picosecond" {
        value 2;
        description
          "Delay in Picoseconds";
      }
      enum "microsecond" {
        value 3;
        description
          "Delay in Microseconds";
      }
    }
    description
      "EIGRP delay unit";
  }

  typedef Eigrp-bd-path-rib-state {
    type enumeration {
      enum "active-path" {
        value 0;
        description
          "Active path";
      }
      enum "backup-path" {
        value 1;
        description
          "Backup path";
      }
      enum "path-sent-to-rib" {
        value 2;
        description
          "Path sent to RIB";
      }
      enum "path-not-selected" {
        value 3;
        description
          "Path not selected for installation in RIB";
      }
      enum "error-state" {
        value 4;
        description
          "Path in error state";
      }
    }
    description
      "Eigrp bd path rib state";
  }

  typedef Eigrp-bd-soo {
    type enumeration {
      enum "none" {
        value 0;
        description
          "No SoO configured";
      }
      enum "as" {
        value 1;
        description
          "AS:nn format";
      }
      enum "ipv4-address" {
        value 2;
        description
          "IPV4Address:nn format";
      }
      enum "four-byte-as" {
        value 3;
        description
          "AS2.AS:nn format";
      }
    }
    description
      "EIGRP SoO types";
  }

  grouping ncs_template_EIGRP-SHOW-AF-STATS-BD {
    description
      "EIGRP AF statistics";
    leaf afi {
      type string;
      description
        "AFI";
    }
    leaf as-number {
      type string;
      description
        "AS Number";
    }
    leaf configured-interface-count {
      type string;
      description
        "Configured interfaces";
    }
    leaf active-interfaces-count {
      type string;
      description
        "Active interfaces";
    }
    leaf activate-count {
      type string;
      description
        "Activate address family success count";
    }
    leaf activate-error {
      type string;
      description
        "Activate address family failure count";
    }
    leaf activate-last-error {
      type string;
      description
        "Activate address family last error";
    }
    leaf deactivate-count {
      type string;
      description
        "Deactivate address family success count";
    }
    leaf deactivate-error {
      type string;
      description
        "Deactivate address family failure count";
    }
    leaf deactivate-last-error {
      type string;
      description
        "Deactivate address family last error";
    }
    leaf socket-set {
      type string;
      description
        "Socket setup success count";
    }
    leaf socket-set-error {
      type string;
      description
        "Socket setup failure count";
    }
    leaf sock-set-last-error {
      type string;
      description
        "Socket setup last error";
    }
    leaf raw-packet-in {
      type string;
      description
        "Succeeded RAW packets in";
    }
    leaf raw-packet-in-error {
      type string;
      description
        "Failed RAW packets ln";
    }
    leaf raw-packet-in-last-error {
      type string;
      description
        "RAW packets in last error";
    }
    leaf raw-packet-out {
      type string;
      description
        "Succeeded RAW packets out";
    }
    leaf raw-packet-out-error {
      type string;
      description
        "Failed RAW packets out";
    }
    leaf raw-packet-out-last-error {
      type string;
      description
        "RAW Packets out last error";
    }
  }

  grouping ncs_template_EIGRP-SHOW-NBR-Q-BD {
    description
      "EIGRP Neighbor queue";
    leaf operation-code {
      type string;
      description
        "Operation Code";
    }
    leaf ack-sequnce-number {
      type string;
      description
        "ACK sequence number";
    }
    leaf start-serial-number {
      type string;
      description
        "Starting serial number";
    }
    leaf end-serial-number {
      type string;
      description
        "Ending serial number";
    }
    leaf pregenerated {
      type string;
      description
        "Pregenerated pak";
    }
    leaf packet-length {
      type string;
      description
        "pak len";
    }
    leaf time-sent-flag {
      type string;
      description
        "Has a pak been sent";
    }
    leaf time-sent {
      type string;
      description
        "Time sent";
    }
    leaf init-bit-set {
      type string;
      description
        "Is the init bit set";
    }
    leaf sequenced {
      type string;
      description
        "Is it sequenced";
    }
  }

  grouping ncs_template_EIGRP-SHOW-NEIGHBORS-BD {
    description
      "EIGRP neighbor";
    container source {
      description
        "Peer address";
      uses ncs_template_EIGRP-ADDR-BD;
    }
    leaf afi {
      type string;
      description
        "AFI";
    }
    leaf as-number {
      type string;
      description
        "AS Number";
    }
    leaf peer-suspended {
      type string;
      description
        "Is it a suspended peer";
    }
    leaf peer-handle {
      type string;
      description
        "Peer handle";
    }
    leaf interface-list {
      type string;
      description
        "Interface name";
    }
    leaf holdtime {
      type string;
      description
        "Hold time";
    }
    leaf uptime {
      type string;
      units "second";
      description
        "UP time (seconds)";
    }
    leaf srtt {
      type string;
      description
        "Round trip time";
    }
    leaf rto {
      type string;
      description
        "RTO";
    }
    leaf bfd-enabled {
      type string;
      description
        "BFD enabled";
    }
    leaf queue-count {
      type string;
      description
        "Q counts";
    }
    leaf last-sequence-number {
      type string;
      description
        "Last sequence number";
    }
    leaf static-neighbor {
      type string;
      description
        "Is it a static neighbor";
    }
    leaf remote-neighbor {
      type string;
      description
        "Is it a remote ucast neighbor";
    }
    leaf hop-count {
      type string;
      description
        "Hop count of the static peer";
    }
    leaf restart-configured {
      type string;
      description
        "Is Restart time configured";
    }
    leaf restart-time {
      type string;
      units "second";
      description
        "Restart time (seconds)";
    }
    leaf last-startup-serial-number {
      type string;
      description
        "Last startup serial number";
    }
    leaf ios-major-version {
      type string;
      description
        "IOS Major version";
    }
    leaf ios-minor-version {
      type string;
      description
        "IOS Minor version";
    }
    leaf eigrp-major-version {
      type string;
      description
        "EIGRP Major version";
    }
    leaf eigrp-minor-version {
      type string;
      description
        "EIGRP Major version";
    }
    leaf retransmission-count {
      type string;
      description
        "Retransmission count";
    }
    leaf retry-count {
      type string;
      description
        "Retry count";
    }
    leaf need-init {
      type string;
      description
        "Need EIGRP Init message";
    }
    leaf need-init-ack {
      type string;
      description
        "Need EIGRP InitAck message";
    }
    leaf reinitialization-needed {
      type string;
      description
        "Reinitialization needed";
    }
    leaf reinit-start {
      type string;
      description
        "Reinit period";
    }
    leaf peer-prefix-count {
      type string;
      description
        "Prefix count";
    }
    leaf stubbed {
      type string;
      description
        "Is it stubbed";
    }
    leaf allow-connected {
      type string;
      description
        "Connected routes accepted";
    }
    leaf allow-static {
      type string;
      description
        "Static routes accepted";
    }
    leaf allow-summaries {
      type string;
      description
        "Summary routes accepted";
    }
    leaf allow-redistributed {
      type string;
      description
        "Redist'ed routes accepted";
    }
    leaf test-handle {
      type string;
      description
        "Test handle flag";
    }
    leaf stubbed-interface {
      type string;
      description
        "Is it stubbed";
    }
    leaf suspended-reset {
      type string;
      description
        "Suspension manually reset";
    }
    leaf suspended-time-left {
      type string;
      description
        "Suspended time left";
    }
    list neighbor-queue {
      // NCS patched for predictable order
      ordered-by user;
      description
        "Neighbor Queue";
      uses ncs_template_EIGRP-SHOW-NBR-Q-BD;
    }
  }

  grouping ncs_template_EIGRP-SHOW-EVENTS-BD {
    description
      "EIGRP DUAL events";
    leaf afi {
      type string;
      description
        "AFI";
    }
    leaf as-number {
      type string;
      description
        "AS Number";
    }
    leaf current-event-index {
      type string;
      description
        "Current event";
    }
    leaf eigrp-start-absolute-seconds {
      type string;
      units "second";
      description
        "Seconds since EIGRP started (absolute)";
    }
    leaf eigrp-start-absolute-nanoseconds {
      type string;
      units "second";
      description
        "Seconds since EIGRP started (absolute)";
    }
    leaf eigrp-start-relative-seconds {
      type string;
      units "second";
      description
        "Seconds since EIGRP started (relative)";
    }
    leaf eigrp-start-relative-nanoseconds {
      type string;
      units "second";
      description
        "Seconds since EIGRP started (relative)";
    }
  }

  grouping ncs_template_EIGRP-SHOW-INTERFACES-BD {
    description
      "An EIGRP interface";
    leaf afi {
      type string;
      description
        "AFI";
    }
    leaf as-number {
      type string;
      description
        "AS Number";
    }
    leaf peer-count {
      type string;
      description
        "Peer Count";
    }
    leaf classic-peer-count {
      type string;
      description
        "Classic Peer Count";
    }
    leaf wide-peer-count {
      type string;
      description
        "Wide Peer Count";
    }
    leaf unreliable-transmits {
      type string;
      description
        "Unreliable transmissions";
    }
    leaf reliable-transmits {
      type string;
      description
        "Reliable transmissions";
    }
    leaf total-srtt {
      type string;
      description
        "Total SRTT";
    }
    leaf unreliable-send-interval {
      type string;
      description
        "Send interval for Unreliable transmissions";
    }
    leaf reliable-send-interval {
      type string;
      description
        "Send interval for Reliable transmissions";
    }
    leaf last-mc-flow-delay {
      type string;
      description
        "Last multicast flow delay";
    }
    leaf pending-routes {
      type string;
      description
        "Number of pending routes";
    }
    leaf hello-interval {
      type string;
      description
        "Hello interval";
    }
    leaf holdtime {
      type string;
      description
        "Hold time";
    }
    leaf bfd-enabled {
      type string;
      description
        "BFD enabled";
    }
    leaf bfd-interval {
      type string;
      description
        "BFD interval";
    }
    leaf bfd-multiplier {
      type string;
      description
        "BFD multiplier";
    }
    leaf serial-number-present {
      type string;
      description
        "Is serno present";
    }
    leaf transmit-serial-number {
      type string;
      description
        "Thread serial number";
    }
    leaf packetize-pending {
      type string;
      description
        "Packetize Timer pending";
    }
    leaf unreliable-multicast-sent {
      type string;
      description
        "Unreliable multicasts sent";
    }
    leaf reliable-multicast-sent {
      type string;
      description
        "Reliable multicasts sent";
    }
    leaf unreliable-unicast-sent {
      type string;
      description
        "Unreliable unicasts sent";
    }
    leaf reliable-unicast-sent {
      type string;
      description
        "Reliable unicasts sent";
    }
    leaf multicast-exceptions-sent {
      type string;
      description
        "Multicast Exceptions sent";
    }
    leaf cr-packets-sent {
      type string;
      description
        "CR packets sent";
    }
    leaf acks-suppressed {
      type string;
      description
        "Suppressed Acks";
    }
    leaf retransmissions-sent {
      type string;
      description
        "Retransmissions sent";
    }
    leaf out-of-sequence-received {
      type string;
      description
        "Out-of-sequence received";
    }
    leaf stub-interface {
      type string;
      description
        "All stub peers";
    }
    leaf next-hop-self-enabled {
      type string;
      description
        "Next-hop-self enabled";
    }
    leaf split-horizon-enabled {
      type string;
      description
        "SplitHorizon enabled";
    }
    leaf passive-interface {
      type string;
      description
        "Interface is passive";
    }
    leaf bandwidth-percent {
      type string;
      units "percentage";
      description
        "Bandwidth percent";
    }
    leaf site-of-origin-type {
      type string;
      description
        "Site of Origin Type";
    }
    leaf site-of-origin {
      type string;
      description
        "Site of Origin";
    }
    leaf auth-mode {
      type string;
      description
        "Authentication Mode";
    }
    leaf auth-keychain {
      type string;
      description
        "Authentication Keychain Name";
    }
    leaf auth-key-exists {
      type string;
      description
        "Authentication key exists";
    }
    leaf auth-key-md5 {
      type string;
      description
        "Authentication key programmed with MD5 algorithm";
    }
    leaf auth-key-id {
      type string;
      description
        "Current active Authentication Key Id";
    }
    leaf total-pkt-recvd {
      type string;
      description
        "Total packets received";
    }
    leaf pkt-drop-wrong-kc {
      type string;
      description
        "Packets dropped due to wrong keychain configured";
    }
    leaf pkt-drop-no-auth {
      type string;
      description
        "Packets dropped due to missing authentication
         data";
    }
    leaf pkt-drop-invalid-auth {
      type string;
      description
        "Packets dropped due to invalid authentication
         data";
    }
    leaf pkt-accepted-valid-auth {
      type string;
      description
        "Packets accepted with valid authentication data";
    }
    leaf bandwidth {
      type string;
      description
        "Deprecated. Please migrate to use Bandwidth64.";
    }
    leaf bandwidth64 {
      type string;
      description
        "Bandwidth";
    }
    leaf delay {
      type string;
      description
        "Deprecated. Please migrate to use Delay64. The
         value of this object might wrap if it is in
         picosecond units";
    }
    leaf delay64 {
      type string;
      description
        "Delay";
    }
    leaf delay-unit {
      type string;
      description
        "Delay unit";
    }
    leaf reliability {
      type string;
      description
        "Reliability";
    }
    leaf load {
      type string;
      description
        "Load";
    }
    leaf mtu {
      type string;
      description
        "MTU";
    }
    leaf configured-bandwidth {
      type string;
      description
        "Deprecated. Please migrate to use
         ConfiguredBandwidth64.";
    }
    leaf configured-bandwidth64 {
      type string;
      description
        "Configured bandwidth";
    }
    leaf configured-delay {
      type string;
      description
        "Deprecated. Please migrate to use
         ConfiguredDelay64. The value of this object
         might wrap if it is in picosecond units";
    }
    leaf configured-delay64 {
      type string;
      description
        "Configured delay";
    }
    leaf configured-delay-unit {
      type string;
      description
        "Configured delay unit";
    }
    leaf configured-reliability {
      type string;
      description
        "Configured reliability";
    }
    leaf configured-load {
      type string;
      description
        "Configured load";
    }
    leaf configured-bandwidth-flag {
      type string;
      description
        "Bandwidth configured";
    }
    leaf configured-delay-flag {
      type string;
      description
        "Delay configured";
    }
    leaf configured-reliability-flag {
      type string;
      description
        "Reliability configured";
    }
    leaf configured-load-flag {
      type string;
      description
        "Load configured";
    }
    leaf up {
      type string;
      description
        "Interface is UP";
    }
    leaf type-supported {
      type string;
      description
        "Interface type is supported";
    }
    leaf ital-record-found {
      type string;
      description
        "ITAL Record valid";
    }
    leaf configured {
      type string;
      description
        "Interface config exists";
    }
    leaf multicast-enabled {
      type string;
      description
        "Requested socket state";
    }
    leaf socket-setup {
      type string;
      description
        "Setup socket state";
    }
    leaf lpts-socket-setup {
      type string;
      description
        "Setup LPTS socket state";
    }
    leaf primary-ipv4-address {
      type string;
      description
        "Primary IPv4 Address";
    }
    leaf ipv6-link-local-addr {
      type string;
      description
        "IPv6 LL Address";
    }
    leaf primary-prefix-length {
      type string;
      description
        "Primary prefix length";
    }
    leaf interface-handle {
      type string;
      description
        "Interface Handle";
    }
    leaf interface-type {
      type string;
      description
        "IM Interface Type";
    }
    leaf configured-items {
      type string;
      description
        "Interface Configured Items";
    }
    leaf is-passive-enabled {
      type string;
      description
        "Passive-Interface configured";
    }
    leaf is-passive-disabled {
      type string;
      description
        "Passive-Interface disabled";
    }
    list static-neighbor {
      // NCS patched for predictable order
      ordered-by user;
      description
        "Static Neighbors";
      uses ncs_template_EIGRP-ADDR-BD;
    }
  }

  grouping ncs_template_EIGRP-SHOW-QUIESCENT-IF-BD {
    description
      "EIGRP Quiescent Interface";
    leaf quiescent-interface-list {
      type string;
      description
        "Interface Name";
    }
  }

  grouping ncs_template_EIGRP-SHOW-TOP-SUMMARY-BD {
    description
      "EIGRP Topology summary";
    leaf afi {
      type string;
      description
        "AFI";
    }
    leaf as-number {
      type string;
      description
        "AS Number";
    }
    leaf router-id {
      type string;
      description
        "Router ID";
    }
    leaf thread-present {
      type string;
      description
        "Is thread present ?";
    }
    leaf transmit-serial-number {
      type string;
      description
        "Thread serial number";
    }
    leaf next-serial-number {
      type string;
      description
        "Next serial number";
    }
    leaf route-count {
      type string;
      description
        "Number of routes";
    }
    leaf path-count {
      type string;
      description
        "Number of paths";
    }
    leaf dummy-count {
      type string;
      description
        "Dummy count";
    }
    leaf ddb-name {
      type string;
      description
        "DDB Name";
    }
    leaf interface-count {
      type string;
      description
        "Number of interfaces";
    }
    leaf handles-used {
      type string;
      description
        "Number of handles used";
    }
    leaf active-interface-count {
      type string;
      description
        "Number of active interfaces";
    }
    list quiescent {
      // NCS patched for predictable order
      ordered-by user;
      description
        "Quiescent interfaces";
      uses ncs_template_EIGRP-SHOW-QUIESCENT-IF-BD;
    }
  }

  grouping ncs_template_EIGRP-SHOW-TRAFFIC-BD {
    description
      "EIGRP Traffic Statistics";
    leaf afi {
      type string;
      description
        "AFI";
    }
    leaf as-number {
      type string;
      description
        "AS Number";
    }
    leaf hellos-sent {
      type string;
      description
        "Hellos sent";
    }
    leaf hellos-received {
      type string;
      description
        "Hellos received";
    }
    leaf updates-sent {
      type string;
      description
        "Updates sent";
    }
    leaf updates-received {
      type string;
      description
        "Updates received";
    }
    leaf queries-sent {
      type string;
      description
        "Queries sent";
    }
    leaf queries-received {
      type string;
      description
        "Queries received";
    }
    leaf replies-sent {
      type string;
      description
        "Replies sent";
    }
    leaf replies-received {
      type string;
      description
        "Replies received";
    }
    leaf acks-sent {
      type string;
      description
        "Acks sent";
    }
    leaf acks-received {
      type string;
      description
        "Acks received";
    }
    leaf sia-queries-sent {
      type string;
      description
        "SIA Queries sent";
    }
    leaf sia-queries-received {
      type string;
      description
        "SIA Queries received";
    }
    leaf sia-replies-sent {
      type string;
      description
        "SIA Replies sent";
    }
    leaf sia-replies-received {
      type string;
      description
        "SIA Replies received";
    }
    leaf max-queue-depth {
      type string;
      description
        "Maximum queue depth";
    }
    leaf queue-drops {
      type string;
      description
        "Queue drops";
    }
  }

  grouping ncs_template_EIGRP-PEER-STATS-BD {
    description
      "EIGRP peer prefix statistics";
    container source {
      description
        "Source address";
      uses ncs_template_EIGRP-ADDR-BD;
    }
    leaf afi {
      type string;
      description
        "AFI";
    }
    leaf state {
      type string;
      description
        "State";
    }
    leaf interface-list {
      type string;
      description
        "Interface name";
    }
    leaf peer-prefix-count {
      type string;
      description
        "Peer prefix count";
    }
    leaf restart-count {
      type string;
      description
        "Restart count";
    }
    leaf time-left {
      type string;
      description
        "Time left";
    }
  }

  grouping ncs_template_EIGRP-SHOW-ACCOUNTING-BD {
    description
      "EIGRP Accounting";
    leaf afi {
      type string;
      description
        "AFI";
    }
    leaf as-number {
      type string;
      description
        "AS Number";
    }
    leaf router-id {
      type string;
      description
        "Router ID";
    }
    leaf aggregate-count {
      type string;
      description
        "Number of aggregates";
    }
    leaf state {
      type string;
      description
        "Redist state";
    }
    leaf redist-prefix-count {
      type string;
      description
        "Redist prefix count";
    }
    leaf restart-count {
      type string;
      description
        "Restart count";
    }
    leaf time-left {
      type string;
      description
        "Time left";
    }
    leaf redist-prefix-present {
      type string;
      description
        "Are there redist'ed prefixes ?";
    }
    list peer-statistics {
      // NCS patched for predictable order
      ordered-by user;
      description
        "Peers and their status";
      uses ncs_template_EIGRP-PEER-STATS-BD;
    }
  }

  grouping ncs_template_EIGRP-SHOW-ACT-BD {
    description
      "EIGRP route's active peer information";
    container source {
      description
        "Peer Address";
      uses ncs_template_EIGRP-ADDR-BD;
    }
    leaf peer-available {
      type string;
      description
        "Peer available";
    }
    leaf interface-list {
      type string;
      description
        "Interface name";
    }
    leaf handle-number {
      type string;
      description
        "Handle number";
    }
  }

  grouping ncs_template_EIGRP-SHOW-PATH-BD {
    description
      "An EIGRP path";
    container next-hop-address {
      description
        "Nexthop address";
      uses ncs_template_EIGRP-ADDR-BD;
    }
    container infosource {
      description
        "Source of route";
      uses ncs_template_EIGRP-ADDR-BD;
    }
    leaf afi {
      type string;
      description
        "AFI";
    }
    leaf next-hop-present {
      type string;
      description
        "NH flag";
    }
    leaf interface-handle {
      type string;
      description
        "Interface handle";
    }
    leaf interface-name {
      type string;
      description
        "Interface name";
    }
    leaf origin {
      type string;
      description
        "Origin of route";
    }
    leaf send-flag {
      type string;
      description
        "Send flag";
    }
    leaf reply-outstanding {
      type string;
      description
        "Outstanding reply";
    }
    leaf metric {
      type string;
      description
        "Deprecated. Please migrate to use Metric64. The
         value of this object might wrap since the metric
         value can go up to (2^48 - 1) in 64-bit metric
         mode";
    }
    leaf metric64 {
      type string;
      description
        "Metric";
    }
    leaf successor-metric {
      type string;
      description
        "Deprecated. Please migrate to use
         SuccessorMetric64. The value of this object
         might wrap since the metric value can go up to
         (2^48 - 1) in 64-bit metric mode";
    }
    leaf successor-metric64 {
      type string;
      description
        "Successor metric";
    }
    leaf reply-status {
      type string;
      description
        "Reply status";
    }
    leaf sia-status {
      type string;
      description
        "SIA status";
    }
    leaf transmit-serial-number {
      type string;
      description
        "Transmit thread serial number";
    }
    leaf anchored {
      type string;
      description
        "Is Transmit thread anchored";
    }
    leaf external-path {
      type string;
      description
        "External";
    }
    leaf bandwidth {
      type string;
      description
        "Deprecated. Please migrate to use Bandwidth64.";
    }
    leaf bandwidth64 {
      type string;
      description
        "Bandwidth";
    }
    leaf delay {
      type string;
      description
        "Deprecated. Please migrate to use Delay64. The
         value of this object might wrap if it is in
         picosecond units ";
    }
    leaf delay64 {
      type string;
      description
        "Delay";
    }
    leaf delay-unit {
      type string;
      description
        "Delay units";
    }
    leaf mtu {
      type string;
      description
        "MTU";
    }
    leaf hop-count {
      type string;
      description
        "Hopcount";
    }
    leaf reliability {
      type string;
      description
        "Reliability";
    }
    leaf load {
      type string;
      description
        "Load";
    }
    leaf internal-router-id {
      type string;
      description
        "Router ID";
    }
    leaf internal-tag {
      type string;
      description
        "Internal Tag";
    }
    leaf extended-communities-present {
      type string;
      description
        "Extended communities present";
    }
    leaf extended-communities-length {
      type string;
      description
        "Length of extended communities";
    }
    leaf extended-communities {
      type string;
      description
        "Extended communities";
    }
    leaf external-information-present {
      type string;
      description
        "External information present";
    }
    leaf external-router-id {
      type string;
      description
        "Router ID";
    }
    leaf external-this-system {
      type string;
      description
        "Is it this system";
    }
    leaf external-as {
      type string;
      description
        "AS Number";
    }
    leaf external-protocol {
      type string;
      description
        "Protocol ID";
    }
    leaf external-metric {
      type string;
      description
        "Metric";
    }
    leaf external-tag {
      type string;
      description
        "Tag";
    }
    leaf conditional-default-path {
      type string;
      description
        "Conditional Default flag";
    }
    leaf rib-state {
      type string;
      description
        "State of path in RIB";
    }
  }

  grouping ncs_template_EIGRP-PREFIX-BD {
    description
      "EIGRP IP v4/v6 Prefix";
    leaf ipv4-prefix {
      type string;
      description
        "IPv4 Prefix";
    }
    leaf ipv6-prefix {
      type string;
      description
        "IPv6 Prefix";
    }
    leaf prefix-length {
      type string;
      description
        "Prefix length";
    }
  }

  grouping ncs_template_EIGRP-SHOW-ROUTE-BD {
    description
      "EIGRP Route";
    container prefix-xr {
      description
        "IP Prefix/length";
      uses ncs_template_EIGRP-PREFIX-BD;
    }
    leaf afi {
      type string;
      description
        "AFI";
    }
    leaf as-number {
      type string;
      description
        "AS Number";
    }
    leaf router-id {
      type string;
      description
        "Router ID";
    }
    leaf active {
      type string;
      description
        "Active route";
    }
    leaf successors {
      type string;
      description
        "Successors";
    }
    leaf successors-present {
      type string;
      description
        "Are there successors";
    }
    leaf old-metric {
      type string;
      description
        "Deprecated. Please migrate to use OldMetric64.
         The value of this object might wrap since the
         metric value can go up to (2^48 - 1) in 64-bit
         metric mode";
    }
    leaf old-metric64 {
      type string;
      description
        "Old metric";
    }
    leaf metric {
      type string;
      description
        "Deprecated. Please migrate to use Metric64. The
         value of this object might wrap since the metric
         value can go up to (2^48 - 1) in 64-bit metric
         mode";
    }
    leaf metric64 {
      type string;
      description
        "Metric";
    }
    leaf rib-metric {
      type string;
      description
        "Metric downloaded to RIB";
    }
    leaf tag {
      type string;
      description
        "Tag";
    }
    leaf send-flag {
      type string;
      description
        "Send flag";
    }
    leaf transmit-serial-number {
      type string;
      description
        "Transmit thread Serial Number";
    }
    leaf transmit-refcount {
      type string;
      description
        "Transmit thread refcount";
    }
    leaf transmit-anchored {
      type string;
      description
        "Is Transmit thread anchored";
    }
    leaf reply-handles {
      type string;
      description
        "Reply handles used";
    }
    leaf active-time-secs {
      type string;
      units "second";
      description
        "Active time seconds";
    }
    leaf active-time-nsecs {
      type string;
      units "nanosecond";
      description
        "Active time nanoseconds";
    }
    leaf origin {
      type string;
      description
        "Origin";
    }
    leaf retry-count {
      type string;
      description
        "Retry count";
    }
    leaf active-stats {
      type string;
      description
        "Active stats flag";
    }
    leaf min-time {
      type string;
      description
        "Active stats min time";
    }
    leaf max-time {
      type string;
      description
        "Active stats max time";
    }
    leaf average-time {
      type string;
      description
        "Active stats average time";
    }
    leaf ack-count {
      type string;
      description
        "Active stats active count";
    }
    leaf replies {
      type string;
      description
        "Number of replies outstanding";
    }
    leaf route-in-sia {
      type string;
      description
        "Route is SIA";
    }
    leaf sia-reply-handles {
      type string;
      description
        "Reply handles used";
    }
    list paths {
      // NCS patched for predictable order
      ordered-by user;
      description
        "Paths for this route";
      uses ncs_template_EIGRP-SHOW-PATH-BD;
    }
    list active-peer {
      // NCS patched for predictable order
      ordered-by user;
      description
        "Peers yet to respond";
      uses ncs_template_EIGRP-SHOW-ACT-BD;
    }
    list sia-peer {
      // NCS patched for predictable order
      ordered-by user;
      description
        "SIA Peers yet to respond";
      uses ncs_template_EIGRP-SHOW-ACT-BD;
    }
  }

  grouping ncs_template_EIGRP-ADDR-BD {
    description
      "EIGRP IP v4/v6 Address";
    leaf ipv4-address {
      type string;
      description
        "IPv4 Address";
    }
    leaf ipv6-address {
      type string;
      description
        "IPv6 Address";
    }
  }

  grouping ncs_template_EIGRP-SHOW-STATIC-NEIGHBORS-BD {
    description
      "EIGRP Static neighbor";
    container source {
      description
        "Neighbor address";
      uses ncs_template_EIGRP-ADDR-BD;
    }
    leaf afi {
      type string;
      description
        "AFI";
    }
    leaf as-number {
      type string;
      description
        "AS Number";
    }
    leaf interface-list {
      type string;
      description
        "Interface Name";
    }
  }

  grouping ncs_template_EIGRP-SHOW-PROT-INT-BD {
    description
      "EIGRP Protocol Interface information";
    leaf afi {
      type string;
      description
        "AFI";
    }
    leaf interface {
      type string;
      description
        "Interface";
    }
    leaf outbound-filter-policy {
      type string;
      description
        "Outbound Filter Policy";
    }
    leaf inbound-filter-policy {
      type string;
      description
        "Inbound Filter Policy";
    }
    leaf inactive {
      type string;
      description
        "Interface is DOWN";
    }
    leaf passive-interface {
      type string;
      description
        "Interface is passive";
    }
  }

  grouping ncs_template_EIGRP-SHOW-REDIST-BD {
    description
      "EIGRP Redist Protocol information";
    leaf afi {
      type string;
      description
        "AFI";
    }
    leaf redistributed-protocol {
      type string;
      description
        "Redistributed Protocol";
    }
    leaf redistributed-protocol-tag {
      type string;
      description
        "Redistributed Protocol tag";
    }
    leaf redristribute-policy {
      type string;
      description
        "Redistribute Filter policy";
    }
    leaf redistribute-protocol-id {
      type string;
      description
        "Redistributed Protocol ID";
    }
    leaf rib-handle {
      type string;
      description
        "Redistributed Protocol handle";
    }
  }

  grouping ncs_template_EIGRP-SHOW-PROT-VRF-BD {
    description
      "EIGRP VRF protocol information";
    leaf afi {
      type string;
      description
        "AFI";
    }
    leaf as-number {
      type string;
      description
        "AS Number";
    }
    leaf router-id {
      type string;
      description
        "Router ID";
    }
    leaf auto-summarization {
      type string;
      description
        "Auto Summarization";
    }
    leaf log-neighbor-changes {
      type string;
      description
        "Neighbor changes logged";
    }
    leaf log-neighbor-warnings {
      type string;
      description
        "Neighbor warnings logged";
    }
    leaf rib-table-limit-reached {
      type string;
      description
        "RIB Table limit has been reached";
    }
    leaf outbound-filter-policy {
      type string;
      description
        "Outbound Filter Policy";
    }
    leaf inbound-filter-policy {
      type string;
      description
        "Inbound Filter Policy";
    }
    leaf outgoing-candidate-default-flagged {
      type string;
      description
        "Default Allowed Out";
    }
    leaf outgoing-candidate-default-policy {
      type string;
      description
        "Default Allowed Out Policy";
    }
    leaf incoming-candidate-default-flagged {
      type string;
      description
        "Default Allowed In";
    }
    leaf incoming-candidate-default-policy {
      type string;
      description
        "Default Allowed In Policy";
    }
    leaf internal-distance {
      type string;
      description
        "Internal Distance";
    }
    leaf external-distance {
      type string;
      description
        "External Distance";
    }
    leaf maximum-paths {
      type string;
      description
        "Maximum paths";
    }
    leaf variance {
      type string;
      description
        "Variance";
    }
    leaf metric-weight-k1 {
      type string;
      description
        "K1 value";
    }
    leaf metric-weight-k2 {
      type string;
      description
        "K2 value";
    }
    leaf metric-weight-k3 {
      type string;
      description
        "K3 value";
    }
    leaf metric-weight-k4 {
      type string;
      description
        "K4 value";
    }
    leaf metric-weight-k5 {
      type string;
      description
        "K5 value";
    }
    leaf metric-weight-k6 {
      type string;
      description
        "K6 value";
    }
    leaf rib-scale {
      type string;
      description
        "RIB Scale";
    }
    leaf metric-version {
      type string;
      description
        "Metric Version";
    }
    leaf metric-maximum-hopcount {
      type string;
      description
        "Metric MaxHops configured";
    }
    leaf default-metric-configured {
      type string;
      description
        "Default Metric Configured";
    }
    leaf default-bandwidth {
      type string;
      description
        "Default Bandwidth";
    }
    leaf default-delay {
      type string;
      description
        "Default Delay";
    }
    leaf default-reliability {
      type string;
      description
        "Default Reliability";
    }
    leaf default-load {
      type string;
      description
        "Default Load";
    }
    leaf default-mtu {
      type string;
      description
        "Default MTU";
    }
    leaf stub-configured {
      type string;
      description
        "Stub Configured";
    }
    leaf stub-receive-only {
      type string;
      description
        "Stub Receive-only configured";
    }
    leaf stub-allow-connected-routes {
      type string;
      description
        "ConnectedRoutes allowed";
    }
    leaf stub-allow-static-routes {
      type string;
      description
        "Static Routes allowed";
    }
    leaf stub-allow-summary-routes {
      type string;
      description
        "Summary Routes allowed";
    }
    leaf stub-allow-redistributed-routes {
      type string;
      description
        "Redistributed Routes allowed";
    }
    leaf nsf-enabled {
      type string;
      description
        "NSF Enabled";
    }
    leaf nsf-route-hold-time {
      type string;
      description
        "NSF Route Hold Time";
    }
    leaf nsf-signal-time {
      type string;
      description
        "NSF Signal Time";
    }
    leaf nsf-converge-time {
      type string;
      description
        "NSF Converge Time";
    }
    leaf restart-configured {
      type string;
      description
        "Is Restart time configured";
    }
    leaf restart-time {
      type string;
      units "second";
      description
        "Restart time (seconds)";
    }
    leaf sia-active-time {
      type string;
      description
        "SIA Active Time";
    }
    leaf rib-protocol-id {
      type string;
      description
        "RIB Protocol ID";
    }
    leaf table-id {
      type string;
      description
        "Table ID";
    }
    leaf vrf-id {
      type string;
      description
        "VRF ID";
    }
    leaf ital-activation-received {
      type string;
      description
        "VRF activated by ITAL";
    }
    leaf vrf-activated {
      type string;
      description
        "VRF activated by EIGRP";
    }
    leaf up {
      type string;
      description
        "VRF information available";
    }
    leaf rib-initialized {
      type string;
      description
        "RIB initialization for VRF";
    }
    leaf rib-converged {
      type string;
      description
        "RIB convergence for VRF";
    }
    leaf rib-converged-reload {
      type string;
      description
        "Reload following RIB Convergence";
    }
    leaf socket-request {
      type string;
      description
        "Requested Socket Option for VRF";
    }
    leaf socket-setup {
      type string;
      description
        "Setup socket state for VRF";
    }
    leaf default-vrf {
      type string;
      description
        "VRF represents default-context";
    }
    leaf af-enabled {
      type string;
      description
        "AF Enabled";
    }
    leaf is-passive-default {
      type string;
      description
        "Passive-Interface default configured";
    }
    leaf configured-items {
      type string;
      description
        "VRF Configured Items";
    }
    leaf af-configured-items {
      type string;
      description
        "AF Configured Items";
    }
    leaf ip-arm-router-id {
      type string;
      description
        "IP ARM Router ID";
    }
    leaf first-interface-up-address {
      type string;
      description
        "IP Address of first UP interface";
    }
    leaf nsf-in-progress {
      type string;
      description
        "DDB NSF in progress indication";
    }
    leaf rib-table-converged {
      type string;
      description
        "RIB Table convergence indication";
    }
    list redistributed-protocol {
      // NCS patched for predictable order
      ordered-by user;
      description
        "Redistributed Protocols";
      uses ncs_template_EIGRP-SHOW-REDIST-BD;
    }
    list interface {
      // NCS patched for predictable order
      ordered-by user;
      description
        "Interfaces";
      uses ncs_template_EIGRP-SHOW-PROT-INT-BD;
    }
  }

  grouping ncs_template_EIGRP-VRFS-BD {
    description
      "EIGRP VRF Name";
    leaf vrf-name-xr {
      type string;
      description
        "VRF Name";
    }
  }

  grouping ncs_rpc_notif_EIGRP-SHOW-AF-STATS-BD {
    description
      "EIGRP AF statistics";
    leaf afi {
      type uint32;
      description
        "AFI";
    }
    leaf as-number {
      type uint32;
      description
        "AS Number";
    }
    leaf configured-interface-count {
      type uint32;
      description
        "Configured interfaces";
    }
    leaf active-interfaces-count {
      type uint32;
      description
        "Active interfaces";
    }
    leaf activate-count {
      type uint64;
      description
        "Activate address family success count";
    }
    leaf activate-error {
      type uint64;
      description
        "Activate address family failure count";
    }
    leaf activate-last-error {
      type int32;
      description
        "Activate address family last error";
    }
    leaf deactivate-count {
      type uint64;
      description
        "Deactivate address family success count";
    }
    leaf deactivate-error {
      type uint64;
      description
        "Deactivate address family failure count";
    }
    leaf deactivate-last-error {
      type int32;
      description
        "Deactivate address family last error";
    }
    leaf socket-set {
      type uint64;
      description
        "Socket setup success count";
    }
    leaf socket-set-error {
      type uint64;
      description
        "Socket setup failure count";
    }
    leaf sock-set-last-error {
      type int32;
      description
        "Socket setup last error";
    }
    leaf raw-packet-in {
      type uint64;
      description
        "Succeeded RAW packets in";
    }
    leaf raw-packet-in-error {
      type uint64;
      description
        "Failed RAW packets ln";
    }
    leaf raw-packet-in-last-error {
      type int32;
      description
        "RAW packets in last error";
    }
    leaf raw-packet-out {
      type uint64;
      description
        "Succeeded RAW packets out";
    }
    leaf raw-packet-out-error {
      type uint64;
      description
        "Failed RAW packets out";
    }
    leaf raw-packet-out-last-error {
      type int32;
      description
        "RAW Packets out last error";
    }
  }

  grouping ncs_rpc_notif_EIGRP-SHOW-NBR-Q-BD {
    description
      "EIGRP Neighbor queue";
    leaf operation-code {
      type uint32;
      description
        "Operation Code";
    }
    leaf ack-sequnce-number {
      type uint32;
      description
        "ACK sequence number";
    }
    leaf start-serial-number {
      type uint64;
      description
        "Starting serial number";
    }
    leaf end-serial-number {
      type uint64;
      description
        "Ending serial number";
    }
    leaf pregenerated {
      type boolean;
      description
        "Pregenerated pak";
    }
    leaf packet-length {
      type uint32;
      description
        "pak len";
    }
    leaf time-sent-flag {
      type boolean;
      description
        "Has a pak been sent";
    }
    leaf time-sent {
      type uint32;
      description
        "Time sent";
    }
    leaf init-bit-set {
      type boolean;
      description
        "Is the init bit set";
    }
    leaf sequenced {
      type boolean;
      description
        "Is it sequenced";
    }
  }

  grouping ncs_rpc_notif_EIGRP-SHOW-NEIGHBORS-BD {
    description
      "EIGRP neighbor";
    container source {
      description
        "Peer address";
      uses ncs_rpc_notif_EIGRP-ADDR-BD;
    }
    leaf afi {
      type uint32;
      description
        "AFI";
    }
    leaf as-number {
      type uint32;
      description
        "AS Number";
    }
    leaf peer-suspended {
      type boolean;
      description
        "Is it a suspended peer";
    }
    leaf peer-handle {
      type uint32;
      description
        "Peer handle";
    }
    leaf interface-list {
      type string;
      description
        "Interface name";
    }
    leaf holdtime {
      type uint32;
      description
        "Hold time";
    }
    leaf uptime {
      type uint32;
      units "second";
      description
        "UP time (seconds)";
    }
    leaf srtt {
      type uint32;
      description
        "Round trip time";
    }
    leaf rto {
      type uint32;
      description
        "RTO";
    }
    leaf bfd-enabled {
      type boolean;
      description
        "BFD enabled";
    }
    leaf queue-count {
      type uint32;
      description
        "Q counts";
    }
    leaf last-sequence-number {
      type uint32;
      description
        "Last sequence number";
    }
    leaf static-neighbor {
      type boolean;
      description
        "Is it a static neighbor";
    }
    leaf remote-neighbor {
      type boolean;
      description
        "Is it a remote ucast neighbor";
    }
    leaf hop-count {
      type uint8;
      description
        "Hop count of the static peer";
    }
    leaf restart-configured {
      type boolean;
      description
        "Is Restart time configured";
    }
    leaf restart-time {
      type uint32;
      units "second";
      description
        "Restart time (seconds)";
    }
    leaf last-startup-serial-number {
      type uint64;
      description
        "Last startup serial number";
    }
    leaf ios-major-version {
      type uint8;
      description
        "IOS Major version";
    }
    leaf ios-minor-version {
      type uint8;
      description
        "IOS Minor version";
    }
    leaf eigrp-major-version {
      type uint8;
      description
        "EIGRP Major version";
    }
    leaf eigrp-minor-version {
      type uint8;
      description
        "EIGRP Major version";
    }
    leaf retransmission-count {
      type uint32;
      description
        "Retransmission count";
    }
    leaf retry-count {
      type uint32;
      description
        "Retry count";
    }
    leaf need-init {
      type boolean;
      description
        "Need EIGRP Init message";
    }
    leaf need-init-ack {
      type boolean;
      description
        "Need EIGRP InitAck message";
    }
    leaf reinitialization-needed {
      type boolean;
      description
        "Reinitialization needed";
    }
    leaf reinit-start {
      type uint32;
      description
        "Reinit period";
    }
    leaf peer-prefix-count {
      type uint32;
      description
        "Prefix count";
    }
    leaf stubbed {
      type boolean;
      description
        "Is it stubbed";
    }
    leaf allow-connected {
      type boolean;
      description
        "Connected routes accepted";
    }
    leaf allow-static {
      type boolean;
      description
        "Static routes accepted";
    }
    leaf allow-summaries {
      type boolean;
      description
        "Summary routes accepted";
    }
    leaf allow-redistributed {
      type boolean;
      description
        "Redist'ed routes accepted";
    }
    leaf test-handle {
      type boolean;
      description
        "Test handle flag";
    }
    leaf stubbed-interface {
      type boolean;
      description
        "Is it stubbed";
    }
    leaf suspended-reset {
      type boolean;
      description
        "Suspension manually reset";
    }
    leaf suspended-time-left {
      type uint32;
      description
        "Suspended time left";
    }
    list neighbor-queue {
      description
        "Neighbor Queue";
      uses ncs_rpc_notif_EIGRP-SHOW-NBR-Q-BD;
    }
  }

  grouping ncs_rpc_notif_EIGRP-SHOW-EVENTS-BD {
    description
      "EIGRP DUAL events";
    leaf afi {
      type uint32;
      description
        "AFI";
    }
    leaf as-number {
      type uint32;
      description
        "AS Number";
    }
    leaf current-event-index {
      type uint32;
      description
        "Current event";
    }
    leaf eigrp-start-absolute-seconds {
      type uint32;
      units "second";
      description
        "Seconds since EIGRP started (absolute)";
    }
    leaf eigrp-start-absolute-nanoseconds {
      type uint32;
      units "second";
      description
        "Seconds since EIGRP started (absolute)";
    }
    leaf eigrp-start-relative-seconds {
      type uint32;
      units "second";
      description
        "Seconds since EIGRP started (relative)";
    }
    leaf eigrp-start-relative-nanoseconds {
      type uint32;
      units "second";
      description
        "Seconds since EIGRP started (relative)";
    }
  }

  grouping ncs_rpc_notif_EIGRP-SHOW-INTERFACES-BD {
    description
      "An EIGRP interface";
    leaf afi {
      type uint32;
      description
        "AFI";
    }
    leaf as-number {
      type uint32;
      description
        "AS Number";
    }
    leaf peer-count {
      type uint32;
      description
        "Peer Count";
    }
    leaf classic-peer-count {
      type uint32;
      description
        "Classic Peer Count";
    }
    leaf wide-peer-count {
      type uint32;
      description
        "Wide Peer Count";
    }
    leaf unreliable-transmits {
      type uint32;
      description
        "Unreliable transmissions";
    }
    leaf reliable-transmits {
      type uint32;
      description
        "Reliable transmissions";
    }
    leaf total-srtt {
      type uint32;
      description
        "Total SRTT";
    }
    leaf unreliable-send-interval {
      type uint32;
      description
        "Send interval for Unreliable transmissions";
    }
    leaf reliable-send-interval {
      type uint32;
      description
        "Send interval for Reliable transmissions";
    }
    leaf last-mc-flow-delay {
      type uint32;
      description
        "Last multicast flow delay";
    }
    leaf pending-routes {
      type uint32;
      description
        "Number of pending routes";
    }
    leaf hello-interval {
      type uint32;
      description
        "Hello interval";
    }
    leaf holdtime {
      type uint32;
      description
        "Hold time";
    }
    leaf bfd-enabled {
      type boolean;
      description
        "BFD enabled";
    }
    leaf bfd-interval {
      type uint32;
      description
        "BFD interval";
    }
    leaf bfd-multiplier {
      type uint32;
      description
        "BFD multiplier";
    }
    leaf serial-number-present {
      type boolean;
      description
        "Is serno present";
    }
    leaf transmit-serial-number {
      type uint64;
      description
        "Thread serial number";
    }
    leaf packetize-pending {
      type boolean;
      description
        "Packetize Timer pending";
    }
    leaf unreliable-multicast-sent {
      type uint32;
      description
        "Unreliable multicasts sent";
    }
    leaf reliable-multicast-sent {
      type uint32;
      description
        "Reliable multicasts sent";
    }
    leaf unreliable-unicast-sent {
      type uint32;
      description
        "Unreliable unicasts sent";
    }
    leaf reliable-unicast-sent {
      type uint32;
      description
        "Reliable unicasts sent";
    }
    leaf multicast-exceptions-sent {
      type uint32;
      description
        "Multicast Exceptions sent";
    }
    leaf cr-packets-sent {
      type uint32;
      description
        "CR packets sent";
    }
    leaf acks-suppressed {
      type uint32;
      description
        "Suppressed Acks";
    }
    leaf retransmissions-sent {
      type uint32;
      description
        "Retransmissions sent";
    }
    leaf out-of-sequence-received {
      type uint32;
      description
        "Out-of-sequence received";
    }
    leaf stub-interface {
      type boolean;
      description
        "All stub peers";
    }
    leaf next-hop-self-enabled {
      type boolean;
      description
        "Next-hop-self enabled";
    }
    leaf split-horizon-enabled {
      type boolean;
      description
        "SplitHorizon enabled";
    }
    leaf passive-interface {
      type boolean;
      description
        "Interface is passive";
    }
    leaf bandwidth-percent {
      type uint32;
      units "percentage";
      description
        "Bandwidth percent";
    }
    leaf site-of-origin-type {
      type Eigrp-bd-soo;
      description
        "Site of Origin Type";
    }
    leaf site-of-origin {
      type string;
      description
        "Site of Origin";
    }
    leaf auth-mode {
      type uint32;
      description
        "Authentication Mode";
    }
    leaf auth-keychain {
      type string;
      description
        "Authentication Keychain Name";
    }
    leaf auth-key-exists {
      type boolean;
      description
        "Authentication key exists";
    }
    leaf auth-key-md5 {
      type boolean;
      description
        "Authentication key programmed with MD5 algorithm";
    }
    leaf auth-key-id {
      type uint64;
      description
        "Current active Authentication Key Id";
    }
    leaf total-pkt-recvd {
      type uint32;
      description
        "Total packets received";
    }
    leaf pkt-drop-wrong-kc {
      type uint32;
      description
        "Packets dropped due to wrong keychain configured";
    }
    leaf pkt-drop-no-auth {
      type uint32;
      description
        "Packets dropped due to missing authentication
         data";
    }
    leaf pkt-drop-invalid-auth {
      type uint32;
      description
        "Packets dropped due to invalid authentication
         data";
    }
    leaf pkt-accepted-valid-auth {
      type uint32;
      description
        "Packets accepted with valid authentication data";
    }
    leaf bandwidth {
      type uint32;
      description
        "Deprecated. Please migrate to use Bandwidth64.";
    }
    leaf bandwidth64 {
      type uint64;
      description
        "Bandwidth";
    }
    leaf delay {
      type uint32;
      description
        "Deprecated. Please migrate to use Delay64. The
         value of this object might wrap if it is in
         picosecond units";
    }
    leaf delay64 {
      type uint64;
      description
        "Delay";
    }
    leaf delay-unit {
      type Eigrp-bd-delay-unit;
      description
        "Delay unit";
    }
    leaf reliability {
      type uint32;
      description
        "Reliability";
    }
    leaf load {
      type uint32;
      description
        "Load";
    }
    leaf mtu {
      type uint32;
      description
        "MTU";
    }
    leaf configured-bandwidth {
      type uint32;
      description
        "Deprecated. Please migrate to use
         ConfiguredBandwidth64.";
    }
    leaf configured-bandwidth64 {
      type uint64;
      description
        "Configured bandwidth";
    }
    leaf configured-delay {
      type uint32;
      description
        "Deprecated. Please migrate to use
         ConfiguredDelay64. The value of this object
         might wrap if it is in picosecond units";
    }
    leaf configured-delay64 {
      type uint64;
      description
        "Configured delay";
    }
    leaf configured-delay-unit {
      type Eigrp-bd-delay-unit;
      description
        "Configured delay unit";
    }
    leaf configured-reliability {
      type uint32;
      description
        "Configured reliability";
    }
    leaf configured-load {
      type uint32;
      description
        "Configured load";
    }
    leaf configured-bandwidth-flag {
      type boolean;
      description
        "Bandwidth configured";
    }
    leaf configured-delay-flag {
      type boolean;
      description
        "Delay configured";
    }
    leaf configured-reliability-flag {
      type boolean;
      description
        "Reliability configured";
    }
    leaf configured-load-flag {
      type boolean;
      description
        "Load configured";
    }
    leaf up {
      type boolean;
      description
        "Interface is UP";
    }
    leaf type-supported {
      type boolean;
      description
        "Interface type is supported";
    }
    leaf ital-record-found {
      type boolean;
      description
        "ITAL Record valid";
    }
    leaf configured {
      type boolean;
      description
        "Interface config exists";
    }
    leaf multicast-enabled {
      type boolean;
      description
        "Requested socket state";
    }
    leaf socket-setup {
      type boolean;
      description
        "Setup socket state";
    }
    leaf lpts-socket-setup {
      type boolean;
      description
        "Setup LPTS socket state";
    }
    leaf primary-ipv4-address {
      type inet:ipv4-address;
      description
        "Primary IPv4 Address";
    }
    leaf ipv6-link-local-addr {
      type inet:ipv6-address;
      description
        "IPv6 LL Address";
    }
    leaf primary-prefix-length {
      type uint32;
      description
        "Primary prefix length";
    }
    leaf interface-handle {
      type uint32;
      description
        "Interface Handle";
    }
    leaf interface-type {
      type uint32;
      description
        "IM Interface Type";
    }
    leaf configured-items {
      type uint32;
      description
        "Interface Configured Items";
    }
    leaf is-passive-enabled {
      type boolean;
      description
        "Passive-Interface configured";
    }
    leaf is-passive-disabled {
      type boolean;
      description
        "Passive-Interface disabled";
    }
    list static-neighbor {
      description
        "Static Neighbors";
      uses ncs_rpc_notif_EIGRP-ADDR-BD;
    }
  }

  grouping ncs_rpc_notif_EIGRP-SHOW-QUIESCENT-IF-BD {
    description
      "EIGRP Quiescent Interface";
    leaf quiescent-interface-list {
      type string;
      description
        "Interface Name";
    }
  }

  grouping ncs_rpc_notif_EIGRP-SHOW-TOP-SUMMARY-BD {
    description
      "EIGRP Topology summary";
    leaf afi {
      type uint32;
      description
        "AFI";
    }
    leaf as-number {
      type uint32;
      description
        "AS Number";
    }
    leaf router-id {
      type inet:ipv4-address;
      description
        "Router ID";
    }
    leaf thread-present {
      type boolean;
      description
        "Is thread present ?";
    }
    leaf transmit-serial-number {
      type uint64;
      description
        "Thread serial number";
    }
    leaf next-serial-number {
      type uint64;
      description
        "Next serial number";
    }
    leaf route-count {
      type uint32;
      description
        "Number of routes";
    }
    leaf path-count {
      type uint32;
      description
        "Number of paths";
    }
    leaf dummy-count {
      type uint32;
      description
        "Dummy count";
    }
    leaf ddb-name {
      type string;
      description
        "DDB Name";
    }
    leaf interface-count {
      type uint32;
      description
        "Number of interfaces";
    }
    leaf handles-used {
      type uint32;
      description
        "Number of handles used";
    }
    leaf active-interface-count {
      type uint32;
      description
        "Number of active interfaces";
    }
    list quiescent {
      description
        "Quiescent interfaces";
      uses ncs_rpc_notif_EIGRP-SHOW-QUIESCENT-IF-BD;
    }
  }

  grouping ncs_rpc_notif_EIGRP-SHOW-TRAFFIC-BD {
    description
      "EIGRP Traffic Statistics";
    leaf afi {
      type uint32;
      description
        "AFI";
    }
    leaf as-number {
      type uint32;
      description
        "AS Number";
    }
    leaf hellos-sent {
      type uint32;
      description
        "Hellos sent";
    }
    leaf hellos-received {
      type uint32;
      description
        "Hellos received";
    }
    leaf updates-sent {
      type uint32;
      description
        "Updates sent";
    }
    leaf updates-received {
      type uint32;
      description
        "Updates received";
    }
    leaf queries-sent {
      type uint32;
      description
        "Queries sent";
    }
    leaf queries-received {
      type uint32;
      description
        "Queries received";
    }
    leaf replies-sent {
      type uint32;
      description
        "Replies sent";
    }
    leaf replies-received {
      type uint32;
      description
        "Replies received";
    }
    leaf acks-sent {
      type uint32;
      description
        "Acks sent";
    }
    leaf acks-received {
      type uint32;
      description
        "Acks received";
    }
    leaf sia-queries-sent {
      type uint32;
      description
        "SIA Queries sent";
    }
    leaf sia-queries-received {
      type uint32;
      description
        "SIA Queries received";
    }
    leaf sia-replies-sent {
      type uint32;
      description
        "SIA Replies sent";
    }
    leaf sia-replies-received {
      type uint32;
      description
        "SIA Replies received";
    }
    leaf max-queue-depth {
      type uint32;
      description
        "Maximum queue depth";
    }
    leaf queue-drops {
      type uint32;
      description
        "Queue drops";
    }
  }

  grouping ncs_rpc_notif_EIGRP-PEER-STATS-BD {
    description
      "EIGRP peer prefix statistics";
    container source {
      description
        "Source address";
      uses ncs_rpc_notif_EIGRP-ADDR-BD;
    }
    leaf afi {
      type uint32;
      description
        "AFI";
    }
    leaf state {
      type int8;
      description
        "State";
    }
    leaf interface-list {
      type string;
      description
        "Interface name";
    }
    leaf peer-prefix-count {
      type uint32;
      description
        "Peer prefix count";
    }
    leaf restart-count {
      type uint32;
      description
        "Restart count";
    }
    leaf time-left {
      type uint32;
      description
        "Time left";
    }
  }

  grouping ncs_rpc_notif_EIGRP-SHOW-ACCOUNTING-BD {
    description
      "EIGRP Accounting";
    leaf afi {
      type uint32;
      description
        "AFI";
    }
    leaf as-number {
      type uint32;
      description
        "AS Number";
    }
    leaf router-id {
      type inet:ipv4-address;
      description
        "Router ID";
    }
    leaf aggregate-count {
      type uint32;
      description
        "Number of aggregates";
    }
    leaf state {
      type int8;
      description
        "Redist state";
    }
    leaf redist-prefix-count {
      type uint32;
      description
        "Redist prefix count";
    }
    leaf restart-count {
      type uint32;
      description
        "Restart count";
    }
    leaf time-left {
      type uint32;
      description
        "Time left";
    }
    leaf redist-prefix-present {
      type boolean;
      description
        "Are there redist'ed prefixes ?";
    }
    list peer-statistics {
      description
        "Peers and their status";
      uses ncs_rpc_notif_EIGRP-PEER-STATS-BD;
    }
  }

  grouping ncs_rpc_notif_EIGRP-SHOW-ACT-BD {
    description
      "EIGRP route's active peer information";
    container source {
      description
        "Peer Address";
      uses ncs_rpc_notif_EIGRP-ADDR-BD;
    }
    leaf peer-available {
      type boolean;
      description
        "Peer available";
    }
    leaf interface-list {
      type string;
      description
        "Interface name";
    }
    leaf handle-number {
      type uint32;
      description
        "Handle number";
    }
  }

  grouping ncs_rpc_notif_EIGRP-SHOW-PATH-BD {
    description
      "An EIGRP path";
    container next-hop-address {
      description
        "Nexthop address";
      uses ncs_rpc_notif_EIGRP-ADDR-BD;
    }
    container infosource {
      description
        "Source of route";
      uses ncs_rpc_notif_EIGRP-ADDR-BD;
    }
    leaf afi {
      type uint32;
      description
        "AFI";
    }
    leaf next-hop-present {
      type boolean;
      description
        "NH flag";
    }
    leaf interface-handle {
      type xr:Interface-name;
      description
        "Interface handle";
    }
    leaf interface-name {
      type string;
      description
        "Interface name";
    }
    leaf origin {
      type Eigrp-bd-path-origin;
      description
        "Origin of route";
    }
    leaf send-flag {
      type Eigrp-bd-path-send-flag;
      description
        "Send flag";
    }
    leaf reply-outstanding {
      type boolean;
      description
        "Outstanding reply";
    }
    leaf metric {
      type uint32;
      description
        "Deprecated. Please migrate to use Metric64. The
         value of this object might wrap since the metric
         value can go up to (2^48 - 1) in 64-bit metric
         mode";
    }
    leaf metric64 {
      type uint64;
      description
        "Metric";
    }
    leaf successor-metric {
      type uint32;
      description
        "Deprecated. Please migrate to use
         SuccessorMetric64. The value of this object
         might wrap since the metric value can go up to
         (2^48 - 1) in 64-bit metric mode";
    }
    leaf successor-metric64 {
      type uint64;
      description
        "Successor metric";
    }
    leaf reply-status {
      type boolean;
      description
        "Reply status";
    }
    leaf sia-status {
      type boolean;
      description
        "SIA status";
    }
    leaf transmit-serial-number {
      type uint64;
      description
        "Transmit thread serial number";
    }
    leaf anchored {
      type boolean;
      description
        "Is Transmit thread anchored";
    }
    leaf external-path {
      type boolean;
      description
        "External";
    }
    leaf bandwidth {
      type uint32;
      description
        "Deprecated. Please migrate to use Bandwidth64.";
    }
    leaf bandwidth64 {
      type uint64;
      description
        "Bandwidth";
    }
    leaf delay {
      type uint32;
      description
        "Deprecated. Please migrate to use Delay64. The
         value of this object might wrap if it is in
         picosecond units ";
    }
    leaf delay64 {
      type uint64;
      description
        "Delay";
    }
    leaf delay-unit {
      type Eigrp-bd-delay-unit;
      description
        "Delay units";
    }
    leaf mtu {
      type uint32;
      description
        "MTU";
    }
    leaf hop-count {
      type uint32;
      description
        "Hopcount";
    }
    leaf reliability {
      type uint8;
      description
        "Reliability";
    }
    leaf load {
      type uint8;
      description
        "Load";
    }
    leaf internal-router-id {
      type inet:ipv4-address;
      description
        "Router ID";
    }
    leaf internal-tag {
      type uint8;
      description
        "Internal Tag";
    }
    leaf extended-communities-present {
      type boolean;
      description
        "Extended communities present";
    }
    leaf extended-communities-length {
      type uint32;
      description
        "Length of extended communities";
    }
    leaf extended-communities {
      type yang:hex-string;
      description
        "Extended communities";
    }
    leaf external-information-present {
      type boolean;
      description
        "External information present";
    }
    leaf external-router-id {
      type uint32;
      description
        "Router ID";
    }
    leaf external-this-system {
      type boolean;
      description
        "Is it this system";
    }
    leaf external-as {
      type uint32;
      description
        "AS Number";
    }
    leaf external-protocol {
      type string;
      description
        "Protocol ID";
    }
    leaf external-metric {
      type uint32;
      description
        "Metric";
    }
    leaf external-tag {
      type uint32;
      description
        "Tag";
    }
    leaf conditional-default-path {
      type boolean;
      description
        "Conditional Default flag";
    }
    leaf rib-state {
      type Eigrp-bd-path-rib-state;
      description
        "State of path in RIB";
    }
  }

  grouping ncs_rpc_notif_EIGRP-PREFIX-BD {
    description
      "EIGRP IP v4/v6 Prefix";
    leaf ipv4-prefix {
      type inet:ipv4-address;
      description
        "IPv4 Prefix";
    }
    leaf ipv6-prefix {
      type inet:ipv6-address;
      description
        "IPv6 Prefix";
    }
    leaf prefix-length {
      type uint32;
      description
        "Prefix length";
    }
  }

  grouping ncs_rpc_notif_EIGRP-SHOW-ROUTE-BD {
    description
      "EIGRP Route";
    container prefix-xr {
      description
        "IP Prefix/length";
      uses ncs_rpc_notif_EIGRP-PREFIX-BD;
    }
    leaf afi {
      type uint32;
      description
        "AFI";
    }
    leaf as-number {
      type uint32;
      description
        "AS Number";
    }
    leaf router-id {
      type inet:ipv4-address;
      description
        "Router ID";
    }
    leaf active {
      type boolean;
      description
        "Active route";
    }
    leaf successors {
      type uint32;
      description
        "Successors";
    }
    leaf successors-present {
      type boolean;
      description
        "Are there successors";
    }
    leaf old-metric {
      type uint32;
      description
        "Deprecated. Please migrate to use OldMetric64.
         The value of this object might wrap since the
         metric value can go up to (2^48 - 1) in 64-bit
         metric mode";
    }
    leaf old-metric64 {
      type uint64;
      description
        "Old metric";
    }
    leaf metric {
      type uint32;
      description
        "Deprecated. Please migrate to use Metric64. The
         value of this object might wrap since the metric
         value can go up to (2^48 - 1) in 64-bit metric
         mode";
    }
    leaf metric64 {
      type uint64;
      description
        "Metric";
    }
    leaf rib-metric {
      type uint32;
      description
        "Metric downloaded to RIB";
    }
    leaf tag {
      type uint32;
      description
        "Tag";
    }
    leaf send-flag {
      type Eigrp-bd-path-send-flag;
      description
        "Send flag";
    }
    leaf transmit-serial-number {
      type uint64;
      description
        "Transmit thread Serial Number";
    }
    leaf transmit-refcount {
      type uint32;
      description
        "Transmit thread refcount";
    }
    leaf transmit-anchored {
      type boolean;
      description
        "Is Transmit thread anchored";
    }
    leaf reply-handles {
      type uint32;
      description
        "Reply handles used";
    }
    leaf active-time-secs {
      type uint32;
      units "second";
      description
        "Active time seconds";
    }
    leaf active-time-nsecs {
      type uint32;
      units "nanosecond";
      description
        "Active time nanoseconds";
    }
    leaf origin {
      type uint32;
      description
        "Origin";
    }
    leaf retry-count {
      type uint32;
      description
        "Retry count";
    }
    leaf active-stats {
      type boolean;
      description
        "Active stats flag";
    }
    leaf min-time {
      type uint32;
      description
        "Active stats min time";
    }
    leaf max-time {
      type uint32;
      description
        "Active stats max time";
    }
    leaf average-time {
      type uint32;
      description
        "Active stats average time";
    }
    leaf ack-count {
      type uint32;
      description
        "Active stats active count";
    }
    leaf replies {
      type uint32;
      description
        "Number of replies outstanding";
    }
    leaf route-in-sia {
      type boolean;
      description
        "Route is SIA";
    }
    leaf sia-reply-handles {
      type uint32;
      description
        "Reply handles used";
    }
    list paths {
      description
        "Paths for this route";
      uses ncs_rpc_notif_EIGRP-SHOW-PATH-BD;
    }
    list active-peer {
      description
        "Peers yet to respond";
      uses ncs_rpc_notif_EIGRP-SHOW-ACT-BD;
    }
    list sia-peer {
      description
        "SIA Peers yet to respond";
      uses ncs_rpc_notif_EIGRP-SHOW-ACT-BD;
    }
  }

  grouping ncs_rpc_notif_EIGRP-ADDR-BD {
    description
      "EIGRP IP v4/v6 Address";
    leaf ipv4-address {
      type inet:ipv4-address;
      description
        "IPv4 Address";
    }
    leaf ipv6-address {
      type inet:ipv6-address;
      description
        "IPv6 Address";
    }
  }

  grouping ncs_rpc_notif_EIGRP-SHOW-STATIC-NEIGHBORS-BD {
    description
      "EIGRP Static neighbor";
    container source {
      description
        "Neighbor address";
      uses ncs_rpc_notif_EIGRP-ADDR-BD;
    }
    leaf afi {
      type uint32;
      description
        "AFI";
    }
    leaf as-number {
      type uint32;
      description
        "AS Number";
    }
    leaf interface-list {
      type string;
      description
        "Interface Name";
    }
  }

  grouping ncs_rpc_notif_EIGRP-SHOW-PROT-INT-BD {
    description
      "EIGRP Protocol Interface information";
    leaf afi {
      type uint32;
      description
        "AFI";
    }
    leaf interface {
      type string;
      description
        "Interface";
    }
    leaf outbound-filter-policy {
      type string;
      description
        "Outbound Filter Policy";
    }
    leaf inbound-filter-policy {
      type string;
      description
        "Inbound Filter Policy";
    }
    leaf inactive {
      type boolean;
      description
        "Interface is DOWN";
    }
    leaf passive-interface {
      type boolean;
      description
        "Interface is passive";
    }
  }

  grouping ncs_rpc_notif_EIGRP-SHOW-REDIST-BD {
    description
      "EIGRP Redist Protocol information";
    leaf afi {
      type uint32;
      description
        "AFI";
    }
    leaf redistributed-protocol {
      type string;
      description
        "Redistributed Protocol";
    }
    leaf redistributed-protocol-tag {
      type string;
      description
        "Redistributed Protocol tag";
    }
    leaf redristribute-policy {
      type string;
      description
        "Redistribute Filter policy";
    }
    leaf redistribute-protocol-id {
      type uint32;
      description
        "Redistributed Protocol ID";
    }
    leaf rib-handle {
      type uint32;
      description
        "Redistributed Protocol handle";
    }
  }

  grouping ncs_rpc_notif_EIGRP-SHOW-PROT-VRF-BD {
    description
      "EIGRP VRF protocol information";
    leaf afi {
      type uint32;
      description
        "AFI";
    }
    leaf as-number {
      type uint32;
      description
        "AS Number";
    }
    leaf router-id {
      type inet:ipv4-address;
      description
        "Router ID";
    }
    leaf auto-summarization {
      type boolean;
      description
        "Auto Summarization";
    }
    leaf log-neighbor-changes {
      type boolean;
      description
        "Neighbor changes logged";
    }
    leaf log-neighbor-warnings {
      type boolean;
      description
        "Neighbor warnings logged";
    }
    leaf rib-table-limit-reached {
      type boolean;
      description
        "RIB Table limit has been reached";
    }
    leaf outbound-filter-policy {
      type string;
      description
        "Outbound Filter Policy";
    }
    leaf inbound-filter-policy {
      type string;
      description
        "Inbound Filter Policy";
    }
    leaf outgoing-candidate-default-flagged {
      type boolean;
      description
        "Default Allowed Out";
    }
    leaf outgoing-candidate-default-policy {
      type string;
      description
        "Default Allowed Out Policy";
    }
    leaf incoming-candidate-default-flagged {
      type boolean;
      description
        "Default Allowed In";
    }
    leaf incoming-candidate-default-policy {
      type string;
      description
        "Default Allowed In Policy";
    }
    leaf internal-distance {
      type uint8;
      description
        "Internal Distance";
    }
    leaf external-distance {
      type uint8;
      description
        "External Distance";
    }
    leaf maximum-paths {
      type uint8;
      description
        "Maximum paths";
    }
    leaf variance {
      type uint8;
      description
        "Variance";
    }
    leaf metric-weight-k1 {
      type uint32;
      description
        "K1 value";
    }
    leaf metric-weight-k2 {
      type uint32;
      description
        "K2 value";
    }
    leaf metric-weight-k3 {
      type uint32;
      description
        "K3 value";
    }
    leaf metric-weight-k4 {
      type uint32;
      description
        "K4 value";
    }
    leaf metric-weight-k5 {
      type uint32;
      description
        "K5 value";
    }
    leaf metric-weight-k6 {
      type uint32;
      description
        "K6 value";
    }
    leaf rib-scale {
      type uint32;
      description
        "RIB Scale";
    }
    leaf metric-version {
      type Eigrp-bd-metric-version;
      description
        "Metric Version";
    }
    leaf metric-maximum-hopcount {
      type uint32;
      description
        "Metric MaxHops configured";
    }
    leaf default-metric-configured {
      type boolean;
      description
        "Default Metric Configured";
    }
    leaf default-bandwidth {
      type uint32;
      description
        "Default Bandwidth";
    }
    leaf default-delay {
      type uint32;
      description
        "Default Delay";
    }
    leaf default-reliability {
      type uint32;
      description
        "Default Reliability";
    }
    leaf default-load {
      type uint32;
      description
        "Default Load";
    }
    leaf default-mtu {
      type uint32;
      description
        "Default MTU";
    }
    leaf stub-configured {
      type boolean;
      description
        "Stub Configured";
    }
    leaf stub-receive-only {
      type boolean;
      description
        "Stub Receive-only configured";
    }
    leaf stub-allow-connected-routes {
      type boolean;
      description
        "ConnectedRoutes allowed";
    }
    leaf stub-allow-static-routes {
      type boolean;
      description
        "Static Routes allowed";
    }
    leaf stub-allow-summary-routes {
      type boolean;
      description
        "Summary Routes allowed";
    }
    leaf stub-allow-redistributed-routes {
      type boolean;
      description
        "Redistributed Routes allowed";
    }
    leaf nsf-enabled {
      type boolean;
      description
        "NSF Enabled";
    }
    leaf nsf-route-hold-time {
      type uint32;
      description
        "NSF Route Hold Time";
    }
    leaf nsf-signal-time {
      type uint32;
      description
        "NSF Signal Time";
    }
    leaf nsf-converge-time {
      type uint32;
      description
        "NSF Converge Time";
    }
    leaf restart-configured {
      type boolean;
      description
        "Is Restart time configured";
    }
    leaf restart-time {
      type uint32;
      units "second";
      description
        "Restart time (seconds)";
    }
    leaf sia-active-time {
      type uint32;
      description
        "SIA Active Time";
    }
    leaf rib-protocol-id {
      type uint32;
      description
        "RIB Protocol ID";
    }
    leaf table-id {
      type uint32;
      description
        "Table ID";
    }
    leaf vrf-id {
      type uint32;
      description
        "VRF ID";
    }
    leaf ital-activation-received {
      type boolean;
      description
        "VRF activated by ITAL";
    }
    leaf vrf-activated {
      type boolean;
      description
        "VRF activated by EIGRP";
    }
    leaf up {
      type boolean;
      description
        "VRF information available";
    }
    leaf rib-initialized {
      type boolean;
      description
        "RIB initialization for VRF";
    }
    leaf rib-converged {
      type boolean;
      description
        "RIB convergence for VRF";
    }
    leaf rib-converged-reload {
      type boolean;
      description
        "Reload following RIB Convergence";
    }
    leaf socket-request {
      type boolean;
      description
        "Requested Socket Option for VRF";
    }
    leaf socket-setup {
      type boolean;
      description
        "Setup socket state for VRF";
    }
    leaf default-vrf {
      type boolean;
      description
        "VRF represents default-context";
    }
    leaf af-enabled {
      type boolean;
      description
        "AF Enabled";
    }
    leaf is-passive-default {
      type boolean;
      description
        "Passive-Interface default configured";
    }
    leaf configured-items {
      type uint32;
      description
        "VRF Configured Items";
    }
    leaf af-configured-items {
      type uint32;
      description
        "AF Configured Items";
    }
    leaf ip-arm-router-id {
      type uint32;
      description
        "IP ARM Router ID";
    }
    leaf first-interface-up-address {
      type uint32;
      description
        "IP Address of first UP interface";
    }
    leaf nsf-in-progress {
      type uint32;
      description
        "DDB NSF in progress indication";
    }
    leaf rib-table-converged {
      type uint32;
      description
        "RIB Table convergence indication";
    }
    list redistributed-protocol {
      description
        "Redistributed Protocols";
      uses ncs_rpc_notif_EIGRP-SHOW-REDIST-BD;
    }
    list interface {
      description
        "Interfaces";
      uses ncs_rpc_notif_EIGRP-SHOW-PROT-INT-BD;
    }
  }

  grouping ncs_rpc_notif_EIGRP-VRFS-BD {
    description
      "EIGRP VRF Name";
    leaf vrf-name-xr {
      type string;
      description
        "VRF Name";
    }
  }

  grouping live_ncs_EIGRP-SHOW-AF-STATS-BD {
    description
      "EIGRP AF statistics";
    leaf afi {
      type uint32;
      description
        "AFI";
    }
    leaf as-number {
      type uint32;
      description
        "AS Number";
    }
    leaf configured-interface-count {
      type uint32;
      description
        "Configured interfaces";
    }
    leaf active-interfaces-count {
      type uint32;
      description
        "Active interfaces";
    }
    leaf activate-count {
      type uint64;
      description
        "Activate address family success count";
    }
    leaf activate-error {
      type uint64;
      description
        "Activate address family failure count";
    }
    leaf activate-last-error {
      type int32;
      description
        "Activate address family last error";
    }
    leaf deactivate-count {
      type uint64;
      description
        "Deactivate address family success count";
    }
    leaf deactivate-error {
      type uint64;
      description
        "Deactivate address family failure count";
    }
    leaf deactivate-last-error {
      type int32;
      description
        "Deactivate address family last error";
    }
    leaf socket-set {
      type uint64;
      description
        "Socket setup success count";
    }
    leaf socket-set-error {
      type uint64;
      description
        "Socket setup failure count";
    }
    leaf sock-set-last-error {
      type int32;
      description
        "Socket setup last error";
    }
    leaf raw-packet-in {
      type uint64;
      description
        "Succeeded RAW packets in";
    }
    leaf raw-packet-in-error {
      type uint64;
      description
        "Failed RAW packets ln";
    }
    leaf raw-packet-in-last-error {
      type int32;
      description
        "RAW packets in last error";
    }
    leaf raw-packet-out {
      type uint64;
      description
        "Succeeded RAW packets out";
    }
    leaf raw-packet-out-error {
      type uint64;
      description
        "Failed RAW packets out";
    }
    leaf raw-packet-out-last-error {
      type int32;
      description
        "RAW Packets out last error";
    }
  }

  grouping live_ncs_EIGRP-SHOW-NBR-Q-BD {
    description
      "EIGRP Neighbor queue";
    leaf operation-code {
      type uint32;
      description
        "Operation Code";
    }
    leaf ack-sequnce-number {
      type uint32;
      description
        "ACK sequence number";
    }
    leaf start-serial-number {
      type uint64;
      description
        "Starting serial number";
    }
    leaf end-serial-number {
      type uint64;
      description
        "Ending serial number";
    }
    leaf pregenerated {
      type boolean;
      description
        "Pregenerated pak";
    }
    leaf packet-length {
      type uint32;
      description
        "pak len";
    }
    leaf time-sent-flag {
      type boolean;
      description
        "Has a pak been sent";
    }
    leaf time-sent {
      type uint32;
      description
        "Time sent";
    }
    leaf init-bit-set {
      type boolean;
      description
        "Is the init bit set";
    }
    leaf sequenced {
      type boolean;
      description
        "Is it sequenced";
    }
  }

  grouping live_ncs_EIGRP-SHOW-NEIGHBORS-BD {
    description
      "EIGRP neighbor";
    container source {
      description
        "Peer address";
      uses live_ncs_EIGRP-ADDR-BD;
    }
    leaf afi {
      type uint32;
      description
        "AFI";
    }
    leaf as-number {
      type uint32;
      description
        "AS Number";
    }
    leaf peer-suspended {
      type boolean;
      description
        "Is it a suspended peer";
    }
    leaf peer-handle {
      type uint32;
      description
        "Peer handle";
    }
    leaf interface-list {
      type string;
      description
        "Interface name";
    }
    leaf holdtime {
      type uint32;
      description
        "Hold time";
    }
    leaf uptime {
      type uint32;
      units "second";
      description
        "UP time (seconds)";
    }
    leaf srtt {
      type uint32;
      description
        "Round trip time";
    }
    leaf rto {
      type uint32;
      description
        "RTO";
    }
    leaf bfd-enabled {
      type boolean;
      description
        "BFD enabled";
    }
    leaf queue-count {
      type uint32;
      description
        "Q counts";
    }
    leaf last-sequence-number {
      type uint32;
      description
        "Last sequence number";
    }
    leaf static-neighbor {
      type boolean;
      description
        "Is it a static neighbor";
    }
    leaf remote-neighbor {
      type boolean;
      description
        "Is it a remote ucast neighbor";
    }
    leaf hop-count {
      type uint8;
      description
        "Hop count of the static peer";
    }
    leaf restart-configured {
      type boolean;
      description
        "Is Restart time configured";
    }
    leaf restart-time {
      type uint32;
      units "second";
      description
        "Restart time (seconds)";
    }
    leaf last-startup-serial-number {
      type uint64;
      description
        "Last startup serial number";
    }
    leaf ios-major-version {
      type uint8;
      description
        "IOS Major version";
    }
    leaf ios-minor-version {
      type uint8;
      description
        "IOS Minor version";
    }
    leaf eigrp-major-version {
      type uint8;
      description
        "EIGRP Major version";
    }
    leaf eigrp-minor-version {
      type uint8;
      description
        "EIGRP Major version";
    }
    leaf retransmission-count {
      type uint32;
      description
        "Retransmission count";
    }
    leaf retry-count {
      type uint32;
      description
        "Retry count";
    }
    leaf need-init {
      type boolean;
      description
        "Need EIGRP Init message";
    }
    leaf need-init-ack {
      type boolean;
      description
        "Need EIGRP InitAck message";
    }
    leaf reinitialization-needed {
      type boolean;
      description
        "Reinitialization needed";
    }
    leaf reinit-start {
      type uint32;
      description
        "Reinit period";
    }
    leaf peer-prefix-count {
      type uint32;
      description
        "Prefix count";
    }
    leaf stubbed {
      type boolean;
      description
        "Is it stubbed";
    }
    leaf allow-connected {
      type boolean;
      description
        "Connected routes accepted";
    }
    leaf allow-static {
      type boolean;
      description
        "Static routes accepted";
    }
    leaf allow-summaries {
      type boolean;
      description
        "Summary routes accepted";
    }
    leaf allow-redistributed {
      type boolean;
      description
        "Redist'ed routes accepted";
    }
    leaf test-handle {
      type boolean;
      description
        "Test handle flag";
    }
    leaf stubbed-interface {
      type boolean;
      description
        "Is it stubbed";
    }
    leaf suspended-reset {
      type boolean;
      description
        "Suspension manually reset";
    }
    leaf suspended-time-left {
      type uint32;
      description
        "Suspended time left";
    }
    list neighbor-queue {
      description
        "Neighbor Queue";
      uses live_ncs_EIGRP-SHOW-NBR-Q-BD;
    }
  }

  grouping live_ncs_EIGRP-SHOW-EVENTS-BD {
    description
      "EIGRP DUAL events";
    leaf afi {
      type uint32;
      description
        "AFI";
    }
    leaf as-number {
      type uint32;
      description
        "AS Number";
    }
    leaf current-event-index {
      type uint32;
      description
        "Current event";
    }
    leaf eigrp-start-absolute-seconds {
      type uint32;
      units "second";
      description
        "Seconds since EIGRP started (absolute)";
    }
    leaf eigrp-start-absolute-nanoseconds {
      type uint32;
      units "second";
      description
        "Seconds since EIGRP started (absolute)";
    }
    leaf eigrp-start-relative-seconds {
      type uint32;
      units "second";
      description
        "Seconds since EIGRP started (relative)";
    }
    leaf eigrp-start-relative-nanoseconds {
      type uint32;
      units "second";
      description
        "Seconds since EIGRP started (relative)";
    }
  }

  grouping live_ncs_EIGRP-SHOW-INTERFACES-BD {
    description
      "An EIGRP interface";
    leaf afi {
      type uint32;
      description
        "AFI";
    }
    leaf as-number {
      type uint32;
      description
        "AS Number";
    }
    leaf peer-count {
      type uint32;
      description
        "Peer Count";
    }
    leaf classic-peer-count {
      type uint32;
      description
        "Classic Peer Count";
    }
    leaf wide-peer-count {
      type uint32;
      description
        "Wide Peer Count";
    }
    leaf unreliable-transmits {
      type uint32;
      description
        "Unreliable transmissions";
    }
    leaf reliable-transmits {
      type uint32;
      description
        "Reliable transmissions";
    }
    leaf total-srtt {
      type uint32;
      description
        "Total SRTT";
    }
    leaf unreliable-send-interval {
      type uint32;
      description
        "Send interval for Unreliable transmissions";
    }
    leaf reliable-send-interval {
      type uint32;
      description
        "Send interval for Reliable transmissions";
    }
    leaf last-mc-flow-delay {
      type uint32;
      description
        "Last multicast flow delay";
    }
    leaf pending-routes {
      type uint32;
      description
        "Number of pending routes";
    }
    leaf hello-interval {
      type uint32;
      description
        "Hello interval";
    }
    leaf holdtime {
      type uint32;
      description
        "Hold time";
    }
    leaf bfd-enabled {
      type boolean;
      description
        "BFD enabled";
    }
    leaf bfd-interval {
      type uint32;
      description
        "BFD interval";
    }
    leaf bfd-multiplier {
      type uint32;
      description
        "BFD multiplier";
    }
    leaf serial-number-present {
      type boolean;
      description
        "Is serno present";
    }
    leaf transmit-serial-number {
      type uint64;
      description
        "Thread serial number";
    }
    leaf packetize-pending {
      type boolean;
      description
        "Packetize Timer pending";
    }
    leaf unreliable-multicast-sent {
      type uint32;
      description
        "Unreliable multicasts sent";
    }
    leaf reliable-multicast-sent {
      type uint32;
      description
        "Reliable multicasts sent";
    }
    leaf unreliable-unicast-sent {
      type uint32;
      description
        "Unreliable unicasts sent";
    }
    leaf reliable-unicast-sent {
      type uint32;
      description
        "Reliable unicasts sent";
    }
    leaf multicast-exceptions-sent {
      type uint32;
      description
        "Multicast Exceptions sent";
    }
    leaf cr-packets-sent {
      type uint32;
      description
        "CR packets sent";
    }
    leaf acks-suppressed {
      type uint32;
      description
        "Suppressed Acks";
    }
    leaf retransmissions-sent {
      type uint32;
      description
        "Retransmissions sent";
    }
    leaf out-of-sequence-received {
      type uint32;
      description
        "Out-of-sequence received";
    }
    leaf stub-interface {
      type boolean;
      description
        "All stub peers";
    }
    leaf next-hop-self-enabled {
      type boolean;
      description
        "Next-hop-self enabled";
    }
    leaf split-horizon-enabled {
      type boolean;
      description
        "SplitHorizon enabled";
    }
    leaf passive-interface {
      type boolean;
      description
        "Interface is passive";
    }
    leaf bandwidth-percent {
      type uint32;
      units "percentage";
      description
        "Bandwidth percent";
    }
    leaf site-of-origin-type {
      type Eigrp-bd-soo;
      description
        "Site of Origin Type";
    }
    leaf site-of-origin {
      type string;
      description
        "Site of Origin";
    }
    leaf auth-mode {
      type uint32;
      description
        "Authentication Mode";
    }
    leaf auth-keychain {
      type string;
      description
        "Authentication Keychain Name";
    }
    leaf auth-key-exists {
      type boolean;
      description
        "Authentication key exists";
    }
    leaf auth-key-md5 {
      type boolean;
      description
        "Authentication key programmed with MD5 algorithm";
    }
    leaf auth-key-id {
      type uint64;
      description
        "Current active Authentication Key Id";
    }
    leaf total-pkt-recvd {
      type uint32;
      description
        "Total packets received";
    }
    leaf pkt-drop-wrong-kc {
      type uint32;
      description
        "Packets dropped due to wrong keychain configured";
    }
    leaf pkt-drop-no-auth {
      type uint32;
      description
        "Packets dropped due to missing authentication
         data";
    }
    leaf pkt-drop-invalid-auth {
      type uint32;
      description
        "Packets dropped due to invalid authentication
         data";
    }
    leaf pkt-accepted-valid-auth {
      type uint32;
      description
        "Packets accepted with valid authentication data";
    }
    leaf bandwidth {
      type uint32;
      description
        "Deprecated. Please migrate to use Bandwidth64.";
    }
    leaf bandwidth64 {
      type uint64;
      description
        "Bandwidth";
    }
    leaf delay {
      type uint32;
      description
        "Deprecated. Please migrate to use Delay64. The
         value of this object might wrap if it is in
         picosecond units";
    }
    leaf delay64 {
      type uint64;
      description
        "Delay";
    }
    leaf delay-unit {
      type Eigrp-bd-delay-unit;
      description
        "Delay unit";
    }
    leaf reliability {
      type uint32;
      description
        "Reliability";
    }
    leaf load {
      type uint32;
      description
        "Load";
    }
    leaf mtu {
      type uint32;
      description
        "MTU";
    }
    leaf configured-bandwidth {
      type uint32;
      description
        "Deprecated. Please migrate to use
         ConfiguredBandwidth64.";
    }
    leaf configured-bandwidth64 {
      type uint64;
      description
        "Configured bandwidth";
    }
    leaf configured-delay {
      type uint32;
      description
        "Deprecated. Please migrate to use
         ConfiguredDelay64. The value of this object
         might wrap if it is in picosecond units";
    }
    leaf configured-delay64 {
      type uint64;
      description
        "Configured delay";
    }
    leaf configured-delay-unit {
      type Eigrp-bd-delay-unit;
      description
        "Configured delay unit";
    }
    leaf configured-reliability {
      type uint32;
      description
        "Configured reliability";
    }
    leaf configured-load {
      type uint32;
      description
        "Configured load";
    }
    leaf configured-bandwidth-flag {
      type boolean;
      description
        "Bandwidth configured";
    }
    leaf configured-delay-flag {
      type boolean;
      description
        "Delay configured";
    }
    leaf configured-reliability-flag {
      type boolean;
      description
        "Reliability configured";
    }
    leaf configured-load-flag {
      type boolean;
      description
        "Load configured";
    }
    leaf up {
      type boolean;
      description
        "Interface is UP";
    }
    leaf type-supported {
      type boolean;
      description
        "Interface type is supported";
    }
    leaf ital-record-found {
      type boolean;
      description
        "ITAL Record valid";
    }
    leaf configured {
      type boolean;
      description
        "Interface config exists";
    }
    leaf multicast-enabled {
      type boolean;
      description
        "Requested socket state";
    }
    leaf socket-setup {
      type boolean;
      description
        "Setup socket state";
    }
    leaf lpts-socket-setup {
      type boolean;
      description
        "Setup LPTS socket state";
    }
    leaf primary-ipv4-address {
      type inet:ipv4-address;
      description
        "Primary IPv4 Address";
    }
    leaf ipv6-link-local-addr {
      type inet:ipv6-address;
      description
        "IPv6 LL Address";
    }
    leaf primary-prefix-length {
      type uint32;
      description
        "Primary prefix length";
    }
    leaf interface-handle {
      type uint32;
      description
        "Interface Handle";
    }
    leaf interface-type {
      type uint32;
      description
        "IM Interface Type";
    }
    leaf configured-items {
      type uint32;
      description
        "Interface Configured Items";
    }
    leaf is-passive-enabled {
      type boolean;
      description
        "Passive-Interface configured";
    }
    leaf is-passive-disabled {
      type boolean;
      description
        "Passive-Interface disabled";
    }
    list static-neighbor {
      description
        "Static Neighbors";
      uses live_ncs_EIGRP-ADDR-BD;
    }
  }

  grouping live_ncs_EIGRP-SHOW-QUIESCENT-IF-BD {
    description
      "EIGRP Quiescent Interface";
    leaf quiescent-interface-list {
      type string;
      description
        "Interface Name";
    }
  }

  grouping live_ncs_EIGRP-SHOW-TOP-SUMMARY-BD {
    description
      "EIGRP Topology summary";
    leaf afi {
      type uint32;
      description
        "AFI";
    }
    leaf as-number {
      type uint32;
      description
        "AS Number";
    }
    leaf router-id {
      type inet:ipv4-address;
      description
        "Router ID";
    }
    leaf thread-present {
      type boolean;
      description
        "Is thread present ?";
    }
    leaf transmit-serial-number {
      type uint64;
      description
        "Thread serial number";
    }
    leaf next-serial-number {
      type uint64;
      description
        "Next serial number";
    }
    leaf route-count {
      type uint32;
      description
        "Number of routes";
    }
    leaf path-count {
      type uint32;
      description
        "Number of paths";
    }
    leaf dummy-count {
      type uint32;
      description
        "Dummy count";
    }
    leaf ddb-name {
      type string;
      description
        "DDB Name";
    }
    leaf interface-count {
      type uint32;
      description
        "Number of interfaces";
    }
    leaf handles-used {
      type uint32;
      description
        "Number of handles used";
    }
    leaf active-interface-count {
      type uint32;
      description
        "Number of active interfaces";
    }
    list quiescent {
      description
        "Quiescent interfaces";
      uses live_ncs_EIGRP-SHOW-QUIESCENT-IF-BD;
    }
  }

  grouping live_ncs_EIGRP-SHOW-TRAFFIC-BD {
    description
      "EIGRP Traffic Statistics";
    leaf afi {
      type uint32;
      description
        "AFI";
    }
    leaf as-number {
      type uint32;
      description
        "AS Number";
    }
    leaf hellos-sent {
      type uint32;
      description
        "Hellos sent";
    }
    leaf hellos-received {
      type uint32;
      description
        "Hellos received";
    }
    leaf updates-sent {
      type uint32;
      description
        "Updates sent";
    }
    leaf updates-received {
      type uint32;
      description
        "Updates received";
    }
    leaf queries-sent {
      type uint32;
      description
        "Queries sent";
    }
    leaf queries-received {
      type uint32;
      description
        "Queries received";
    }
    leaf replies-sent {
      type uint32;
      description
        "Replies sent";
    }
    leaf replies-received {
      type uint32;
      description
        "Replies received";
    }
    leaf acks-sent {
      type uint32;
      description
        "Acks sent";
    }
    leaf acks-received {
      type uint32;
      description
        "Acks received";
    }
    leaf sia-queries-sent {
      type uint32;
      description
        "SIA Queries sent";
    }
    leaf sia-queries-received {
      type uint32;
      description
        "SIA Queries received";
    }
    leaf sia-replies-sent {
      type uint32;
      description
        "SIA Replies sent";
    }
    leaf sia-replies-received {
      type uint32;
      description
        "SIA Replies received";
    }
    leaf max-queue-depth {
      type uint32;
      description
        "Maximum queue depth";
    }
    leaf queue-drops {
      type uint32;
      description
        "Queue drops";
    }
  }

  grouping live_ncs_EIGRP-PEER-STATS-BD {
    description
      "EIGRP peer prefix statistics";
    container source {
      description
        "Source address";
      uses live_ncs_EIGRP-ADDR-BD;
    }
    leaf afi {
      type uint32;
      description
        "AFI";
    }
    leaf state {
      type int8;
      description
        "State";
    }
    leaf interface-list {
      type string;
      description
        "Interface name";
    }
    leaf peer-prefix-count {
      type uint32;
      description
        "Peer prefix count";
    }
    leaf restart-count {
      type uint32;
      description
        "Restart count";
    }
    leaf time-left {
      type uint32;
      description
        "Time left";
    }
  }

  grouping live_ncs_EIGRP-SHOW-ACCOUNTING-BD {
    description
      "EIGRP Accounting";
    leaf afi {
      type uint32;
      description
        "AFI";
    }
    leaf as-number {
      type uint32;
      description
        "AS Number";
    }
    leaf router-id {
      type inet:ipv4-address;
      description
        "Router ID";
    }
    leaf aggregate-count {
      type uint32;
      description
        "Number of aggregates";
    }
    leaf state {
      type int8;
      description
        "Redist state";
    }
    leaf redist-prefix-count {
      type uint32;
      description
        "Redist prefix count";
    }
    leaf restart-count {
      type uint32;
      description
        "Restart count";
    }
    leaf time-left {
      type uint32;
      description
        "Time left";
    }
    leaf redist-prefix-present {
      type boolean;
      description
        "Are there redist'ed prefixes ?";
    }
    list peer-statistics {
      description
        "Peers and their status";
      uses live_ncs_EIGRP-PEER-STATS-BD;
    }
  }

  grouping live_ncs_EIGRP-SHOW-ACT-BD {
    description
      "EIGRP route's active peer information";
    container source {
      description
        "Peer Address";
      uses live_ncs_EIGRP-ADDR-BD;
    }
    leaf peer-available {
      type boolean;
      description
        "Peer available";
    }
    leaf interface-list {
      type string;
      description
        "Interface name";
    }
    leaf handle-number {
      type uint32;
      description
        "Handle number";
    }
  }

  grouping live_ncs_EIGRP-SHOW-PATH-BD {
    description
      "An EIGRP path";
    container next-hop-address {
      description
        "Nexthop address";
      uses live_ncs_EIGRP-ADDR-BD;
    }
    container infosource {
      description
        "Source of route";
      uses live_ncs_EIGRP-ADDR-BD;
    }
    leaf afi {
      type uint32;
      description
        "AFI";
    }
    leaf next-hop-present {
      type boolean;
      description
        "NH flag";
    }
    leaf interface-handle {
      type xr:Interface-name;
      description
        "Interface handle";
    }
    leaf interface-name {
      type string;
      description
        "Interface name";
    }
    leaf origin {
      type Eigrp-bd-path-origin;
      description
        "Origin of route";
    }
    leaf send-flag {
      type Eigrp-bd-path-send-flag;
      description
        "Send flag";
    }
    leaf reply-outstanding {
      type boolean;
      description
        "Outstanding reply";
    }
    leaf metric {
      type uint32;
      description
        "Deprecated. Please migrate to use Metric64. The
         value of this object might wrap since the metric
         value can go up to (2^48 - 1) in 64-bit metric
         mode";
    }
    leaf metric64 {
      type uint64;
      description
        "Metric";
    }
    leaf successor-metric {
      type uint32;
      description
        "Deprecated. Please migrate to use
         SuccessorMetric64. The value of this object
         might wrap since the metric value can go up to
         (2^48 - 1) in 64-bit metric mode";
    }
    leaf successor-metric64 {
      type uint64;
      description
        "Successor metric";
    }
    leaf reply-status {
      type boolean;
      description
        "Reply status";
    }
    leaf sia-status {
      type boolean;
      description
        "SIA status";
    }
    leaf transmit-serial-number {
      type uint64;
      description
        "Transmit thread serial number";
    }
    leaf anchored {
      type boolean;
      description
        "Is Transmit thread anchored";
    }
    leaf external-path {
      type boolean;
      description
        "External";
    }
    leaf bandwidth {
      type uint32;
      description
        "Deprecated. Please migrate to use Bandwidth64.";
    }
    leaf bandwidth64 {
      type uint64;
      description
        "Bandwidth";
    }
    leaf delay {
      type uint32;
      description
        "Deprecated. Please migrate to use Delay64. The
         value of this object might wrap if it is in
         picosecond units ";
    }
    leaf delay64 {
      type uint64;
      description
        "Delay";
    }
    leaf delay-unit {
      type Eigrp-bd-delay-unit;
      description
        "Delay units";
    }
    leaf mtu {
      type uint32;
      description
        "MTU";
    }
    leaf hop-count {
      type uint32;
      description
        "Hopcount";
    }
    leaf reliability {
      type uint8;
      description
        "Reliability";
    }
    leaf load {
      type uint8;
      description
        "Load";
    }
    leaf internal-router-id {
      type inet:ipv4-address;
      description
        "Router ID";
    }
    leaf internal-tag {
      type uint8;
      description
        "Internal Tag";
    }
    leaf extended-communities-present {
      type boolean;
      description
        "Extended communities present";
    }
    leaf extended-communities-length {
      type uint32;
      description
        "Length of extended communities";
    }
    leaf extended-communities {
      type yang:hex-string;
      description
        "Extended communities";
    }
    leaf external-information-present {
      type boolean;
      description
        "External information present";
    }
    leaf external-router-id {
      type uint32;
      description
        "Router ID";
    }
    leaf external-this-system {
      type boolean;
      description
        "Is it this system";
    }
    leaf external-as {
      type uint32;
      description
        "AS Number";
    }
    leaf external-protocol {
      type string;
      description
        "Protocol ID";
    }
    leaf external-metric {
      type uint32;
      description
        "Metric";
    }
    leaf external-tag {
      type uint32;
      description
        "Tag";
    }
    leaf conditional-default-path {
      type boolean;
      description
        "Conditional Default flag";
    }
    leaf rib-state {
      type Eigrp-bd-path-rib-state;
      description
        "State of path in RIB";
    }
  }

  grouping live_ncs_EIGRP-PREFIX-BD {
    description
      "EIGRP IP v4/v6 Prefix";
    leaf ipv4-prefix {
      type inet:ipv4-address;
      description
        "IPv4 Prefix";
    }
    leaf ipv6-prefix {
      type inet:ipv6-address;
      description
        "IPv6 Prefix";
    }
    leaf prefix-length {
      type uint32;
      description
        "Prefix length";
    }
  }

  grouping live_ncs_EIGRP-SHOW-ROUTE-BD {
    description
      "EIGRP Route";
    container prefix-xr {
      description
        "IP Prefix/length";
      uses live_ncs_EIGRP-PREFIX-BD;
    }
    leaf afi {
      type uint32;
      description
        "AFI";
    }
    leaf as-number {
      type uint32;
      description
        "AS Number";
    }
    leaf router-id {
      type inet:ipv4-address;
      description
        "Router ID";
    }
    leaf active {
      type boolean;
      description
        "Active route";
    }
    leaf successors {
      type uint32;
      description
        "Successors";
    }
    leaf successors-present {
      type boolean;
      description
        "Are there successors";
    }
    leaf old-metric {
      type uint32;
      description
        "Deprecated. Please migrate to use OldMetric64.
         The value of this object might wrap since the
         metric value can go up to (2^48 - 1) in 64-bit
         metric mode";
    }
    leaf old-metric64 {
      type uint64;
      description
        "Old metric";
    }
    leaf metric {
      type uint32;
      description
        "Deprecated. Please migrate to use Metric64. The
         value of this object might wrap since the metric
         value can go up to (2^48 - 1) in 64-bit metric
         mode";
    }
    leaf metric64 {
      type uint64;
      description
        "Metric";
    }
    leaf rib-metric {
      type uint32;
      description
        "Metric downloaded to RIB";
    }
    leaf tag {
      type uint32;
      description
        "Tag";
    }
    leaf send-flag {
      type Eigrp-bd-path-send-flag;
      description
        "Send flag";
    }
    leaf transmit-serial-number {
      type uint64;
      description
        "Transmit thread Serial Number";
    }
    leaf transmit-refcount {
      type uint32;
      description
        "Transmit thread refcount";
    }
    leaf transmit-anchored {
      type boolean;
      description
        "Is Transmit thread anchored";
    }
    leaf reply-handles {
      type uint32;
      description
        "Reply handles used";
    }
    leaf active-time-secs {
      type uint32;
      units "second";
      description
        "Active time seconds";
    }
    leaf active-time-nsecs {
      type uint32;
      units "nanosecond";
      description
        "Active time nanoseconds";
    }
    leaf origin {
      type uint32;
      description
        "Origin";
    }
    leaf retry-count {
      type uint32;
      description
        "Retry count";
    }
    leaf active-stats {
      type boolean;
      description
        "Active stats flag";
    }
    leaf min-time {
      type uint32;
      description
        "Active stats min time";
    }
    leaf max-time {
      type uint32;
      description
        "Active stats max time";
    }
    leaf average-time {
      type uint32;
      description
        "Active stats average time";
    }
    leaf ack-count {
      type uint32;
      description
        "Active stats active count";
    }
    leaf replies {
      type uint32;
      description
        "Number of replies outstanding";
    }
    leaf route-in-sia {
      type boolean;
      description
        "Route is SIA";
    }
    leaf sia-reply-handles {
      type uint32;
      description
        "Reply handles used";
    }
    list paths {
      description
        "Paths for this route";
      uses live_ncs_EIGRP-SHOW-PATH-BD;
    }
    list active-peer {
      description
        "Peers yet to respond";
      uses live_ncs_EIGRP-SHOW-ACT-BD;
    }
    list sia-peer {
      description
        "SIA Peers yet to respond";
      uses live_ncs_EIGRP-SHOW-ACT-BD;
    }
  }

  grouping live_ncs_EIGRP-ADDR-BD {
    description
      "EIGRP IP v4/v6 Address";
    leaf ipv4-address {
      type inet:ipv4-address;
      description
        "IPv4 Address";
    }
    leaf ipv6-address {
      type inet:ipv6-address;
      description
        "IPv6 Address";
    }
  }

  grouping live_ncs_EIGRP-SHOW-STATIC-NEIGHBORS-BD {
    description
      "EIGRP Static neighbor";
    container source {
      description
        "Neighbor address";
      uses live_ncs_EIGRP-ADDR-BD;
    }
    leaf afi {
      type uint32;
      description
        "AFI";
    }
    leaf as-number {
      type uint32;
      description
        "AS Number";
    }
    leaf interface-list {
      type string;
      description
        "Interface Name";
    }
  }

  grouping live_ncs_EIGRP-SHOW-PROT-INT-BD {
    description
      "EIGRP Protocol Interface information";
    leaf afi {
      type uint32;
      description
        "AFI";
    }
    leaf interface {
      type string;
      description
        "Interface";
    }
    leaf outbound-filter-policy {
      type string;
      description
        "Outbound Filter Policy";
    }
    leaf inbound-filter-policy {
      type string;
      description
        "Inbound Filter Policy";
    }
    leaf inactive {
      type boolean;
      description
        "Interface is DOWN";
    }
    leaf passive-interface {
      type boolean;
      description
        "Interface is passive";
    }
  }

  grouping live_ncs_EIGRP-SHOW-REDIST-BD {
    description
      "EIGRP Redist Protocol information";
    leaf afi {
      type uint32;
      description
        "AFI";
    }
    leaf redistributed-protocol {
      type string;
      description
        "Redistributed Protocol";
    }
    leaf redistributed-protocol-tag {
      type string;
      description
        "Redistributed Protocol tag";
    }
    leaf redristribute-policy {
      type string;
      description
        "Redistribute Filter policy";
    }
    leaf redistribute-protocol-id {
      type uint32;
      description
        "Redistributed Protocol ID";
    }
    leaf rib-handle {
      type uint32;
      description
        "Redistributed Protocol handle";
    }
  }

  grouping live_ncs_EIGRP-SHOW-PROT-VRF-BD {
    description
      "EIGRP VRF protocol information";
    leaf afi {
      type uint32;
      description
        "AFI";
    }
    leaf as-number {
      type uint32;
      description
        "AS Number";
    }
    leaf router-id {
      type inet:ipv4-address;
      description
        "Router ID";
    }
    leaf auto-summarization {
      type boolean;
      description
        "Auto Summarization";
    }
    leaf log-neighbor-changes {
      type boolean;
      description
        "Neighbor changes logged";
    }
    leaf log-neighbor-warnings {
      type boolean;
      description
        "Neighbor warnings logged";
    }
    leaf rib-table-limit-reached {
      type boolean;
      description
        "RIB Table limit has been reached";
    }
    leaf outbound-filter-policy {
      type string;
      description
        "Outbound Filter Policy";
    }
    leaf inbound-filter-policy {
      type string;
      description
        "Inbound Filter Policy";
    }
    leaf outgoing-candidate-default-flagged {
      type boolean;
      description
        "Default Allowed Out";
    }
    leaf outgoing-candidate-default-policy {
      type string;
      description
        "Default Allowed Out Policy";
    }
    leaf incoming-candidate-default-flagged {
      type boolean;
      description
        "Default Allowed In";
    }
    leaf incoming-candidate-default-policy {
      type string;
      description
        "Default Allowed In Policy";
    }
    leaf internal-distance {
      type uint8;
      description
        "Internal Distance";
    }
    leaf external-distance {
      type uint8;
      description
        "External Distance";
    }
    leaf maximum-paths {
      type uint8;
      description
        "Maximum paths";
    }
    leaf variance {
      type uint8;
      description
        "Variance";
    }
    leaf metric-weight-k1 {
      type uint32;
      description
        "K1 value";
    }
    leaf metric-weight-k2 {
      type uint32;
      description
        "K2 value";
    }
    leaf metric-weight-k3 {
      type uint32;
      description
        "K3 value";
    }
    leaf metric-weight-k4 {
      type uint32;
      description
        "K4 value";
    }
    leaf metric-weight-k5 {
      type uint32;
      description
        "K5 value";
    }
    leaf metric-weight-k6 {
      type uint32;
      description
        "K6 value";
    }
    leaf rib-scale {
      type uint32;
      description
        "RIB Scale";
    }
    leaf metric-version {
      type Eigrp-bd-metric-version;
      description
        "Metric Version";
    }
    leaf metric-maximum-hopcount {
      type uint32;
      description
        "Metric MaxHops configured";
    }
    leaf default-metric-configured {
      type boolean;
      description
        "Default Metric Configured";
    }
    leaf default-bandwidth {
      type uint32;
      description
        "Default Bandwidth";
    }
    leaf default-delay {
      type uint32;
      description
        "Default Delay";
    }
    leaf default-reliability {
      type uint32;
      description
        "Default Reliability";
    }
    leaf default-load {
      type uint32;
      description
        "Default Load";
    }
    leaf default-mtu {
      type uint32;
      description
        "Default MTU";
    }
    leaf stub-configured {
      type boolean;
      description
        "Stub Configured";
    }
    leaf stub-receive-only {
      type boolean;
      description
        "Stub Receive-only configured";
    }
    leaf stub-allow-connected-routes {
      type boolean;
      description
        "ConnectedRoutes allowed";
    }
    leaf stub-allow-static-routes {
      type boolean;
      description
        "Static Routes allowed";
    }
    leaf stub-allow-summary-routes {
      type boolean;
      description
        "Summary Routes allowed";
    }
    leaf stub-allow-redistributed-routes {
      type boolean;
      description
        "Redistributed Routes allowed";
    }
    leaf nsf-enabled {
      type boolean;
      description
        "NSF Enabled";
    }
    leaf nsf-route-hold-time {
      type uint32;
      description
        "NSF Route Hold Time";
    }
    leaf nsf-signal-time {
      type uint32;
      description
        "NSF Signal Time";
    }
    leaf nsf-converge-time {
      type uint32;
      description
        "NSF Converge Time";
    }
    leaf restart-configured {
      type boolean;
      description
        "Is Restart time configured";
    }
    leaf restart-time {
      type uint32;
      units "second";
      description
        "Restart time (seconds)";
    }
    leaf sia-active-time {
      type uint32;
      description
        "SIA Active Time";
    }
    leaf rib-protocol-id {
      type uint32;
      description
        "RIB Protocol ID";
    }
    leaf table-id {
      type uint32;
      description
        "Table ID";
    }
    leaf vrf-id {
      type uint32;
      description
        "VRF ID";
    }
    leaf ital-activation-received {
      type boolean;
      description
        "VRF activated by ITAL";
    }
    leaf vrf-activated {
      type boolean;
      description
        "VRF activated by EIGRP";
    }
    leaf up {
      type boolean;
      description
        "VRF information available";
    }
    leaf rib-initialized {
      type boolean;
      description
        "RIB initialization for VRF";
    }
    leaf rib-converged {
      type boolean;
      description
        "RIB convergence for VRF";
    }
    leaf rib-converged-reload {
      type boolean;
      description
        "Reload following RIB Convergence";
    }
    leaf socket-request {
      type boolean;
      description
        "Requested Socket Option for VRF";
    }
    leaf socket-setup {
      type boolean;
      description
        "Setup socket state for VRF";
    }
    leaf default-vrf {
      type boolean;
      description
        "VRF represents default-context";
    }
    leaf af-enabled {
      type boolean;
      description
        "AF Enabled";
    }
    leaf is-passive-default {
      type boolean;
      description
        "Passive-Interface default configured";
    }
    leaf configured-items {
      type uint32;
      description
        "VRF Configured Items";
    }
    leaf af-configured-items {
      type uint32;
      description
        "AF Configured Items";
    }
    leaf ip-arm-router-id {
      type uint32;
      description
        "IP ARM Router ID";
    }
    leaf first-interface-up-address {
      type uint32;
      description
        "IP Address of first UP interface";
    }
    leaf nsf-in-progress {
      type uint32;
      description
        "DDB NSF in progress indication";
    }
    leaf rib-table-converged {
      type uint32;
      description
        "RIB Table convergence indication";
    }
    list redistributed-protocol {
      description
        "Redistributed Protocols";
      uses live_ncs_EIGRP-SHOW-REDIST-BD;
    }
    list interface {
      description
        "Interfaces";
      uses live_ncs_EIGRP-SHOW-PROT-INT-BD;
    }
  }

  grouping live_ncs_EIGRP-VRFS-BD {
    description
      "EIGRP VRF Name";
    leaf vrf-name-xr {
      type string;
      description
        "VRF Name";
    }
  }

  grouping EIGRP-SHOW-AF-STATS-BD {
    description
      "EIGRP AF statistics";
    leaf afi {
      type uint32;
      description
        "AFI";
    }
    leaf as-number {
      type uint32;
      description
        "AS Number";
    }
    leaf configured-interface-count {
      type uint32;
      description
        "Configured interfaces";
    }
    leaf active-interfaces-count {
      type uint32;
      description
        "Active interfaces";
    }
    leaf activate-count {
      type uint64;
      description
        "Activate address family success count";
    }
    leaf activate-error {
      type uint64;
      description
        "Activate address family failure count";
    }
    leaf activate-last-error {
      type int32;
      description
        "Activate address family last error";
    }
    leaf deactivate-count {
      type uint64;
      description
        "Deactivate address family success count";
    }
    leaf deactivate-error {
      type uint64;
      description
        "Deactivate address family failure count";
    }
    leaf deactivate-last-error {
      type int32;
      description
        "Deactivate address family last error";
    }
    leaf socket-set {
      type uint64;
      description
        "Socket setup success count";
    }
    leaf socket-set-error {
      type uint64;
      description
        "Socket setup failure count";
    }
    leaf sock-set-last-error {
      type int32;
      description
        "Socket setup last error";
    }
    leaf raw-packet-in {
      type uint64;
      description
        "Succeeded RAW packets in";
    }
    leaf raw-packet-in-error {
      type uint64;
      description
        "Failed RAW packets ln";
    }
    leaf raw-packet-in-last-error {
      type int32;
      description
        "RAW packets in last error";
    }
    leaf raw-packet-out {
      type uint64;
      description
        "Succeeded RAW packets out";
    }
    leaf raw-packet-out-error {
      type uint64;
      description
        "Failed RAW packets out";
    }
    leaf raw-packet-out-last-error {
      type int32;
      description
        "RAW Packets out last error";
    }
  }

  grouping EIGRP-SHOW-NBR-Q-BD {
    description
      "EIGRP Neighbor queue";
    leaf operation-code {
      type uint32;
      description
        "Operation Code";
    }
    leaf ack-sequnce-number {
      type uint32;
      description
        "ACK sequence number";
    }
    leaf start-serial-number {
      type uint64;
      description
        "Starting serial number";
    }
    leaf end-serial-number {
      type uint64;
      description
        "Ending serial number";
    }
    leaf pregenerated {
      type boolean;
      description
        "Pregenerated pak";
    }
    leaf packet-length {
      type uint32;
      description
        "pak len";
    }
    leaf time-sent-flag {
      type boolean;
      description
        "Has a pak been sent";
    }
    leaf time-sent {
      type uint32;
      description
        "Time sent";
    }
    leaf init-bit-set {
      type boolean;
      description
        "Is the init bit set";
    }
    leaf sequenced {
      type boolean;
      description
        "Is it sequenced";
    }
  }

  grouping EIGRP-SHOW-NEIGHBORS-BD {
    description
      "EIGRP neighbor";
    container source {
      description
        "Peer address";
      uses EIGRP-ADDR-BD;
    }
    leaf afi {
      type uint32;
      description
        "AFI";
    }
    leaf as-number {
      type uint32;
      description
        "AS Number";
    }
    leaf peer-suspended {
      type boolean;
      description
        "Is it a suspended peer";
    }
    leaf peer-handle {
      type uint32;
      description
        "Peer handle";
    }
    leaf interface-list {
      type string;
      description
        "Interface name";
    }
    leaf holdtime {
      type uint32;
      description
        "Hold time";
    }
    leaf uptime {
      type uint32;
      units "second";
      description
        "UP time (seconds)";
    }
    leaf srtt {
      type uint32;
      description
        "Round trip time";
    }
    leaf rto {
      type uint32;
      description
        "RTO";
    }
    leaf bfd-enabled {
      type boolean;
      description
        "BFD enabled";
    }
    leaf queue-count {
      type uint32;
      description
        "Q counts";
    }
    leaf last-sequence-number {
      type uint32;
      description
        "Last sequence number";
    }
    leaf static-neighbor {
      type boolean;
      description
        "Is it a static neighbor";
    }
    leaf remote-neighbor {
      type boolean;
      description
        "Is it a remote ucast neighbor";
    }
    leaf hop-count {
      type uint8;
      description
        "Hop count of the static peer";
    }
    leaf restart-configured {
      type boolean;
      description
        "Is Restart time configured";
    }
    leaf restart-time {
      type uint32;
      units "second";
      description
        "Restart time (seconds)";
    }
    leaf last-startup-serial-number {
      type uint64;
      description
        "Last startup serial number";
    }
    leaf ios-major-version {
      type uint8;
      description
        "IOS Major version";
    }
    leaf ios-minor-version {
      type uint8;
      description
        "IOS Minor version";
    }
    leaf eigrp-major-version {
      type uint8;
      description
        "EIGRP Major version";
    }
    leaf eigrp-minor-version {
      type uint8;
      description
        "EIGRP Major version";
    }
    leaf retransmission-count {
      type uint32;
      description
        "Retransmission count";
    }
    leaf retry-count {
      type uint32;
      description
        "Retry count";
    }
    leaf need-init {
      type boolean;
      description
        "Need EIGRP Init message";
    }
    leaf need-init-ack {
      type boolean;
      description
        "Need EIGRP InitAck message";
    }
    leaf reinitialization-needed {
      type boolean;
      description
        "Reinitialization needed";
    }
    leaf reinit-start {
      type uint32;
      description
        "Reinit period";
    }
    leaf peer-prefix-count {
      type uint32;
      description
        "Prefix count";
    }
    leaf stubbed {
      type boolean;
      description
        "Is it stubbed";
    }
    leaf allow-connected {
      type boolean;
      description
        "Connected routes accepted";
    }
    leaf allow-static {
      type boolean;
      description
        "Static routes accepted";
    }
    leaf allow-summaries {
      type boolean;
      description
        "Summary routes accepted";
    }
    leaf allow-redistributed {
      type boolean;
      description
        "Redist'ed routes accepted";
    }
    leaf test-handle {
      type boolean;
      description
        "Test handle flag";
    }
    leaf stubbed-interface {
      type boolean;
      description
        "Is it stubbed";
    }
    leaf suspended-reset {
      type boolean;
      description
        "Suspension manually reset";
    }
    leaf suspended-time-left {
      type uint32;
      description
        "Suspended time left";
    }
    list neighbor-queue {
      description
        "Neighbor Queue";
      uses EIGRP-SHOW-NBR-Q-BD;
    }
  }

  grouping EIGRP-SHOW-EVENTS-BD {
    description
      "EIGRP DUAL events";
    leaf afi {
      type uint32;
      description
        "AFI";
    }
    leaf as-number {
      type uint32;
      description
        "AS Number";
    }
    leaf current-event-index {
      type uint32;
      description
        "Current event";
    }
    leaf eigrp-start-absolute-seconds {
      type uint32;
      units "second";
      description
        "Seconds since EIGRP started (absolute)";
    }
    leaf eigrp-start-absolute-nanoseconds {
      type uint32;
      units "second";
      description
        "Seconds since EIGRP started (absolute)";
    }
    leaf eigrp-start-relative-seconds {
      type uint32;
      units "second";
      description
        "Seconds since EIGRP started (relative)";
    }
    leaf eigrp-start-relative-nanoseconds {
      type uint32;
      units "second";
      description
        "Seconds since EIGRP started (relative)";
    }
  }

  grouping EIGRP-SHOW-INTERFACES-BD {
    description
      "An EIGRP interface";
    leaf afi {
      type uint32;
      description
        "AFI";
    }
    leaf as-number {
      type uint32;
      description
        "AS Number";
    }
    leaf peer-count {
      type uint32;
      description
        "Peer Count";
    }
    leaf classic-peer-count {
      type uint32;
      description
        "Classic Peer Count";
    }
    leaf wide-peer-count {
      type uint32;
      description
        "Wide Peer Count";
    }
    leaf unreliable-transmits {
      type uint32;
      description
        "Unreliable transmissions";
    }
    leaf reliable-transmits {
      type uint32;
      description
        "Reliable transmissions";
    }
    leaf total-srtt {
      type uint32;
      description
        "Total SRTT";
    }
    leaf unreliable-send-interval {
      type uint32;
      description
        "Send interval for Unreliable transmissions";
    }
    leaf reliable-send-interval {
      type uint32;
      description
        "Send interval for Reliable transmissions";
    }
    leaf last-mc-flow-delay {
      type uint32;
      description
        "Last multicast flow delay";
    }
    leaf pending-routes {
      type uint32;
      description
        "Number of pending routes";
    }
    leaf hello-interval {
      type uint32;
      description
        "Hello interval";
    }
    leaf holdtime {
      type uint32;
      description
        "Hold time";
    }
    leaf bfd-enabled {
      type boolean;
      description
        "BFD enabled";
    }
    leaf bfd-interval {
      type uint32;
      description
        "BFD interval";
    }
    leaf bfd-multiplier {
      type uint32;
      description
        "BFD multiplier";
    }
    leaf serial-number-present {
      type boolean;
      description
        "Is serno present";
    }
    leaf transmit-serial-number {
      type uint64;
      description
        "Thread serial number";
    }
    leaf packetize-pending {
      type boolean;
      description
        "Packetize Timer pending";
    }
    leaf unreliable-multicast-sent {
      type uint32;
      description
        "Unreliable multicasts sent";
    }
    leaf reliable-multicast-sent {
      type uint32;
      description
        "Reliable multicasts sent";
    }
    leaf unreliable-unicast-sent {
      type uint32;
      description
        "Unreliable unicasts sent";
    }
    leaf reliable-unicast-sent {
      type uint32;
      description
        "Reliable unicasts sent";
    }
    leaf multicast-exceptions-sent {
      type uint32;
      description
        "Multicast Exceptions sent";
    }
    leaf cr-packets-sent {
      type uint32;
      description
        "CR packets sent";
    }
    leaf acks-suppressed {
      type uint32;
      description
        "Suppressed Acks";
    }
    leaf retransmissions-sent {
      type uint32;
      description
        "Retransmissions sent";
    }
    leaf out-of-sequence-received {
      type uint32;
      description
        "Out-of-sequence received";
    }
    leaf stub-interface {
      type boolean;
      description
        "All stub peers";
    }
    leaf next-hop-self-enabled {
      type boolean;
      description
        "Next-hop-self enabled";
    }
    leaf split-horizon-enabled {
      type boolean;
      description
        "SplitHorizon enabled";
    }
    leaf passive-interface {
      type boolean;
      description
        "Interface is passive";
    }
    leaf bandwidth-percent {
      type uint32;
      units "percentage";
      description
        "Bandwidth percent";
    }
    leaf site-of-origin-type {
      type Eigrp-bd-soo;
      description
        "Site of Origin Type";
    }
    leaf site-of-origin {
      type string;
      description
        "Site of Origin";
    }
    leaf auth-mode {
      type uint32;
      description
        "Authentication Mode";
    }
    leaf auth-keychain {
      type string;
      description
        "Authentication Keychain Name";
    }
    leaf auth-key-exists {
      type boolean;
      description
        "Authentication key exists";
    }
    leaf auth-key-md5 {
      type boolean;
      description
        "Authentication key programmed with MD5 algorithm";
    }
    leaf auth-key-id {
      type uint64;
      description
        "Current active Authentication Key Id";
    }
    leaf total-pkt-recvd {
      type uint32;
      description
        "Total packets received";
    }
    leaf pkt-drop-wrong-kc {
      type uint32;
      description
        "Packets dropped due to wrong keychain configured";
    }
    leaf pkt-drop-no-auth {
      type uint32;
      description
        "Packets dropped due to missing authentication
         data";
    }
    leaf pkt-drop-invalid-auth {
      type uint32;
      description
        "Packets dropped due to invalid authentication
         data";
    }
    leaf pkt-accepted-valid-auth {
      type uint32;
      description
        "Packets accepted with valid authentication data";
    }
    leaf bandwidth {
      type uint32;
      description
        "Deprecated. Please migrate to use Bandwidth64.";
    }
    leaf bandwidth64 {
      type uint64;
      description
        "Bandwidth";
    }
    leaf delay {
      type uint32;
      description
        "Deprecated. Please migrate to use Delay64. The
         value of this object might wrap if it is in
         picosecond units";
    }
    leaf delay64 {
      type uint64;
      description
        "Delay";
    }
    leaf delay-unit {
      type Eigrp-bd-delay-unit;
      description
        "Delay unit";
    }
    leaf reliability {
      type uint32;
      description
        "Reliability";
    }
    leaf load {
      type uint32;
      description
        "Load";
    }
    leaf mtu {
      type uint32;
      description
        "MTU";
    }
    leaf configured-bandwidth {
      type uint32;
      description
        "Deprecated. Please migrate to use
         ConfiguredBandwidth64.";
    }
    leaf configured-bandwidth64 {
      type uint64;
      description
        "Configured bandwidth";
    }
    leaf configured-delay {
      type uint32;
      description
        "Deprecated. Please migrate to use
         ConfiguredDelay64. The value of this object
         might wrap if it is in picosecond units";
    }
    leaf configured-delay64 {
      type uint64;
      description
        "Configured delay";
    }
    leaf configured-delay-unit {
      type Eigrp-bd-delay-unit;
      description
        "Configured delay unit";
    }
    leaf configured-reliability {
      type uint32;
      description
        "Configured reliability";
    }
    leaf configured-load {
      type uint32;
      description
        "Configured load";
    }
    leaf configured-bandwidth-flag {
      type boolean;
      description
        "Bandwidth configured";
    }
    leaf configured-delay-flag {
      type boolean;
      description
        "Delay configured";
    }
    leaf configured-reliability-flag {
      type boolean;
      description
        "Reliability configured";
    }
    leaf configured-load-flag {
      type boolean;
      description
        "Load configured";
    }
    leaf up {
      type boolean;
      description
        "Interface is UP";
    }
    leaf type-supported {
      type boolean;
      description
        "Interface type is supported";
    }
    leaf ital-record-found {
      type boolean;
      description
        "ITAL Record valid";
    }
    leaf configured {
      type boolean;
      description
        "Interface config exists";
    }
    leaf multicast-enabled {
      type boolean;
      description
        "Requested socket state";
    }
    leaf socket-setup {
      type boolean;
      description
        "Setup socket state";
    }
    leaf lpts-socket-setup {
      type boolean;
      description
        "Setup LPTS socket state";
    }
    leaf primary-ipv4-address {
      type inet:ipv4-address;
      description
        "Primary IPv4 Address";
    }
    leaf ipv6-link-local-addr {
      type inet:ipv6-address;
      description
        "IPv6 LL Address";
    }
    leaf primary-prefix-length {
      type uint32;
      description
        "Primary prefix length";
    }
    leaf interface-handle {
      type uint32;
      description
        "Interface Handle";
    }
    leaf interface-type {
      type uint32;
      description
        "IM Interface Type";
    }
    leaf configured-items {
      type uint32;
      description
        "Interface Configured Items";
    }
    leaf is-passive-enabled {
      type boolean;
      description
        "Passive-Interface configured";
    }
    leaf is-passive-disabled {
      type boolean;
      description
        "Passive-Interface disabled";
    }
    list static-neighbor {
      description
        "Static Neighbors";
      uses EIGRP-ADDR-BD;
    }
  }

  grouping EIGRP-SHOW-QUIESCENT-IF-BD {
    description
      "EIGRP Quiescent Interface";
    leaf quiescent-interface-list {
      type string;
      description
        "Interface Name";
    }
  }

  grouping EIGRP-SHOW-TOP-SUMMARY-BD {
    description
      "EIGRP Topology summary";
    leaf afi {
      type uint32;
      description
        "AFI";
    }
    leaf as-number {
      type uint32;
      description
        "AS Number";
    }
    leaf router-id {
      type inet:ipv4-address;
      description
        "Router ID";
    }
    leaf thread-present {
      type boolean;
      description
        "Is thread present ?";
    }
    leaf transmit-serial-number {
      type uint64;
      description
        "Thread serial number";
    }
    leaf next-serial-number {
      type uint64;
      description
        "Next serial number";
    }
    leaf route-count {
      type uint32;
      description
        "Number of routes";
    }
    leaf path-count {
      type uint32;
      description
        "Number of paths";
    }
    leaf dummy-count {
      type uint32;
      description
        "Dummy count";
    }
    leaf ddb-name {
      type string;
      description
        "DDB Name";
    }
    leaf interface-count {
      type uint32;
      description
        "Number of interfaces";
    }
    leaf handles-used {
      type uint32;
      description
        "Number of handles used";
    }
    leaf active-interface-count {
      type uint32;
      description
        "Number of active interfaces";
    }
    list quiescent {
      description
        "Quiescent interfaces";
      uses EIGRP-SHOW-QUIESCENT-IF-BD;
    }
  }

  grouping EIGRP-SHOW-TRAFFIC-BD {
    description
      "EIGRP Traffic Statistics";
    leaf afi {
      type uint32;
      description
        "AFI";
    }
    leaf as-number {
      type uint32;
      description
        "AS Number";
    }
    leaf hellos-sent {
      type uint32;
      description
        "Hellos sent";
    }
    leaf hellos-received {
      type uint32;
      description
        "Hellos received";
    }
    leaf updates-sent {
      type uint32;
      description
        "Updates sent";
    }
    leaf updates-received {
      type uint32;
      description
        "Updates received";
    }
    leaf queries-sent {
      type uint32;
      description
        "Queries sent";
    }
    leaf queries-received {
      type uint32;
      description
        "Queries received";
    }
    leaf replies-sent {
      type uint32;
      description
        "Replies sent";
    }
    leaf replies-received {
      type uint32;
      description
        "Replies received";
    }
    leaf acks-sent {
      type uint32;
      description
        "Acks sent";
    }
    leaf acks-received {
      type uint32;
      description
        "Acks received";
    }
    leaf sia-queries-sent {
      type uint32;
      description
        "SIA Queries sent";
    }
    leaf sia-queries-received {
      type uint32;
      description
        "SIA Queries received";
    }
    leaf sia-replies-sent {
      type uint32;
      description
        "SIA Replies sent";
    }
    leaf sia-replies-received {
      type uint32;
      description
        "SIA Replies received";
    }
    leaf max-queue-depth {
      type uint32;
      description
        "Maximum queue depth";
    }
    leaf queue-drops {
      type uint32;
      description
        "Queue drops";
    }
  }

  grouping EIGRP-PEER-STATS-BD {
    description
      "EIGRP peer prefix statistics";
    container source {
      description
        "Source address";
      uses EIGRP-ADDR-BD;
    }
    leaf afi {
      type uint32;
      description
        "AFI";
    }
    leaf state {
      type int8;
      description
        "State";
    }
    leaf interface-list {
      type string;
      description
        "Interface name";
    }
    leaf peer-prefix-count {
      type uint32;
      description
        "Peer prefix count";
    }
    leaf restart-count {
      type uint32;
      description
        "Restart count";
    }
    leaf time-left {
      type uint32;
      description
        "Time left";
    }
  }

  grouping EIGRP-SHOW-ACCOUNTING-BD {
    description
      "EIGRP Accounting";
    leaf afi {
      type uint32;
      description
        "AFI";
    }
    leaf as-number {
      type uint32;
      description
        "AS Number";
    }
    leaf router-id {
      type inet:ipv4-address;
      description
        "Router ID";
    }
    leaf aggregate-count {
      type uint32;
      description
        "Number of aggregates";
    }
    leaf state {
      type int8;
      description
        "Redist state";
    }
    leaf redist-prefix-count {
      type uint32;
      description
        "Redist prefix count";
    }
    leaf restart-count {
      type uint32;
      description
        "Restart count";
    }
    leaf time-left {
      type uint32;
      description
        "Time left";
    }
    leaf redist-prefix-present {
      type boolean;
      description
        "Are there redist'ed prefixes ?";
    }
    list peer-statistics {
      description
        "Peers and their status";
      uses EIGRP-PEER-STATS-BD;
    }
  }

  grouping EIGRP-SHOW-ACT-BD {
    description
      "EIGRP route's active peer information";
    container source {
      description
        "Peer Address";
      uses EIGRP-ADDR-BD;
    }
    leaf peer-available {
      type boolean;
      description
        "Peer available";
    }
    leaf interface-list {
      type string;
      description
        "Interface name";
    }
    leaf handle-number {
      type uint32;
      description
        "Handle number";
    }
  }

  grouping EIGRP-SHOW-PATH-BD {
    description
      "An EIGRP path";
    container next-hop-address {
      description
        "Nexthop address";
      uses EIGRP-ADDR-BD;
    }
    container infosource {
      description
        "Source of route";
      uses EIGRP-ADDR-BD;
    }
    leaf afi {
      type uint32;
      description
        "AFI";
    }
    leaf next-hop-present {
      type boolean;
      description
        "NH flag";
    }
    leaf interface-handle {
      type xr:Interface-name;
      description
        "Interface handle";
    }
    leaf interface-name {
      type string;
      description
        "Interface name";
    }
    leaf origin {
      type Eigrp-bd-path-origin;
      description
        "Origin of route";
    }
    leaf send-flag {
      type Eigrp-bd-path-send-flag;
      description
        "Send flag";
    }
    leaf reply-outstanding {
      type boolean;
      description
        "Outstanding reply";
    }
    leaf metric {
      type uint32;
      description
        "Deprecated. Please migrate to use Metric64. The
         value of this object might wrap since the metric
         value can go up to (2^48 - 1) in 64-bit metric
         mode";
    }
    leaf metric64 {
      type uint64;
      description
        "Metric";
    }
    leaf successor-metric {
      type uint32;
      description
        "Deprecated. Please migrate to use
         SuccessorMetric64. The value of this object
         might wrap since the metric value can go up to
         (2^48 - 1) in 64-bit metric mode";
    }
    leaf successor-metric64 {
      type uint64;
      description
        "Successor metric";
    }
    leaf reply-status {
      type boolean;
      description
        "Reply status";
    }
    leaf sia-status {
      type boolean;
      description
        "SIA status";
    }
    leaf transmit-serial-number {
      type uint64;
      description
        "Transmit thread serial number";
    }
    leaf anchored {
      type boolean;
      description
        "Is Transmit thread anchored";
    }
    leaf external-path {
      type boolean;
      description
        "External";
    }
    leaf bandwidth {
      type uint32;
      description
        "Deprecated. Please migrate to use Bandwidth64.";
    }
    leaf bandwidth64 {
      type uint64;
      description
        "Bandwidth";
    }
    leaf delay {
      type uint32;
      description
        "Deprecated. Please migrate to use Delay64. The
         value of this object might wrap if it is in
         picosecond units ";
    }
    leaf delay64 {
      type uint64;
      description
        "Delay";
    }
    leaf delay-unit {
      type Eigrp-bd-delay-unit;
      description
        "Delay units";
    }
    leaf mtu {
      type uint32;
      description
        "MTU";
    }
    leaf hop-count {
      type uint32;
      description
        "Hopcount";
    }
    leaf reliability {
      type uint8;
      description
        "Reliability";
    }
    leaf load {
      type uint8;
      description
        "Load";
    }
    leaf internal-router-id {
      type inet:ipv4-address;
      description
        "Router ID";
    }
    leaf internal-tag {
      type uint8;
      description
        "Internal Tag";
    }
    leaf extended-communities-present {
      type boolean;
      description
        "Extended communities present";
    }
    leaf extended-communities-length {
      type uint32;
      description
        "Length of extended communities";
    }
    leaf extended-communities {
      type yang:hex-string;
      description
        "Extended communities";
    }
    leaf external-information-present {
      type boolean;
      description
        "External information present";
    }
    leaf external-router-id {
      type uint32;
      description
        "Router ID";
    }
    leaf external-this-system {
      type boolean;
      description
        "Is it this system";
    }
    leaf external-as {
      type uint32;
      description
        "AS Number";
    }
    leaf external-protocol {
      type string;
      description
        "Protocol ID";
    }
    leaf external-metric {
      type uint32;
      description
        "Metric";
    }
    leaf external-tag {
      type uint32;
      description
        "Tag";
    }
    leaf conditional-default-path {
      type boolean;
      description
        "Conditional Default flag";
    }
    leaf rib-state {
      type Eigrp-bd-path-rib-state;
      description
        "State of path in RIB";
    }
  }

  grouping EIGRP-PREFIX-BD {
    description
      "EIGRP IP v4/v6 Prefix";
    leaf ipv4-prefix {
      type inet:ipv4-address;
      description
        "IPv4 Prefix";
    }
    leaf ipv6-prefix {
      type inet:ipv6-address;
      description
        "IPv6 Prefix";
    }
    leaf prefix-length {
      type uint32;
      description
        "Prefix length";
    }
  }

  grouping EIGRP-SHOW-ROUTE-BD {
    description
      "EIGRP Route";
    container prefix-xr {
      description
        "IP Prefix/length";
      uses EIGRP-PREFIX-BD;
    }
    leaf afi {
      type uint32;
      description
        "AFI";
    }
    leaf as-number {
      type uint32;
      description
        "AS Number";
    }
    leaf router-id {
      type inet:ipv4-address;
      description
        "Router ID";
    }
    leaf active {
      type boolean;
      description
        "Active route";
    }
    leaf successors {
      type uint32;
      description
        "Successors";
    }
    leaf successors-present {
      type boolean;
      description
        "Are there successors";
    }
    leaf old-metric {
      type uint32;
      description
        "Deprecated. Please migrate to use OldMetric64.
         The value of this object might wrap since the
         metric value can go up to (2^48 - 1) in 64-bit
         metric mode";
    }
    leaf old-metric64 {
      type uint64;
      description
        "Old metric";
    }
    leaf metric {
      type uint32;
      description
        "Deprecated. Please migrate to use Metric64. The
         value of this object might wrap since the metric
         value can go up to (2^48 - 1) in 64-bit metric
         mode";
    }
    leaf metric64 {
      type uint64;
      description
        "Metric";
    }
    leaf rib-metric {
      type uint32;
      description
        "Metric downloaded to RIB";
    }
    leaf tag {
      type uint32;
      description
        "Tag";
    }
    leaf send-flag {
      type Eigrp-bd-path-send-flag;
      description
        "Send flag";
    }
    leaf transmit-serial-number {
      type uint64;
      description
        "Transmit thread Serial Number";
    }
    leaf transmit-refcount {
      type uint32;
      description
        "Transmit thread refcount";
    }
    leaf transmit-anchored {
      type boolean;
      description
        "Is Transmit thread anchored";
    }
    leaf reply-handles {
      type uint32;
      description
        "Reply handles used";
    }
    leaf active-time-secs {
      type uint32;
      units "second";
      description
        "Active time seconds";
    }
    leaf active-time-nsecs {
      type uint32;
      units "nanosecond";
      description
        "Active time nanoseconds";
    }
    leaf origin {
      type uint32;
      description
        "Origin";
    }
    leaf retry-count {
      type uint32;
      description
        "Retry count";
    }
    leaf active-stats {
      type boolean;
      description
        "Active stats flag";
    }
    leaf min-time {
      type uint32;
      description
        "Active stats min time";
    }
    leaf max-time {
      type uint32;
      description
        "Active stats max time";
    }
    leaf average-time {
      type uint32;
      description
        "Active stats average time";
    }
    leaf ack-count {
      type uint32;
      description
        "Active stats active count";
    }
    leaf replies {
      type uint32;
      description
        "Number of replies outstanding";
    }
    leaf route-in-sia {
      type boolean;
      description
        "Route is SIA";
    }
    leaf sia-reply-handles {
      type uint32;
      description
        "Reply handles used";
    }
    list paths {
      description
        "Paths for this route";
      uses EIGRP-SHOW-PATH-BD;
    }
    list active-peer {
      description
        "Peers yet to respond";
      uses EIGRP-SHOW-ACT-BD;
    }
    list sia-peer {
      description
        "SIA Peers yet to respond";
      uses EIGRP-SHOW-ACT-BD;
    }
  }

  grouping EIGRP-ADDR-BD {
    description
      "EIGRP IP v4/v6 Address";
    leaf ipv4-address {
      type inet:ipv4-address;
      description
        "IPv4 Address";
    }
    leaf ipv6-address {
      type inet:ipv6-address;
      description
        "IPv6 Address";
    }
  }

  grouping EIGRP-SHOW-STATIC-NEIGHBORS-BD {
    description
      "EIGRP Static neighbor";
    container source {
      description
        "Neighbor address";
      uses EIGRP-ADDR-BD;
    }
    leaf afi {
      type uint32;
      description
        "AFI";
    }
    leaf as-number {
      type uint32;
      description
        "AS Number";
    }
    leaf interface-list {
      type string;
      description
        "Interface Name";
    }
  }

  grouping EIGRP-SHOW-PROT-INT-BD {
    description
      "EIGRP Protocol Interface information";
    leaf afi {
      type uint32;
      description
        "AFI";
    }
    leaf interface {
      type string;
      description
        "Interface";
    }
    leaf outbound-filter-policy {
      type string;
      description
        "Outbound Filter Policy";
    }
    leaf inbound-filter-policy {
      type string;
      description
        "Inbound Filter Policy";
    }
    leaf inactive {
      type boolean;
      description
        "Interface is DOWN";
    }
    leaf passive-interface {
      type boolean;
      description
        "Interface is passive";
    }
  }

  grouping EIGRP-SHOW-REDIST-BD {
    description
      "EIGRP Redist Protocol information";
    leaf afi {
      type uint32;
      description
        "AFI";
    }
    leaf redistributed-protocol {
      type string;
      description
        "Redistributed Protocol";
    }
    leaf redistributed-protocol-tag {
      type string;
      description
        "Redistributed Protocol tag";
    }
    leaf redristribute-policy {
      type string;
      description
        "Redistribute Filter policy";
    }
    leaf redistribute-protocol-id {
      type uint32;
      description
        "Redistributed Protocol ID";
    }
    leaf rib-handle {
      type uint32;
      description
        "Redistributed Protocol handle";
    }
  }

  grouping EIGRP-SHOW-PROT-VRF-BD {
    description
      "EIGRP VRF protocol information";
    leaf afi {
      type uint32;
      description
        "AFI";
    }
    leaf as-number {
      type uint32;
      description
        "AS Number";
    }
    leaf router-id {
      type inet:ipv4-address;
      description
        "Router ID";
    }
    leaf auto-summarization {
      type boolean;
      description
        "Auto Summarization";
    }
    leaf log-neighbor-changes {
      type boolean;
      description
        "Neighbor changes logged";
    }
    leaf log-neighbor-warnings {
      type boolean;
      description
        "Neighbor warnings logged";
    }
    leaf rib-table-limit-reached {
      type boolean;
      description
        "RIB Table limit has been reached";
    }
    leaf outbound-filter-policy {
      type string;
      description
        "Outbound Filter Policy";
    }
    leaf inbound-filter-policy {
      type string;
      description
        "Inbound Filter Policy";
    }
    leaf outgoing-candidate-default-flagged {
      type boolean;
      description
        "Default Allowed Out";
    }
    leaf outgoing-candidate-default-policy {
      type string;
      description
        "Default Allowed Out Policy";
    }
    leaf incoming-candidate-default-flagged {
      type boolean;
      description
        "Default Allowed In";
    }
    leaf incoming-candidate-default-policy {
      type string;
      description
        "Default Allowed In Policy";
    }
    leaf internal-distance {
      type uint8;
      description
        "Internal Distance";
    }
    leaf external-distance {
      type uint8;
      description
        "External Distance";
    }
    leaf maximum-paths {
      type uint8;
      description
        "Maximum paths";
    }
    leaf variance {
      type uint8;
      description
        "Variance";
    }
    leaf metric-weight-k1 {
      type uint32;
      description
        "K1 value";
    }
    leaf metric-weight-k2 {
      type uint32;
      description
        "K2 value";
    }
    leaf metric-weight-k3 {
      type uint32;
      description
        "K3 value";
    }
    leaf metric-weight-k4 {
      type uint32;
      description
        "K4 value";
    }
    leaf metric-weight-k5 {
      type uint32;
      description
        "K5 value";
    }
    leaf metric-weight-k6 {
      type uint32;
      description
        "K6 value";
    }
    leaf rib-scale {
      type uint32;
      description
        "RIB Scale";
    }
    leaf metric-version {
      type Eigrp-bd-metric-version;
      description
        "Metric Version";
    }
    leaf metric-maximum-hopcount {
      type uint32;
      description
        "Metric MaxHops configured";
    }
    leaf default-metric-configured {
      type boolean;
      description
        "Default Metric Configured";
    }
    leaf default-bandwidth {
      type uint32;
      description
        "Default Bandwidth";
    }
    leaf default-delay {
      type uint32;
      description
        "Default Delay";
    }
    leaf default-reliability {
      type uint32;
      description
        "Default Reliability";
    }
    leaf default-load {
      type uint32;
      description
        "Default Load";
    }
    leaf default-mtu {
      type uint32;
      description
        "Default MTU";
    }
    leaf stub-configured {
      type boolean;
      description
        "Stub Configured";
    }
    leaf stub-receive-only {
      type boolean;
      description
        "Stub Receive-only configured";
    }
    leaf stub-allow-connected-routes {
      type boolean;
      description
        "ConnectedRoutes allowed";
    }
    leaf stub-allow-static-routes {
      type boolean;
      description
        "Static Routes allowed";
    }
    leaf stub-allow-summary-routes {
      type boolean;
      description
        "Summary Routes allowed";
    }
    leaf stub-allow-redistributed-routes {
      type boolean;
      description
        "Redistributed Routes allowed";
    }
    leaf nsf-enabled {
      type boolean;
      description
        "NSF Enabled";
    }
    leaf nsf-route-hold-time {
      type uint32;
      description
        "NSF Route Hold Time";
    }
    leaf nsf-signal-time {
      type uint32;
      description
        "NSF Signal Time";
    }
    leaf nsf-converge-time {
      type uint32;
      description
        "NSF Converge Time";
    }
    leaf restart-configured {
      type boolean;
      description
        "Is Restart time configured";
    }
    leaf restart-time {
      type uint32;
      units "second";
      description
        "Restart time (seconds)";
    }
    leaf sia-active-time {
      type uint32;
      description
        "SIA Active Time";
    }
    leaf rib-protocol-id {
      type uint32;
      description
        "RIB Protocol ID";
    }
    leaf table-id {
      type uint32;
      description
        "Table ID";
    }
    leaf vrf-id {
      type uint32;
      description
        "VRF ID";
    }
    leaf ital-activation-received {
      type boolean;
      description
        "VRF activated by ITAL";
    }
    leaf vrf-activated {
      type boolean;
      description
        "VRF activated by EIGRP";
    }
    leaf up {
      type boolean;
      description
        "VRF information available";
    }
    leaf rib-initialized {
      type boolean;
      description
        "RIB initialization for VRF";
    }
    leaf rib-converged {
      type boolean;
      description
        "RIB convergence for VRF";
    }
    leaf rib-converged-reload {
      type boolean;
      description
        "Reload following RIB Convergence";
    }
    leaf socket-request {
      type boolean;
      description
        "Requested Socket Option for VRF";
    }
    leaf socket-setup {
      type boolean;
      description
        "Setup socket state for VRF";
    }
    leaf default-vrf {
      type boolean;
      description
        "VRF represents default-context";
    }
    leaf af-enabled {
      type boolean;
      description
        "AF Enabled";
    }
    leaf is-passive-default {
      type boolean;
      description
        "Passive-Interface default configured";
    }
    leaf configured-items {
      type uint32;
      description
        "VRF Configured Items";
    }
    leaf af-configured-items {
      type uint32;
      description
        "AF Configured Items";
    }
    leaf ip-arm-router-id {
      type uint32;
      description
        "IP ARM Router ID";
    }
    leaf first-interface-up-address {
      type uint32;
      description
        "IP Address of first UP interface";
    }
    leaf nsf-in-progress {
      type uint32;
      description
        "DDB NSF in progress indication";
    }
    leaf rib-table-converged {
      type uint32;
      description
        "RIB Table convergence indication";
    }
    list redistributed-protocol {
      description
        "Redistributed Protocols";
      uses EIGRP-SHOW-REDIST-BD;
    }
    list interface {
      description
        "Interfaces";
      uses EIGRP-SHOW-PROT-INT-BD;
    }
  }

  grouping EIGRP-VRFS-BD {
    description
      "EIGRP VRF Name";
    leaf vrf-name-xr {
      type string;
      description
        "VRF Name";
    }
  }
}
