module Cisco-IOS-XR-hwmod-mpa-reload-act {
  // Generated by yanger -t ncs
  tailf:mount-id f5500-nc-1.0:f5500-nc-1.0;
  tailf:ncs-device-type "netconf";

  namespace "http://cisco.com/ns/yang/Cisco-IOS-XR-hwmod-mpa-reload-act";
  prefix Cisco-IOS-XR-hwmod-mpa-reload-act;

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR MPA reload action package configuration.

     Copyright (c) 2016-2017 by Cisco Systems, Inc.
     All rights reserved.";

  revision 2016-06-30 {
    description
      "IOS XR 6.2.1 revision.";
  }

  augment "/ncs:devices/ncs:device/ncs:rpc" {
    container rpc-hw-module-subslot {
      tailf:ncs-device-type "netconf";
      tailf:display-when "not(../../ncs:module) or ../../ncs:module[ncs:name='Cisco-IOS-XR-hwmod-mpa-reload-act']";
      tailf:action hw-module-subslot {
        tailf:actionpoint ncsproxy {
          tailf:internal;
        }
        description
          "Execute subslot h/w module operations";
        input {
          leaf subslot {
            description
              "Fully qualified location specification";
            type string;
          }
          leaf reload {
            description
              "Cycle subslot h/w reset";
            type empty;
          }
        }
      }
    }
  }
  augment "/ncs:devices/ncs:device-group/ncs:ned-id/ncs:rpc" {
    container rpc-hw-module-subslot {
      tailf:ncs-device-type "netconf";
      tailf:display-when "/ncs:devices/ncs:device[ncs:name=current()/../../../ncs:member]/ncs:module[ncs:name='Cisco-IOS-XR-hwmod-mpa-reload-act']";
      tailf:action hw-module-subslot {
        tailf:actionpoint ncsproxy {
          tailf:internal;
        }
        description
          "Execute subslot h/w module operations";
        input {
          leaf subslot {
            description
              "Fully qualified location specification";
            type string;
          }
          leaf reload {
            description
              "Cycle subslot h/w reset";
            type empty;
          }
        }
      }
    }
  }
}
