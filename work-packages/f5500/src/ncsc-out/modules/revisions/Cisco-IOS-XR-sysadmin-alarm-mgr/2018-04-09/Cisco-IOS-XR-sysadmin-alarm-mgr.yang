module Cisco-IOS-XR-sysadmin-alarm-mgr {
  // Generated by yanger -t ncs
  tailf:mount-id f5500-nc-1.0:f5500-nc-1.0;
  tailf:ncs-device-type "netconf";

  namespace "http://www.cisco.com/ns/yang/Cisco-IOS-XR-sysadmin-alarm-mgr";
  prefix Cisco-IOS-XR-sysadmin-alarm-mgr;

  import ietf-yang-types {
    prefix yang;
  }
  import Cisco-IOS-XR-sysadmin-types {
    prefix calvados;
  }
  import Cisco-IOS-XR-sysadmin-show-trace {
    prefix show_trace;
  }
  import "f5500-nc-1.0" {
    prefix "f5500-nc-1.0";
  }
  import tailf-ncs {
    prefix ncs;
  }
  import tailf-common {
    prefix tailf;
  }

  organization
    "Cisco Systems Inc.";
  contact
    "Cisco Systems, Inc.
     Customer Service

     Postal: 170 West Tasman Drive
     San Jose, CA 95134

     Tel: +1 800 553-NETS

     E-mail: cs-yang@cisco.com";
  description
    "This module contains definitions
     for the Calvados model objects.

     This module contains a collection of YANG
     definitions for Cisco IOS-XR SysAdmin configuration.

     Alarm management YANG model

     Copyright(c) 2011-2017 by Cisco Systems, Inc.
     All rights reserved.

     Copyright (c) 2012-2018 by Cisco Systems, Inc.
     All rights reserved.";

  revision 2018-04-09 {
    description
      "Required changes for ConfD 6.4.5";
  }

  typedef timestamp_td {
    type yang:date-and-time;
    description
      "The Alarm timestamp type for all times in alarm";
  }

  typedef agent_type_td {
    type enumeration {
      enum "unknown" {
        value 0;
      }
      enum "producer" {
        value 1;
      }
      enum "consumer" {
        value 2;
      }
      enum "subscriber" {
        value 3;
      }
    }
  }

  typedef agent_state_td {
    type enumeration {
      enum "start" {
        value 0;
      }
      enum "init" {
        value 1;
      }
      enum "connecting" {
        value 2;
      }
      enum "connected" {
        value 3;
      }
      enum "registered" {
        value 4;
      }
      enum "disconnected" {
        value 5;
      }
    }
  }

  typedef group_td {
    type enumeration {
      enum "unknown" {
        value 0;
      }
      enum "environ" {
        value 1;
      }
      enum "ethernet" {
        value 2;
      }
      enum "fabric" {
        value 3;
      }
      enum "power" {
        value 4;
      }
      enum "software" {
        value 5;
      }
      enum "slice" {
        value 7;
      }
      enum "cpu" {
        value 8;
      }
      enum "controller" {
        value 9;
      }
      enum "sonet" {
        value 10;
      }
      enum "otn" {
        value 11;
      }
      enum "sdh_controller" {
        value 12;
      }
      enum "asic" {
        value 13;
      }
      enum "fpd_infra" {
        value 14;
      }
      enum "shelf" {
        value 15;
      }
      enum "mpa" {
        value 16;
      }
      enum "ots" {
        value 17;
      }
      enum "timing" {
        value 18;
      }
      enum "last" {
        value 19;
      }
    }
    description
      "The group enumeration type of an alarm ";
  }

  typedef status_td {
    type enumeration {
      enum "unknown" {
        value 0;
      }
      enum "set" {
        value 1;
      }
      enum "clear" {
        value 2;
      }
      enum "suppress" {
        value 3;
      }
    }
    description
      "The status enumeration type of an alarm ";
  }

  typedef severity_td {
    type enumeration {
      enum "unknown" {
        value 0;
      }
      enum "not_reported" {
        value 1;
      }
      enum "not_alarmed" {
        value 2;
      }
      enum "minor" {
        value 3;
      }
      enum "major" {
        value 4;
      }
      enum "critical" {
        value 5;
      }
    }
    description
      "The severity enumeration type of an alarm ";
  }

  grouping ncs_template_alarmBasicFilters {
    leaf aid {
      type string;
      description
        "The AID for the current alarm";
    }
    leaf tag {
      type string;
      description
        "The Fault Tag for the current alarm";
    }
    leaf module {
      type string;
      description
        "The Module for the current alarm";
    }
    leaf gen_location {
      type string;
      description
        "The location for the current alarm";
    }
    leaf eid {
      type string;
      description
        "The Object Id for the current alarm";
    }
    leaf severity {
      type string;
      description
        "The alarm severity.";
    }
    leaf group {
      type string;
      description
        "The alarm grouping ";
    }
    leaf description {
      type string;
      description
        "Alarm description";
    }
    leaf set_time {
      type string;
      description
        "Alarm set time stamp";
    }
  }

  grouping ncs_template_alarmBasicHistoryFilters {
    leaf clear_time {
      type string;
      description
        "Alarm clear time stamp";
    }
  }

  grouping ncs_template_alarmBasicSuppressedFilters {
    leaf suppressed_time {
      type string;
      description
        "Alarm suppressed time stamp";
    }
  }

  grouping ncs_template_alarmExtFilters {
    leaf state {
      type string;
      description
        "The current state of the bi-state alarm";
    }
    leaf reporting_agent_id {
      type string;
      description
        "The reporting agent id.";
    }
    leaf resynced {
      type string;
      description
        "The condition bit-flags of the alarm";
    }
    leaf detail_desc {
      type string;
      description
        "Alarm detailed description";
    }
  }

  grouping ncs_template_alarmFilters {
    description
      "Alarm attributes that can be used to filter.";
    uses ncs_template_alarmBasicFilters;
    uses ncs_template_alarmExtFilters;
    uses ncs_template_alarmBasicHistoryFilters;
  }

  grouping ncs_template_alarmDetailSuppressedFilters {
    description
      "Suppressed alarm detail attributes that can be used to filter.";
    uses ncs_template_alarmBasicFilters;
    uses ncs_template_alarmExtFilters;
    uses ncs_template_alarmBasicSuppressedFilters;
  }

  grouping ncs_template_alarmBriefFilters {
    description
      "Alarm brief attributes that can be used to filter.";
    uses ncs_template_alarmBasicFilters;
    uses ncs_template_alarmBasicHistoryFilters;
  }

  grouping ncs_template_alarmBriefActiveFilters {
    description
      "Alarm brief attributes that can be used to filter.";
    uses ncs_template_alarmBasicFilters;
  }

  grouping ncs_template_alarmBriefSuppressedFilters {
    description
      "Suppressed alarm brief attributes that can be used to filter.";
    uses ncs_template_alarmBasicFilters;
    uses ncs_template_alarmBasicSuppressedFilters;
  }

  grouping ncs_template_alarmStats {
    description
      "Alarm Statistics.";
    leaf attime {
      type string;
      description
        "Alarms statistics at specified time";
    }
    leaf reported {
      type string;
      description
        "Total alarms reported into this service.";
    }
    leaf dropped {
      type string;
      description
        "Alarms dropped due to some error or other.";
    }
    leaf bi_set {
      type string;
      description
        "Total active alarms current in this service.";
    }
    leaf bi_clear {
      type string;
      description
        "Alarms that are currently in the cleared state.";
    }
    leaf suppressed {
      type string;
      description
        "Alarms that are currently in the suppressed state.";
    }
    leaf drop_inv_aid {
      type string;
      description
        "Alarms dropped due to invalid aid in the alarm report.";
    }
    leaf drop_no_mem {
      type string;
      description
        "Alarms dropped due to low memory condition.";
    }
    leaf drop_db_error {
      type string;
      description
        "Alarms dropped due to database internal error.";
    }
    leaf drop_clear_no_set {
      type string;
      description
        "Alarms dropped due to clear without a set.";
    }
    leaf drop_dup {
      type string;
      description
        "Alarms dropped due to duplicate alarm report.";
    }
    leaf cache_hit {
      type string;
      description
        "Alarms present in the cached for show";
    }
    leaf cache_miss {
      type string;
      description
        "Alarms not present in the cached for show";
    }
  }

  grouping ncs_template_alarmClients {
    description
      "Alarm clients.";
    leaf agent_name {
      type string;
      description
        "Alarms client";
    }
    leaf agent_id {
      type string;
      description
        "Alarms agent id of the client";
    }
    leaf agent_location {
      type string;
      description
        "The location of this client";
    }
    leaf agent_handle {
      type string;
      description
        "The client handle through which interface";
    }
    leaf agent_state {
      type string;
      description
        "The current state of the client";
    }
    leaf agent_type {
      type string;
      description
        "The type of  the client";
    }
    leaf agent_filter_disp {
      type string;
      description
        "The current subscription status of the client";
    }
    leaf agent_subs_id {
      type string;
      description
        "The subscriber id of the client";
    }
    leaf agent_filter_state {
      type string;
      description
        "The filter used for alarm bi-state state";
    }
    leaf agent_filter_severity {
      type string;
      description
        "The filter used for alarm severity";
    }
    leaf agent_filter_group {
      type string;
      description
        "The filter used for alarm group";
    }
    leaf agent_sdr_id {
      type string;
      description
        "agent alarm_sm register with sdr_id in SOMT mode";
    }
    leaf agent_connect_count {
      type string;
      description
        "Number of times the agent connected to the alarm mgr";
    }
    leaf agent_connect_time {
      type string;
      description
        "Agent connect timestamp";
    }
    leaf agent_get_count {
      type string;
      description
        "Number of times the agent queried for alarms";
    }
    leaf agent_subscribe_count {
      type string;
      description
        "Number of times the agent subscribed for alarms";
    }
    leaf agent_report_count {
      type string;
      description
        "Number of times the agent reported alarms";
    }
  }

  grouping ncs_template_scope_brief_shows {
    list active {
      // NCS patched for predictable order
      ordered-by user;
      key "aid eid";
      // NCS drop max-elements statement
      uses ncs_template_alarmBriefActiveFilters;
    }
    list history {
      // NCS patched for predictable order
      ordered-by user;
      key "aid eid";
      // NCS drop max-elements statement
      uses ncs_template_alarmBriefFilters;
    }
    list suppressed {
      // NCS patched for predictable order
      ordered-by user;
      key "aid eid";
      // NCS drop max-elements statement
      uses ncs_template_alarmBriefSuppressedFilters;
    }
  }

  grouping ncs_template_scope_detail_shows {
    list active {
      // NCS patched for predictable order
      ordered-by user;
      key "aid eid";
      // NCS drop max-elements statement
      uses ncs_template_alarmFilters;
    }
    list history {
      // NCS patched for predictable order
      ordered-by user;
      key "aid eid";
      // NCS drop max-elements statement
      uses ncs_template_alarmFilters;
    }
    list stats {
      // NCS patched for predictable order
      ordered-by user;
      key "attime";
      // NCS drop max-elements statement
      uses ncs_template_alarmStats;
    }
    list clients {
      // NCS patched for predictable order
      ordered-by user;
      key "agent_handle";
      // NCS drop max-elements statement
      uses ncs_template_alarmClients;
    }
    list suppressed {
      // NCS patched for predictable order
      ordered-by user;
      key "aid eid";
      // NCS drop max-elements statement
      uses ncs_template_alarmDetailSuppressedFilters;
    }
  }

  grouping ncs_rpc_notif_alarmBasicFilters {
    leaf aid {
      type string;
      description
        "The AID for the current alarm";
    }
    leaf tag {
      type string;
      description
        "The Fault Tag for the current alarm";
    }
    leaf module {
      type string;
      description
        "The Module for the current alarm";
    }
    leaf gen_location {
      type string;
      description
        "The location for the current alarm";
    }
    leaf eid {
      type string;
      description
        "The Object Id for the current alarm";
    }
    leaf severity {
      type severity_td;
      description
        "The alarm severity.";
    }
    leaf group {
      type group_td;
      description
        "The alarm grouping ";
    }
    leaf description {
      type string;
      description
        "Alarm description";
    }
    leaf set_time {
      type string;
      description
        "Alarm set time stamp";
    }
  }

  grouping ncs_rpc_notif_alarmBasicHistoryFilters {
    leaf clear_time {
      type string;
      description
        "Alarm clear time stamp";
    }
  }

  grouping ncs_rpc_notif_alarmBasicSuppressedFilters {
    leaf suppressed_time {
      type string;
      description
        "Alarm suppressed time stamp";
    }
  }

  grouping ncs_rpc_notif_alarmExtFilters {
    leaf state {
      type status_td;
      description
        "The current state of the bi-state alarm";
    }
    leaf reporting_agent_id {
      type uint32;
      description
        "The reporting agent id.";
    }
    leaf resynced {
      type uint32;
      description
        "The condition bit-flags of the alarm";
    }
    leaf detail_desc {
      type string;
      description
        "Alarm detailed description";
    }
  }

  grouping ncs_rpc_notif_alarmFilters {
    description
      "Alarm attributes that can be used to filter.";
    uses ncs_rpc_notif_alarmBasicFilters;
    uses ncs_rpc_notif_alarmExtFilters;
    uses ncs_rpc_notif_alarmBasicHistoryFilters;
  }

  grouping ncs_rpc_notif_alarmDetailSuppressedFilters {
    description
      "Suppressed alarm detail attributes that can be used to filter.";
    uses ncs_rpc_notif_alarmBasicFilters;
    uses ncs_rpc_notif_alarmExtFilters;
    uses ncs_rpc_notif_alarmBasicSuppressedFilters;
  }

  grouping ncs_rpc_notif_alarmBriefFilters {
    description
      "Alarm brief attributes that can be used to filter.";
    uses ncs_rpc_notif_alarmBasicFilters;
    uses ncs_rpc_notif_alarmBasicHistoryFilters;
  }

  grouping ncs_rpc_notif_alarmBriefActiveFilters {
    description
      "Alarm brief attributes that can be used to filter.";
    uses ncs_rpc_notif_alarmBasicFilters;
  }

  grouping ncs_rpc_notif_alarmBriefSuppressedFilters {
    description
      "Suppressed alarm brief attributes that can be used to filter.";
    uses ncs_rpc_notif_alarmBasicFilters;
    uses ncs_rpc_notif_alarmBasicSuppressedFilters;
  }

  grouping ncs_rpc_notif_alarmStats {
    description
      "Alarm Statistics.";
    leaf attime {
      type string;
      description
        "Alarms statistics at specified time";
    }
    leaf reported {
      type uint64;
      description
        "Total alarms reported into this service.";
    }
    leaf dropped {
      type uint64;
      description
        "Alarms dropped due to some error or other.";
    }
    leaf bi_set {
      type uint64;
      description
        "Total active alarms current in this service.";
    }
    leaf bi_clear {
      type uint64;
      description
        "Alarms that are currently in the cleared state.";
    }
    leaf suppressed {
      type uint64;
      description
        "Alarms that are currently in the suppressed state.";
    }
    leaf drop_inv_aid {
      type uint64;
      description
        "Alarms dropped due to invalid aid in the alarm report.";
    }
    leaf drop_no_mem {
      type uint64;
      description
        "Alarms dropped due to low memory condition.";
    }
    leaf drop_db_error {
      type uint64;
      description
        "Alarms dropped due to database internal error.";
    }
    leaf drop_clear_no_set {
      type uint64;
      description
        "Alarms dropped due to clear without a set.";
    }
    leaf drop_dup {
      type uint64;
      description
        "Alarms dropped due to duplicate alarm report.";
    }
    leaf cache_hit {
      type uint64;
      description
        "Alarms present in the cached for show";
    }
    leaf cache_miss {
      type uint64;
      description
        "Alarms not present in the cached for show";
    }
  }

  grouping ncs_rpc_notif_alarmClients {
    description
      "Alarm clients.";
    leaf agent_name {
      type string;
      description
        "Alarms client";
    }
    leaf agent_id {
      type uint32;
      description
        "Alarms agent id of the client";
    }
    leaf agent_location {
      type string;
      description
        "The location of this client";
    }
    leaf agent_handle {
      type string;
      description
        "The client handle through which interface";
    }
    leaf agent_state {
      type agent_state_td;
      description
        "The current state of the client";
    }
    leaf agent_type {
      type agent_type_td;
      description
        "The type of  the client";
    }
    leaf agent_filter_disp {
      type boolean;
      description
        "The current subscription status of the client";
    }
    leaf agent_subs_id {
      type uint32;
      description
        "The subscriber id of the client";
    }
    leaf agent_filter_state {
      type status_td;
      description
        "The filter used for alarm bi-state state";
    }
    leaf agent_filter_severity {
      type severity_td;
      description
        "The filter used for alarm severity";
    }
    leaf agent_filter_group {
      type group_td;
      description
        "The filter used for alarm group";
    }
    leaf agent_sdr_id {
      type uint32;
      description
        "agent alarm_sm register with sdr_id in SOMT mode";
    }
    leaf agent_connect_count {
      type uint64;
      description
        "Number of times the agent connected to the alarm mgr";
    }
    leaf agent_connect_time {
      type string;
      description
        "Agent connect timestamp";
    }
    leaf agent_get_count {
      type uint64;
      description
        "Number of times the agent queried for alarms";
    }
    leaf agent_subscribe_count {
      type uint64;
      description
        "Number of times the agent subscribed for alarms";
    }
    leaf agent_report_count {
      type uint64;
      description
        "Number of times the agent reported alarms";
    }
  }

  grouping ncs_rpc_notif_scope_brief_shows {
    list active {
      key "aid eid";
      max-elements 1024;
      uses ncs_rpc_notif_alarmBriefActiveFilters;
    }
    list history {
      key "aid eid";
      max-elements 1024;
      uses ncs_rpc_notif_alarmBriefFilters;
    }
    list suppressed {
      key "aid eid";
      max-elements 1024;
      uses ncs_rpc_notif_alarmBriefSuppressedFilters;
    }
  }

  grouping ncs_rpc_notif_scope_detail_shows {
    list active {
      key "aid eid";
      max-elements 1024;
      uses ncs_rpc_notif_alarmFilters;
    }
    list history {
      key "aid eid";
      max-elements 1024;
      uses ncs_rpc_notif_alarmFilters;
    }
    list stats {
      key "attime";
      max-elements 1024;
      uses ncs_rpc_notif_alarmStats;
    }
    list clients {
      key "agent_handle";
      max-elements 1024;
      uses ncs_rpc_notif_alarmClients;
    }
    list suppressed {
      key "aid eid";
      max-elements 1024;
      uses ncs_rpc_notif_alarmDetailSuppressedFilters;
    }
  }

  grouping live_ncs_alarmBasicFilters {
    leaf aid {
      type string;
      description
        "The AID for the current alarm";
    }
    leaf tag {
      type string;
      description
        "The Fault Tag for the current alarm";
    }
    leaf module {
      type string;
      description
        "The Module for the current alarm";
    }
    leaf gen_location {
      type string;
      description
        "The location for the current alarm";
    }
    leaf eid {
      type string;
      description
        "The Object Id for the current alarm";
    }
    leaf severity {
      type severity_td;
      description
        "The alarm severity.";
    }
    leaf group {
      type group_td;
      description
        "The alarm grouping ";
    }
    leaf description {
      type string;
      description
        "Alarm description";
    }
    leaf set_time {
      type string;
      description
        "Alarm set time stamp";
    }
  }

  grouping live_ncs_alarmBasicHistoryFilters {
    leaf clear_time {
      type string;
      description
        "Alarm clear time stamp";
    }
  }

  grouping live_ncs_alarmBasicSuppressedFilters {
    leaf suppressed_time {
      type string;
      description
        "Alarm suppressed time stamp";
    }
  }

  grouping live_ncs_alarmExtFilters {
    leaf state {
      type status_td;
      description
        "The current state of the bi-state alarm";
    }
    leaf reporting_agent_id {
      type uint32;
      description
        "The reporting agent id.";
    }
    leaf resynced {
      type uint32;
      description
        "The condition bit-flags of the alarm";
    }
    leaf detail_desc {
      type string;
      description
        "Alarm detailed description";
    }
  }

  grouping live_ncs_alarmFilters {
    description
      "Alarm attributes that can be used to filter.";
    uses live_ncs_alarmBasicFilters;
    uses live_ncs_alarmExtFilters;
    uses live_ncs_alarmBasicHistoryFilters;
  }

  grouping live_ncs_alarmDetailSuppressedFilters {
    description
      "Suppressed alarm detail attributes that can be used to filter.";
    uses live_ncs_alarmBasicFilters;
    uses live_ncs_alarmExtFilters;
    uses live_ncs_alarmBasicSuppressedFilters;
  }

  grouping live_ncs_alarmBriefFilters {
    description
      "Alarm brief attributes that can be used to filter.";
    uses live_ncs_alarmBasicFilters;
    uses live_ncs_alarmBasicHistoryFilters;
  }

  grouping live_ncs_alarmBriefActiveFilters {
    description
      "Alarm brief attributes that can be used to filter.";
    uses live_ncs_alarmBasicFilters;
  }

  grouping live_ncs_alarmBriefSuppressedFilters {
    description
      "Suppressed alarm brief attributes that can be used to filter.";
    uses live_ncs_alarmBasicFilters;
    uses live_ncs_alarmBasicSuppressedFilters;
  }

  grouping live_ncs_alarmStats {
    description
      "Alarm Statistics.";
    leaf attime {
      type string;
      description
        "Alarms statistics at specified time";
    }
    leaf reported {
      type uint64;
      description
        "Total alarms reported into this service.";
    }
    leaf dropped {
      type uint64;
      description
        "Alarms dropped due to some error or other.";
    }
    leaf bi_set {
      type uint64;
      description
        "Total active alarms current in this service.";
    }
    leaf bi_clear {
      type uint64;
      description
        "Alarms that are currently in the cleared state.";
    }
    leaf suppressed {
      type uint64;
      description
        "Alarms that are currently in the suppressed state.";
    }
    leaf drop_inv_aid {
      type uint64;
      description
        "Alarms dropped due to invalid aid in the alarm report.";
    }
    leaf drop_no_mem {
      type uint64;
      description
        "Alarms dropped due to low memory condition.";
    }
    leaf drop_db_error {
      type uint64;
      description
        "Alarms dropped due to database internal error.";
    }
    leaf drop_clear_no_set {
      type uint64;
      description
        "Alarms dropped due to clear without a set.";
    }
    leaf drop_dup {
      type uint64;
      description
        "Alarms dropped due to duplicate alarm report.";
    }
    leaf cache_hit {
      type uint64;
      description
        "Alarms present in the cached for show";
    }
    leaf cache_miss {
      type uint64;
      description
        "Alarms not present in the cached for show";
    }
  }

  grouping live_ncs_alarmClients {
    description
      "Alarm clients.";
    leaf agent_name {
      type string;
      description
        "Alarms client";
    }
    leaf agent_id {
      type uint32;
      description
        "Alarms agent id of the client";
    }
    leaf agent_location {
      type string;
      description
        "The location of this client";
    }
    leaf agent_handle {
      type string;
      description
        "The client handle through which interface";
    }
    leaf agent_state {
      type agent_state_td;
      description
        "The current state of the client";
    }
    leaf agent_type {
      type agent_type_td;
      description
        "The type of  the client";
    }
    leaf agent_filter_disp {
      type boolean;
      description
        "The current subscription status of the client";
    }
    leaf agent_subs_id {
      type uint32;
      description
        "The subscriber id of the client";
    }
    leaf agent_filter_state {
      type status_td;
      description
        "The filter used for alarm bi-state state";
    }
    leaf agent_filter_severity {
      type severity_td;
      description
        "The filter used for alarm severity";
    }
    leaf agent_filter_group {
      type group_td;
      description
        "The filter used for alarm group";
    }
    leaf agent_sdr_id {
      type uint32;
      description
        "agent alarm_sm register with sdr_id in SOMT mode";
    }
    leaf agent_connect_count {
      type uint64;
      description
        "Number of times the agent connected to the alarm mgr";
    }
    leaf agent_connect_time {
      type string;
      description
        "Agent connect timestamp";
    }
    leaf agent_get_count {
      type uint64;
      description
        "Number of times the agent queried for alarms";
    }
    leaf agent_subscribe_count {
      type uint64;
      description
        "Number of times the agent subscribed for alarms";
    }
    leaf agent_report_count {
      type uint64;
      description
        "Number of times the agent reported alarms";
    }
  }

  grouping live_ncs_scope_brief_shows {
    list active {
      key "aid eid";
      // NCS drop max-elements statement
      uses live_ncs_alarmBriefActiveFilters;
    }
    list history {
      key "aid eid";
      // NCS drop max-elements statement
      uses live_ncs_alarmBriefFilters;
    }
    list suppressed {
      key "aid eid";
      // NCS drop max-elements statement
      uses live_ncs_alarmBriefSuppressedFilters;
    }
  }

  grouping live_ncs_scope_detail_shows {
    list active {
      key "aid eid";
      // NCS drop max-elements statement
      uses live_ncs_alarmFilters;
    }
    list history {
      key "aid eid";
      // NCS drop max-elements statement
      uses live_ncs_alarmFilters;
    }
    list stats {
      key "attime";
      // NCS drop max-elements statement
      uses live_ncs_alarmStats;
    }
    list clients {
      key "agent_handle";
      // NCS drop max-elements statement
      uses live_ncs_alarmClients;
    }
    list suppressed {
      key "aid eid";
      // NCS drop max-elements statement
      uses live_ncs_alarmDetailSuppressedFilters;
    }
  }

  grouping alarmBasicFilters {
    leaf aid {
      type string;
      description
        "The AID for the current alarm";
    }
    leaf tag {
      type string;
      description
        "The Fault Tag for the current alarm";
    }
    leaf module {
      type string;
      description
        "The Module for the current alarm";
    }
    leaf gen_location {
      type string;
      description
        "The location for the current alarm";
    }
    leaf eid {
      type string;
      description
        "The Object Id for the current alarm";
    }
    leaf severity {
      type severity_td;
      description
        "The alarm severity.";
    }
    leaf group {
      type group_td;
      description
        "The alarm grouping ";
    }
    leaf description {
      type string;
      description
        "Alarm description";
    }
    leaf set_time {
      type string;
      description
        "Alarm set time stamp";
    }
  }

  grouping alarmBasicHistoryFilters {
    leaf clear_time {
      type string;
      description
        "Alarm clear time stamp";
    }
  }

  grouping alarmBasicSuppressedFilters {
    leaf suppressed_time {
      type string;
      description
        "Alarm suppressed time stamp";
    }
  }

  grouping alarmExtFilters {
    leaf state {
      type status_td;
      description
        "The current state of the bi-state alarm";
    }
    leaf reporting_agent_id {
      type uint32;
      description
        "The reporting agent id.";
    }
    leaf resynced {
      type uint32;
      description
        "The condition bit-flags of the alarm";
    }
    leaf detail_desc {
      type string;
      description
        "Alarm detailed description";
    }
  }

  grouping alarmFilters {
    description
      "Alarm attributes that can be used to filter.";
    uses alarmBasicFilters;
    uses alarmExtFilters;
    uses alarmBasicHistoryFilters;
  }

  grouping alarmDetailSuppressedFilters {
    description
      "Suppressed alarm detail attributes that can be used to filter.";
    uses alarmBasicFilters;
    uses alarmExtFilters;
    uses alarmBasicSuppressedFilters;
  }

  grouping alarmBriefFilters {
    description
      "Alarm brief attributes that can be used to filter.";
    uses alarmBasicFilters;
    uses alarmBasicHistoryFilters;
  }

  grouping alarmBriefActiveFilters {
    description
      "Alarm brief attributes that can be used to filter.";
    uses alarmBasicFilters;
  }

  grouping alarmBriefSuppressedFilters {
    description
      "Suppressed alarm brief attributes that can be used to filter.";
    uses alarmBasicFilters;
    uses alarmBasicSuppressedFilters;
  }

  grouping alarmStats {
    description
      "Alarm Statistics.";
    leaf attime {
      type string;
      description
        "Alarms statistics at specified time";
    }
    leaf reported {
      type uint64;
      description
        "Total alarms reported into this service.";
    }
    leaf dropped {
      type uint64;
      description
        "Alarms dropped due to some error or other.";
    }
    leaf bi_set {
      type uint64;
      description
        "Total active alarms current in this service.";
    }
    leaf bi_clear {
      type uint64;
      description
        "Alarms that are currently in the cleared state.";
    }
    leaf suppressed {
      type uint64;
      description
        "Alarms that are currently in the suppressed state.";
    }
    leaf drop_inv_aid {
      type uint64;
      description
        "Alarms dropped due to invalid aid in the alarm report.";
    }
    leaf drop_no_mem {
      type uint64;
      description
        "Alarms dropped due to low memory condition.";
    }
    leaf drop_db_error {
      type uint64;
      description
        "Alarms dropped due to database internal error.";
    }
    leaf drop_clear_no_set {
      type uint64;
      description
        "Alarms dropped due to clear without a set.";
    }
    leaf drop_dup {
      type uint64;
      description
        "Alarms dropped due to duplicate alarm report.";
    }
    leaf cache_hit {
      type uint64;
      description
        "Alarms present in the cached for show";
    }
    leaf cache_miss {
      type uint64;
      description
        "Alarms not present in the cached for show";
    }
  }

  grouping alarmClients {
    description
      "Alarm clients.";
    leaf agent_name {
      type string;
      description
        "Alarms client";
    }
    leaf agent_id {
      type uint32;
      description
        "Alarms agent id of the client";
    }
    leaf agent_location {
      type string;
      description
        "The location of this client";
    }
    leaf agent_handle {
      type string;
      description
        "The client handle through which interface";
    }
    leaf agent_state {
      type agent_state_td;
      description
        "The current state of the client";
    }
    leaf agent_type {
      type agent_type_td;
      description
        "The type of  the client";
    }
    leaf agent_filter_disp {
      type boolean;
      description
        "The current subscription status of the client";
    }
    leaf agent_subs_id {
      type uint32;
      description
        "The subscriber id of the client";
    }
    leaf agent_filter_state {
      type status_td;
      description
        "The filter used for alarm bi-state state";
    }
    leaf agent_filter_severity {
      type severity_td;
      description
        "The filter used for alarm severity";
    }
    leaf agent_filter_group {
      type group_td;
      description
        "The filter used for alarm group";
    }
    leaf agent_sdr_id {
      type uint32;
      description
        "agent alarm_sm register with sdr_id in SOMT mode";
    }
    leaf agent_connect_count {
      type uint64;
      description
        "Number of times the agent connected to the alarm mgr";
    }
    leaf agent_connect_time {
      type string;
      description
        "Agent connect timestamp";
    }
    leaf agent_get_count {
      type uint64;
      description
        "Number of times the agent queried for alarms";
    }
    leaf agent_subscribe_count {
      type uint64;
      description
        "Number of times the agent subscribed for alarms";
    }
    leaf agent_report_count {
      type uint64;
      description
        "Number of times the agent reported alarms";
    }
  }

  grouping scope_brief_shows {
    list active {
      key "aid eid";
      max-elements 1024;
      uses alarmBriefActiveFilters;
    }
    list history {
      key "aid eid";
      max-elements 1024;
      uses alarmBriefFilters;
    }
    list suppressed {
      key "aid eid";
      max-elements 1024;
      uses alarmBriefSuppressedFilters;
    }
  }

  grouping scope_detail_shows {
    list active {
      key "aid eid";
      max-elements 1024;
      uses alarmFilters;
    }
    list history {
      key "aid eid";
      max-elements 1024;
      uses alarmFilters;
    }
    list stats {
      key "attime";
      max-elements 1024;
      uses alarmStats;
    }
    list clients {
      key "agent_handle";
      max-elements 1024;
      uses alarmClients;
    }
    list suppressed {
      key "aid eid";
      max-elements 1024;
      uses alarmDetailSuppressedFilters;
    }
  }

  augment "/ncs:devices/ncs:device/ncs:config" {
    // NCS drop config false container alarm_mgr
  }
  augment "/ncs:devices/ncs:device/ncs:live-status" {
    container alarm_mgr {
      tailf:ncs-device-type "netconf";
      tailf:display-when "not(../../ncs:module) or ../../ncs:module[ncs:name='Cisco-IOS-XR-sysadmin-alarm-mgr'] or (../../ncs:live-status-protocol[not(ncs:capability)]) or (../../ncs:live-status-protocol/ncs:capability/ncs:module[.='Cisco-IOS-XR-sysadmin-alarm-mgr'])";
      description
        "Calvados alarms operational data model";
      uses show_trace:live_ncs_traceable;
      container brief {
        description
          "A set of brief alarm commands";
        container card {
          description
            "Alarms reported at the local card as
             specified by the location parameter";
          list location {
            key "locations";
            leaf locations {
              type calvados:location-id;
            }
            uses live_ncs_scope_brief_shows;
          }
        }
        container rack {
          description
            "Alarms reported at the rack scope
             specified by the rack-id";
          list rack_locations {
            key "rackid";
            leaf rackid {
              type uint32;
            }
            uses live_ncs_scope_brief_shows;
          }
        }
        container system {
          description
            "Alarms reported at the system scope";
          uses live_ncs_scope_brief_shows;
        }
      }
      container detail {
        description
          "A set of detail alarm commands";
        container card {
          description
            "Alarms reported at the local card as
             specified by the location parameter";
          list location {
            key "locations";
            leaf locations {
              type calvados:location-id;
            }
            uses live_ncs_scope_detail_shows;
          }
        }
        container rack {
          description
            "Alarms reported at the rack as
             specified by the location parameter";
          list rack_locations {
            key "rackid";
            leaf rackid {
              type uint32;
            }
            uses live_ncs_scope_detail_shows;
          }
        }
        container system {
          description
            "Alarms reported at the system as
             specified by the location parameter";
          uses live_ncs_scope_detail_shows;
        }
      }
    }
  }
  augment "/ncs:devices/ncs:template/ncs:ned-id/ncs:config" {
    // NCS drop config false container alarm_mgr
  }
}
