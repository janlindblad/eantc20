module Cisco-IOS-XR-infra-alarm-logger-oper {
  // Generated by yanger -t ncs
  tailf:mount-id f5500-nc-1.0:f5500-nc-1.0;
  tailf:ncs-device-type "netconf";

  namespace "http://cisco.com/ns/yang/Cisco-IOS-XR-infra-alarm-logger-oper";
  prefix Cisco-IOS-XR-infra-alarm-logger-oper;

  include Cisco-IOS-XR-infra-alarm-logger-oper-sub1 {
    revision-date 2017-09-07;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR infra-alarm-logger package operational data.

     This module contains definitions
     for the following management objects:
       alarm-logger: Alarm Logger operational data

     Copyright (c) 2013-2018 by Cisco Systems, Inc.
     All rights reserved.";

  revision 2017-09-07 {
    description
      "Fixed type translation error.";
  }
  revision 2015-01-07 {
    description
      "IOS XR 5.3.1 revision.";
  }

  augment "/ncs:devices/ncs:device/ncs:config" {
    // NCS drop config false container 'alarm-logger'
  }
  augment "/ncs:devices/ncs:device/ncs:live-status" {
    container alarm-logger {
      tailf:ncs-device-type "netconf";
      tailf:display-when "not(../../ncs:module) or ../../ncs:module[ncs:name='Cisco-IOS-XR-infra-alarm-logger-oper'] or (../../ncs:live-status-protocol[not(ncs:capability)]) or (../../ncs:live-status-protocol/ncs:capability/ncs:module[.='Cisco-IOS-XR-infra-alarm-logger-oper'])";
      description
        "Alarm Logger operational data";
      container buffer-status {
        description
          "Describes buffer utilization and parameters
           configured";
        uses live_ncs_AL-LOGGING-INFO-BAG;
      }
      container alarms {
        description
          "Table that contains the database of logged
           alarms";
        list alarm {
          key "event-id";
          description
            "One of the logged alarms";
          leaf event-id {
            type uint32;
            description
              "Event ID";
          }
          uses live_ncs_AL-ALDEMS-ALARM-BAG;
        }
      }
    }
  }
  augment "/ncs:devices/ncs:template/ncs:ned-id/ncs:config" {
    // NCS drop config false container 'alarm-logger'
  }
}
