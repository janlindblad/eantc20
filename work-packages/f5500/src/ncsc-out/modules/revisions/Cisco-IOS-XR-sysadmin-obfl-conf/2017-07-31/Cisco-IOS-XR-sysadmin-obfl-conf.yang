module Cisco-IOS-XR-sysadmin-obfl-conf {
  // Generated by yanger -t ncs
  tailf:mount-id f5500-nc-1.0:f5500-nc-1.0;
  tailf:ncs-device-type "netconf";

  namespace "http://www.cisco.com/ns/yang/Cisco-IOS-XR-sysadmin-obfl-conf";
  prefix Cisco-IOS-XR-sysadmin-obfl-conf;

  import "f5500-nc-1.0" {
    prefix "f5500-nc-1.0";
  }
  import tailf-ncs {
    prefix ncs;
  }
  import tailf-common {
    prefix tailf;
  }

  organization
    "Cisco Systems Inc.";
  contact
    "Cisco Systems, Inc.
     Customer Service

     Postal: 170 West Tasman Drive
     San Jose, CA 95134

     Tel: +1 800 553-NETS

     E-mail: cs-yang@cisco.com";
  description
    "This module contains definitions
     for the Calvados model objects.

     This module is for setting certain OBFL params.

     Copyright (c) 2012-2018 by Cisco Systems, Inc.
     All rights reserved.";

  revision 2017-07-31 {
    description
      "Changed namespace to Cisco guidelines on naming convention";
  }

  grouping ncs_template_hw-module-config-group {
    uses ncs_template_hw-module-obfl-config-group;
  }

  grouping ncs_template_hw-module-obfl-config-group {
    list location {
      // NCS patched for predictable order
      ordered-by user;
      key "location";
      leaf location {
        type string;
      }
      container logging {
        container onboard {
          choice onboard_target {
            case target_disable {
              leaf disable {
                type empty;
              }
            }
          }
        }
      }
    }
  }

  grouping ncs_rpc_notif_hw-module-config-group {
    uses ncs_rpc_notif_hw-module-obfl-config-group;
  }

  grouping ncs_rpc_notif_hw-module-obfl-config-group {
    list location {
      key "location";
      leaf location {
        type string;
      }
      container logging {
        container onboard {
          choice onboard_target {
            case target_disable {
              leaf disable {
                type empty;
              }
            }
          }
        }
      }
    }
  }

  grouping live_ncs_hw-module-config-group {
    uses live_ncs_hw-module-obfl-config-group;
  }

  grouping live_ncs_hw-module-obfl-config-group {
    list location {
      key "location";
      leaf location {
        type string;
      }
      container logging {
        container onboard {
          choice onboard_target {
            case target_disable {
              leaf disable {
                type empty;
              }
            }
          }
        }
      }
    }
  }

  grouping hw-module-config-group {
    uses hw-module-obfl-config-group;
  }

  grouping hw-module-obfl-config-group {
    list location {
      key "location";
      leaf location {
        type string;
      }
      container logging {
        container onboard {
          choice onboard_target {
            case target_disable {
              leaf disable {
                type empty;
              }
            }
          }
        }
      }
    }
  }
}
