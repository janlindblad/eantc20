module Cisco-IOS-XR-ip-rip-oper {
  // Generated by yanger -t ncs
  tailf:mount-id f5500-nc-1.0:f5500-nc-1.0;
  tailf:ncs-device-type "netconf";

  namespace "http://cisco.com/ns/yang/Cisco-IOS-XR-ip-rip-oper";
  prefix Cisco-IOS-XR-ip-rip-oper;

  import ietf-inet-types {
    prefix inet;
  }
  import Cisco-IOS-XR-types {
    prefix xr;
  }
  include Cisco-IOS-XR-ip-rip-oper-sub1 {
    revision-date 2015-11-09;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ip-rip package operational data.

     This module contains definitions
     for the following management objects:
       rip: RIP operational data

     Copyright (c) 2013-2018 by Cisco Systems, Inc.
     All rights reserved.";

  revision 2015-11-09 {
    description
      "IOS XR 6.0 revision.";
  }

  grouping ncs_template_ROUTE-TABLE {
    description
      "Common node of default-vrf, vrf";
    container routes {
      description
        "RIP route database";
      list route {
        // NCS patched for predictable order
        ordered-by user;
        description
          "A route in the RIP database";
        leaf prefix {
          type string;
          description
            "Network prefix";
        }
        leaf prefix-length {
          type string;
          description
            "Prefix length";
        }
        uses ncs_template_RIP-SHOW-ROUTE-BD;
      }
    }
  }

  grouping ncs_template_STATISTICS {
    description
      "Common node of default-vrf, vrf";
    container statistics {
      description
        "RIP statistics information";
      uses ncs_template_RIP-SHOW-STATISTICS-BD;
    }
  }

  grouping ncs_template_DEFAULT-VRF {
    description
      "Common node of rip, protocol";
    container default-vrf {
      description
        "RIP operational data for Default VRF";
      uses ncs_template_ROUTE-TABLE;
      uses ncs_template_CONFIGURATION;
      uses ncs_template_STATISTICS;
      uses ncs_template_INTERFACE-TABLE;
      uses ncs_template_GLOBAL;
    }
  }

  grouping ncs_template_CONFIGURATION {
    description
      "Common node of default-vrf, vrf";
    container configuration {
      description
        "RIP global configuration";
      uses ncs_template_RIP-SHOW-GLOBAL-CONFIG-BD;
    }
  }

  grouping ncs_template_INTERFACE-TABLE {
    description
      "Common node of default-vrf, vrf";
    container interfaces {
      description
        "RIP interfaces";
      list interface {
        // NCS patched for predictable order
        ordered-by user;
        key "interface-name";
        description
          "Information about a particular RIP interface";
        leaf interface-name {
          type string;
          description
            "Interface name";
        }
        uses ncs_template_RIP-SHOW-INTERFACE-BD;
      }
    }
  }

  grouping ncs_template_GLOBAL {
    description
      "Common node of default-vrf, vrf";
    container global {
      description
        "Global Information ";
      uses ncs_template_RIP-SHOW-PROTO-VRF-BD;
    }
  }

  grouping ncs_rpc_notif_ROUTE-TABLE {
    description
      "Common node of default-vrf, vrf";
    container routes {
      description
        "RIP route database";
      list route {
        description
          "A route in the RIP database";
        leaf prefix {
          type inet:ipv4-address-no-zone;
          description
            "Network prefix";
        }
        leaf prefix-length {
          type uint32 {
            range "0..32";
          }
          description
            "Prefix length";
        }
        uses ncs_rpc_notif_RIP-SHOW-ROUTE-BD;
      }
    }
  }

  grouping ncs_rpc_notif_STATISTICS {
    description
      "Common node of default-vrf, vrf";
    container statistics {
      description
        "RIP statistics information";
      uses ncs_rpc_notif_RIP-SHOW-STATISTICS-BD;
    }
  }

  grouping ncs_rpc_notif_DEFAULT-VRF {
    description
      "Common node of rip, protocol";
    container default-vrf {
      description
        "RIP operational data for Default VRF";
      uses ncs_rpc_notif_ROUTE-TABLE;
      uses ncs_rpc_notif_CONFIGURATION;
      uses ncs_rpc_notif_STATISTICS;
      uses ncs_rpc_notif_INTERFACE-TABLE;
      uses ncs_rpc_notif_GLOBAL;
    }
  }

  grouping ncs_rpc_notif_CONFIGURATION {
    description
      "Common node of default-vrf, vrf";
    container configuration {
      description
        "RIP global configuration";
      uses ncs_rpc_notif_RIP-SHOW-GLOBAL-CONFIG-BD;
    }
  }

  grouping ncs_rpc_notif_INTERFACE-TABLE {
    description
      "Common node of default-vrf, vrf";
    container interfaces {
      description
        "RIP interfaces";
      list interface {
        key "interface-name";
        description
          "Information about a particular RIP interface";
        leaf interface-name {
          type xr:Interface-name;
          description
            "Interface name";
        }
        uses ncs_rpc_notif_RIP-SHOW-INTERFACE-BD;
      }
    }
  }

  grouping ncs_rpc_notif_GLOBAL {
    description
      "Common node of default-vrf, vrf";
    container global {
      description
        "Global Information ";
      uses ncs_rpc_notif_RIP-SHOW-PROTO-VRF-BD;
    }
  }

  grouping live_ncs_ROUTE-TABLE {
    description
      "Common node of default-vrf, vrf";
    container routes {
      description
        "RIP route database";
      list route {
        description
          "A route in the RIP database";
        leaf prefix {
          type inet:ipv4-address-no-zone;
          description
            "Network prefix";
        }
        leaf prefix-length {
          type uint32 {
            range "0..32";
          }
          description
            "Prefix length";
        }
        uses live_ncs_RIP-SHOW-ROUTE-BD;
      }
    }
  }

  grouping live_ncs_STATISTICS {
    description
      "Common node of default-vrf, vrf";
    container statistics {
      description
        "RIP statistics information";
      uses live_ncs_RIP-SHOW-STATISTICS-BD;
    }
  }

  grouping live_ncs_DEFAULT-VRF {
    description
      "Common node of rip, protocol";
    container default-vrf {
      description
        "RIP operational data for Default VRF";
      uses live_ncs_ROUTE-TABLE;
      uses live_ncs_CONFIGURATION;
      uses live_ncs_STATISTICS;
      uses live_ncs_INTERFACE-TABLE;
      uses live_ncs_GLOBAL;
    }
  }

  grouping live_ncs_CONFIGURATION {
    description
      "Common node of default-vrf, vrf";
    container configuration {
      description
        "RIP global configuration";
      uses live_ncs_RIP-SHOW-GLOBAL-CONFIG-BD;
    }
  }

  grouping live_ncs_INTERFACE-TABLE {
    description
      "Common node of default-vrf, vrf";
    container interfaces {
      description
        "RIP interfaces";
      list interface {
        key "interface-name";
        description
          "Information about a particular RIP interface";
        leaf interface-name {
          type xr:Interface-name;
          description
            "Interface name";
        }
        uses live_ncs_RIP-SHOW-INTERFACE-BD;
      }
    }
  }

  grouping live_ncs_GLOBAL {
    description
      "Common node of default-vrf, vrf";
    container global {
      description
        "Global Information ";
      uses live_ncs_RIP-SHOW-PROTO-VRF-BD;
    }
  }

  grouping ROUTE-TABLE {
    description
      "Common node of default-vrf, vrf";
    container routes {
      description
        "RIP route database";
      list route {
        description
          "A route in the RIP database";
        leaf prefix {
          type inet:ipv4-address-no-zone;
          description
            "Network prefix";
        }
        leaf prefix-length {
          type uint32 {
            range "0..32";
          }
          description
            "Prefix length";
        }
        uses RIP-SHOW-ROUTE-BD;
      }
    }
  }

  grouping STATISTICS {
    description
      "Common node of default-vrf, vrf";
    container statistics {
      description
        "RIP statistics information";
      uses RIP-SHOW-STATISTICS-BD;
    }
  }

  grouping DEFAULT-VRF {
    description
      "Common node of rip, protocol";
    container default-vrf {
      description
        "RIP operational data for Default VRF";
      uses ROUTE-TABLE;
      uses CONFIGURATION;
      uses STATISTICS;
      uses INTERFACE-TABLE;
      uses GLOBAL;
    }
  }

  grouping CONFIGURATION {
    description
      "Common node of default-vrf, vrf";
    container configuration {
      description
        "RIP global configuration";
      uses RIP-SHOW-GLOBAL-CONFIG-BD;
    }
  }

  grouping INTERFACE-TABLE {
    description
      "Common node of default-vrf, vrf";
    container interfaces {
      description
        "RIP interfaces";
      list interface {
        key "interface-name";
        description
          "Information about a particular RIP interface";
        leaf interface-name {
          type xr:Interface-name;
          description
            "Interface name";
        }
        uses RIP-SHOW-INTERFACE-BD;
      }
    }
  }

  grouping GLOBAL {
    description
      "Common node of default-vrf, vrf";
    container global {
      description
        "Global Information ";
      uses RIP-SHOW-PROTO-VRF-BD;
    }
  }

  augment "/ncs:devices/ncs:device/ncs:config" {
    // NCS drop config false container rip
  }
  augment "/ncs:devices/ncs:device/ncs:live-status" {
    container rip {
      tailf:ncs-device-type "netconf";
      tailf:display-when "not(../../ncs:module) or ../../ncs:module[ncs:name='Cisco-IOS-XR-ip-rip-oper'] or (../../ncs:live-status-protocol[not(ncs:capability)]) or (../../ncs:live-status-protocol/ncs:capability/ncs:module[.='Cisco-IOS-XR-ip-rip-oper'])";
      description
        "RIP operational data";
      container vrfs {
        description
          "VRF related operational data";
        list vrf {
          key "vrf-name";
          description
            "Operational data for a particular VRF";
          leaf vrf-name {
            type xr:Cisco-ios-xr-string;
            description
              "Name of the VRF";
          }
          uses live_ncs_ROUTE-TABLE;
          uses live_ncs_CONFIGURATION;
          uses live_ncs_STATISTICS;
          uses live_ncs_INTERFACE-TABLE;
          uses live_ncs_GLOBAL;
        }
      }
      container protocol {
        description
          "Protocol operational data";
        container process {
          description
            "RIP global process ";
          uses live_ncs_RIP-SHOW-PROTO-PROC-BD;
        }
        uses live_ncs_DEFAULT-VRF;
      }
      uses live_ncs_DEFAULT-VRF;
    }
  }
  augment "/ncs:devices/ncs:template/ncs:ned-id/ncs:config" {
    // NCS drop config false container rip
  }
}
