module Cisco-IOS-XR-li-cfg {
  // Generated by yanger -t ncs
  tailf:mount-id f5500-nc-1.0:f5500-nc-1.0;
  tailf:ncs-device-type "netconf";

  namespace "http://cisco.com/ns/yang/Cisco-IOS-XR-li-cfg";
  prefix Cisco-IOS-XR-li-cfg;

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR li package configuration.

     This module contains definitions
     for the following management objects:
       lawful-intercept: Lawful intercept configuration

     Copyright (c) 2013-2018 by Cisco Systems, Inc.
     All rights reserved.";

  revision 2015-11-09 {
    description
      "IOS XR 6.0 revision.";
  }

  augment "/ncs:devices/ncs:device/ncs:config" {
    container lawful-intercept {
      tailf:ncs-device-type "netconf";
      tailf:display-when "not(../../ncs:module) or ../../ncs:module[ncs:name='Cisco-IOS-XR-li-cfg']";
      description
        "Lawful intercept configuration";
      leaf disable {
        type empty;
        description
          "Disable lawful intercept feature";
      }
    }
  }
  augment "/ncs:devices/ncs:device/ncs:live-status" {
    container lawful-intercept {
      tailf:ncs-device-type "netconf";
      tailf:display-when "not(../../ncs:module) or ../../ncs:module[ncs:name='Cisco-IOS-XR-li-cfg'] or (../../ncs:live-status-protocol[not(ncs:capability)]) or (../../ncs:live-status-protocol/ncs:capability/ncs:module[.='Cisco-IOS-XR-li-cfg'])";
      description
        "Lawful intercept configuration";
      leaf disable {
        type empty;
        description
          "Disable lawful intercept feature";
      }
    }
  }
  augment "/ncs:devices/ncs:template/ncs:ned-id/ncs:config" {
    container lawful-intercept {
      description
        "Lawful intercept configuration";
      leaf disable {
        type empty;
        description
          "Disable lawful intercept feature";
      }
    }
  }
}
