module Cisco-IOS-XR-perf-meas-cfg {
  // Generated by yanger -t ncs
  tailf:mount-id f5500-nc-1.0:f5500-nc-1.0;
  tailf:ncs-device-type "netconf";

  namespace "http://cisco.com/ns/yang/Cisco-IOS-XR-perf-meas-cfg";
  prefix Cisco-IOS-XR-perf-meas-cfg;

  import Cisco-IOS-XR-types {
    prefix xr;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR perf-meas package configuration.

     This module contains definitions
     for the following management objects:
       performance-measurement: The root of performance-measurement
         configuration

     Copyright (c) 2013-2018 by Cisco Systems, Inc.
     All rights reserved.";

  revision 2017-10-17 {
    description
      "Revision Zero.";
  }
  revision 2015-11-09 {
    description
      "IOS XR 6.0 revision.";
  }

  augment "/ncs:devices/ncs:device/ncs:config" {
    container performance-measurement {
      tailf:ncs-device-type "netconf";
      tailf:display-when "not(../../ncs:module) or ../../ncs:module[ncs:name='Cisco-IOS-XR-perf-meas-cfg']";
      description
        "The root of performance-measurement configuration";
      container delay-profile-interface {
        description
          "PM Delay Profile";
        container advertisement {
          description
            "Advertisement Profile";
          container accelerated {
            description
              "Accelerated Advertisement Profile";
            leaf threshold {
              type uint32 {
                range "0..100";
              }
              units "percentage";
              default "20";
              description
                "Accelerated advertisement threshold
                 percentage";
            }
            leaf minimum-change {
              type uint32 {
                range "0..100000";
              }
              default "500";
              description
                "Accelerated advertisement minimum value in
                 uSec";
            }
            leaf enable {
              type empty;
              description
                "Enable Accelerated Advertisement";
            }
          }
          container periodic {
            description
              "Periodic Advertisement Profile";
            leaf interval {
              type uint32 {
                range "30..3600";
              }
              units "second";
              default "120";
              description
                "Periodic advertisement interval in seconds";
            }
            leaf threshold {
              type uint32 {
                range "0..100";
              }
              units "percentage";
              default "10";
              description
                "Periodic advertisement threshold percentage";
            }
            leaf minimum-change {
              type uint32 {
                range "0..100000";
              }
              default "500";
              description
                "Periodic advertisement minimum value in uSec";
            }
            leaf disable {
              type empty;
              description
                "Enable Performance Measurement Periodic
                 Advertisement";
            }
          }
        }
        container probe {
          description
            "PM Delay Profile Probe";
          container burst {
            description
              "PM Delay Profile Probe Burst";
            leaf count {
              type uint32 {
                range "1..30";
              }
              default "10";
              description
                "The value for delay profile probe burst count";
            }
            leaf interval {
              type uint32 {
                range "30..15000";
              }
              default "3000";
              description
                "The value for delay profile probe burst
                 interval";
            }
          }
          leaf one-way-measurement {
            type empty;
            description
              "Enable one-way measurement";
          }
          leaf interval {
            type uint32 {
              range "30..3600";
            }
            units "second";
            default "30";
            description
              "The value for delay profile probe interval in
               seconds";
          }
        }
      }
      container interfaces {
        description
          "Configure performance-measurement interfaces";
        list interface {
          key "interface-name";
          description
            "Configure a performance-measurement interface";
          container delay-measurement {
            description
              "Interface delay measurement";
            leaf enable-delay-measurement {
              type empty;
              description
                "Enable interface delay measurement";
            }
            leaf advertise-delay {
              type uint32 {
                range "0..16777215";
              }
              description
                "The value for interface delay measurement
                 advertisement delay in uSec";
            }
          }
          leaf enable-interface {
            type empty;
            description
              "Enable interface submode";
          }
          leaf interface-name {
            type xr:Interface-name;
            description
              "Interface name";
          }
        }
      }
      leaf enable-performance-measurement {
        type empty;
        description
          "Enable the performance measurement feature";
      }
    }
  }
  augment "/ncs:devices/ncs:device/ncs:live-status" {
    container performance-measurement {
      tailf:ncs-device-type "netconf";
      tailf:display-when "not(../../ncs:module) or ../../ncs:module[ncs:name='Cisco-IOS-XR-perf-meas-cfg'] or (../../ncs:live-status-protocol[not(ncs:capability)]) or (../../ncs:live-status-protocol/ncs:capability/ncs:module[.='Cisco-IOS-XR-perf-meas-cfg'])";
      description
        "The root of performance-measurement configuration";
      container delay-profile-interface {
        description
          "PM Delay Profile";
        container advertisement {
          description
            "Advertisement Profile";
          container accelerated {
            description
              "Accelerated Advertisement Profile";
            leaf threshold {
              type uint32 {
                range "0..100";
              }
              units "percentage";
              // NCS drop default statement
              description
                "Accelerated advertisement threshold
                 percentage";
            }
            leaf minimum-change {
              type uint32 {
                range "0..100000";
              }
              // NCS drop default statement
              description
                "Accelerated advertisement minimum value in
                 uSec";
            }
            leaf enable {
              type empty;
              description
                "Enable Accelerated Advertisement";
            }
          }
          container periodic {
            description
              "Periodic Advertisement Profile";
            leaf interval {
              type uint32 {
                range "30..3600";
              }
              units "second";
              // NCS drop default statement
              description
                "Periodic advertisement interval in seconds";
            }
            leaf threshold {
              type uint32 {
                range "0..100";
              }
              units "percentage";
              // NCS drop default statement
              description
                "Periodic advertisement threshold percentage";
            }
            leaf minimum-change {
              type uint32 {
                range "0..100000";
              }
              // NCS drop default statement
              description
                "Periodic advertisement minimum value in uSec";
            }
            leaf disable {
              type empty;
              description
                "Enable Performance Measurement Periodic
                 Advertisement";
            }
          }
        }
        container probe {
          description
            "PM Delay Profile Probe";
          container burst {
            description
              "PM Delay Profile Probe Burst";
            leaf count {
              type uint32 {
                range "1..30";
              }
              // NCS drop default statement
              description
                "The value for delay profile probe burst count";
            }
            leaf interval {
              type uint32 {
                range "30..15000";
              }
              // NCS drop default statement
              description
                "The value for delay profile probe burst
                 interval";
            }
          }
          leaf one-way-measurement {
            type empty;
            description
              "Enable one-way measurement";
          }
          leaf interval {
            type uint32 {
              range "30..3600";
            }
            units "second";
            // NCS drop default statement
            description
              "The value for delay profile probe interval in
               seconds";
          }
        }
      }
      container interfaces {
        description
          "Configure performance-measurement interfaces";
        list interface {
          key "interface-name";
          description
            "Configure a performance-measurement interface";
          container delay-measurement {
            description
              "Interface delay measurement";
            leaf enable-delay-measurement {
              type empty;
              description
                "Enable interface delay measurement";
            }
            leaf advertise-delay {
              type uint32 {
                range "0..16777215";
              }
              description
                "The value for interface delay measurement
                 advertisement delay in uSec";
            }
          }
          leaf enable-interface {
            type empty;
            description
              "Enable interface submode";
          }
          leaf interface-name {
            type xr:Interface-name;
            description
              "Interface name";
          }
        }
      }
      leaf enable-performance-measurement {
        type empty;
        description
          "Enable the performance measurement feature";
      }
    }
  }
  augment "/ncs:devices/ncs:template/ncs:ned-id/ncs:config" {
    container performance-measurement {
      description
        "The root of performance-measurement configuration";
      container delay-profile-interface {
        description
          "PM Delay Profile";
        container advertisement {
          description
            "Advertisement Profile";
          container accelerated {
            description
              "Accelerated Advertisement Profile";
            leaf threshold {
              type string;
              units "percentage";
              // NCS drop default statement
              description
                "Accelerated advertisement threshold
                 percentage";
            }
            leaf minimum-change {
              type string;
              // NCS drop default statement
              description
                "Accelerated advertisement minimum value in
                 uSec";
            }
            leaf enable {
              type empty;
              description
                "Enable Accelerated Advertisement";
            }
          }
          container periodic {
            description
              "Periodic Advertisement Profile";
            leaf interval {
              type string;
              units "second";
              // NCS drop default statement
              description
                "Periodic advertisement interval in seconds";
            }
            leaf threshold {
              type string;
              units "percentage";
              // NCS drop default statement
              description
                "Periodic advertisement threshold percentage";
            }
            leaf minimum-change {
              type string;
              // NCS drop default statement
              description
                "Periodic advertisement minimum value in uSec";
            }
            leaf disable {
              type empty;
              description
                "Enable Performance Measurement Periodic
                 Advertisement";
            }
          }
        }
        container probe {
          description
            "PM Delay Profile Probe";
          container burst {
            description
              "PM Delay Profile Probe Burst";
            leaf count {
              type string;
              // NCS drop default statement
              description
                "The value for delay profile probe burst count";
            }
            leaf interval {
              type string;
              // NCS drop default statement
              description
                "The value for delay profile probe burst
                 interval";
            }
          }
          leaf one-way-measurement {
            type empty;
            description
              "Enable one-way measurement";
          }
          leaf interval {
            type string;
            units "second";
            // NCS drop default statement
            description
              "The value for delay profile probe interval in
               seconds";
          }
        }
      }
      container interfaces {
        description
          "Configure performance-measurement interfaces";
        list interface {
          // NCS patched for predictable order
          ordered-by user;
          key "interface-name";
          description
            "Configure a performance-measurement interface";
          container delay-measurement {
            description
              "Interface delay measurement";
            leaf enable-delay-measurement {
              type empty;
              description
                "Enable interface delay measurement";
            }
            leaf advertise-delay {
              type string;
              description
                "The value for interface delay measurement
                 advertisement delay in uSec";
            }
          }
          leaf enable-interface {
            type empty;
            description
              "Enable interface submode";
          }
          leaf interface-name {
            type string;
            description
              "Interface name";
          }
        }
      }
      leaf enable-performance-measurement {
        type empty;
        description
          "Enable the performance measurement feature";
      }
    }
  }
}
