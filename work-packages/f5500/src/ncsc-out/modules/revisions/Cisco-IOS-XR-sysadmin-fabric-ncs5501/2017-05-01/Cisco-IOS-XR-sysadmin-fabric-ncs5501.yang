module Cisco-IOS-XR-sysadmin-fabric-ncs5501 {
  // Generated by yanger -t ncs
  tailf:mount-id f5500-nc-1.0:f5500-nc-1.0;
  tailf:ncs-device-type "netconf";

  namespace "http://www.cisco.com/ns/yang/Cisco-IOS-XR-sysadmin-fabric-ncs5501";
  prefix Cisco-IOS-XR-sysadmin-fabric-ncs5501;

  import Cisco-IOS-XR-sysadmin-fabric-mgr-fgid {
    prefix fabric-fgid;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains definitions
     for the Calvados model objects.

     Copyright (c) 2012-2018 by Cisco Systems, Inc.
     All rights reserved.";

  revision 2017-05-01 {
    description
      "Namespace change to comply with Cisco guidelines on namespace";
  }

  grouping ncs_template_fabric {
    container fabric {
      description
        "Fabric resource commands";
      // NCS drop config false container oper
    }
  }

  grouping ncs_rpc_notif_fabric {
    container fabric {
      description
        "Fabric resource commands";
      container oper {
        config false;
        uses fabric-fgid:ncs_rpc_notif_fgid;
      }
    }
  }

  grouping live_ncs_fabric {
    container fabric {
      description
        "Fabric resource commands";
      container oper {
        uses fabric-fgid:live_ncs_fgid;
      }
    }
  }

  grouping fabric {
    container fabric {
      description
        "Fabric resource commands";
      // NCS drop config false container oper
    }
  }
}
