submodule Cisco-IOS-XR-infra-rmf-oper-sub1 {
  // Generated by yanger -t ncs
  tailf:mount-id f5500-nc-1.0:f5500-nc-1.0;

  belongs-to Cisco-IOS-XR-infra-rmf-oper {
    prefix Cisco-IOS-XR-infra-rmf-oper-sub1;
  }

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR infra-rmf package operational data.

     Copyright (c) 2013-2018 by Cisco Systems, Inc.
     All rights reserved.";

  revision 2015-11-09 {
    description
      "IOS XR 6.0 revision.";
  }

  grouping ncs_template_RED-SUMMARY {
    description
      "rmf show";
    leaf err-log {
      type string;
      description
        "Error Log";
    }
    list red-pair {
      // NCS patched for predictable order
      ordered-by user;
      description
        "Redundancy Pair";
      uses ncs_template_RED-SUMMARY-PAIR;
    }
  }

  grouping ncs_template_RED-GROUP-INFO {
    description
      "RED GROUP INFO";
    leaf active {
      type string;
      description
        "Active";
    }
    leaf standby {
      type string;
      description
        "Standby";
    }
    leaf ha-state {
      type string;
      description
        "HAState";
    }
    leaf nsr-state {
      type string;
      description
        "NSRState";
    }
  }

  grouping ncs_template_RED-SUMMARY-PAIR {
    description
      "rmf row show";
    leaf active {
      type string;
      description
        "Active node name R/S/I";
    }
    leaf standby {
      type string;
      description
        "Standby node name R/S/I";
    }
    leaf ha-state {
      type string;
      description
        "High Availability state Ready/Not Ready";
    }
    leaf nsr-state {
      type string;
      description
        "NSR state Configured/Not Configured";
    }
    list groupinfo {
      // NCS patched for predictable order
      ordered-by user;
      description
        "groupinfo";
      uses ncs_template_RED-GROUP-INFO;
    }
  }

  grouping ncs_template_RED-NODE-INFO {
    description
      "Node Information";
    container redundancy {
      description
        "Row information";
      uses ncs_template_RED-SUMMARY-PAIR;
    }
    leaf log {
      type string;
      description
        "Reload and boot logs";
    }
    leaf active-reboot-reason {
      type string;
      description
        "Active node reload";
    }
    leaf standby-reboot-reason {
      type string;
      description
        "Standby node reload";
    }
    leaf err-log {
      type string;
      description
        "Error Log";
    }
  }

  grouping ncs_rpc_notif_RED-SUMMARY {
    description
      "rmf show";
    leaf err-log {
      type string;
      description
        "Error Log";
    }
    list red-pair {
      description
        "Redundancy Pair";
      uses ncs_rpc_notif_RED-SUMMARY-PAIR;
    }
  }

  grouping ncs_rpc_notif_RED-GROUP-INFO {
    description
      "RED GROUP INFO";
    leaf active {
      type string;
      description
        "Active";
    }
    leaf standby {
      type string;
      description
        "Standby";
    }
    leaf ha-state {
      type string;
      description
        "HAState";
    }
    leaf nsr-state {
      type string;
      description
        "NSRState";
    }
  }

  grouping ncs_rpc_notif_RED-SUMMARY-PAIR {
    description
      "rmf row show";
    leaf active {
      type string;
      description
        "Active node name R/S/I";
    }
    leaf standby {
      type string;
      description
        "Standby node name R/S/I";
    }
    leaf ha-state {
      type string;
      description
        "High Availability state Ready/Not Ready";
    }
    leaf nsr-state {
      type string;
      description
        "NSR state Configured/Not Configured";
    }
    list groupinfo {
      description
        "groupinfo";
      uses ncs_rpc_notif_RED-GROUP-INFO;
    }
  }

  grouping ncs_rpc_notif_RED-NODE-INFO {
    description
      "Node Information";
    container redundancy {
      description
        "Row information";
      uses ncs_rpc_notif_RED-SUMMARY-PAIR;
    }
    leaf log {
      type string;
      description
        "Reload and boot logs";
    }
    leaf active-reboot-reason {
      type string;
      description
        "Active node reload";
    }
    leaf standby-reboot-reason {
      type string;
      description
        "Standby node reload";
    }
    leaf err-log {
      type string;
      description
        "Error Log";
    }
  }

  grouping live_ncs_RED-SUMMARY {
    description
      "rmf show";
    leaf err-log {
      type string;
      description
        "Error Log";
    }
    list red-pair {
      description
        "Redundancy Pair";
      uses live_ncs_RED-SUMMARY-PAIR;
    }
  }

  grouping live_ncs_RED-GROUP-INFO {
    description
      "RED GROUP INFO";
    leaf active {
      type string;
      description
        "Active";
    }
    leaf standby {
      type string;
      description
        "Standby";
    }
    leaf ha-state {
      type string;
      description
        "HAState";
    }
    leaf nsr-state {
      type string;
      description
        "NSRState";
    }
  }

  grouping live_ncs_RED-SUMMARY-PAIR {
    description
      "rmf row show";
    leaf active {
      type string;
      description
        "Active node name R/S/I";
    }
    leaf standby {
      type string;
      description
        "Standby node name R/S/I";
    }
    leaf ha-state {
      type string;
      description
        "High Availability state Ready/Not Ready";
    }
    leaf nsr-state {
      type string;
      description
        "NSR state Configured/Not Configured";
    }
    list groupinfo {
      description
        "groupinfo";
      uses live_ncs_RED-GROUP-INFO;
    }
  }

  grouping live_ncs_RED-NODE-INFO {
    description
      "Node Information";
    container redundancy {
      description
        "Row information";
      uses live_ncs_RED-SUMMARY-PAIR;
    }
    leaf log {
      type string;
      description
        "Reload and boot logs";
    }
    leaf active-reboot-reason {
      type string;
      description
        "Active node reload";
    }
    leaf standby-reboot-reason {
      type string;
      description
        "Standby node reload";
    }
    leaf err-log {
      type string;
      description
        "Error Log";
    }
  }

  grouping RED-SUMMARY {
    description
      "rmf show";
    leaf err-log {
      type string;
      description
        "Error Log";
    }
    list red-pair {
      description
        "Redundancy Pair";
      uses RED-SUMMARY-PAIR;
    }
  }

  grouping RED-GROUP-INFO {
    description
      "RED GROUP INFO";
    leaf active {
      type string;
      description
        "Active";
    }
    leaf standby {
      type string;
      description
        "Standby";
    }
    leaf ha-state {
      type string;
      description
        "HAState";
    }
    leaf nsr-state {
      type string;
      description
        "NSRState";
    }
  }

  grouping RED-SUMMARY-PAIR {
    description
      "rmf row show";
    leaf active {
      type string;
      description
        "Active node name R/S/I";
    }
    leaf standby {
      type string;
      description
        "Standby node name R/S/I";
    }
    leaf ha-state {
      type string;
      description
        "High Availability state Ready/Not Ready";
    }
    leaf nsr-state {
      type string;
      description
        "NSR state Configured/Not Configured";
    }
    list groupinfo {
      description
        "groupinfo";
      uses RED-GROUP-INFO;
    }
  }

  grouping RED-NODE-INFO {
    description
      "Node Information";
    container redundancy {
      description
        "Row information";
      uses RED-SUMMARY-PAIR;
    }
    leaf log {
      type string;
      description
        "Reload and boot logs";
    }
    leaf active-reboot-reason {
      type string;
      description
        "Active node reload";
    }
    leaf standby-reboot-reason {
      type string;
      description
        "Standby node reload";
    }
    leaf err-log {
      type string;
      description
        "Error Log";
    }
  }
}
