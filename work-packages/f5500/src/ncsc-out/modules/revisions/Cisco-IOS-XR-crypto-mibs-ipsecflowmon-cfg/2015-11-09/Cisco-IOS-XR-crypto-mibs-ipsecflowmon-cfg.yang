module Cisco-IOS-XR-crypto-mibs-ipsecflowmon-cfg {
  // Generated by yanger -t ncs
  tailf:mount-id f5500-nc-1.0:f5500-nc-1.0;
  tailf:ncs-device-type "netconf";

  namespace "http://cisco.com/ns/yang/Cisco-IOS-XR-crypto-mibs-ipsecflowmon-cfg";
  prefix Cisco-IOS-XR-crypto-mibs-ipsecflowmon-cfg;

  import Cisco-IOS-XR-snmp-agent-cfg {
    prefix a1;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR crypto-mibs-ipsecflowmon package configuration.

     This YANG module augments the
       Cisco-IOS-XR-snmp-agent-cfg
     module with configuration data.

     Copyright (c) 2013-2018 by Cisco Systems, Inc.
     All rights reserved.";

  revision 2015-11-09 {
    description
      "IOS XR 6.0 revision.";
  }

  augment "/ncs:devices/ncs:template/ncs:ned-id/ncs:config/a1:snmp/a1:notification" {
    container ip-sec {
      description
        "Enable CISCO-IPSEC-FLOW-MONITOR-MIB
         notifications";
      leaf tunnel-stop {
        type empty;
        description
          "Enable cipSecTunnelStop notification";
      }
      leaf tunnel-start {
        type empty;
        description
          "Enable cipSecTunnelStart notification";
      }
    }
    description
      "This augment extends the configuration data of
       'Cisco-IOS-XR-snmp-agent-cfg'";
  }
  augment "/ncs:devices/ncs:device/ncs:live-status/a1:snmp/a1:notification" {
    container ip-sec {
      tailf:ncs-device-type "netconf";
      tailf:display-when "not(../../../../ncs:module) or ../../../../ncs:module[ncs:name='Cisco-IOS-XR-crypto-mibs-ipsecflowmon-cfg'] or (../../../../ncs:live-status-protocol[not(ncs:capability)]) or (../../../../ncs:live-status-protocol/ncs:capability/ncs:module[.='Cisco-IOS-XR-crypto-mibs-ipsecflowmon-cfg'])";
      description
        "Enable CISCO-IPSEC-FLOW-MONITOR-MIB
         notifications";
      leaf tunnel-stop {
        type empty;
        description
          "Enable cipSecTunnelStop notification";
      }
      leaf tunnel-start {
        type empty;
        description
          "Enable cipSecTunnelStart notification";
      }
    }
    description
      "This augment extends the configuration data of
       'Cisco-IOS-XR-snmp-agent-cfg'";
  }
  augment "/ncs:devices/ncs:device/ncs:config/a1:snmp/a1:notification" {
    container ip-sec {
      tailf:ncs-device-type "netconf";
      tailf:display-when "not(../../../../ncs:module) or ../../../../ncs:module[ncs:name='Cisco-IOS-XR-crypto-mibs-ipsecflowmon-cfg']";
      description
        "Enable CISCO-IPSEC-FLOW-MONITOR-MIB
         notifications";
      leaf tunnel-stop {
        type empty;
        description
          "Enable cipSecTunnelStop notification";
      }
      leaf tunnel-start {
        type empty;
        description
          "Enable cipSecTunnelStart notification";
      }
    }
    description
      "This augment extends the configuration data of
       'Cisco-IOS-XR-snmp-agent-cfg'";
  }
  augment "/ncs:devices/ncs:template/ncs:ned-id/ncs:config/a1:snmp/a1:notification" {
    container isakmp {
      description
        "Enable CISCO-IPSEC-FLOW-MONITOR-MIB
         notifications";
      leaf tunnel-stop {
        type empty;
        description
          "Enable cikeTunnelStop notification";
      }
      leaf tunnel-start {
        type empty;
        description
          "Enable cikeTunnelStart notification";
      }
    }
    description
      "This augment extends the configuration data of
       'Cisco-IOS-XR-snmp-agent-cfg'";
  }
  augment "/ncs:devices/ncs:device/ncs:live-status/a1:snmp/a1:notification" {
    container isakmp {
      tailf:ncs-device-type "netconf";
      tailf:display-when "not(../../../../ncs:module) or ../../../../ncs:module[ncs:name='Cisco-IOS-XR-crypto-mibs-ipsecflowmon-cfg'] or (../../../../ncs:live-status-protocol[not(ncs:capability)]) or (../../../../ncs:live-status-protocol/ncs:capability/ncs:module[.='Cisco-IOS-XR-crypto-mibs-ipsecflowmon-cfg'])";
      description
        "Enable CISCO-IPSEC-FLOW-MONITOR-MIB
         notifications";
      leaf tunnel-stop {
        type empty;
        description
          "Enable cikeTunnelStop notification";
      }
      leaf tunnel-start {
        type empty;
        description
          "Enable cikeTunnelStart notification";
      }
    }
    description
      "This augment extends the configuration data of
       'Cisco-IOS-XR-snmp-agent-cfg'";
  }
  augment "/ncs:devices/ncs:device/ncs:config/a1:snmp/a1:notification" {
    container isakmp {
      tailf:ncs-device-type "netconf";
      tailf:display-when "not(../../../../ncs:module) or ../../../../ncs:module[ncs:name='Cisco-IOS-XR-crypto-mibs-ipsecflowmon-cfg']";
      description
        "Enable CISCO-IPSEC-FLOW-MONITOR-MIB
         notifications";
      leaf tunnel-stop {
        type empty;
        description
          "Enable cikeTunnelStop notification";
      }
      leaf tunnel-start {
        type empty;
        description
          "Enable cikeTunnelStart notification";
      }
    }
    description
      "This augment extends the configuration data of
       'Cisco-IOS-XR-snmp-agent-cfg'";
  }
}
