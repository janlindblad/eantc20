module Cisco-IOS-XR-sysadmin-sdr-mgr {
  // Generated by yanger -t ncs
  tailf:mount-id f5500-nc-1.0:f5500-nc-1.0;
  tailf:ncs-device-type "netconf";

  namespace "http://www.cisco.com/ns/yang/Cisco-IOS-XR-sysadmin-sdr-mgr";
  prefix Cisco-IOS-XR-sysadmin-sdr-mgr;

  import tailf-common {
    prefix tailf;
  }
  import ietf-inet-types {
    prefix inet;
  }
  import Cisco-IOS-XR-sysadmin-show-trace {
    prefix show_trace;
  }
  import "f5500-nc-1.0" {
    prefix "f5500-nc-1.0";
  }
  import tailf-ncs {
    prefix ncs;
  }

  organization
    "Cisco Systems Inc.";
  contact
    "Cisco Systems, Inc.
     Customer Service

     Postal: 170 West Tasman Drive
     San Jose, CA 95134

     Tel: +1 800 553-NETS

     E-mail: cs-yang@cisco.com";
  description
    "This module contains definitions
     for the Calvados model objects.

     This module contains a collection of YANG
     definitions for Cisco IOS-XR SysAdmin configuration.

     This module defines the SDR-SM support config for SDR

     Copyright(c) 2011-2017 by Cisco Systems, Inc.
     All rights reserved.

     Copyright (c) 2012-2018 by Cisco Systems, Inc.
     All rights reserved.";

  revision 2018-10-22 {
    description
      "Removed choice for action re_pair";
  }

  typedef vm_reload_reason {
    type enumeration {
      enum "CARD_OFFLINE";
      enum "CARD_SHUTDOWN";
      enum "ALL_VM_RELOAD";
      enum "VM_REQUESTED_GRACEFUL_RELOAD";
      enum "VM_REQUESTED_UNGRACEFUL_RELOAD";
      enum "SDR_CLI_REQUESTED";
      enum "SDR_VCPU_VMEM_CHANGED";
      enum "SDR_HEARTBEAT_FAILURE";
      enum "FIRST_BOOT";
      enum "SMU";
      enum "REASON_UNKNOWN";
    }
    description
      "The List of vm reload reasons";
  }

  typedef CardType {
    type enumeration {
      enum "RP";
      enum "LC";
      enum "CC";
    }
    description
      "The List of supported Card Types";
  }

  typedef VMLocationall {
    type string {
      pattern '((0?[0-9]|1[1-5]|[bB]\d)/((([rR]([sS]){0,1}[pP])|[cC][bB])?\d{1,2})/[V][M](0?[0-9]|1[1-5]))?|all';
    }
    description
      "A system location in Rack/Slot/Instance";
  }

  typedef VMLocation {
    type string {
      pattern '((0?[0-9]|1[1-5]|[bB]\d)/((([rR]([sS]){0,1}[pP])|[cC][bB])?\d{1,2})/[V][M](0?[0-9]|1[1-5]))?';
    }
    description
      "A system location in Rack/Slot/Instance";
  }

  typedef RPLocation {
    type string {
      pattern '((0?[0-9]|1[1-5]|[bB]\d)/(([rR][pP]|[cC][bB])\d{1,2}))(/[cC][pP][uU]0)?';
    }
    description
      "A system location in Rack/Slot/Instance";
  }

  typedef Location {
    type string {
      pattern '((0?[0-9]|1[1-5]|[bB]\d)/(([rR][pP]|[lL][cC]|[cC][bB])?\d{1,2}))(/[cC][pP][uU]0)?|all';
    }
    description
      "A system location in Rack/Slot/Instance";
  }

  augment "/ncs:devices/ncs:device/ncs:config" {
    container sdr-config {
      tailf:ncs-device-type "netconf";
      tailf:display-when "not(../../ncs:module) or ../../ncs:module[ncs:name='Cisco-IOS-XR-sysadmin-sdr-mgr']";
      list sdr {
        description
          "Add/Edit a Secure Domain Router by name";
        key "name";
        leaf name {
          type string {
            pattern '[a-zA-Z0-9_-]{1,30}';
          }
          description
            "Name of the Secure Domain Router , 30 max characters";
        }
        leaf initial-image {
          type string;
          description
            "List of the initial image and packages for the Secure Domain Router.";
        }
        leaf lead_down_delta {
          type uint32;
          description
            "Amount of time between lead down to declare SDR down";
        }
        leaf pairing-mode {
          type enumeration {
            enum "intra-rack";
            enum "inter-rack";
          }
          description
            "Setting for pairing mode";
        }
        leaf issu {
          type enumeration {
            enum "disable";
          }
          description
            "ISSU flag. Once disabled, ISSU won't be performed for this SDR.";
        }
        container resources {
          description
            "Edit resources for a Secure Domain Router";
          leaf fgid {
            type uint32 {
              range "25000..524288";
            }
            description
              "Fgids for a Secure Domain Router";
          }
          leaf mgmt_ext_vlan {
            type uint32 {
              range "2..4094";
            }
            description
              "Management External VLAN for Secure Domain Router";
          }
          list card-type {
            key "type";
            leaf type {
              type CardType;
              description
                "Card Type";
            }
            leaf vm-memory {
              type uint32 {
                range "1..128";
              }
              description
                "VM Memory Size in units of [GB]";
            }
            leaf vm-cpu {
              type uint32 {
                range "1..128";
              }
              description
                "VM Number of CPUs";
            }
          }
        }
        list location {
          min-elements 1;
          max-elements 64;
          description
            "Enter list of nodes' location to add to this LR";
          key "node-location";
          leaf node-location {
            type Location;
            description
              "Enter location or all";
          }
          leaf-list slice {
            max-elements 4;
            description
              "Enter list of slices to add to this SDR";
            type uint8 {
              range "0 .. 4";
            }
          }
        }
        // NCS drop config false container 'Action'
        // NCS drop config false container detail
        // NCS drop config false container 'reboot-history'
        // NCS drop config false container nodes
        // NCS drop config false container pairing2
        list pairing {
          description
            "Add/Edit a RP Pairing by name";
          key "name";
          leaf name {
            type string {
              pattern '[a-zA-Z0-9_-]{1,64}';
            }
          }
          leaf rp1 {
            type RPLocation;
            description
              "Enter RP Node location";
            mandatory true;
          }
          leaf rp2 {
            type RPLocation;
            description
              "Enter RP Node location";
            mandatory true;
          }
        }
      }
    }
    // NCS drop config false container 'sdr-manager'
    // NCS drop config false container 'sdr-operation'
    container private-sdr {
      tailf:ncs-device-type "netconf";
      tailf:display-when "not(../../ncs:module) or ../../ncs:module[ncs:name='Cisco-IOS-XR-sysadmin-sdr-mgr']";
      list sdr-name {
        min-elements 0;
        max-elements 64;
        key "name";
        leaf name {
          type string;
        }
        leaf id {
          type uint32;
        }
        leaf lead_rack0 {
          type uint32;
        }
        leaf lead_rack1 {
          type uint32;
        }
        list pairing {
          min-elements 0;
          max-elements 64;
          key "num";
          leaf num {
            type uint32;
          }
          leaf second_exist {
            type boolean;
          }
          leaf rp1_rack {
            type uint32;
          }
          leaf rp1_slot {
            type uint32;
          }
          leaf rp2_rack {
            type uint32;
          }
          leaf rp2_slot {
            type uint32;
          }
        }
      }
    }
  }
  augment "/ncs:devices/ncs:device/ncs:live-status" {
    container sdr-config {
      tailf:ncs-device-type "netconf";
      tailf:display-when "not(../../ncs:module) or ../../ncs:module[ncs:name='Cisco-IOS-XR-sysadmin-sdr-mgr'] or (../../ncs:live-status-protocol[not(ncs:capability)]) or (../../ncs:live-status-protocol/ncs:capability/ncs:module[.='Cisco-IOS-XR-sysadmin-sdr-mgr'])";
      list sdr {
        description
          "Add/Edit a Secure Domain Router by name";
        key "name";
        leaf name {
          type string {
            pattern '[a-zA-Z0-9_-]{1,30}';
          }
          description
            "Name of the Secure Domain Router , 30 max characters";
        }
        leaf initial-image {
          type string;
          description
            "List of the initial image and packages for the Secure Domain Router.";
        }
        leaf lead_down_delta {
          type uint32;
          description
            "Amount of time between lead down to declare SDR down";
        }
        leaf pairing-mode {
          type enumeration {
            enum "intra-rack";
            enum "inter-rack";
          }
          description
            "Setting for pairing mode";
        }
        leaf issu {
          type enumeration {
            enum "disable";
          }
          description
            "ISSU flag. Once disabled, ISSU won't be performed for this SDR.";
        }
        container resources {
          description
            "Edit resources for a Secure Domain Router";
          leaf fgid {
            type uint32 {
              range "25000..524288";
            }
            description
              "Fgids for a Secure Domain Router";
          }
          leaf mgmt_ext_vlan {
            type uint32 {
              range "2..4094";
            }
            description
              "Management External VLAN for Secure Domain Router";
          }
          list card-type {
            key "type";
            leaf type {
              type CardType;
              description
                "Card Type";
            }
            leaf vm-memory {
              type uint32 {
                range "1..128";
              }
              description
                "VM Memory Size in units of [GB]";
            }
            leaf vm-cpu {
              type uint32 {
                range "1..128";
              }
              description
                "VM Number of CPUs";
            }
          }
        }
        list location {
          // NCS drop min-elements statement
          // NCS drop max-elements statement
          description
            "Enter list of nodes' location to add to this LR";
          key "node-location";
          leaf node-location {
            type Location;
            description
              "Enter location or all";
          }
          leaf-list slice {
            // NCS drop max-elements statement
            description
              "Enter list of slices to add to this SDR";
            type uint8 {
              range "0 .. 4";
            }
          }
        }
        container Action {
          tailf:action re_pair {
            tailf:actionpoint ncsproxy {
              tailf:internal;
            }
            input;
            output {
              leaf result {
                type string;
                mandatory true;
              }
            }
          }
          list location {
            // NCS drop min-elements statement
            // NCS drop max-elements statement
            key "node-location";
            leaf node-location {
              type VMLocationall;
              description
                "Enter location or all";
            }
            tailf:action reload {
              tailf:actionpoint ncsproxy {
                tailf:internal;
              }
              input {
                choice what_act {
                  case act_force {
                    leaf force {
                      type empty;
                      mandatory false;
                    }
                  }
                  case act_coredump {
                    leaf coredump {
                      type empty;
                      mandatory false;
                    }
                  }
                }
              }
              output {
                leaf result {
                  type string;
                  mandatory true;
                }
              }
            }
            tailf:action shut {
              tailf:actionpoint ncsproxy {
                tailf:internal;
              }
              input;
              output {
                leaf result {
                  type string;
                  mandatory true;
                }
              }
            }
            tailf:action start {
              tailf:actionpoint ncsproxy {
                tailf:internal;
              }
              input;
              output {
                leaf result {
                  type string;
                  mandatory true;
                }
              }
            }
          }
        }
        container detail {
          list location {
            // NCS drop min-elements statement
            // NCS drop max-elements statement
            key "node-location";
            leaf node-location {
              type VMLocation;
            }
            leaf sdr-id {
              type uint32;
            }
            leaf ip-addr {
              type inet:ip-address;
              description
                "IP address of VM";
            }
            leaf mac-address {
              type string;
              description
                "MAC address of VM";
            }
            leaf boot_part {
              type string;
            }
            leaf data_part {
              type string;
            }
            leaf big_disk {
              type string;
            }
            leaf vm_id {
              type uint32;
            }
            leaf vmcpu {
              type uint32;
            }
            leaf vmmemory {
              type uint32;
            }
            leaf card-type {
              type string;
            }
            leaf card_serial {
              type string;
            }
            leaf rack-type {
              type string;
            }
            leaf-list slice {
              type union {
                type uint8;
                type string;
              }
              description
                "Slice numbers if configured";
            }
            leaf chassis_serial {
              type string;
            }
            leaf hw_version {
              type string;
            }
            leaf mgmt_ext_vlan {
              type string;
            }
            leaf state {
              type string;
              description
                "State of VM";
            }
            leaf start-time {
              type string;
            }
            leaf reboot_count {
              type uint32;
              description
                "Number of times rebooted since first boot";
            }
            leaf rh_count {
              type uint32;
              description
                "Number of times rebooted since lasr card reload";
            }
            list reboot_hist1 {
              key "count";
              leaf count {
                type uint32;
              }
              leaf Time {
                type string;
              }
              leaf Reason {
                type string;
                description
                  "Reason for reload";
              }
            }
          }
        }
        container reboot-history {
          container reverse {
            uses rebhist;
          }
          container default-disp {
            uses rebhist;
          }

          grouping rebhist {
            list location {
              // NCS drop min-elements statement
              // NCS drop max-elements statement
              key "node-location";
              leaf node-location {
                type VMLocation;
              }
              leaf reboot_count {
                type uint32;
                description
                  "Number of times rebooted since first boot";
              }
              leaf rh_count {
                type uint32;
                description
                  "Number of times rebooted since last card reload";
              }
              list reboot_hist2 {
                key "count";
                leaf count {
                  type uint32;
                }
                leaf Time {
                  type string;
                }
                leaf Reason {
                  type string;
                  description
                    "Reason for reload";
                }
              }
            }
          }
        }
        container nodes {
          list location {
            // NCS drop min-elements statement
            // NCS drop max-elements statement
            key "node-location";
            leaf node-location {
              type VMLocation;
            }
            leaf sdr-id {
              type uint32;
            }
            leaf ip-addr {
              type inet:ip-address;
              description
                "IP address of VM";
            }
            leaf mac-address {
              type string;
              description
                "MAC address of VM";
            }
            leaf state {
              type string;
              description
                "State of VM";
            }
            leaf start-time {
              type string;
            }
            leaf reload_reason {
              type string;
              description
                "Reason for last reload";
            }
            leaf reboot_count {
              type uint32;
              description
                "Number of times rebooted since first boot";
            }
            leaf rh_count {
              type uint32;
              description
                "Number of times rebooted since first boot";
            }
          }
        }
        container pairing2 {
          leaf pairing-mode {
            type string;
            description
              "Mode of Pairing";
          }
          container sdrlead {
            leaf rp1 {
              type string;
            }
            leaf rp2 {
              type string;
            }
          }
          list pairing {
            // NCS drop min-elements statement
            // NCS drop max-elements statement
            key "name";
            leaf name {
              type string;
            }
            leaf rp1 {
              type string;
            }
            leaf rp2 {
              type string;
            }
          }
        }
        list pairing {
          description
            "Add/Edit a RP Pairing by name";
          key "name";
          leaf name {
            type string {
              pattern '[a-zA-Z0-9_-]{1,64}';
            }
          }
          leaf rp1 {
            type RPLocation;
            description
              "Enter RP Node location";
            // NCS drop mandatory statement
          }
          leaf rp2 {
            type RPLocation;
            description
              "Enter RP Node location";
            // NCS drop mandatory statement
          }
        }
      }
    }
    container sdr-manager {
      tailf:ncs-device-type "netconf";
      tailf:display-when "not(../../ncs:module) or ../../ncs:module[ncs:name='Cisco-IOS-XR-sysadmin-sdr-mgr'] or (../../ncs:live-status-protocol[not(ncs:capability)]) or (../../ncs:live-status-protocol/ncs:capability/ncs:module[.='Cisco-IOS-XR-sysadmin-sdr-mgr'])";
      container sdr_mgr {
        uses show_trace:live_ncs_traceable;
      }
    }
    container sdr-operation {
      tailf:ncs-device-type "netconf";
      tailf:display-when "not(../../ncs:module) or ../../ncs:module[ncs:name='Cisco-IOS-XR-sysadmin-sdr-mgr'] or (../../ncs:live-status-protocol[not(ncs:capability)]) or (../../ncs:live-status-protocol/ncs:capability/ncs:module[.='Cisco-IOS-XR-sysadmin-sdr-mgr'])";
      list sdr {
        description
          "SDR";
        key "name";
        leaf name {
          type string {
            pattern '[a-zA-Z0-9_-]{1,30}';
          }
          description
            "Name of the Secure Domain Router, 30 max characters";
        }
        container nodes {
          list location {
            // NCS drop min-elements statement
            // NCS drop max-elements statement
            key "node-location node-type";
            leaf node-location {
              type string;
            }
            leaf node-type {
              type uint32;
            }
            leaf progress {
              type string;
              description
                "Progress of Operation";
            }
            leaf state {
              type string;
              description
                "State of Operation";
            }
          }
        }
      }
    }
    container private-sdr {
      tailf:ncs-device-type "netconf";
      tailf:display-when "not(../../ncs:module) or ../../ncs:module[ncs:name='Cisco-IOS-XR-sysadmin-sdr-mgr'] or (../../ncs:live-status-protocol[not(ncs:capability)]) or (../../ncs:live-status-protocol/ncs:capability/ncs:module[.='Cisco-IOS-XR-sysadmin-sdr-mgr'])";
      list sdr-name {
        // NCS drop min-elements statement
        // NCS drop max-elements statement
        key "name";
        leaf name {
          type string;
        }
        leaf id {
          type uint32;
        }
        leaf lead_rack0 {
          type uint32;
        }
        leaf lead_rack1 {
          type uint32;
        }
        list pairing {
          // NCS drop min-elements statement
          // NCS drop max-elements statement
          key "num";
          leaf num {
            type uint32;
          }
          leaf second_exist {
            type boolean;
          }
          leaf rp1_rack {
            type uint32;
          }
          leaf rp1_slot {
            type uint32;
          }
          leaf rp2_rack {
            type uint32;
          }
          leaf rp2_slot {
            type uint32;
          }
        }
      }
    }
  }
  augment "/ncs:devices/ncs:template/ncs:ned-id/ncs:config" {
    container sdr-config {
      list sdr {
        // NCS patched for predictable order
        ordered-by user;
        description
          "Add/Edit a Secure Domain Router by name";
        key "name";
        leaf name {
          type string;
          description
            "Name of the Secure Domain Router , 30 max characters";
        }
        leaf initial-image {
          type string;
          description
            "List of the initial image and packages for the Secure Domain Router.";
        }
        leaf lead_down_delta {
          type string;
          description
            "Amount of time between lead down to declare SDR down";
        }
        leaf pairing-mode {
          type string;
          description
            "Setting for pairing mode";
        }
        leaf issu {
          type string;
          description
            "ISSU flag. Once disabled, ISSU won't be performed for this SDR.";
        }
        container resources {
          description
            "Edit resources for a Secure Domain Router";
          leaf fgid {
            type string;
            description
              "Fgids for a Secure Domain Router";
          }
          leaf mgmt_ext_vlan {
            type string;
            description
              "Management External VLAN for Secure Domain Router";
          }
          list card-type {
            // NCS patched for predictable order
            ordered-by user;
            key "type";
            leaf type {
              type string;
              description
                "Card Type";
            }
            leaf vm-memory {
              type string;
              description
                "VM Memory Size in units of [GB]";
            }
            leaf vm-cpu {
              type string;
              description
                "VM Number of CPUs";
            }
          }
        }
        list location {
          // NCS patched for predictable order
          ordered-by user;
          // NCS drop min-elements statement
          // NCS drop max-elements statement
          description
            "Enter list of nodes' location to add to this LR";
          key "node-location";
          leaf node-location {
            type string;
            description
              "Enter location or all";
          }
          leaf-list slice {
            // NCS patched for predictable order
            ordered-by user;
            // NCS drop max-elements statement
            description
              "Enter list of slices to add to this SDR";
            type string;
          }
        }
        // NCS drop config false container 'Action'
        // NCS drop config false container detail
        // NCS drop config false container 'reboot-history'
        // NCS drop config false container nodes
        // NCS drop config false container pairing2
        list pairing {
          // NCS patched for predictable order
          ordered-by user;
          description
            "Add/Edit a RP Pairing by name";
          key "name";
          leaf name {
            type string;
          }
          leaf rp1 {
            type string;
            description
              "Enter RP Node location";
            // NCS drop mandatory statement
          }
          leaf rp2 {
            type string;
            description
              "Enter RP Node location";
            // NCS drop mandatory statement
          }
        }
      }
    }
    // NCS drop config false container 'sdr-manager'
    // NCS drop config false container 'sdr-operation'
    container private-sdr {
      list sdr-name {
        // NCS patched for predictable order
        ordered-by user;
        // NCS drop min-elements statement
        // NCS drop max-elements statement
        key "name";
        leaf name {
          type string;
        }
        leaf id {
          type string;
        }
        leaf lead_rack0 {
          type string;
        }
        leaf lead_rack1 {
          type string;
        }
        list pairing {
          // NCS patched for predictable order
          ordered-by user;
          // NCS drop min-elements statement
          // NCS drop max-elements statement
          key "num";
          leaf num {
            type string;
          }
          leaf second_exist {
            type string;
          }
          leaf rp1_rack {
            type string;
          }
          leaf rp1_slot {
            type string;
          }
          leaf rp2_rack {
            type string;
          }
          leaf rp2_slot {
            type string;
          }
        }
      }
    }
  }
}
