module Cisco-IOS-XR-fpd-infra-cfg {
  // Generated by yanger -t ncs
  tailf:mount-id f5500-nc-1.0:f5500-nc-1.0;
  tailf:ncs-device-type "netconf";

  namespace "http://cisco.com/ns/yang/Cisco-IOS-XR-fpd-infra-cfg";
  prefix Cisco-IOS-XR-fpd-infra-cfg;

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR fpd-infra package configuration.

     This module contains definitions
     for the following management objects:
       fpd: Configuration for fpd auto-upgrade enable/disable

     Copyright (c) 2013-2018 by Cisco Systems, Inc.
     All rights reserved.";

  revision 2015-11-09 {
    description
      "IOS XR 6.0 revision.";
  }

  typedef Auto-upgrade {
    type enumeration {
      enum "disable" {
        value 0;
        description
          "fpd auto-upgrade disable";
      }
      enum "enable" {
        value 1;
        description
          "fpd auto-upgrade enable";
      }
    }
    description
      "Auto upgrade";
  }

  typedef Auto-reload {
    type enumeration {
      enum "disable" {
        value 0;
        description
          "fpd auto-reload disable";
      }
      enum "enable" {
        value 1;
        description
          "fpd auto-reload enable";
      }
    }
    description
      "Auto reload";
  }

  augment "/ncs:devices/ncs:device/ncs:config" {
    container fpd {
      tailf:ncs-device-type "netconf";
      tailf:display-when "not(../../ncs:module) or ../../ncs:module[ncs:name='Cisco-IOS-XR-fpd-infra-cfg']";
      description
        "Configuration for fpd auto-upgrade enable/disable";
      leaf auto-reload {
        type Auto-reload;
        description
          "Variable for fpd auto-reload enable/disable";
      }
      leaf auto-upgrade {
        type Auto-upgrade;
        description
          "Variable for fpd auto-upgrade enable/disable";
      }
    }
  }
  augment "/ncs:devices/ncs:device/ncs:live-status" {
    container fpd {
      tailf:ncs-device-type "netconf";
      tailf:display-when "not(../../ncs:module) or ../../ncs:module[ncs:name='Cisco-IOS-XR-fpd-infra-cfg'] or (../../ncs:live-status-protocol[not(ncs:capability)]) or (../../ncs:live-status-protocol/ncs:capability/ncs:module[.='Cisco-IOS-XR-fpd-infra-cfg'])";
      description
        "Configuration for fpd auto-upgrade enable/disable";
      leaf auto-reload {
        type Auto-reload;
        description
          "Variable for fpd auto-reload enable/disable";
      }
      leaf auto-upgrade {
        type Auto-upgrade;
        description
          "Variable for fpd auto-upgrade enable/disable";
      }
    }
  }
  augment "/ncs:devices/ncs:template/ncs:ned-id/ncs:config" {
    container fpd {
      description
        "Configuration for fpd auto-upgrade enable/disable";
      leaf auto-reload {
        type string;
        description
          "Variable for fpd auto-reload enable/disable";
      }
      leaf auto-upgrade {
        type string;
        description
          "Variable for fpd auto-upgrade enable/disable";
      }
    }
  }
}
