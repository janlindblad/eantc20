module Cisco-IOS-XR-aaa-diameter-oper {
  // Generated by yanger -t ncs
  tailf:mount-id f5500-nc-1.0:f5500-nc-1.0;
  tailf:ncs-device-type "netconf";

  namespace "http://cisco.com/ns/yang/Cisco-IOS-XR-aaa-diameter-oper";
  prefix Cisco-IOS-XR-aaa-diameter-oper;

  import Cisco-IOS-XR-aaa-locald-oper {
    prefix a1;
  }
  include Cisco-IOS-XR-aaa-diameter-oper-sub1 {
    revision-date 2017-09-07;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR aaa-diameter package operational data.

     This YANG module augments the
       Cisco-IOS-XR-aaa-locald-oper
     module with state data.

     Copyright (c) 2013-2018 by Cisco Systems, Inc.
     All rights reserved.";

  revision 2017-09-07 {
    description
      "Fixed type translation error.";
  }
  revision 2015-11-09 {
    description
      "IOS XR 6.0 revision.";
  }

  augment "/ncs:devices/ncs:device/ncs:live-status/a1:aaa" {
    container diameter {
      tailf:ncs-device-type "netconf";
      tailf:display-when "not(../../../ncs:module) or ../../../ncs:module[ncs:name='Cisco-IOS-XR-aaa-diameter-oper'] or (../../../ncs:live-status-protocol[not(ncs:capability)]) or (../../../ncs:live-status-protocol/ncs:capability/ncs:module[.='Cisco-IOS-XR-aaa-diameter-oper'])";
      description
        "Diameter operational data";
      container gy {
        description
          "Diameter global gy data";
        uses live_ncs_DIAMETER-GY;
      }
      container gx-statistics {
        description
          "Diameter Gx Statistics data";
        uses live_ncs_DIAMETER-GX-STATS;
      }
      container gx {
        description
          "Diameter global gx data";
        uses live_ncs_DIAMETER-GX;
      }
      container peers {
        description
          "Diameter peer global data";
        uses live_ncs_DIAMETER-PEERS;
      }
      container nas {
        description
          "Diameter NAS data";
        uses live_ncs_DIAMETER-NAS-LIST;
      }
      container nas-summary {
        description
          "Diameter NAS summary";
        uses live_ncs_DIAMETER-NAS-SUMMARY;
      }
      container gy-session-ids {
        description
          "Diameter Gy Session data list";
        list gy-session-id {
          key "session-id";
          description
            "Diameter Gy Session data";
          leaf session-id {
            type uint32;
            description
              "Session Id";
          }
          uses live_ncs_DIAMETER-GY-SESS;
        }
      }
      container gy-statistics {
        description
          "Diameter Gy Statistics data";
        uses live_ncs_DIAMETER-GY-STATS;
      }
      container gx-session-ids {
        description
          "Diameter Gx Session data list";
        list gx-session-id {
          key "session-id";
          description
            "Diameter Gx Session data";
          leaf session-id {
            type uint32;
            description
              "Session Id";
          }
          uses live_ncs_DIAMETER-GX-SESS;
        }
      }
      container nas-session {
        description
          "Diameter Nas Session data";
        uses live_ncs_DIAMETER-NAS-LIST;
      }
    }
    description
      "This augment extends the operational data of
       'Cisco-IOS-XR-aaa-locald-oper'";
  }
}
