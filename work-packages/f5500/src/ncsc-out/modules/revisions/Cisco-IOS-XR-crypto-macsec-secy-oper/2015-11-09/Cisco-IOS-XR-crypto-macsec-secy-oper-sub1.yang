submodule Cisco-IOS-XR-crypto-macsec-secy-oper-sub1 {
  // Generated by yanger -t ncs
  tailf:mount-id f5500-nc-1.0:f5500-nc-1.0;

  belongs-to Cisco-IOS-XR-crypto-macsec-secy-oper {
    prefix Cisco-IOS-XR-crypto-macsec-secy-oper-sub1;
  }

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR crypto-macsec-secy package operational data.

     Copyright (c) 2013-2018 by Cisco Systems, Inc.
     All rights reserved.";

  revision 2015-11-09 {
    description
      "IOS XR 6.0 revision.";
  }

  grouping ncs_template_MACSEC-RX-SA-STATS {
    description
      "MACSEC RX SA STATS";
    leaf in-pkts-ok {
      type string;
      description
        "InPktsOK";
    }
    leaf in-pkts-invalid {
      type string;
      description
        "InPktsInvalid";
    }
    leaf in-pkts-not-valid {
      type string;
      description
        "InPktsNotValid";
    }
    leaf in-pkts-not-using-sa {
      type string;
      description
        "InPktsNotUsingSA";
    }
    leaf in-pkts-unused-sa {
      type string;
      description
        "InPktsUnusedSA";
    }
    leaf next-pn {
      type string;
      description
        "NextPN";
    }
  }

  grouping ncs_template_MACSEC-RX-SC-STATS {
    description
      "MACSEC RX SC STATS";
    leaf rx-sci {
      type string;
      description
        "Rx SCI";
    }
    leaf in-pkts-unchecked {
      type string;
      description
        "InPktsUnchecked";
    }
    leaf in-pkts-delayed {
      type string;
      description
        "InPktsDelayed";
    }
    leaf in-pkts-late {
      type string;
      description
        "InPktsLate";
    }
    leaf in-pkts-ok {
      type string;
      description
        "InPktsOK";
    }
    leaf in-pkts-invalid {
      type string;
      description
        "InPktsInvalid";
    }
    leaf in-pkts-not-valid {
      type string;
      description
        "InPktsNotValid";
    }
    leaf in-pkts-not-using-sa {
      type string;
      description
        "InPktsNotUsingSA";
    }
    leaf in-pkts-unused-sa {
      type string;
      description
        "InPktsUnusedSA";
    }
    leaf in-pkts-untagged-hit {
      type string;
      description
        "InPktsUntaggedHit";
    }
    leaf in-octets-validated {
      type string;
      description
        "InOctetsValidated";
    }
    leaf in-octets-decrypted {
      type string;
      description
        "InOctetsDecrypted";
    }
    list rxsa-stat {
      // NCS patched for predictable order
      ordered-by user;
      description
        "rxsa stats";
      uses ncs_template_MACSEC-RX-SA-STATS;
    }
  }

  grouping ncs_template_MACSEC-TX-SA-STATS {
    description
      "MACSEC TX SA STATS";
    leaf out-pkts-protected {
      type string;
      description
        "OutPktsProtected";
    }
    leaf out-pkts-encrypted {
      type string;
      description
        "OutPktsEncrypted";
    }
    leaf next-pn {
      type string;
      description
        "NextPN";
    }
  }

  grouping ncs_template_MACSEC-TX-SC-STATS {
    description
      "MACSEC TX SC STATS";
    leaf tx-sci {
      type string;
      description
        "Tx SCI";
    }
    leaf out-pkts-protected {
      type string;
      description
        "OutPktsProtected";
    }
    leaf out-pkts-encrypted {
      type string;
      description
        "OutPktsEncrypted";
    }
    leaf out-octets-protected {
      type string;
      description
        "OutOctetsProtected";
    }
    leaf out-octets-encrypted {
      type string;
      description
        "OutOctetsEncrypted";
    }
    leaf out-pkts-too-long {
      type string;
      description
        "OutPktsTooLong";
    }
    list txsa-stat {
      // NCS patched for predictable order
      ordered-by user;
      description
        "tx sa stats";
      uses ncs_template_MACSEC-TX-SA-STATS;
    }
  }

  grouping ncs_template_MACSEC-IF-STATS {
    description
      "MACSEC IF STATS";
    leaf in-pkts-untagged {
      type string;
      description
        "InPktsUntagged";
    }
    leaf in-pkts-no-tag {
      type string;
      description
        "InPktsNoTag";
    }
    leaf in-pkts-bad-tag {
      type string;
      description
        "InPktsBadTag";
    }
    leaf in-pkts-unknown-sci {
      type string;
      description
        "InPktsUnknownSCI";
    }
    leaf in-pkts-no-sci {
      type string;
      description
        "InPktsNoSCI";
    }
    leaf in-pkts-overrun {
      type string;
      description
        "InPktsOverrun";
    }
    leaf in-octets-validated {
      type string;
      description
        "InOctetsValidated";
    }
    leaf in-octets-decrypted {
      type string;
      description
        "InOctetsDecrypted";
    }
    leaf out-pkts-untagged {
      type string;
      description
        "OutPktsUntagged";
    }
    leaf out-pkts-too-long {
      type string;
      description
        "OutPktsTooLong";
    }
    leaf out-octets-protected {
      type string;
      description
        "OutOctetsProtected";
    }
    leaf out-octets-encrypted {
      type string;
      description
        "OutOctetsEncrypted";
    }
  }

  grouping ncs_template_MACSEC-SECY-STATS {
    description
      "MACSEC SECY STATS";
    container intf-stats {
      description
        "Interface stats";
      uses ncs_template_MACSEC-IF-STATS;
    }
    container tx-sc-stats {
      description
        "Tx SC Stats";
      uses ncs_template_MACSEC-TX-SC-STATS;
    }
    list rx-sc-stats {
      // NCS patched for predictable order
      ordered-by user;
      description
        "RX SC Stats List";
      uses ncs_template_MACSEC-RX-SC-STATS;
    }
  }

  grouping ncs_rpc_notif_MACSEC-RX-SA-STATS {
    description
      "MACSEC RX SA STATS";
    leaf in-pkts-ok {
      type uint64;
      description
        "InPktsOK";
    }
    leaf in-pkts-invalid {
      type uint64;
      description
        "InPktsInvalid";
    }
    leaf in-pkts-not-valid {
      type uint64;
      description
        "InPktsNotValid";
    }
    leaf in-pkts-not-using-sa {
      type uint64;
      description
        "InPktsNotUsingSA";
    }
    leaf in-pkts-unused-sa {
      type uint64;
      description
        "InPktsUnusedSA";
    }
    leaf next-pn {
      type uint64;
      description
        "NextPN";
    }
  }

  grouping ncs_rpc_notif_MACSEC-RX-SC-STATS {
    description
      "MACSEC RX SC STATS";
    leaf rx-sci {
      type uint64;
      description
        "Rx SCI";
    }
    leaf in-pkts-unchecked {
      type uint64;
      description
        "InPktsUnchecked";
    }
    leaf in-pkts-delayed {
      type uint64;
      description
        "InPktsDelayed";
    }
    leaf in-pkts-late {
      type uint64;
      description
        "InPktsLate";
    }
    leaf in-pkts-ok {
      type uint64;
      description
        "InPktsOK";
    }
    leaf in-pkts-invalid {
      type uint64;
      description
        "InPktsInvalid";
    }
    leaf in-pkts-not-valid {
      type uint64;
      description
        "InPktsNotValid";
    }
    leaf in-pkts-not-using-sa {
      type uint64;
      description
        "InPktsNotUsingSA";
    }
    leaf in-pkts-unused-sa {
      type uint64;
      description
        "InPktsUnusedSA";
    }
    leaf in-pkts-untagged-hit {
      type uint64;
      description
        "InPktsUntaggedHit";
    }
    leaf in-octets-validated {
      type uint64;
      description
        "InOctetsValidated";
    }
    leaf in-octets-decrypted {
      type uint64;
      description
        "InOctetsDecrypted";
    }
    list rxsa-stat {
      description
        "rxsa stats";
      uses ncs_rpc_notif_MACSEC-RX-SA-STATS;
    }
  }

  grouping ncs_rpc_notif_MACSEC-TX-SA-STATS {
    description
      "MACSEC TX SA STATS";
    leaf out-pkts-protected {
      type uint64;
      description
        "OutPktsProtected";
    }
    leaf out-pkts-encrypted {
      type uint64;
      description
        "OutPktsEncrypted";
    }
    leaf next-pn {
      type uint64;
      description
        "NextPN";
    }
  }

  grouping ncs_rpc_notif_MACSEC-TX-SC-STATS {
    description
      "MACSEC TX SC STATS";
    leaf tx-sci {
      type uint64;
      description
        "Tx SCI";
    }
    leaf out-pkts-protected {
      type uint64;
      description
        "OutPktsProtected";
    }
    leaf out-pkts-encrypted {
      type uint64;
      description
        "OutPktsEncrypted";
    }
    leaf out-octets-protected {
      type uint64;
      description
        "OutOctetsProtected";
    }
    leaf out-octets-encrypted {
      type uint64;
      description
        "OutOctetsEncrypted";
    }
    leaf out-pkts-too-long {
      type uint64;
      description
        "OutPktsTooLong";
    }
    list txsa-stat {
      description
        "tx sa stats";
      uses ncs_rpc_notif_MACSEC-TX-SA-STATS;
    }
  }

  grouping ncs_rpc_notif_MACSEC-IF-STATS {
    description
      "MACSEC IF STATS";
    leaf in-pkts-untagged {
      type uint64;
      description
        "InPktsUntagged";
    }
    leaf in-pkts-no-tag {
      type uint64;
      description
        "InPktsNoTag";
    }
    leaf in-pkts-bad-tag {
      type uint64;
      description
        "InPktsBadTag";
    }
    leaf in-pkts-unknown-sci {
      type uint64;
      description
        "InPktsUnknownSCI";
    }
    leaf in-pkts-no-sci {
      type uint64;
      description
        "InPktsNoSCI";
    }
    leaf in-pkts-overrun {
      type uint64;
      description
        "InPktsOverrun";
    }
    leaf in-octets-validated {
      type uint64;
      description
        "InOctetsValidated";
    }
    leaf in-octets-decrypted {
      type uint64;
      description
        "InOctetsDecrypted";
    }
    leaf out-pkts-untagged {
      type uint64;
      description
        "OutPktsUntagged";
    }
    leaf out-pkts-too-long {
      type uint64;
      description
        "OutPktsTooLong";
    }
    leaf out-octets-protected {
      type uint64;
      description
        "OutOctetsProtected";
    }
    leaf out-octets-encrypted {
      type uint64;
      description
        "OutOctetsEncrypted";
    }
  }

  grouping ncs_rpc_notif_MACSEC-SECY-STATS {
    description
      "MACSEC SECY STATS";
    container intf-stats {
      description
        "Interface stats";
      uses ncs_rpc_notif_MACSEC-IF-STATS;
    }
    container tx-sc-stats {
      description
        "Tx SC Stats";
      uses ncs_rpc_notif_MACSEC-TX-SC-STATS;
    }
    list rx-sc-stats {
      description
        "RX SC Stats List";
      uses ncs_rpc_notif_MACSEC-RX-SC-STATS;
    }
  }

  grouping live_ncs_MACSEC-RX-SA-STATS {
    description
      "MACSEC RX SA STATS";
    leaf in-pkts-ok {
      type uint64;
      description
        "InPktsOK";
    }
    leaf in-pkts-invalid {
      type uint64;
      description
        "InPktsInvalid";
    }
    leaf in-pkts-not-valid {
      type uint64;
      description
        "InPktsNotValid";
    }
    leaf in-pkts-not-using-sa {
      type uint64;
      description
        "InPktsNotUsingSA";
    }
    leaf in-pkts-unused-sa {
      type uint64;
      description
        "InPktsUnusedSA";
    }
    leaf next-pn {
      type uint64;
      description
        "NextPN";
    }
  }

  grouping live_ncs_MACSEC-RX-SC-STATS {
    description
      "MACSEC RX SC STATS";
    leaf rx-sci {
      type uint64;
      description
        "Rx SCI";
    }
    leaf in-pkts-unchecked {
      type uint64;
      description
        "InPktsUnchecked";
    }
    leaf in-pkts-delayed {
      type uint64;
      description
        "InPktsDelayed";
    }
    leaf in-pkts-late {
      type uint64;
      description
        "InPktsLate";
    }
    leaf in-pkts-ok {
      type uint64;
      description
        "InPktsOK";
    }
    leaf in-pkts-invalid {
      type uint64;
      description
        "InPktsInvalid";
    }
    leaf in-pkts-not-valid {
      type uint64;
      description
        "InPktsNotValid";
    }
    leaf in-pkts-not-using-sa {
      type uint64;
      description
        "InPktsNotUsingSA";
    }
    leaf in-pkts-unused-sa {
      type uint64;
      description
        "InPktsUnusedSA";
    }
    leaf in-pkts-untagged-hit {
      type uint64;
      description
        "InPktsUntaggedHit";
    }
    leaf in-octets-validated {
      type uint64;
      description
        "InOctetsValidated";
    }
    leaf in-octets-decrypted {
      type uint64;
      description
        "InOctetsDecrypted";
    }
    list rxsa-stat {
      description
        "rxsa stats";
      uses live_ncs_MACSEC-RX-SA-STATS;
    }
  }

  grouping live_ncs_MACSEC-TX-SA-STATS {
    description
      "MACSEC TX SA STATS";
    leaf out-pkts-protected {
      type uint64;
      description
        "OutPktsProtected";
    }
    leaf out-pkts-encrypted {
      type uint64;
      description
        "OutPktsEncrypted";
    }
    leaf next-pn {
      type uint64;
      description
        "NextPN";
    }
  }

  grouping live_ncs_MACSEC-TX-SC-STATS {
    description
      "MACSEC TX SC STATS";
    leaf tx-sci {
      type uint64;
      description
        "Tx SCI";
    }
    leaf out-pkts-protected {
      type uint64;
      description
        "OutPktsProtected";
    }
    leaf out-pkts-encrypted {
      type uint64;
      description
        "OutPktsEncrypted";
    }
    leaf out-octets-protected {
      type uint64;
      description
        "OutOctetsProtected";
    }
    leaf out-octets-encrypted {
      type uint64;
      description
        "OutOctetsEncrypted";
    }
    leaf out-pkts-too-long {
      type uint64;
      description
        "OutPktsTooLong";
    }
    list txsa-stat {
      description
        "tx sa stats";
      uses live_ncs_MACSEC-TX-SA-STATS;
    }
  }

  grouping live_ncs_MACSEC-IF-STATS {
    description
      "MACSEC IF STATS";
    leaf in-pkts-untagged {
      type uint64;
      description
        "InPktsUntagged";
    }
    leaf in-pkts-no-tag {
      type uint64;
      description
        "InPktsNoTag";
    }
    leaf in-pkts-bad-tag {
      type uint64;
      description
        "InPktsBadTag";
    }
    leaf in-pkts-unknown-sci {
      type uint64;
      description
        "InPktsUnknownSCI";
    }
    leaf in-pkts-no-sci {
      type uint64;
      description
        "InPktsNoSCI";
    }
    leaf in-pkts-overrun {
      type uint64;
      description
        "InPktsOverrun";
    }
    leaf in-octets-validated {
      type uint64;
      description
        "InOctetsValidated";
    }
    leaf in-octets-decrypted {
      type uint64;
      description
        "InOctetsDecrypted";
    }
    leaf out-pkts-untagged {
      type uint64;
      description
        "OutPktsUntagged";
    }
    leaf out-pkts-too-long {
      type uint64;
      description
        "OutPktsTooLong";
    }
    leaf out-octets-protected {
      type uint64;
      description
        "OutOctetsProtected";
    }
    leaf out-octets-encrypted {
      type uint64;
      description
        "OutOctetsEncrypted";
    }
  }

  grouping live_ncs_MACSEC-SECY-STATS {
    description
      "MACSEC SECY STATS";
    container intf-stats {
      description
        "Interface stats";
      uses live_ncs_MACSEC-IF-STATS;
    }
    container tx-sc-stats {
      description
        "Tx SC Stats";
      uses live_ncs_MACSEC-TX-SC-STATS;
    }
    list rx-sc-stats {
      description
        "RX SC Stats List";
      uses live_ncs_MACSEC-RX-SC-STATS;
    }
  }

  grouping MACSEC-RX-SA-STATS {
    description
      "MACSEC RX SA STATS";
    leaf in-pkts-ok {
      type uint64;
      description
        "InPktsOK";
    }
    leaf in-pkts-invalid {
      type uint64;
      description
        "InPktsInvalid";
    }
    leaf in-pkts-not-valid {
      type uint64;
      description
        "InPktsNotValid";
    }
    leaf in-pkts-not-using-sa {
      type uint64;
      description
        "InPktsNotUsingSA";
    }
    leaf in-pkts-unused-sa {
      type uint64;
      description
        "InPktsUnusedSA";
    }
    leaf next-pn {
      type uint64;
      description
        "NextPN";
    }
  }

  grouping MACSEC-RX-SC-STATS {
    description
      "MACSEC RX SC STATS";
    leaf rx-sci {
      type uint64;
      description
        "Rx SCI";
    }
    leaf in-pkts-unchecked {
      type uint64;
      description
        "InPktsUnchecked";
    }
    leaf in-pkts-delayed {
      type uint64;
      description
        "InPktsDelayed";
    }
    leaf in-pkts-late {
      type uint64;
      description
        "InPktsLate";
    }
    leaf in-pkts-ok {
      type uint64;
      description
        "InPktsOK";
    }
    leaf in-pkts-invalid {
      type uint64;
      description
        "InPktsInvalid";
    }
    leaf in-pkts-not-valid {
      type uint64;
      description
        "InPktsNotValid";
    }
    leaf in-pkts-not-using-sa {
      type uint64;
      description
        "InPktsNotUsingSA";
    }
    leaf in-pkts-unused-sa {
      type uint64;
      description
        "InPktsUnusedSA";
    }
    leaf in-pkts-untagged-hit {
      type uint64;
      description
        "InPktsUntaggedHit";
    }
    leaf in-octets-validated {
      type uint64;
      description
        "InOctetsValidated";
    }
    leaf in-octets-decrypted {
      type uint64;
      description
        "InOctetsDecrypted";
    }
    list rxsa-stat {
      description
        "rxsa stats";
      uses MACSEC-RX-SA-STATS;
    }
  }

  grouping MACSEC-TX-SA-STATS {
    description
      "MACSEC TX SA STATS";
    leaf out-pkts-protected {
      type uint64;
      description
        "OutPktsProtected";
    }
    leaf out-pkts-encrypted {
      type uint64;
      description
        "OutPktsEncrypted";
    }
    leaf next-pn {
      type uint64;
      description
        "NextPN";
    }
  }

  grouping MACSEC-TX-SC-STATS {
    description
      "MACSEC TX SC STATS";
    leaf tx-sci {
      type uint64;
      description
        "Tx SCI";
    }
    leaf out-pkts-protected {
      type uint64;
      description
        "OutPktsProtected";
    }
    leaf out-pkts-encrypted {
      type uint64;
      description
        "OutPktsEncrypted";
    }
    leaf out-octets-protected {
      type uint64;
      description
        "OutOctetsProtected";
    }
    leaf out-octets-encrypted {
      type uint64;
      description
        "OutOctetsEncrypted";
    }
    leaf out-pkts-too-long {
      type uint64;
      description
        "OutPktsTooLong";
    }
    list txsa-stat {
      description
        "tx sa stats";
      uses MACSEC-TX-SA-STATS;
    }
  }

  grouping MACSEC-IF-STATS {
    description
      "MACSEC IF STATS";
    leaf in-pkts-untagged {
      type uint64;
      description
        "InPktsUntagged";
    }
    leaf in-pkts-no-tag {
      type uint64;
      description
        "InPktsNoTag";
    }
    leaf in-pkts-bad-tag {
      type uint64;
      description
        "InPktsBadTag";
    }
    leaf in-pkts-unknown-sci {
      type uint64;
      description
        "InPktsUnknownSCI";
    }
    leaf in-pkts-no-sci {
      type uint64;
      description
        "InPktsNoSCI";
    }
    leaf in-pkts-overrun {
      type uint64;
      description
        "InPktsOverrun";
    }
    leaf in-octets-validated {
      type uint64;
      description
        "InOctetsValidated";
    }
    leaf in-octets-decrypted {
      type uint64;
      description
        "InOctetsDecrypted";
    }
    leaf out-pkts-untagged {
      type uint64;
      description
        "OutPktsUntagged";
    }
    leaf out-pkts-too-long {
      type uint64;
      description
        "OutPktsTooLong";
    }
    leaf out-octets-protected {
      type uint64;
      description
        "OutOctetsProtected";
    }
    leaf out-octets-encrypted {
      type uint64;
      description
        "OutOctetsEncrypted";
    }
  }

  grouping MACSEC-SECY-STATS {
    description
      "MACSEC SECY STATS";
    container intf-stats {
      description
        "Interface stats";
      uses MACSEC-IF-STATS;
    }
    container tx-sc-stats {
      description
        "Tx SC Stats";
      uses MACSEC-TX-SC-STATS;
    }
    list rx-sc-stats {
      description
        "RX SC Stats List";
      uses MACSEC-RX-SC-STATS;
    }
  }
}
