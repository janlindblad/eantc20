module Cisco-IOS-XR-dot1x-oper {
  // Generated by yanger -t ncs
  tailf:mount-id f5500-nc-1.0:f5500-nc-1.0;
  tailf:ncs-device-type "netconf";

  namespace "http://cisco.com/ns/yang/Cisco-IOS-XR-dot1x-oper";
  prefix Cisco-IOS-XR-dot1x-oper;

  import Cisco-IOS-XR-types {
    prefix xr;
  }
  include Cisco-IOS-XR-dot1x-oper-sub1 {
    revision-date 2015-11-09;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR dot1x package operational data.

     This module contains definitions
     for the following management objects:
       dot1x: Dot1x operational data

     Copyright (c) 2013-2018 by Cisco Systems, Inc.
     All rights reserved.";

  revision 2015-11-09 {
    description
      "IOS XR 6.0 revision.";
  }

  augment "/ncs:devices/ncs:device/ncs:config" {
    // NCS drop config false container dot1x
  }
  augment "/ncs:devices/ncs:device/ncs:live-status" {
    container dot1x {
      tailf:ncs-device-type "netconf";
      tailf:display-when "not(../../ncs:module) or ../../ncs:module[ncs:name='Cisco-IOS-XR-dot1x-oper'] or (../../ncs:live-status-protocol[not(ncs:capability)]) or (../../ncs:live-status-protocol/ncs:capability/ncs:module[.='Cisco-IOS-XR-dot1x-oper'])";
      description
        "Dot1x operational data";
      container statistics {
        description
          "Dot1x operational data";
        container interface-statistics {
          description
            "Interfaces with Dot1x";
          list interface-statistic {
            key "name";
            description
              "Dot1x Data for that Interface";
            leaf name {
              type xr:Interface-name;
              description
                "Interface Name";
            }
            uses live_ncs_DOT1X-IF-STATISTICS;
          }
        }
      }
      container nodes {
        description
          "Node-specific Dot1x operational data";
        list node {
          key "node-name";
          description
            "Dot1x operational data for a particular node";
          container dot1x-defaults {
            description
              "Dot1x Default Values";
            uses live_ncs_DOT1X-DEFAULT;
          }
          container statistics {
            description
              "Dot1x Default Values";
            uses live_ncs_DOT1X-STATISTICS;
          }
          leaf node-name {
            type xr:Node-id;
            description
              "The node name";
          }
        }
      }
      container session {
        description
          "Dot1x operational data";
        container interface-sessions {
          description
            "Interfaces with Dot1x";
          list interface-session {
            key "name";
            description
              "Dot1x Data for that Interface";
            leaf name {
              type xr:Interface-name;
              description
                "Interface Name";
            }
            uses live_ncs_DOT1X-INTERFACE-DETAIL;
          }
        }
      }
    }
  }
  augment "/ncs:devices/ncs:template/ncs:ned-id/ncs:config" {
    // NCS drop config false container dot1x
  }
}
