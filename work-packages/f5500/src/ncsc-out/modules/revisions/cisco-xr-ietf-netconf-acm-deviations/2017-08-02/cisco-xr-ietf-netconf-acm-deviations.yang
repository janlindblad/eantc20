module cisco-xr-ietf-netconf-acm-deviations {
  // Generated by yanger -t ncs
  tailf:mount-id f5500-nc-1.0:f5500-nc-1.0;
  tailf:ncs-device-type "netconf";

  prefix cisco-xr-ietf-netconf-acm-deviations;
  namespace "http://cisco.com/ns/yang/cisco-xr-ietf-netconf-acm-deviations";

  import ietf-netconf-acm {
    prefix nacm;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a set of deviations for

     ietf-netconf-acm.yang@2012-02-22

     on Cisco IOS-XR devices.

     Copyright (c) 2016-2017 by Cisco Systems, Inc.
     All rights reserved.";

  revision 2017-08-02 {
    description
      "Initial revision applicable to IOS-XR 6.2.1";
  }

  deviation "/ncs:devices/ncs:template/ncs:ned-id/ncs:config/nacm:nacm/nacm:enable-nacm" {
    deviate not-supported;
  }
  deviation "/ncs:devices/ncs:device/ncs:live-status/nacm:nacm/nacm:enable-nacm" {
    deviate not-supported;
  }
  deviation "/ncs:devices/ncs:device/ncs:config/nacm:nacm/nacm:enable-nacm" {
    deviate not-supported;
  }
  deviation "/ncs:devices/ncs:device/ncs:live-status/nacm:nacm/nacm:denied-notifications" {
    deviate not-supported;
  }
}
