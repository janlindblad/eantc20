module Cisco-IOS-XR-isis-act {
  // Generated by yanger -t ncs
  tailf:mount-id f5500-nc-1.0:f5500-nc-1.0;
  tailf:ncs-device-type "netconf";

  namespace "http://cisco.com/ns/yang/Cisco-IOS-XR-isis-act";
  prefix Cisco-IOS-XR-isis-act;

  import Cisco-IOS-XR-types {
    prefix xr;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ISIS action package configuration.

     Copyright (c) 2016-2018 by Cisco Systems, Inc.
     All rights reserved.";

  revision 2016-06-30 {
    description
      "IOS XR 6.2.1 revision.";
  }

  augment "/ncs:devices/ncs:device/ncs:rpc" {
    container rpc-clear-isis {
      tailf:ncs-device-type "netconf";
      tailf:display-when "not(../../ncs:module) or ../../ncs:module[ncs:name='Cisco-IOS-XR-isis-act']";
      tailf:action clear-isis {
        tailf:actionpoint ncsproxy {
          tailf:internal;
        }
        description
          "Clear IS-IS data structures";
        input {
          container instance {
            description
              "Clear data from single IS-IS instance";
            leaf instance-identifier {
              description
                "IS-IS process instance identifier";
              type string;
            }
          }
          leaf rt-type {
            description
              "Clear data for these route types";
            type enumeration {
              enum "AFI-ALL-MULTICAST" {
                value 0;
              }
              enum "AFI-ALL-SAFI-ALL" {
                value 1;
              }
              enum "AFI-ALL-UNICAST" {
                value 2;
              }
              enum "IPv4-MULTICAST" {
                value 3;
              }
              enum "IPv4-SAFI-ALL" {
                value 4;
              }
              enum "IPv4-UNICAST" {
                value 5;
              }
              enum "IPv6-MULTICAST" {
                value 6;
              }
              enum "IPv6-SAFI-ALL" {
                value 7;
              }
              enum "IPv6-UNICAST" {
                value 8;
              }
            }
          }
          choice route-topology {
            leaf route {
              description
                "Clear IS-IS routes";
              type empty;
            }
            leaf topology {
              description
                "Topology table information";
              type string;
            }
          }
        }
      }
    }
  }
  augment "/ncs:devices/ncs:device-group/ncs:ned-id/ncs:rpc" {
    container rpc-clear-isis {
      tailf:ncs-device-type "netconf";
      tailf:display-when "/ncs:devices/ncs:device[ncs:name=current()/../../../ncs:member]/ncs:module[ncs:name='Cisco-IOS-XR-isis-act']";
      tailf:action clear-isis {
        tailf:actionpoint ncsproxy {
          tailf:internal;
        }
        description
          "Clear IS-IS data structures";
        input {
          container instance {
            description
              "Clear data from single IS-IS instance";
            leaf instance-identifier {
              description
                "IS-IS process instance identifier";
              type string;
            }
          }
          leaf rt-type {
            description
              "Clear data for these route types";
            type enumeration {
              enum "AFI-ALL-MULTICAST" {
                value 0;
              }
              enum "AFI-ALL-SAFI-ALL" {
                value 1;
              }
              enum "AFI-ALL-UNICAST" {
                value 2;
              }
              enum "IPv4-MULTICAST" {
                value 3;
              }
              enum "IPv4-SAFI-ALL" {
                value 4;
              }
              enum "IPv4-UNICAST" {
                value 5;
              }
              enum "IPv6-MULTICAST" {
                value 6;
              }
              enum "IPv6-SAFI-ALL" {
                value 7;
              }
              enum "IPv6-UNICAST" {
                value 8;
              }
            }
          }
          choice route-topology {
            leaf route {
              description
                "Clear IS-IS routes";
              type empty;
            }
            leaf topology {
              description
                "Topology table information";
              type string;
            }
          }
        }
      }
    }
  }
  augment "/ncs:devices/ncs:device/ncs:rpc" {
    container rpc-clear-isis-local-lsp {
      tailf:ncs-device-type "netconf";
      tailf:display-when "not(../../ncs:module) or ../../ncs:module[ncs:name='Cisco-IOS-XR-isis-act']";
      tailf:action clear-isis-local-lsp {
        tailf:actionpoint ncsproxy {
          tailf:internal;
        }
        description
          "Clean and regenerate local LSPs";
        input {
          container instance {
            description
              "Clean and regenerate local LSPs from single IS-IS instance";
            leaf instance-identifier {
              description
                "IS-IS process instance identifier";
              type string;
            }
          }
          leaf local-lsp {
            description
              "Clean and regenerate local LSPs";
            type empty;
          }
        }
      }
    }
  }
  augment "/ncs:devices/ncs:device-group/ncs:ned-id/ncs:rpc" {
    container rpc-clear-isis-local-lsp {
      tailf:ncs-device-type "netconf";
      tailf:display-when "/ncs:devices/ncs:device[ncs:name=current()/../../../ncs:member]/ncs:module[ncs:name='Cisco-IOS-XR-isis-act']";
      tailf:action clear-isis-local-lsp {
        tailf:actionpoint ncsproxy {
          tailf:internal;
        }
        description
          "Clean and regenerate local LSPs";
        input {
          container instance {
            description
              "Clean and regenerate local LSPs from single IS-IS instance";
            leaf instance-identifier {
              description
                "IS-IS process instance identifier";
              type string;
            }
          }
          leaf local-lsp {
            description
              "Clean and regenerate local LSPs";
            type empty;
          }
        }
      }
    }
  }
  augment "/ncs:devices/ncs:device/ncs:rpc" {
    container rpc-clear-isis-dist {
      tailf:ncs-device-type "netconf";
      tailf:display-when "not(../../ncs:module) or ../../ncs:module[ncs:name='Cisco-IOS-XR-isis-act']";
      tailf:action clear-isis-dist {
        tailf:actionpoint ncsproxy {
          tailf:internal;
        }
        description
          "Reset BGP-LS topology distribution";
        input {
          container instance {
            description
              "Reset BGP-LS topology from single IS-IS instance";
            leaf instance-identifier {
              description
                "IS-IS process instance identifier";
              type string;
            }
          }
          leaf distribution {
            description
              "Reset BGP-LS topology distribution";
            type empty;
          }
        }
      }
    }
  }
  augment "/ncs:devices/ncs:device-group/ncs:ned-id/ncs:rpc" {
    container rpc-clear-isis-dist {
      tailf:ncs-device-type "netconf";
      tailf:display-when "/ncs:devices/ncs:device[ncs:name=current()/../../../ncs:member]/ncs:module[ncs:name='Cisco-IOS-XR-isis-act']";
      tailf:action clear-isis-dist {
        tailf:actionpoint ncsproxy {
          tailf:internal;
        }
        description
          "Reset BGP-LS topology distribution";
        input {
          container instance {
            description
              "Reset BGP-LS topology from single IS-IS instance";
            leaf instance-identifier {
              description
                "IS-IS process instance identifier";
              type string;
            }
          }
          leaf distribution {
            description
              "Reset BGP-LS topology distribution";
            type empty;
          }
        }
      }
    }
  }
  augment "/ncs:devices/ncs:device/ncs:rpc" {
    container rpc-clear-isis-stat {
      tailf:ncs-device-type "netconf";
      tailf:display-when "not(../../ncs:module) or ../../ncs:module[ncs:name='Cisco-IOS-XR-isis-act']";
      tailf:action clear-isis-stat {
        tailf:actionpoint ncsproxy {
          tailf:internal;
        }
        description
          "Clear IS-IS protocol statistics";
        input {
          container instance {
            description
              "Clear data from single IS-IS instance";
            leaf instance-identifier {
              description
                "IS-IS process instance identifier";
              type string;
            }
          }
          container statistics {
            description
              "Clear IS-IS protocol statistics";
            leaf interface-name {
              mandatory true;
              description
                "Interface name";
              type xr:Interface-name;
            }
          }
        }
      }
    }
  }
  augment "/ncs:devices/ncs:device-group/ncs:ned-id/ncs:rpc" {
    container rpc-clear-isis-stat {
      tailf:ncs-device-type "netconf";
      tailf:display-when "/ncs:devices/ncs:device[ncs:name=current()/../../../ncs:member]/ncs:module[ncs:name='Cisco-IOS-XR-isis-act']";
      tailf:action clear-isis-stat {
        tailf:actionpoint ncsproxy {
          tailf:internal;
        }
        description
          "Clear IS-IS protocol statistics";
        input {
          container instance {
            description
              "Clear data from single IS-IS instance";
            leaf instance-identifier {
              description
                "IS-IS process instance identifier";
              type string;
            }
          }
          container statistics {
            description
              "Clear IS-IS protocol statistics";
            leaf interface-name {
              mandatory true;
              description
                "Interface name";
              type xr:Interface-name;
            }
          }
        }
      }
    }
  }
  augment "/ncs:devices/ncs:device/ncs:rpc" {
    container rpc-clear-isis-route {
      tailf:ncs-device-type "netconf";
      tailf:display-when "not(../../ncs:module) or ../../ncs:module[ncs:name='Cisco-IOS-XR-isis-act']";
      tailf:action clear-isis-route {
        tailf:actionpoint ncsproxy {
          tailf:internal;
        }
        description
          "Clear IS-IS routes";
        input {
          container instance {
            description
              "Clear data from single IS-IS instance";
            leaf instance-identifier {
              description
                "IS-IS process instance identifier";
              type string;
            }
          }
          leaf route {
            description
              "Clear IS-IS routes";
            type empty;
          }
        }
      }
    }
  }
  augment "/ncs:devices/ncs:device-group/ncs:ned-id/ncs:rpc" {
    container rpc-clear-isis-route {
      tailf:ncs-device-type "netconf";
      tailf:display-when "/ncs:devices/ncs:device[ncs:name=current()/../../../ncs:member]/ncs:module[ncs:name='Cisco-IOS-XR-isis-act']";
      tailf:action clear-isis-route {
        tailf:actionpoint ncsproxy {
          tailf:internal;
        }
        description
          "Clear IS-IS routes";
        input {
          container instance {
            description
              "Clear data from single IS-IS instance";
            leaf instance-identifier {
              description
                "IS-IS process instance identifier";
              type string;
            }
          }
          leaf route {
            description
              "Clear IS-IS routes";
            type empty;
          }
        }
      }
    }
  }
  augment "/ncs:devices/ncs:device/ncs:rpc" {
    container rpc-clear-isis-process {
      tailf:ncs-device-type "netconf";
      tailf:display-when "not(../../ncs:module) or ../../ncs:module[ncs:name='Cisco-IOS-XR-isis-act']";
      tailf:action clear-isis-process {
        tailf:actionpoint ncsproxy {
          tailf:internal;
        }
        description
          "Clear all IS-IS data structures";
        input {
          container instance {
            description
              "Clear data from single IS-IS instance";
            leaf instance-identifier {
              description
                "IS-IS process instance identifier";
              type string;
            }
          }
          leaf process {
            description
              "Clear all IS-IS data structures";
            type empty;
          }
        }
      }
    }
  }
  augment "/ncs:devices/ncs:device-group/ncs:ned-id/ncs:rpc" {
    container rpc-clear-isis-process {
      tailf:ncs-device-type "netconf";
      tailf:display-when "/ncs:devices/ncs:device[ncs:name=current()/../../../ncs:member]/ncs:module[ncs:name='Cisco-IOS-XR-isis-act']";
      tailf:action clear-isis-process {
        tailf:actionpoint ncsproxy {
          tailf:internal;
        }
        description
          "Clear all IS-IS data structures";
        input {
          container instance {
            description
              "Clear data from single IS-IS instance";
            leaf instance-identifier {
              description
                "IS-IS process instance identifier";
              type string;
            }
          }
          leaf process {
            description
              "Clear all IS-IS data structures";
            type empty;
          }
        }
      }
    }
  }
}
