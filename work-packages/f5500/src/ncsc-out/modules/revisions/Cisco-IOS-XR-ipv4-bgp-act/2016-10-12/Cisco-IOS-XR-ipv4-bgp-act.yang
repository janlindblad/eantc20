module Cisco-IOS-XR-ipv4-bgp-act {
  // Generated by yanger -t ncs
  tailf:mount-id f5500-nc-1.0:f5500-nc-1.0;
  tailf:ncs-device-type "netconf";

  namespace "http://cisco.com/ns/yang/Cisco-IOS-XR-ipv4-bgp-act";
  prefix Cisco-IOS-XR-ipv4-bgp-act;

  import Cisco-IOS-XR-types {
    prefix csc;
  }
  import ietf-inet-types {
    prefix inet;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2016-2018 by Cisco Systems, Inc.
     All rights reserved.";

  revision 2016-10-12 {
    description
      "IOS XR 6.2.1 revision.";
  }

  typedef vrf-name {
    type union {
      type enumeration {
        enum "all";
      }
      type string;
    }
  }

  typedef instance-name {
    type union {
      type enumeration {
        enum "all";
      }
      type string;
    }
  }

  typedef vpnv6-safi {
    type enumeration {
      enum "flowspec";
      enum "multicast";
      enum "unicast";
    }
  }

  typedef vpnv4-safi {
    type enumeration {
      enum "flowspec";
      enum "multicast";
      enum "unicast";
    }
  }

  typedef link-state-safi {
    type enumeration {
      enum "link-state";
    }
  }

  typedef l2vpn-safi {
    type enumeration {
      enum "evpn";
      enum "mspw";
      enum "vpls";
      enum "vpws";
    }
  }

  typedef ipv6-safi {
    type enumeration {
      enum "all" {
        description
          "Both unicast and multicast address family modifiers";
      }
      enum "flowspec";
      enum "labeled-unicast";
      enum "multicast";
      enum "mvpn";
      enum "sr-policy";
      enum "unicast";
    }
  }

  typedef ipv4-safi {
    type enumeration {
      enum "all" {
        description
          "Both unicast and multicast address family modifiers";
      }
      enum "flowspec";
      enum "labeled-unicast";
      enum "mdt";
      enum "multicast";
      enum "mvpn";
      enum "rt-filter";
      enum "sr-policy";
      enum "tunnel";
      enum "unicast";
    }
  }

  typedef safi {
    type union {
      type ipv4-safi;
      type ipv6-safi;
      type l2vpn-safi;
      type link-state-safi;
      type vpnv4-safi;
      type vpnv6-safi;
    }
  }

  typedef afi {
    type enumeration {
      enum "all" {
        description
          "Both ipv4 and ipv6 address families";
      }
      enum "ipv4";
      enum "ipv6";
      enum "l2vpn";
      enum "link-state";
      enum "vpnv4";
      enum "vpnv6";
    }
  }

  typedef afi-safi-type {
    type enumeration {
      enum "all-all" {
        description
          "Both unicast and multicast address family modifiers
           of ipv4 and ipv6 address family";
      }
      enum "all-evpn";
      enum "all-flowspec";
      enum "all-labeled-unicast";
      enum "all-mdt";
      enum "all-mspw";
      enum "all-multicast";
      enum "all-mvpn";
      enum "all-rt-filter";
      enum "all-sr-policy";
      enum "all-tunnel";
      enum "all-unicast";
      enum "all-vpls";
      enum "all-vpws";
      enum "ipv4-all" {
        description
          "Both unicast and multicast address family modifiers";
      }
      enum "ipv4-flowspec";
      enum "ipv4-labeled-unicast";
      enum "ipv4-mdt";
      enum "ipv4-multicast";
      enum "ipv4-mvpn";
      enum "ipv4-rt-filter";
      enum "ipv4-sr-policy";
      enum "ipv4-tunnel";
      enum "ipv4-unicast";
      enum "ipv6-all" {
        description
          "Both unicast and multicast address family modifiers";
      }
      enum "ipv6-flowspec";
      enum "ipv6-labeled-unicast";
      enum "ipv6-multicast";
      enum "ipv6-mvpn";
      enum "ipv6-sr-policy";
      enum "ipv6-unicast";
      enum "l2vpn-evpn";
      enum "l2vpn-mspw";
      enum "l2vpn-vpls";
      enum "l2vpn-vpws";
      enum "link-state";
      enum "vpnv4-flowspec";
      enum "vpnv4-multicast";
      enum "vpnv4-unicast";
      enum "vpnv6-flowspec";
      enum "vpnv6-multicast";
      enum "vpnv6-unicast";
    }
  }

  typedef rd-ipv4-address {
    type string {
      pattern '(([0-9]|[1-9][0-9]|1[0-9][0-9]|2[0-4][0-9]|25[0-5])\.){3}([0-9]|[1-9][0-9]|1[0-9][0-9]|2[0-4][0-9]|25[0-5])(:\d+)';
    }
  }

  typedef rd-plain-as {
    type string {
      pattern '(\d+:\d+)';
    }
  }

  typedef rd-two-byte-as {
    type string {
      pattern '(\d+:\d+)';
    }
  }

  typedef rd-four-byte-as {
    type string {
      pattern '(\d+\.\d+:\d+)';
    }
  }

  typedef rd {
    description
      "Route distinguisher";
    type union {
      type rd-four-byte-as;
      type rd-two-byte-as;
      type rd-plain-as;
      type rd-ipv4-address;
    }
  }

  typedef as-plain {
    type uint32 {
      range "65536..4294967295";
    }
  }

  typedef as-four-byte {
    type string {
      pattern '(\d+\.\d+)';
    }
  }

  typedef four-byte-as {
    type union {
      type as-four-byte;
      type as-plain;
    }
  }

  typedef two-byte-as {
    type uint16 {
      range "1..65535";
    }
  }

  typedef as-number {
    description
      "AS number";
    type union {
      type two-byte-as;
      type four-byte-as;
    }
  }

  typedef two-byte {
    type uint16 {
      range "1..65535";
    }
  }

  typedef ipv6-netmask {
    type inet:ipv6-address;
  }

  typedef ipv4-netmask {
    type inet:ipv4-address;
  }

  typedef ip-netmask {
    type inet:ip-address;
  }

  typedef refresh-sub-group-id {
    type string {
      pattern '(([0-9]|1[0-5])\.\d+)(:\d+)';
    }
  }

  typedef update-group-id {
    type string {
      pattern '(([0-9]|1[0-5])\.\d+)';
    }
  }

  augment "/ncs:devices/ncs:device/ncs:rpc" {
    container rpc-clear-bgp-vrf-update-outq-update-group {
      tailf:ncs-device-type "netconf";
      tailf:display-when "not(../../ncs:module) or ../../ncs:module[ncs:name='Cisco-IOS-XR-ipv4-bgp-act']";
      tailf:action clear-bgp-vrf-update-outq-update-group {
        tailf:actionpoint ncsproxy {
          tailf:internal;
        }
        csc:xr-task "bgp";
        csc:cli-command "clear bgp vrf <vrf-all> update outq update-group <update-group>";
        description
          "Specify a VRF.
           Clear Update information (Do NOT execute without cisco support)(cisco-support).
           Clear Update generation OutQ counters (Do NOT execute without cisco support)(cisco-support).
           Update-group.
          ";
        input {
          leaf vrf-all {
            mandatory true;
            type vrf-name;
            description
              "VRF name or all";
          }
          leaf update-group {
            mandatory true;
            type update-group-id;
            description
              "Update-group process ID <x.y>";
          }
        }
      }
    }
  }
  augment "/ncs:devices/ncs:device-group/ncs:ned-id/ncs:rpc" {
    container rpc-clear-bgp-vrf-update-outq-update-group {
      tailf:ncs-device-type "netconf";
      tailf:display-when "/ncs:devices/ncs:device[ncs:name=current()/../../../ncs:member]/ncs:module[ncs:name='Cisco-IOS-XR-ipv4-bgp-act']";
      tailf:action clear-bgp-vrf-update-outq-update-group {
        tailf:actionpoint ncsproxy {
          tailf:internal;
        }
        csc:xr-task "bgp";
        csc:cli-command "clear bgp vrf <vrf-all> update outq update-group <update-group>";
        description
          "Specify a VRF.
           Clear Update information (Do NOT execute without cisco support)(cisco-support).
           Clear Update generation OutQ counters (Do NOT execute without cisco support)(cisco-support).
           Update-group.
          ";
        input {
          leaf vrf-all {
            mandatory true;
            type vrf-name;
            description
              "VRF name or all";
          }
          leaf update-group {
            mandatory true;
            type update-group-id;
            description
              "Update-group process ID <x.y>";
          }
        }
      }
    }
  }
  augment "/ncs:devices/ncs:device/ncs:rpc" {
    container rpc-clear-bgp-vrf-update-outq-update-group-update-parent {
      tailf:ncs-device-type "netconf";
      tailf:display-when "not(../../ncs:module) or ../../ncs:module[ncs:name='Cisco-IOS-XR-ipv4-bgp-act']";
      tailf:action clear-bgp-vrf-update-outq-update-group-update-parent {
        tailf:actionpoint ncsproxy {
          tailf:internal;
        }
        csc:xr-task "bgp";
        csc:cli-command "clear bgp vrf <vrf-all> update outq update-group <update-group> update-parent";
        description
          "Specify a VRF.
           Clear Update information (Do NOT execute without cisco support)(cisco-support).
           Clear Update generation OutQ counters (Do NOT execute without cisco support)(cisco-support).
           Update-group.
           Update parents' OutQ counters too.
          ";
        input {
          leaf vrf-all {
            mandatory true;
            type vrf-name;
            description
              "VRF name or all";
          }
          leaf update-group {
            mandatory true;
            type update-group-id;
            description
              "Update-group process ID <x.y>";
          }
        }
      }
    }
  }
  augment "/ncs:devices/ncs:device-group/ncs:ned-id/ncs:rpc" {
    container rpc-clear-bgp-vrf-update-outq-update-group-update-parent {
      tailf:ncs-device-type "netconf";
      tailf:display-when "/ncs:devices/ncs:device[ncs:name=current()/../../../ncs:member]/ncs:module[ncs:name='Cisco-IOS-XR-ipv4-bgp-act']";
      tailf:action clear-bgp-vrf-update-outq-update-group-update-parent {
        tailf:actionpoint ncsproxy {
          tailf:internal;
        }
        csc:xr-task "bgp";
        csc:cli-command "clear bgp vrf <vrf-all> update outq update-group <update-group> update-parent";
        description
          "Specify a VRF.
           Clear Update information (Do NOT execute without cisco support)(cisco-support).
           Clear Update generation OutQ counters (Do NOT execute without cisco support)(cisco-support).
           Update-group.
           Update parents' OutQ counters too.
          ";
        input {
          leaf vrf-all {
            mandatory true;
            type vrf-name;
            description
              "VRF name or all";
          }
          leaf update-group {
            mandatory true;
            type update-group-id;
            description
              "Update-group process ID <x.y>";
          }
        }
      }
    }
  }
  augment "/ncs:devices/ncs:device/ncs:rpc" {
    container rpc-clear-bgp-vrf-update-outq-update-group-sub-group-refresh-sub-group {
      tailf:ncs-device-type "netconf";
      tailf:display-when "not(../../ncs:module) or ../../ncs:module[ncs:name='Cisco-IOS-XR-ipv4-bgp-act']";
      tailf:action clear-bgp-vrf-update-outq-update-group-sub-group-refresh-sub-group {
        tailf:actionpoint ncsproxy {
          tailf:internal;
        }
        csc:xr-task "bgp";
        csc:cli-command "clear bgp vrf <vrf-all> update outq update-group <update-group> sub-group <refresh-sub-group>";
        description
          "Specify a VRF.
           Clear Update information (Do NOT execute without cisco support)(cisco-support).
           Clear Update generation OutQ counters (Do NOT execute without cisco support)(cisco-support).
           Update-group.
           Sub-group.
          ";
        input {
          leaf vrf-all {
            mandatory true;
            type vrf-name;
            description
              "VRF name or all";
          }
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device-group/ncs:ned-id/ncs:rpc" {
    container rpc-clear-bgp-vrf-update-outq-update-group-sub-group-refresh-sub-group {
      tailf:ncs-device-type "netconf";
      tailf:display-when "/ncs:devices/ncs:device[ncs:name=current()/../../../ncs:member]/ncs:module[ncs:name='Cisco-IOS-XR-ipv4-bgp-act']";
      tailf:action clear-bgp-vrf-update-outq-update-group-sub-group-refresh-sub-group {
        tailf:actionpoint ncsproxy {
          tailf:internal;
        }
        csc:xr-task "bgp";
        csc:cli-command "clear bgp vrf <vrf-all> update outq update-group <update-group> sub-group <refresh-sub-group>";
        description
          "Specify a VRF.
           Clear Update information (Do NOT execute without cisco support)(cisco-support).
           Clear Update generation OutQ counters (Do NOT execute without cisco support)(cisco-support).
           Update-group.
           Sub-group.
          ";
        input {
          leaf vrf-all {
            mandatory true;
            type vrf-name;
            description
              "VRF name or all";
          }
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device/ncs:rpc" {
    container rpc-clear-bgp-vrf-update-outq-update-group-sub-group-refresh-sub-group-update-parent {
      tailf:ncs-device-type "netconf";
      tailf:display-when "not(../../ncs:module) or ../../ncs:module[ncs:name='Cisco-IOS-XR-ipv4-bgp-act']";
      tailf:action clear-bgp-vrf-update-outq-update-group-sub-group-refresh-sub-group-update-parent {
        tailf:actionpoint ncsproxy {
          tailf:internal;
        }
        csc:xr-task "bgp";
        csc:cli-command "clear bgp vrf <vrf-all> update outq update-group <update-group> sub-group <refresh-sub-group> update-parent";
        description
          "Specify a VRF.
           Clear Update information (Do NOT execute without cisco support)(cisco-support).
           Clear Update generation OutQ counters (Do NOT execute without cisco support)(cisco-support).
           Update-group.
           Sub-group.
           Update parents' OutQ counters too.
          ";
        input {
          leaf vrf-all {
            mandatory true;
            type vrf-name;
            description
              "VRF name or all";
          }
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device-group/ncs:ned-id/ncs:rpc" {
    container rpc-clear-bgp-vrf-update-outq-update-group-sub-group-refresh-sub-group-update-parent {
      tailf:ncs-device-type "netconf";
      tailf:display-when "/ncs:devices/ncs:device[ncs:name=current()/../../../ncs:member]/ncs:module[ncs:name='Cisco-IOS-XR-ipv4-bgp-act']";
      tailf:action clear-bgp-vrf-update-outq-update-group-sub-group-refresh-sub-group-update-parent {
        tailf:actionpoint ncsproxy {
          tailf:internal;
        }
        csc:xr-task "bgp";
        csc:cli-command "clear bgp vrf <vrf-all> update outq update-group <update-group> sub-group <refresh-sub-group> update-parent";
        description
          "Specify a VRF.
           Clear Update information (Do NOT execute without cisco support)(cisco-support).
           Clear Update generation OutQ counters (Do NOT execute without cisco support)(cisco-support).
           Update-group.
           Sub-group.
           Update parents' OutQ counters too.
          ";
        input {
          leaf vrf-all {
            mandatory true;
            type vrf-name;
            description
              "VRF name or all";
          }
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device/ncs:rpc" {
    container rpc-clear-bgp-vrf-update-outq-update-group-sub-group {
      tailf:ncs-device-type "netconf";
      tailf:display-when "not(../../ncs:module) or ../../ncs:module[ncs:name='Cisco-IOS-XR-ipv4-bgp-act']";
      tailf:action clear-bgp-vrf-update-outq-update-group-sub-group {
        tailf:actionpoint ncsproxy {
          tailf:internal;
        }
        csc:xr-task "bgp";
        csc:cli-command "clear bgp vrf <vrf-all> update outq update-group <update-group> sub-group <sub-group>";
        description
          "Specify a VRF.
           Clear Update information (Do NOT execute without cisco support)(cisco-support).
           Clear Update generation OutQ counters (Do NOT execute without cisco support)(cisco-support).
           Update-group.
           Sub-group.
          ";
        input {
          leaf vrf-all {
            mandatory true;
            type vrf-name;
            description
              "VRF name or all";
          }
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device-group/ncs:ned-id/ncs:rpc" {
    container rpc-clear-bgp-vrf-update-outq-update-group-sub-group {
      tailf:ncs-device-type "netconf";
      tailf:display-when "/ncs:devices/ncs:device[ncs:name=current()/../../../ncs:member]/ncs:module[ncs:name='Cisco-IOS-XR-ipv4-bgp-act']";
      tailf:action clear-bgp-vrf-update-outq-update-group-sub-group {
        tailf:actionpoint ncsproxy {
          tailf:internal;
        }
        csc:xr-task "bgp";
        csc:cli-command "clear bgp vrf <vrf-all> update outq update-group <update-group> sub-group <sub-group>";
        description
          "Specify a VRF.
           Clear Update information (Do NOT execute without cisco support)(cisco-support).
           Clear Update generation OutQ counters (Do NOT execute without cisco support)(cisco-support).
           Update-group.
           Sub-group.
          ";
        input {
          leaf vrf-all {
            mandatory true;
            type vrf-name;
            description
              "VRF name or all";
          }
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device/ncs:rpc" {
    container rpc-clear-bgp-vrf-update-outq-update-group-sub-group-update-parent {
      tailf:ncs-device-type "netconf";
      tailf:display-when "not(../../ncs:module) or ../../ncs:module[ncs:name='Cisco-IOS-XR-ipv4-bgp-act']";
      tailf:action clear-bgp-vrf-update-outq-update-group-sub-group-update-parent {
        tailf:actionpoint ncsproxy {
          tailf:internal;
        }
        csc:xr-task "bgp";
        csc:cli-command "clear bgp vrf <vrf-all> update outq update-group <update-group> sub-group <sub-group> update-parent";
        description
          "Specify a VRF.
           Clear Update information (Do NOT execute without cisco support)(cisco-support).
           Clear Update generation OutQ counters (Do NOT execute without cisco support)(cisco-support).
           Update-group.
           Sub-group.
           Update parents' OutQ counters too.
          ";
        input {
          leaf vrf-all {
            mandatory true;
            type vrf-name;
            description
              "VRF name or all";
          }
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device-group/ncs:ned-id/ncs:rpc" {
    container rpc-clear-bgp-vrf-update-outq-update-group-sub-group-update-parent {
      tailf:ncs-device-type "netconf";
      tailf:display-when "/ncs:devices/ncs:device[ncs:name=current()/../../../ncs:member]/ncs:module[ncs:name='Cisco-IOS-XR-ipv4-bgp-act']";
      tailf:action clear-bgp-vrf-update-outq-update-group-sub-group-update-parent {
        tailf:actionpoint ncsproxy {
          tailf:internal;
        }
        csc:xr-task "bgp";
        csc:cli-command "clear bgp vrf <vrf-all> update outq update-group <update-group> sub-group <sub-group> update-parent";
        description
          "Specify a VRF.
           Clear Update information (Do NOT execute without cisco support)(cisco-support).
           Clear Update generation OutQ counters (Do NOT execute without cisco support)(cisco-support).
           Update-group.
           Sub-group.
           Update parents' OutQ counters too.
          ";
        input {
          leaf vrf-all {
            mandatory true;
            type vrf-name;
            description
              "VRF name or all";
          }
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device/ncs:rpc" {
    container rpc-clear-bgp-vrf-update-outq-neighbor-ip-addr {
      tailf:ncs-device-type "netconf";
      tailf:display-when "not(../../ncs:module) or ../../ncs:module[ncs:name='Cisco-IOS-XR-ipv4-bgp-act']";
      tailf:action clear-bgp-vrf-update-outq-neighbor-ip-addr {
        tailf:actionpoint ncsproxy {
          tailf:internal;
        }
        csc:xr-task "bgp";
        csc:cli-command "clear bgp vrf <vrf-all> update outq neighbor <ip-addr>";
        description
          "Specify a VRF.
           Clear Update information (Do NOT execute without cisco support)(cisco-support).
           Clear Update generation OutQ counters (Do NOT execute without cisco support)(cisco-support).
           Neighbor.
          ";
        input {
          leaf vrf-all {
            mandatory true;
            type vrf-name;
            description
              "VRF name or all";
          }
          leaf ip-addr {
            mandatory true;
            type inet:ip-address;
            description
              "Neighbor address";
          }
        }
      }
    }
  }
  augment "/ncs:devices/ncs:device-group/ncs:ned-id/ncs:rpc" {
    container rpc-clear-bgp-vrf-update-outq-neighbor-ip-addr {
      tailf:ncs-device-type "netconf";
      tailf:display-when "/ncs:devices/ncs:device[ncs:name=current()/../../../ncs:member]/ncs:module[ncs:name='Cisco-IOS-XR-ipv4-bgp-act']";
      tailf:action clear-bgp-vrf-update-outq-neighbor-ip-addr {
        tailf:actionpoint ncsproxy {
          tailf:internal;
        }
        csc:xr-task "bgp";
        csc:cli-command "clear bgp vrf <vrf-all> update outq neighbor <ip-addr>";
        description
          "Specify a VRF.
           Clear Update information (Do NOT execute without cisco support)(cisco-support).
           Clear Update generation OutQ counters (Do NOT execute without cisco support)(cisco-support).
           Neighbor.
          ";
        input {
          leaf vrf-all {
            mandatory true;
            type vrf-name;
            description
              "VRF name or all";
          }
          leaf ip-addr {
            mandatory true;
            type inet:ip-address;
            description
              "Neighbor address";
          }
        }
      }
    }
  }
  augment "/ncs:devices/ncs:device/ncs:rpc" {
    container rpc-clear-bgp-vrf-update-outq-neighbor-ip-addr-update-parent {
      tailf:ncs-device-type "netconf";
      tailf:display-when "not(../../ncs:module) or ../../ncs:module[ncs:name='Cisco-IOS-XR-ipv4-bgp-act']";
      tailf:action clear-bgp-vrf-update-outq-neighbor-ip-addr-update-parent {
        tailf:actionpoint ncsproxy {
          tailf:internal;
        }
        csc:xr-task "bgp";
        csc:cli-command "clear bgp vrf <vrf-all> update outq neighbor <ip-addr> update-parent";
        description
          "Specify a VRF.
           Clear Update information (Do NOT execute without cisco support)(cisco-support).
           Clear Update generation OutQ counters (Do NOT execute without cisco support)(cisco-support).
           Neighbor.
           Update parents' OutQ counters too.
          ";
        input {
          leaf vrf-all {
            mandatory true;
            type vrf-name;
            description
              "VRF name or all";
          }
          leaf ip-addr {
            mandatory true;
            type inet:ip-address;
            description
              "Neighbor address";
          }
        }
      }
    }
  }
  augment "/ncs:devices/ncs:device-group/ncs:ned-id/ncs:rpc" {
    container rpc-clear-bgp-vrf-update-outq-neighbor-ip-addr-update-parent {
      tailf:ncs-device-type "netconf";
      tailf:display-when "/ncs:devices/ncs:device[ncs:name=current()/../../../ncs:member]/ncs:module[ncs:name='Cisco-IOS-XR-ipv4-bgp-act']";
      tailf:action clear-bgp-vrf-update-outq-neighbor-ip-addr-update-parent {
        tailf:actionpoint ncsproxy {
          tailf:internal;
        }
        csc:xr-task "bgp";
        csc:cli-command "clear bgp vrf <vrf-all> update outq neighbor <ip-addr> update-parent";
        description
          "Specify a VRF.
           Clear Update information (Do NOT execute without cisco support)(cisco-support).
           Clear Update generation OutQ counters (Do NOT execute without cisco support)(cisco-support).
           Neighbor.
           Update parents' OutQ counters too.
          ";
        input {
          leaf vrf-all {
            mandatory true;
            type vrf-name;
            description
              "VRF name or all";
          }
          leaf ip-addr {
            mandatory true;
            type inet:ip-address;
            description
              "Neighbor address";
          }
        }
      }
    }
  }
  augment "/ncs:devices/ncs:device/ncs:rpc" {
    container rpc-clear-bgp-vrf-update-outq-neighbor-ip-addr-refresh {
      tailf:ncs-device-type "netconf";
      tailf:display-when "not(../../ncs:module) or ../../ncs:module[ncs:name='Cisco-IOS-XR-ipv4-bgp-act']";
      tailf:action clear-bgp-vrf-update-outq-neighbor-ip-addr-refresh {
        tailf:actionpoint ncsproxy {
          tailf:internal;
        }
        csc:xr-task "bgp";
        csc:cli-command "clear bgp vrf <vrf-all> update outq neighbor <ip-addr> refresh";
        description
          "Specify a VRF.
           Clear Update information (Do NOT execute without cisco support)(cisco-support).
           Clear Update generation OutQ counters (Do NOT execute without cisco support)(cisco-support).
           Neighbor.
           Refresh OutQ.
          ";
        input {
          leaf vrf-all {
            mandatory true;
            type vrf-name;
            description
              "VRF name or all";
          }
          leaf ip-addr {
            mandatory true;
            type inet:ip-address;
            description
              "Neighbor address";
          }
        }
      }
    }
  }
  augment "/ncs:devices/ncs:device-group/ncs:ned-id/ncs:rpc" {
    container rpc-clear-bgp-vrf-update-outq-neighbor-ip-addr-refresh {
      tailf:ncs-device-type "netconf";
      tailf:display-when "/ncs:devices/ncs:device[ncs:name=current()/../../../ncs:member]/ncs:module[ncs:name='Cisco-IOS-XR-ipv4-bgp-act']";
      tailf:action clear-bgp-vrf-update-outq-neighbor-ip-addr-refresh {
        tailf:actionpoint ncsproxy {
          tailf:internal;
        }
        csc:xr-task "bgp";
        csc:cli-command "clear bgp vrf <vrf-all> update outq neighbor <ip-addr> refresh";
        description
          "Specify a VRF.
           Clear Update information (Do NOT execute without cisco support)(cisco-support).
           Clear Update generation OutQ counters (Do NOT execute without cisco support)(cisco-support).
           Neighbor.
           Refresh OutQ.
          ";
        input {
          leaf vrf-all {
            mandatory true;
            type vrf-name;
            description
              "VRF name or all";
          }
          leaf ip-addr {
            mandatory true;
            type inet:ip-address;
            description
              "Neighbor address";
          }
        }
      }
    }
  }
  augment "/ncs:devices/ncs:device/ncs:rpc" {
    container rpc-clear-bgp-vrf-update-outq-neighbor-ip-addr-refresh-update-parent {
      tailf:ncs-device-type "netconf";
      tailf:display-when "not(../../ncs:module) or ../../ncs:module[ncs:name='Cisco-IOS-XR-ipv4-bgp-act']";
      tailf:action clear-bgp-vrf-update-outq-neighbor-ip-addr-refresh-update-parent {
        tailf:actionpoint ncsproxy {
          tailf:internal;
        }
        csc:xr-task "bgp";
        csc:cli-command "clear bgp vrf <vrf-all> update outq neighbor <ip-addr> refresh update-parent";
        description
          "Specify a VRF.
           Clear Update information (Do NOT execute without cisco support)(cisco-support).
           Clear Update generation OutQ counters (Do NOT execute without cisco support)(cisco-support).
           Neighbor.
           Refresh OutQ.
           Update parents' OutQ counters too.
          ";
        input {
          leaf vrf-all {
            mandatory true;
            type vrf-name;
            description
              "VRF name or all";
          }
          leaf ip-addr {
            mandatory true;
            type inet:ip-address;
            description
              "Neighbor address";
          }
        }
      }
    }
  }
  augment "/ncs:devices/ncs:device-group/ncs:ned-id/ncs:rpc" {
    container rpc-clear-bgp-vrf-update-outq-neighbor-ip-addr-refresh-update-parent {
      tailf:ncs-device-type "netconf";
      tailf:display-when "/ncs:devices/ncs:device[ncs:name=current()/../../../ncs:member]/ncs:module[ncs:name='Cisco-IOS-XR-ipv4-bgp-act']";
      tailf:action clear-bgp-vrf-update-outq-neighbor-ip-addr-refresh-update-parent {
        tailf:actionpoint ncsproxy {
          tailf:internal;
        }
        csc:xr-task "bgp";
        csc:cli-command "clear bgp vrf <vrf-all> update outq neighbor <ip-addr> refresh update-parent";
        description
          "Specify a VRF.
           Clear Update information (Do NOT execute without cisco support)(cisco-support).
           Clear Update generation OutQ counters (Do NOT execute without cisco support)(cisco-support).
           Neighbor.
           Refresh OutQ.
           Update parents' OutQ counters too.
          ";
        input {
          leaf vrf-all {
            mandatory true;
            type vrf-name;
            description
              "VRF name or all";
          }
          leaf ip-addr {
            mandatory true;
            type inet:ip-address;
            description
              "Neighbor address";
          }
        }
      }
    }
  }
  augment "/ncs:devices/ncs:device/ncs:rpc" {
    container rpc-clear-bgp-vrf-update-outq-address-family {
      tailf:ncs-device-type "netconf";
      tailf:display-when "not(../../ncs:module) or ../../ncs:module[ncs:name='Cisco-IOS-XR-ipv4-bgp-act']";
      tailf:action clear-bgp-vrf-update-outq-address-family {
        tailf:actionpoint ncsproxy {
          tailf:internal;
        }
        csc:xr-task "bgp";
        csc:cli-command "clear bgp vrf <vrf-all> update outq address-family";
        description
          "Specify a VRF.
           Clear Update information (Do NOT execute without cisco support)(cisco-support).
           Clear Update generation OutQ counters (Do NOT execute without cisco support)(cisco-support).
           Address-family.
          ";
        input {
          leaf vrf-all {
            mandatory true;
            type vrf-name;
            description
              "VRF name or all";
          }
        }
      }
    }
  }
  augment "/ncs:devices/ncs:device-group/ncs:ned-id/ncs:rpc" {
    container rpc-clear-bgp-vrf-update-outq-address-family {
      tailf:ncs-device-type "netconf";
      tailf:display-when "/ncs:devices/ncs:device[ncs:name=current()/../../../ncs:member]/ncs:module[ncs:name='Cisco-IOS-XR-ipv4-bgp-act']";
      tailf:action clear-bgp-vrf-update-outq-address-family {
        tailf:actionpoint ncsproxy {
          tailf:internal;
        }
        csc:xr-task "bgp";
        csc:cli-command "clear bgp vrf <vrf-all> update outq address-family";
        description
          "Specify a VRF.
           Clear Update information (Do NOT execute without cisco support)(cisco-support).
           Clear Update generation OutQ counters (Do NOT execute without cisco support)(cisco-support).
           Address-family.
          ";
        input {
          leaf vrf-all {
            mandatory true;
            type vrf-name;
            description
              "VRF name or all";
          }
        }
      }
    }
  }
  augment "/ncs:devices/ncs:device/ncs:rpc" {
    container rpc-clear-bgp-vrf-update-outq-address-family-update-parent {
      tailf:ncs-device-type "netconf";
      tailf:display-when "not(../../ncs:module) or ../../ncs:module[ncs:name='Cisco-IOS-XR-ipv4-bgp-act']";
      tailf:action clear-bgp-vrf-update-outq-address-family-update-parent {
        tailf:actionpoint ncsproxy {
          tailf:internal;
        }
        csc:xr-task "bgp";
        csc:cli-command "clear bgp vrf <vrf-all> update outq address-family update-parent";
        description
          "Specify a VRF.
           Clear Update information (Do NOT execute without cisco support)(cisco-support).
           Clear Update generation OutQ counters (Do NOT execute without cisco support)(cisco-support).
           Address-family.
           Update parents' OutQ counters too.
          ";
        input {
          leaf vrf-all {
            mandatory true;
            type vrf-name;
            description
              "VRF name or all";
          }
        }
      }
    }
  }
  augment "/ncs:devices/ncs:device-group/ncs:ned-id/ncs:rpc" {
    container rpc-clear-bgp-vrf-update-outq-address-family-update-parent {
      tailf:ncs-device-type "netconf";
      tailf:display-when "/ncs:devices/ncs:device[ncs:name=current()/../../../ncs:member]/ncs:module[ncs:name='Cisco-IOS-XR-ipv4-bgp-act']";
      tailf:action clear-bgp-vrf-update-outq-address-family-update-parent {
        tailf:actionpoint ncsproxy {
          tailf:internal;
        }
        csc:xr-task "bgp";
        csc:cli-command "clear bgp vrf <vrf-all> update outq address-family update-parent";
        description
          "Specify a VRF.
           Clear Update information (Do NOT execute without cisco support)(cisco-support).
           Clear Update generation OutQ counters (Do NOT execute without cisco support)(cisco-support).
           Address-family.
           Update parents' OutQ counters too.
          ";
        input {
          leaf vrf-all {
            mandatory true;
            type vrf-name;
            description
              "VRF name or all";
          }
        }
      }
    }
  }
  augment "/ncs:devices/ncs:device/ncs:rpc" {
    container rpc-clear-bgp-vrf-shutdown {
      tailf:ncs-device-type "netconf";
      tailf:display-when "not(../../ncs:module) or ../../ncs:module[ncs:name='Cisco-IOS-XR-ipv4-bgp-act']";
      tailf:action clear-bgp-vrf-shutdown {
        tailf:actionpoint ncsproxy {
          tailf:internal;
        }
        csc:xr-task "bgp";
        csc:cli-command "clear bgp vrf <vrf-all> shutdown";
        description
          "Specify a VRF.
           Clear all peers which were shut down due to low memory.
          ";
        input {
          leaf vrf-all {
            mandatory true;
            type vrf-name;
            description
              "VRF name or all";
          }
        }
      }
    }
  }
  augment "/ncs:devices/ncs:device-group/ncs:ned-id/ncs:rpc" {
    container rpc-clear-bgp-vrf-shutdown {
      tailf:ncs-device-type "netconf";
      tailf:display-when "/ncs:devices/ncs:device[ncs:name=current()/../../../ncs:member]/ncs:module[ncs:name='Cisco-IOS-XR-ipv4-bgp-act']";
      tailf:action clear-bgp-vrf-shutdown {
        tailf:actionpoint ncsproxy {
          tailf:internal;
        }
        csc:xr-task "bgp";
        csc:cli-command "clear bgp vrf <vrf-all> shutdown";
        description
          "Specify a VRF.
           Clear all peers which were shut down due to low memory.
          ";
        input {
          leaf vrf-all {
            mandatory true;
            type vrf-name;
            description
              "VRF name or all";
          }
        }
      }
    }
  }
  augment "/ncs:devices/ncs:device/ncs:rpc" {
    container rpc-clear-bgp-vrf-performance-statistics {
      tailf:ncs-device-type "netconf";
      tailf:display-when "not(../../ncs:module) or ../../ncs:module[ncs:name='Cisco-IOS-XR-ipv4-bgp-act']";
      tailf:action clear-bgp-vrf-performance-statistics {
        tailf:actionpoint ncsproxy {
          tailf:internal;
        }
        csc:xr-task "bgp";
        csc:cli-command "clear bgp vrf <vrf-all> performance-statistics";
        description
          "Specify a VRF.
           Clear performance statistics.
          ";
        input {
          leaf vrf-all {
            mandatory true;
            type vrf-name;
            description
              "VRF name or all";
          }
        }
      }
    }
  }
  augment "/ncs:devices/ncs:device-group/ncs:ned-id/ncs:rpc" {
    container rpc-clear-bgp-vrf-performance-statistics {
      tailf:ncs-device-type "netconf";
      tailf:display-when "/ncs:devices/ncs:device[ncs:name=current()/../../../ncs:member]/ncs:module[ncs:name='Cisco-IOS-XR-ipv4-bgp-act']";
      tailf:action clear-bgp-vrf-performance-statistics {
        tailf:actionpoint ncsproxy {
          tailf:internal;
        }
        csc:xr-task "bgp";
        csc:cli-command "clear bgp vrf <vrf-all> performance-statistics";
        description
          "Specify a VRF.
           Clear performance statistics.
          ";
        input {
          leaf vrf-all {
            mandatory true;
            type vrf-name;
            description
              "VRF name or all";
          }
        }
      }
    }
  }
  augment "/ncs:devices/ncs:device/ncs:rpc" {
    container rpc-clear-bgp-vrf-peer-drops-ip-addr {
      tailf:ncs-device-type "netconf";
      tailf:display-when "not(../../ncs:module) or ../../ncs:module[ncs:name='Cisco-IOS-XR-ipv4-bgp-act']";
      tailf:action clear-bgp-vrf-peer-drops-ip-addr {
        tailf:actionpoint ncsproxy {
          tailf:internal;
        }
        csc:xr-task "bgp";
        csc:cli-command "clear bgp vrf <vrf-all> peer-drops <ip-addr>";
        description
          "Specify a VRF.
           Clear established/dropped counters for a peer.
          ";
        input {
          leaf vrf-all {
            mandatory true;
            type vrf-name;
            description
              "VRF name or all";
          }
          leaf ip-addr {
            mandatory true;
            type inet:ip-address;
            description
              "BGP neighbor IP address";
          }
        }
      }
    }
  }
  augment "/ncs:devices/ncs:device-group/ncs:ned-id/ncs:rpc" {
    container rpc-clear-bgp-vrf-peer-drops-ip-addr {
      tailf:ncs-device-type "netconf";
      tailf:display-when "/ncs:devices/ncs:device[ncs:name=current()/../../../ncs:member]/ncs:module[ncs:name='Cisco-IOS-XR-ipv4-bgp-act']";
      tailf:action clear-bgp-vrf-peer-drops-ip-addr {
        tailf:actionpoint ncsproxy {
          tailf:internal;
        }
        csc:xr-task "bgp";
        csc:cli-command "clear bgp vrf <vrf-all> peer-drops <ip-addr>";
        description
          "Specify a VRF.
           Clear established/dropped counters for a peer.
          ";
        input {
          leaf vrf-all {
            mandatory true;
            type vrf-name;
            description
              "VRF name or all";
          }
          leaf ip-addr {
            mandatory true;
            type inet:ip-address;
            description
              "BGP neighbor IP address";
          }
        }
      }
    }
  }
  augment "/ncs:devices/ncs:device/ncs:rpc" {
    container rpc-clear-bgp-vrf-peer-drops-all {
      tailf:ncs-device-type "netconf";
      tailf:display-when "not(../../ncs:module) or ../../ncs:module[ncs:name='Cisco-IOS-XR-ipv4-bgp-act']";
      tailf:action clear-bgp-vrf-peer-drops-all {
        tailf:actionpoint ncsproxy {
          tailf:internal;
        }
        csc:xr-task "bgp";
        csc:cli-command "clear bgp vrf <vrf-all> peer-drops *";
        description
          "Specify a VRF.
           Clear established/dropped counters for a peer.
           All Neighbors.
          ";
        input {
          leaf vrf-all {
            mandatory true;
            type vrf-name;
            description
              "VRF name or all";
          }
        }
      }
    }
  }
  augment "/ncs:devices/ncs:device-group/ncs:ned-id/ncs:rpc" {
    container rpc-clear-bgp-vrf-peer-drops-all {
      tailf:ncs-device-type "netconf";
      tailf:display-when "/ncs:devices/ncs:device[ncs:name=current()/../../../ncs:member]/ncs:module[ncs:name='Cisco-IOS-XR-ipv4-bgp-act']";
      tailf:action clear-bgp-vrf-peer-drops-all {
        tailf:actionpoint ncsproxy {
          tailf:internal;
        }
        csc:xr-task "bgp";
        csc:cli-command "clear bgp vrf <vrf-all> peer-drops *";
        description
          "Specify a VRF.
           Clear established/dropped counters for a peer.
           All Neighbors.
          ";
        input {
          leaf vrf-all {
            mandatory true;
            type vrf-name;
            description
              "VRF name or all";
          }
        }
      }
    }
  }
  augment "/ncs:devices/ncs:device/ncs:rpc" {
    container rpc-clear-bgp-vrf-nexthop-registration-ip-addr {
      tailf:ncs-device-type "netconf";
      tailf:display-when "not(../../ncs:module) or ../../ncs:module[ncs:name='Cisco-IOS-XR-ipv4-bgp-act']";
      tailf:action clear-bgp-vrf-nexthop-registration-ip-addr {
        tailf:actionpoint ncsproxy {
          tailf:internal;
        }
        csc:xr-task "bgp";
        csc:cli-command "clear bgp vrf <vrf-all> nexthop registration <ip-addr>";
        description
          "Specify a VRF.
           Clear nexthop.
           Registration with RIB and reregister.
          ";
        input {
          leaf vrf-all {
            mandatory true;
            type vrf-name;
            description
              "VRF name or all";
          }
          leaf ip-addr {
            mandatory true;
            type inet:ip-address;
            description
              "Nexthop address";
          }
        }
      }
    }
  }
  augment "/ncs:devices/ncs:device-group/ncs:ned-id/ncs:rpc" {
    container rpc-clear-bgp-vrf-nexthop-registration-ip-addr {
      tailf:ncs-device-type "netconf";
      tailf:display-when "/ncs:devices/ncs:device[ncs:name=current()/../../../ncs:member]/ncs:module[ncs:name='Cisco-IOS-XR-ipv4-bgp-act']";
      tailf:action clear-bgp-vrf-nexthop-registration-ip-addr {
        tailf:actionpoint ncsproxy {
          tailf:internal;
        }
        csc:xr-task "bgp";
        csc:cli-command "clear bgp vrf <vrf-all> nexthop registration <ip-addr>";
        description
          "Specify a VRF.
           Clear nexthop.
           Registration with RIB and reregister.
          ";
        input {
          leaf vrf-all {
            mandatory true;
            type vrf-name;
            description
              "VRF name or all";
          }
          leaf ip-addr {
            mandatory true;
            type inet:ip-address;
            description
              "Nexthop address";
          }
        }
      }
    }
  }
  augment "/ncs:devices/ncs:device/ncs:rpc" {
    container rpc-clear-bgp-vrf-nexthop-performance-statistics {
      tailf:ncs-device-type "netconf";
      tailf:display-when "not(../../ncs:module) or ../../ncs:module[ncs:name='Cisco-IOS-XR-ipv4-bgp-act']";
      tailf:action clear-bgp-vrf-nexthop-performance-statistics {
        tailf:actionpoint ncsproxy {
          tailf:internal;
        }
        csc:xr-task "bgp";
        csc:cli-command "clear bgp vrf <vrf-all> nexthop performance-statistics";
        description
          "Specify a VRF.
           Clear nexthop.
           Performance statistics information related to processing.
          ";
        input {
          leaf vrf-all {
            mandatory true;
            type vrf-name;
            description
              "VRF name or all";
          }
        }
      }
    }
  }
  augment "/ncs:devices/ncs:device-group/ncs:ned-id/ncs:rpc" {
    container rpc-clear-bgp-vrf-nexthop-performance-statistics {
      tailf:ncs-device-type "netconf";
      tailf:display-when "/ncs:devices/ncs:device[ncs:name=current()/../../../ncs:member]/ncs:module[ncs:name='Cisco-IOS-XR-ipv4-bgp-act']";
      tailf:action clear-bgp-vrf-nexthop-performance-statistics {
        tailf:actionpoint ncsproxy {
          tailf:internal;
        }
        csc:xr-task "bgp";
        csc:cli-command "clear bgp vrf <vrf-all> nexthop performance-statistics";
        description
          "Specify a VRF.
           Clear nexthop.
           Performance statistics information related to processing.
          ";
        input {
          leaf vrf-all {
            mandatory true;
            type vrf-name;
            description
              "VRF name or all";
          }
        }
      }
    }
  }
  augment "/ncs:devices/ncs:device/ncs:rpc" {
    container rpc-clear-bgp-vrf-afi-safi-flap-statistics-ipv6-prefix {
      tailf:ncs-device-type "netconf";
      tailf:display-when "not(../../ncs:module) or ../../ncs:module[ncs:name='Cisco-IOS-XR-ipv4-bgp-act']";
      tailf:action clear-bgp-vrf-afi-safi-flap-statistics-ipv6-prefix {
        tailf:actionpoint ncsproxy {
          tailf:internal;
        }
        csc:xr-task "bgp";
        csc:cli-command "clear bgp vrf <vrf-all> <afi-safi-name> flap-statistics <ipv6-prefix>";
        description
          "Specify a VRF.
           Clear flap statistics.
          ";
        input {
          leaf vrf-all {
            mandatory true;
            type vrf-name;
            description
              "VRF name or all";
          }
          leaf afi-safi-name {
            mandatory true;
            type afi-safi-type;
            description
              "AFI and SAFI";
          }
          leaf ipv6-prefix {
            mandatory true;
            type inet:ipv6-prefix;
            description
              "IPv6 Network and mask or masklength to clear flap statistics";
          }
        }
      }
    }
  }
  augment "/ncs:devices/ncs:device-group/ncs:ned-id/ncs:rpc" {
    container rpc-clear-bgp-vrf-afi-safi-flap-statistics-ipv6-prefix {
      tailf:ncs-device-type "netconf";
      tailf:display-when "/ncs:devices/ncs:device[ncs:name=current()/../../../ncs:member]/ncs:module[ncs:name='Cisco-IOS-XR-ipv4-bgp-act']";
      tailf:action clear-bgp-vrf-afi-safi-flap-statistics-ipv6-prefix {
        tailf:actionpoint ncsproxy {
          tailf:internal;
        }
        csc:xr-task "bgp";
        csc:cli-command "clear bgp vrf <vrf-all> <afi-safi-name> flap-statistics <ipv6-prefix>";
        description
          "Specify a VRF.
           Clear flap statistics.
          ";
        input {
          leaf vrf-all {
            mandatory true;
            type vrf-name;
            description
              "VRF name or all";
          }
          leaf afi-safi-name {
            mandatory true;
            type afi-safi-type;
            description
              "AFI and SAFI";
          }
          leaf ipv6-prefix {
            mandatory true;
            type inet:ipv6-prefix;
            description
              "IPv6 Network and mask or masklength to clear flap statistics";
          }
        }
      }
    }
  }
  augment "/ncs:devices/ncs:device/ncs:rpc" {
    container rpc-clear-bgp-vrf-afi-safi-dampening-ipv6-prefix {
      tailf:ncs-device-type "netconf";
      tailf:display-when "not(../../ncs:module) or ../../ncs:module[ncs:name='Cisco-IOS-XR-ipv4-bgp-act']";
      tailf:action clear-bgp-vrf-afi-safi-dampening-ipv6-prefix {
        tailf:actionpoint ncsproxy {
          tailf:internal;
        }
        csc:xr-task "bgp";
        csc:cli-command "clear bgp vrf <vrf-all> <afi-safi-name> dampening <ipv6-prefix>";
        description
          "Specify a VRF.
           Clear route flap dampening information.
          ";
        input {
          leaf vrf-all {
            mandatory true;
            type vrf-name;
            description
              "VRF name or all";
          }
          leaf afi-safi-name {
            mandatory true;
            type afi-safi-type;
            description
              "AFI and SAFI";
          }
          leaf ipv6-prefix {
            mandatory true;
            type inet:ipv6-prefix;
            description
              "IPv6 Network and mask or masklength to clear dampening information";
          }
        }
      }
    }
  }
  augment "/ncs:devices/ncs:device-group/ncs:ned-id/ncs:rpc" {
    container rpc-clear-bgp-vrf-afi-safi-dampening-ipv6-prefix {
      tailf:ncs-device-type "netconf";
      tailf:display-when "/ncs:devices/ncs:device[ncs:name=current()/../../../ncs:member]/ncs:module[ncs:name='Cisco-IOS-XR-ipv4-bgp-act']";
      tailf:action clear-bgp-vrf-afi-safi-dampening-ipv6-prefix {
        tailf:actionpoint ncsproxy {
          tailf:internal;
        }
        csc:xr-task "bgp";
        csc:cli-command "clear bgp vrf <vrf-all> <afi-safi-name> dampening <ipv6-prefix>";
        description
          "Specify a VRF.
           Clear route flap dampening information.
          ";
        input {
          leaf vrf-all {
            mandatory true;
            type vrf-name;
            description
              "VRF name or all";
          }
          leaf afi-safi-name {
            mandatory true;
            type afi-safi-type;
            description
              "AFI and SAFI";
          }
          leaf ipv6-prefix {
            mandatory true;
            type inet:ipv6-prefix;
            description
              "IPv6 Network and mask or masklength to clear dampening information";
          }
        }
      }
    }
  }
  augment "/ncs:devices/ncs:device/ncs:rpc" {
    container rpc-clear-bgp-vrf-afi-safi-update-outq-update-group {
      tailf:ncs-device-type "netconf";
      tailf:display-when "not(../../ncs:module) or ../../ncs:module[ncs:name='Cisco-IOS-XR-ipv4-bgp-act']";
      tailf:action clear-bgp-vrf-afi-safi-update-outq-update-group {
        tailf:actionpoint ncsproxy {
          tailf:internal;
        }
        csc:xr-task "bgp";
        csc:cli-command "clear bgp vrf <vrf-all> <afi-safi-name> update outq update-group <update-group>";
        description
          "Specify a VRF.
           Clear Update information (Do NOT execute without cisco support)(cisco-support).
           Clear Update generation OutQ counters (Do NOT execute without cisco support)(cisco-support).
           Update-group.
          ";
        input {
          leaf vrf-all {
            mandatory true;
            type vrf-name;
            description
              "VRF name or all";
          }
          leaf afi-safi-name {
            mandatory true;
            type afi-safi-type;
            description
              "AFI and SAFI";
          }
          leaf update-group {
            mandatory true;
            type update-group-id;
            description
              "Update-group process ID <x.y>";
          }
        }
      }
    }
  }
  augment "/ncs:devices/ncs:device-group/ncs:ned-id/ncs:rpc" {
    container rpc-clear-bgp-vrf-afi-safi-update-outq-update-group {
      tailf:ncs-device-type "netconf";
      tailf:display-when "/ncs:devices/ncs:device[ncs:name=current()/../../../ncs:member]/ncs:module[ncs:name='Cisco-IOS-XR-ipv4-bgp-act']";
      tailf:action clear-bgp-vrf-afi-safi-update-outq-update-group {
        tailf:actionpoint ncsproxy {
          tailf:internal;
        }
        csc:xr-task "bgp";
        csc:cli-command "clear bgp vrf <vrf-all> <afi-safi-name> update outq update-group <update-group>";
        description
          "Specify a VRF.
           Clear Update information (Do NOT execute without cisco support)(cisco-support).
           Clear Update generation OutQ counters (Do NOT execute without cisco support)(cisco-support).
           Update-group.
          ";
        input {
          leaf vrf-all {
            mandatory true;
            type vrf-name;
            description
              "VRF name or all";
          }
          leaf afi-safi-name {
            mandatory true;
            type afi-safi-type;
            description
              "AFI and SAFI";
          }
          leaf update-group {
            mandatory true;
            type update-group-id;
            description
              "Update-group process ID <x.y>";
          }
        }
      }
    }
  }
  augment "/ncs:devices/ncs:device/ncs:rpc" {
    container rpc-clear-bgp-vrf-afi-safi-update-outq-update-group-update-parent {
      tailf:ncs-device-type "netconf";
      tailf:display-when "not(../../ncs:module) or ../../ncs:module[ncs:name='Cisco-IOS-XR-ipv4-bgp-act']";
      tailf:action clear-bgp-vrf-afi-safi-update-outq-update-group-update-parent {
        tailf:actionpoint ncsproxy {
          tailf:internal;
        }
        csc:xr-task "bgp";
        csc:cli-command "clear bgp vrf <vrf-all> <afi-safi-name> update outq update-group <update-group> update-parent";
        description
          "Specify a VRF.
           Clear Update information (Do NOT execute without cisco support)(cisco-support).
           Clear Update generation OutQ counters (Do NOT execute without cisco support)(cisco-support).
           Update-group.
           Update parents' OutQ counters too.
          ";
        input {
          leaf vrf-all {
            mandatory true;
            type vrf-name;
            description
              "VRF name or all";
          }
          leaf afi-safi-name {
            mandatory true;
            type afi-safi-type;
            description
              "AFI and SAFI";
          }
          leaf update-group {
            mandatory true;
            type update-group-id;
            description
              "Update-group process ID <x.y>";
          }
        }
      }
    }
  }
  augment "/ncs:devices/ncs:device-group/ncs:ned-id/ncs:rpc" {
    container rpc-clear-bgp-vrf-afi-safi-update-outq-update-group-update-parent {
      tailf:ncs-device-type "netconf";
      tailf:display-when "/ncs:devices/ncs:device[ncs:name=current()/../../../ncs:member]/ncs:module[ncs:name='Cisco-IOS-XR-ipv4-bgp-act']";
      tailf:action clear-bgp-vrf-afi-safi-update-outq-update-group-update-parent {
        tailf:actionpoint ncsproxy {
          tailf:internal;
        }
        csc:xr-task "bgp";
        csc:cli-command "clear bgp vrf <vrf-all> <afi-safi-name> update outq update-group <update-group> update-parent";
        description
          "Specify a VRF.
           Clear Update information (Do NOT execute without cisco support)(cisco-support).
           Clear Update generation OutQ counters (Do NOT execute without cisco support)(cisco-support).
           Update-group.
           Update parents' OutQ counters too.
          ";
        input {
          leaf vrf-all {
            mandatory true;
            type vrf-name;
            description
              "VRF name or all";
          }
          leaf afi-safi-name {
            mandatory true;
            type afi-safi-type;
            description
              "AFI and SAFI";
          }
          leaf update-group {
            mandatory true;
            type update-group-id;
            description
              "Update-group process ID <x.y>";
          }
        }
      }
    }
  }
  augment "/ncs:devices/ncs:device/ncs:rpc" {
    container rpc-clear-bgp-vrf-afi-safi-update-outq-update-group-sub-group-refresh-sub-group {
      tailf:ncs-device-type "netconf";
      tailf:display-when "not(../../ncs:module) or ../../ncs:module[ncs:name='Cisco-IOS-XR-ipv4-bgp-act']";
      tailf:action clear-bgp-vrf-afi-safi-update-outq-update-group-sub-group-refresh-sub-group {
        tailf:actionpoint ncsproxy {
          tailf:internal;
        }
        csc:xr-task "bgp";
        csc:cli-command "clear bgp vrf <vrf-all> <afi-safi-name> update outq update-group <update-group> sub-group <refresh-sub-group>";
        description
          "Specify a VRF.
           Clear Update information (Do NOT execute without cisco support)(cisco-support).
           Clear Update generation OutQ counters (Do NOT execute without cisco support)(cisco-support).
           Update-group.
           Sub-group.
          ";
        input {
          leaf vrf-all {
            mandatory true;
            type vrf-name;
            description
              "VRF name or all";
          }
          leaf afi-safi-name {
            mandatory true;
            type afi-safi-type;
            description
              "AFI and SAFI";
          }
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device-group/ncs:ned-id/ncs:rpc" {
    container rpc-clear-bgp-vrf-afi-safi-update-outq-update-group-sub-group-refresh-sub-group {
      tailf:ncs-device-type "netconf";
      tailf:display-when "/ncs:devices/ncs:device[ncs:name=current()/../../../ncs:member]/ncs:module[ncs:name='Cisco-IOS-XR-ipv4-bgp-act']";
      tailf:action clear-bgp-vrf-afi-safi-update-outq-update-group-sub-group-refresh-sub-group {
        tailf:actionpoint ncsproxy {
          tailf:internal;
        }
        csc:xr-task "bgp";
        csc:cli-command "clear bgp vrf <vrf-all> <afi-safi-name> update outq update-group <update-group> sub-group <refresh-sub-group>";
        description
          "Specify a VRF.
           Clear Update information (Do NOT execute without cisco support)(cisco-support).
           Clear Update generation OutQ counters (Do NOT execute without cisco support)(cisco-support).
           Update-group.
           Sub-group.
          ";
        input {
          leaf vrf-all {
            mandatory true;
            type vrf-name;
            description
              "VRF name or all";
          }
          leaf afi-safi-name {
            mandatory true;
            type afi-safi-type;
            description
              "AFI and SAFI";
          }
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device/ncs:rpc" {
    container rpc-clear-bgp-vrf-afi-safi-update-outq-update-group-sub-group-refresh-sub-group-update-parent {
      tailf:ncs-device-type "netconf";
      tailf:display-when "not(../../ncs:module) or ../../ncs:module[ncs:name='Cisco-IOS-XR-ipv4-bgp-act']";
      tailf:action clear-bgp-vrf-afi-safi-update-outq-update-group-sub-group-refresh-sub-group-update-parent {
        tailf:actionpoint ncsproxy {
          tailf:internal;
        }
        csc:xr-task "bgp";
        csc:cli-command "clear bgp vrf <vrf-all> <afi-safi-name> update outq update-group <update-group> sub-group <refresh-sub-group> update-parent";
        description
          "Specify a VRF.
           Clear Update information (Do NOT execute without cisco support)(cisco-support).
           Clear Update generation OutQ counters (Do NOT execute without cisco support)(cisco-support).
           Update-group.
           Sub-group.
           Update parents' OutQ counters too.
          ";
        input {
          leaf vrf-all {
            mandatory true;
            type vrf-name;
            description
              "VRF name or all";
          }
          leaf afi-safi-name {
            mandatory true;
            type afi-safi-type;
            description
              "AFI and SAFI";
          }
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device-group/ncs:ned-id/ncs:rpc" {
    container rpc-clear-bgp-vrf-afi-safi-update-outq-update-group-sub-group-refresh-sub-group-update-parent {
      tailf:ncs-device-type "netconf";
      tailf:display-when "/ncs:devices/ncs:device[ncs:name=current()/../../../ncs:member]/ncs:module[ncs:name='Cisco-IOS-XR-ipv4-bgp-act']";
      tailf:action clear-bgp-vrf-afi-safi-update-outq-update-group-sub-group-refresh-sub-group-update-parent {
        tailf:actionpoint ncsproxy {
          tailf:internal;
        }
        csc:xr-task "bgp";
        csc:cli-command "clear bgp vrf <vrf-all> <afi-safi-name> update outq update-group <update-group> sub-group <refresh-sub-group> update-parent";
        description
          "Specify a VRF.
           Clear Update information (Do NOT execute without cisco support)(cisco-support).
           Clear Update generation OutQ counters (Do NOT execute without cisco support)(cisco-support).
           Update-group.
           Sub-group.
           Update parents' OutQ counters too.
          ";
        input {
          leaf vrf-all {
            mandatory true;
            type vrf-name;
            description
              "VRF name or all";
          }
          leaf afi-safi-name {
            mandatory true;
            type afi-safi-type;
            description
              "AFI and SAFI";
          }
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device/ncs:rpc" {
    container rpc-clear-bgp-vrf-afi-safi-update-outq-update-group-sub-group {
      tailf:ncs-device-type "netconf";
      tailf:display-when "not(../../ncs:module) or ../../ncs:module[ncs:name='Cisco-IOS-XR-ipv4-bgp-act']";
      tailf:action clear-bgp-vrf-afi-safi-update-outq-update-group-sub-group {
        tailf:actionpoint ncsproxy {
          tailf:internal;
        }
        csc:xr-task "bgp";
        csc:cli-command "clear bgp vrf <vrf-all> <afi-safi-name> update outq update-group <update-group> sub-group <sub-group>";
        description
          "Specify a VRF.
           Clear Update information (Do NOT execute without cisco support)(cisco-support).
           Clear Update generation OutQ counters (Do NOT execute without cisco support)(cisco-support).
           Update-group.
           Sub-group.
          ";
        input {
          leaf vrf-all {
            mandatory true;
            type vrf-name;
            description
              "VRF name or all";
          }
          leaf afi-safi-name {
            mandatory true;
            type afi-safi-type;
            description
              "AFI and SAFI";
          }
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device-group/ncs:ned-id/ncs:rpc" {
    container rpc-clear-bgp-vrf-afi-safi-update-outq-update-group-sub-group {
      tailf:ncs-device-type "netconf";
      tailf:display-when "/ncs:devices/ncs:device[ncs:name=current()/../../../ncs:member]/ncs:module[ncs:name='Cisco-IOS-XR-ipv4-bgp-act']";
      tailf:action clear-bgp-vrf-afi-safi-update-outq-update-group-sub-group {
        tailf:actionpoint ncsproxy {
          tailf:internal;
        }
        csc:xr-task "bgp";
        csc:cli-command "clear bgp vrf <vrf-all> <afi-safi-name> update outq update-group <update-group> sub-group <sub-group>";
        description
          "Specify a VRF.
           Clear Update information (Do NOT execute without cisco support)(cisco-support).
           Clear Update generation OutQ counters (Do NOT execute without cisco support)(cisco-support).
           Update-group.
           Sub-group.
          ";
        input {
          leaf vrf-all {
            mandatory true;
            type vrf-name;
            description
              "VRF name or all";
          }
          leaf afi-safi-name {
            mandatory true;
            type afi-safi-type;
            description
              "AFI and SAFI";
          }
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device/ncs:rpc" {
    container rpc-clear-bgp-vrf-afi-safi-update-outq-update-group-sub-group-update-parent {
      tailf:ncs-device-type "netconf";
      tailf:display-when "not(../../ncs:module) or ../../ncs:module[ncs:name='Cisco-IOS-XR-ipv4-bgp-act']";
      tailf:action clear-bgp-vrf-afi-safi-update-outq-update-group-sub-group-update-parent {
        tailf:actionpoint ncsproxy {
          tailf:internal;
        }
        csc:xr-task "bgp";
        csc:cli-command "clear bgp vrf <vrf-all> <afi-safi-name> update outq update-group <update-group> sub-group <sub-group> update-parent";
        description
          "Specify a VRF.
           Clear Update information (Do NOT execute without cisco support)(cisco-support).
           Clear Update generation OutQ counters (Do NOT execute without cisco support)(cisco-support).
           Update-group.
           Sub-group.
           Update parents' OutQ counters too.
          ";
        input {
          leaf vrf-all {
            mandatory true;
            type vrf-name;
            description
              "VRF name or all";
          }
          leaf afi-safi-name {
            mandatory true;
            type afi-safi-type;
            description
              "AFI and SAFI";
          }
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device-group/ncs:ned-id/ncs:rpc" {
    container rpc-clear-bgp-vrf-afi-safi-update-outq-update-group-sub-group-update-parent {
      tailf:ncs-device-type "netconf";
      tailf:display-when "/ncs:devices/ncs:device[ncs:name=current()/../../../ncs:member]/ncs:module[ncs:name='Cisco-IOS-XR-ipv4-bgp-act']";
      tailf:action clear-bgp-vrf-afi-safi-update-outq-update-group-sub-group-update-parent {
        tailf:actionpoint ncsproxy {
          tailf:internal;
        }
        csc:xr-task "bgp";
        csc:cli-command "clear bgp vrf <vrf-all> <afi-safi-name> update outq update-group <update-group> sub-group <sub-group> update-parent";
        description
          "Specify a VRF.
           Clear Update information (Do NOT execute without cisco support)(cisco-support).
           Clear Update generation OutQ counters (Do NOT execute without cisco support)(cisco-support).
           Update-group.
           Sub-group.
           Update parents' OutQ counters too.
          ";
        input {
          leaf vrf-all {
            mandatory true;
            type vrf-name;
            description
              "VRF name or all";
          }
          leaf afi-safi-name {
            mandatory true;
            type afi-safi-type;
            description
              "AFI and SAFI";
          }
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device/ncs:rpc" {
    container rpc-clear-bgp-vrf-afi-safi-update-outq-neighbor-ip-addr {
      tailf:ncs-device-type "netconf";
      tailf:display-when "not(../../ncs:module) or ../../ncs:module[ncs:name='Cisco-IOS-XR-ipv4-bgp-act']";
      tailf:action clear-bgp-vrf-afi-safi-update-outq-neighbor-ip-addr {
        tailf:actionpoint ncsproxy {
          tailf:internal;
        }
        csc:xr-task "bgp";
        csc:cli-command "clear bgp vrf <vrf-all> <afi-safi-name> update outq neighbor <ip-addr>";
        description
          "Specify a VRF.
           Clear Update information (Do NOT execute without cisco support)(cisco-support).
           Clear Update generation OutQ counters (Do NOT execute without cisco support)(cisco-support).
           Neighbor.
          ";
        input {
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device-group/ncs:ned-id/ncs:rpc" {
    container rpc-clear-bgp-vrf-afi-safi-update-outq-neighbor-ip-addr {
      tailf:ncs-device-type "netconf";
      tailf:display-when "/ncs:devices/ncs:device[ncs:name=current()/../../../ncs:member]/ncs:module[ncs:name='Cisco-IOS-XR-ipv4-bgp-act']";
      tailf:action clear-bgp-vrf-afi-safi-update-outq-neighbor-ip-addr {
        tailf:actionpoint ncsproxy {
          tailf:internal;
        }
        csc:xr-task "bgp";
        csc:cli-command "clear bgp vrf <vrf-all> <afi-safi-name> update outq neighbor <ip-addr>";
        description
          "Specify a VRF.
           Clear Update information (Do NOT execute without cisco support)(cisco-support).
           Clear Update generation OutQ counters (Do NOT execute without cisco support)(cisco-support).
           Neighbor.
          ";
        input {
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device/ncs:rpc" {
    container rpc-clear-bgp-vrf-afi-safi-update-outq-neighbor-ip-addr-update-parent {
      tailf:ncs-device-type "netconf";
      tailf:display-when "not(../../ncs:module) or ../../ncs:module[ncs:name='Cisco-IOS-XR-ipv4-bgp-act']";
      tailf:action clear-bgp-vrf-afi-safi-update-outq-neighbor-ip-addr-update-parent {
        tailf:actionpoint ncsproxy {
          tailf:internal;
        }
        csc:xr-task "bgp";
        csc:cli-command "clear bgp vrf <vrf-all> <afi-safi-name> update outq neighbor <ip-addr> update-parent";
        description
          "Specify a VRF.
           Clear Update information (Do NOT execute without cisco support)(cisco-support).
           Clear Update generation OutQ counters (Do NOT execute without cisco support)(cisco-support).
           Neighbor.
           Update parents' OutQ counters too.
          ";
        input {
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device-group/ncs:ned-id/ncs:rpc" {
    container rpc-clear-bgp-vrf-afi-safi-update-outq-neighbor-ip-addr-update-parent {
      tailf:ncs-device-type "netconf";
      tailf:display-when "/ncs:devices/ncs:device[ncs:name=current()/../../../ncs:member]/ncs:module[ncs:name='Cisco-IOS-XR-ipv4-bgp-act']";
      tailf:action clear-bgp-vrf-afi-safi-update-outq-neighbor-ip-addr-update-parent {
        tailf:actionpoint ncsproxy {
          tailf:internal;
        }
        csc:xr-task "bgp";
        csc:cli-command "clear bgp vrf <vrf-all> <afi-safi-name> update outq neighbor <ip-addr> update-parent";
        description
          "Specify a VRF.
           Clear Update information (Do NOT execute without cisco support)(cisco-support).
           Clear Update generation OutQ counters (Do NOT execute without cisco support)(cisco-support).
           Neighbor.
           Update parents' OutQ counters too.
          ";
        input {
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device/ncs:rpc" {
    container rpc-clear-bgp-vrf-afi-safi-update-outq-neighbor-ip-addr-refresh {
      tailf:ncs-device-type "netconf";
      tailf:display-when "not(../../ncs:module) or ../../ncs:module[ncs:name='Cisco-IOS-XR-ipv4-bgp-act']";
      tailf:action clear-bgp-vrf-afi-safi-update-outq-neighbor-ip-addr-refresh {
        tailf:actionpoint ncsproxy {
          tailf:internal;
        }
        csc:xr-task "bgp";
        csc:cli-command "clear bgp vrf <vrf-all> <afi-safi-name> update outq neighbor <ip-addr> refresh";
        description
          "Specify a VRF.
           Clear Update information (Do NOT execute without cisco support)(cisco-support).
           Clear Update generation OutQ counters (Do NOT execute without cisco support)(cisco-support).
           Neighbor.
           Refresh OutQ.
          ";
        input {
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device-group/ncs:ned-id/ncs:rpc" {
    container rpc-clear-bgp-vrf-afi-safi-update-outq-neighbor-ip-addr-refresh {
      tailf:ncs-device-type "netconf";
      tailf:display-when "/ncs:devices/ncs:device[ncs:name=current()/../../../ncs:member]/ncs:module[ncs:name='Cisco-IOS-XR-ipv4-bgp-act']";
      tailf:action clear-bgp-vrf-afi-safi-update-outq-neighbor-ip-addr-refresh {
        tailf:actionpoint ncsproxy {
          tailf:internal;
        }
        csc:xr-task "bgp";
        csc:cli-command "clear bgp vrf <vrf-all> <afi-safi-name> update outq neighbor <ip-addr> refresh";
        description
          "Specify a VRF.
           Clear Update information (Do NOT execute without cisco support)(cisco-support).
           Clear Update generation OutQ counters (Do NOT execute without cisco support)(cisco-support).
           Neighbor.
           Refresh OutQ.
          ";
        input {
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device/ncs:rpc" {
    container rpc-clear-bgp-vrf-afi-safi-update-outq-neighbor-ip-addr-refresh-update-parent {
      tailf:ncs-device-type "netconf";
      tailf:display-when "not(../../ncs:module) or ../../ncs:module[ncs:name='Cisco-IOS-XR-ipv4-bgp-act']";
      tailf:action clear-bgp-vrf-afi-safi-update-outq-neighbor-ip-addr-refresh-update-parent {
        tailf:actionpoint ncsproxy {
          tailf:internal;
        }
        csc:xr-task "bgp";
        csc:cli-command "clear bgp vrf <vrf-all> <afi-safi-name> update outq neighbor <ip-addr> refresh update-parent";
        description
          "Specify a VRF.
           Clear Update information (Do NOT execute without cisco support)(cisco-support).
           Clear Update generation OutQ counters (Do NOT execute without cisco support)(cisco-support).
           Neighbor.
           Refresh OutQ.
           Update parents' OutQ counters too.
          ";
        input {
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device-group/ncs:ned-id/ncs:rpc" {
    container rpc-clear-bgp-vrf-afi-safi-update-outq-neighbor-ip-addr-refresh-update-parent {
      tailf:ncs-device-type "netconf";
      tailf:display-when "/ncs:devices/ncs:device[ncs:name=current()/../../../ncs:member]/ncs:module[ncs:name='Cisco-IOS-XR-ipv4-bgp-act']";
      tailf:action clear-bgp-vrf-afi-safi-update-outq-neighbor-ip-addr-refresh-update-parent {
        tailf:actionpoint ncsproxy {
          tailf:internal;
        }
        csc:xr-task "bgp";
        csc:cli-command "clear bgp vrf <vrf-all> <afi-safi-name> update outq neighbor <ip-addr> refresh update-parent";
        description
          "Specify a VRF.
           Clear Update information (Do NOT execute without cisco support)(cisco-support).
           Clear Update generation OutQ counters (Do NOT execute without cisco support)(cisco-support).
           Neighbor.
           Refresh OutQ.
           Update parents' OutQ counters too.
          ";
        input {
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device/ncs:rpc" {
    container rpc-clear-bgp-vrf-afi-safi-update-outq-address-family {
      tailf:ncs-device-type "netconf";
      tailf:display-when "not(../../ncs:module) or ../../ncs:module[ncs:name='Cisco-IOS-XR-ipv4-bgp-act']";
      tailf:action clear-bgp-vrf-afi-safi-update-outq-address-family {
        tailf:actionpoint ncsproxy {
          tailf:internal;
        }
        csc:xr-task "bgp";
        csc:cli-command "clear bgp vrf <vrf-all> <afi-safi-name> update outq address-family";
        description
          "Specify a VRF.
           Clear Update information (Do NOT execute without cisco support)(cisco-support).
           Clear Update generation OutQ counters (Do NOT execute without cisco support)(cisco-support).
           Address-family.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-vrf-afi-safi-update-outq-address-family {
      tailf:ncs-device-type "netconf";
      tailf:display-when "/ncs:devices/ncs:device[ncs:name=current()/../../../ncs:member]/ncs:module[ncs:name='Cisco-IOS-XR-ipv4-bgp-act']";
      tailf:action clear-bgp-vrf-afi-safi-update-outq-address-family {
        tailf:actionpoint ncsproxy {
          tailf:internal;
        }
        csc:xr-task "bgp";
        csc:cli-command "clear bgp vrf <vrf-all> <afi-safi-name> update outq address-family";
        description
          "Specify a VRF.
           Clear Update information (Do NOT execute without cisco support)(cisco-support).
           Clear Update generation OutQ counters (Do NOT execute without cisco support)(cisco-support).
           Address-family.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-vrf-afi-safi-update-outq-address-family-update-parent {
      tailf:ncs-device-type "netconf";
      tailf:display-when "not(../../ncs:module) or ../../ncs:module[ncs:name='Cisco-IOS-XR-ipv4-bgp-act']";
      tailf:action clear-bgp-vrf-afi-safi-update-outq-address-family-update-parent {
        tailf:actionpoint ncsproxy {
          tailf:internal;
        }
        csc:xr-task "bgp";
        csc:cli-command "clear bgp vrf <vrf-all> <afi-safi-name> update outq address-family update-parent";
        description
          "Specify a VRF.
           Clear Update information (Do NOT execute without cisco support)(cisco-support).
           Clear Update generation OutQ counters (Do NOT execute without cisco support)(cisco-support).
           Address-family.
           Update parents' OutQ counters too.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-vrf-afi-safi-update-outq-address-family-update-parent {
      tailf:ncs-device-type "netconf";
      tailf:display-when "/ncs:devices/ncs:device[ncs:name=current()/../../../ncs:member]/ncs:module[ncs:name='Cisco-IOS-XR-ipv4-bgp-act']";
      tailf:action clear-bgp-vrf-afi-safi-update-outq-address-family-update-parent {
        tailf:actionpoint ncsproxy {
          tailf:internal;
        }
        csc:xr-task "bgp";
        csc:cli-command "clear bgp vrf <vrf-all> <afi-safi-name> update outq address-family update-parent";
        description
          "Specify a VRF.
           Clear Update information (Do NOT execute without cisco support)(cisco-support).
           Clear Update generation OutQ counters (Do NOT execute without cisco support)(cisco-support).
           Address-family.
           Update parents' OutQ counters too.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-vrf-afi-safi-shutdown {
      tailf:ncs-device-type "netconf";
      tailf:display-when "not(../../ncs:module) or ../../ncs:module[ncs:name='Cisco-IOS-XR-ipv4-bgp-act']";
      tailf:action clear-bgp-vrf-afi-safi-shutdown {
        tailf:actionpoint ncsproxy {
          tailf:internal;
        }
        csc:xr-task "bgp";
        csc:cli-command "clear bgp vrf <vrf-all> <afi-safi-name> shutdown";
        description
          "Specify a VRF.
           Clear all peers which were shut down due to low memory.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-vrf-afi-safi-shutdown {
      tailf:ncs-device-type "netconf";
      tailf:display-when "/ncs:devices/ncs:device[ncs:name=current()/../../../ncs:member]/ncs:module[ncs:name='Cisco-IOS-XR-ipv4-bgp-act']";
      tailf:action clear-bgp-vrf-afi-safi-shutdown {
        tailf:actionpoint ncsproxy {
          tailf:internal;
        }
        csc:xr-task "bgp";
        csc:cli-command "clear bgp vrf <vrf-all> <afi-safi-name> shutdown";
        description
          "Specify a VRF.
           Clear all peers which were shut down due to low memory.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-vrf-afi-safi-self-originated {
      tailf:ncs-device-type "netconf";
      tailf:display-when "not(../../ncs:module) or ../../ncs:module[ncs:name='Cisco-IOS-XR-ipv4-bgp-act']";
      tailf:action clear-bgp-vrf-afi-safi-self-originated {
        tailf:actionpoint ncsproxy {
          tailf:internal;
        }
        csc:xr-task "bgp";
        csc:cli-command "clear bgp vrf <vrf-all> <afi-safi-name> self-originated";
        description
          "Specify a VRF.
           Clear redistributed, network and aggregate routes originated here.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-vrf-afi-safi-self-originated {
      tailf:ncs-device-type "netconf";
      tailf:display-when "/ncs:devices/ncs:device[ncs:name=current()/../../../ncs:member]/ncs:module[ncs:name='Cisco-IOS-XR-ipv4-bgp-act']";
      tailf:action clear-bgp-vrf-afi-safi-self-originated {
        tailf:actionpoint ncsproxy {
          tailf:internal;
        }
        csc:xr-task "bgp";
        csc:cli-command "clear bgp vrf <vrf-all> <afi-safi-name> self-originated";
        description
          "Specify a VRF.
           Clear redistributed, network and aggregate routes originated here.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-vrf-afi-safi-nexthop-registration-ip-addr {
      tailf:ncs-device-type "netconf";
      tailf:display-when "not(../../ncs:module) or ../../ncs:module[ncs:name='Cisco-IOS-XR-ipv4-bgp-act']";
      tailf:action clear-bgp-vrf-afi-safi-nexthop-registration-ip-addr {
        tailf:actionpoint ncsproxy {
          tailf:internal;
        }
        csc:xr-task "bgp";
        csc:cli-command "clear bgp vrf <vrf-all> <afi-safi-name> nexthop registration <ip-addr>";
        description
          "Specify a VRF.
           Clear nexthop.
           Registration with RIB and reregister.
          ";
        input {
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "Nexthop address";
          }
        }
      }
    }
  }
  augment "/ncs:devices/ncs:device-group/ncs:ned-id/ncs:rpc" {
    container rpc-clear-bgp-vrf-afi-safi-nexthop-registration-ip-addr {
      tailf:ncs-device-type "netconf";
      tailf:display-when "/ncs:devices/ncs:device[ncs:name=current()/../../../ncs:member]/ncs:module[ncs:name='Cisco-IOS-XR-ipv4-bgp-act']";
      tailf:action clear-bgp-vrf-afi-safi-nexthop-registration-ip-addr {
        tailf:actionpoint ncsproxy {
          tailf:internal;
        }
        csc:xr-task "bgp";
        csc:cli-command "clear bgp vrf <vrf-all> <afi-safi-name> nexthop registration <ip-addr>";
        description
          "Specify a VRF.
           Clear nexthop.
           Registration with RIB and reregister.
          ";
        input {
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "Nexthop address";
          }
        }
      }
    }
  }
  augment "/ncs:devices/ncs:device/ncs:rpc" {
    container rpc-clear-bgp-vrf-afi-safi-nexthop-performance-statistics {
      tailf:ncs-device-type "netconf";
      tailf:display-when "not(../../ncs:module) or ../../ncs:module[ncs:name='Cisco-IOS-XR-ipv4-bgp-act']";
      tailf:action clear-bgp-vrf-afi-safi-nexthop-performance-statistics {
        tailf:actionpoint ncsproxy {
          tailf:internal;
        }
        csc:xr-task "bgp";
        csc:cli-command "clear bgp vrf <vrf-all> <afi-safi-name> nexthop performance-statistics";
        description
          "Specify a VRF.
           Clear nexthop.
           Performance statistics information related to processing.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-vrf-afi-safi-nexthop-performance-statistics {
      tailf:ncs-device-type "netconf";
      tailf:display-when "/ncs:devices/ncs:device[ncs:name=current()/../../../ncs:member]/ncs:module[ncs:name='Cisco-IOS-XR-ipv4-bgp-act']";
      tailf:action clear-bgp-vrf-afi-safi-nexthop-performance-statistics {
        tailf:actionpoint ncsproxy {
          tailf:internal;
        }
        csc:xr-task "bgp";
        csc:cli-command "clear bgp vrf <vrf-all> <afi-safi-name> nexthop performance-statistics";
        description
          "Specify a VRF.
           Clear nexthop.
           Performance statistics information related to processing.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-vrf-afi-safi-flap-statistics {
      tailf:ncs-device-type "netconf";
      tailf:display-when "not(../../ncs:module) or ../../ncs:module[ncs:name='Cisco-IOS-XR-ipv4-bgp-act']";
      tailf:action clear-bgp-vrf-afi-safi-flap-statistics {
        tailf:actionpoint ncsproxy {
          tailf:internal;
        }
        csc:xr-task "bgp";
        csc:cli-command "clear bgp vrf <vrf-all> <afi-safi-name> flap-statistics";
        description
          "Specify a VRF.
           Clear flap statistics.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-vrf-afi-safi-flap-statistics {
      tailf:ncs-device-type "netconf";
      tailf:display-when "/ncs:devices/ncs:device[ncs:name=current()/../../../ncs:member]/ncs:module[ncs:name='Cisco-IOS-XR-ipv4-bgp-act']";
      tailf:action clear-bgp-vrf-afi-safi-flap-statistics {
        tailf:actionpoint ncsproxy {
          tailf:internal;
        }
        csc:xr-task "bgp";
        csc:cli-command "clear bgp vrf <vrf-all> <afi-safi-name> flap-statistics";
        description
          "Specify a VRF.
           Clear flap statistics.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-vrf-afi-safi-flap-statistics-route-policy {
      tailf:ncs-device-type "netconf";
      tailf:display-when "not(../../ncs:module) or ../../ncs:module[ncs:name='Cisco-IOS-XR-ipv4-bgp-act']";
      tailf:action clear-bgp-vrf-afi-safi-flap-statistics-route-policy {
        tailf:actionpoint ncsproxy {
          tailf:internal;
        }
        csc:xr-task "bgp";
        csc:cli-command "clear bgp vrf <vrf-all> <afi-safi-name> flap-statistics route-policy <route-policy-name>";
        description
          "Specify a VRF.
           Clear flap statistics.
           Clear flap statistics for routes matching the route policy.
          ";
        input {
          leaf vrf-all {
            mandatory true;
            type vrf-name;
            description
              "VRF name or all";
          }
          leaf afi-safi-name {
            mandatory true;
            type afi-safi-type;
            description
              "AFI and SAFI";
          }
          leaf route-policy-name {
            mandatory true;
            type string;
            description
              "Route Policy name";
          }
        }
      }
    }
  }
  augment "/ncs:devices/ncs:device-group/ncs:ned-id/ncs:rpc" {
    container rpc-clear-bgp-vrf-afi-safi-flap-statistics-route-policy {
      tailf:ncs-device-type "netconf";
      tailf:display-when "/ncs:devices/ncs:device[ncs:name=current()/../../../ncs:member]/ncs:module[ncs:name='Cisco-IOS-XR-ipv4-bgp-act']";
      tailf:action clear-bgp-vrf-afi-safi-flap-statistics-route-policy {
        tailf:actionpoint ncsproxy {
          tailf:internal;
        }
        csc:xr-task "bgp";
        csc:cli-command "clear bgp vrf <vrf-all> <afi-safi-name> flap-statistics route-policy <route-policy-name>";
        description
          "Specify a VRF.
           Clear flap statistics.
           Clear flap statistics for routes matching the route policy.
          ";
        input {
          leaf vrf-all {
            mandatory true;
            type vrf-name;
            description
              "VRF name or all";
          }
          leaf afi-safi-name {
            mandatory true;
            type afi-safi-type;
            description
              "AFI and SAFI";
          }
          leaf route-policy-name {
            mandatory true;
            type string;
            description
              "Route Policy name";
          }
        }
      }
    }
  }
  augment "/ncs:devices/ncs:device/ncs:rpc" {
    container rpc-clear-bgp-vrf-afi-safi-flap-statistics-regexp {
      tailf:ncs-device-type "netconf";
      tailf:display-when "not(../../ncs:module) or ../../ncs:module[ncs:name='Cisco-IOS-XR-ipv4-bgp-act']";
      tailf:action clear-bgp-vrf-afi-safi-flap-statistics-regexp {
        tailf:actionpoint ncsproxy {
          tailf:internal;
        }
        csc:xr-task "bgp";
        csc:cli-command "clear bgp vrf <vrf-all> <afi-safi-name> flap-statistics regexp <regexp-pattern>";
        description
          "Specify a VRF.
           Clear flap statistics.
           Clear flap statistics for routes matching the regular expression.
          ";
        input {
          leaf vrf-all {
            mandatory true;
            type vrf-name;
            description
              "VRF name or all";
          }
          leaf afi-safi-name {
            mandatory true;
            type afi-safi-type;
            description
              "AFI and SAFI";
          }
          leaf regexp-pattern {
            mandatory true;
            type string;
            description
              "A regular expression to match the BGP AS paths.  Use 'ctrl-v ?' to enter '?'";
          }
        }
      }
    }
  }
  augment "/ncs:devices/ncs:device-group/ncs:ned-id/ncs:rpc" {
    container rpc-clear-bgp-vrf-afi-safi-flap-statistics-regexp {
      tailf:ncs-device-type "netconf";
      tailf:display-when "/ncs:devices/ncs:device[ncs:name=current()/../../../ncs:member]/ncs:module[ncs:name='Cisco-IOS-XR-ipv4-bgp-act']";
      tailf:action clear-bgp-vrf-afi-safi-flap-statistics-regexp {
        tailf:actionpoint ncsproxy {
          tailf:internal;
        }
        csc:xr-task "bgp";
        csc:cli-command "clear bgp vrf <vrf-all> <afi-safi-name> flap-statistics regexp <regexp-pattern>";
        description
          "Specify a VRF.
           Clear flap statistics.
           Clear flap statistics for routes matching the regular expression.
          ";
        input {
          leaf vrf-all {
            mandatory true;
            type vrf-name;
            description
              "VRF name or all";
          }
          leaf afi-safi-name {
            mandatory true;
            type afi-safi-type;
            description
              "AFI and SAFI";
          }
          leaf regexp-pattern {
            mandatory true;
            type string;
            description
              "A regular expression to match the BGP AS paths.  Use 'ctrl-v ?' to enter '?'";
          }
        }
      }
    }
  }
  augment "/ncs:devices/ncs:device/ncs:rpc" {
    container rpc-clear-bgp-vrf-afi-safi-flap-statistics-ipv4-prefix {
      tailf:ncs-device-type "netconf";
      tailf:display-when "not(../../ncs:module) or ../../ncs:module[ncs:name='Cisco-IOS-XR-ipv4-bgp-act']";
      tailf:action clear-bgp-vrf-afi-safi-flap-statistics-ipv4-prefix {
        tailf:actionpoint ncsproxy {
          tailf:internal;
        }
        csc:xr-task "bgp";
        csc:cli-command "clear bgp vrf <vrf-all> <afi-safi-name> flap-statistics <ipv4-prefix>";
        description
          "Specify a VRF.
           Clear flap statistics.
          ";
        input {
          leaf vrf-all {
            mandatory true;
            type vrf-name;
            description
              "VRF name or all";
          }
          leaf afi-safi-name {
            mandatory true;
            type afi-safi-type;
            description
              "AFI and SAFI";
          }
          leaf ipv4-prefix {
            mandatory true;
            type inet:ipv4-prefix;
            description
              "IPv4 Network and mask or masklength to clear flap statistics";
          }
        }
      }
    }
  }
  augment "/ncs:devices/ncs:device-group/ncs:ned-id/ncs:rpc" {
    container rpc-clear-bgp-vrf-afi-safi-flap-statistics-ipv4-prefix {
      tailf:ncs-device-type "netconf";
      tailf:display-when "/ncs:devices/ncs:device[ncs:name=current()/../../../ncs:member]/ncs:module[ncs:name='Cisco-IOS-XR-ipv4-bgp-act']";
      tailf:action clear-bgp-vrf-afi-safi-flap-statistics-ipv4-prefix {
        tailf:actionpoint ncsproxy {
          tailf:internal;
        }
        csc:xr-task "bgp";
        csc:cli-command "clear bgp vrf <vrf-all> <afi-safi-name> flap-statistics <ipv4-prefix>";
        description
          "Specify a VRF.
           Clear flap statistics.
          ";
        input {
          leaf vrf-all {
            mandatory true;
            type vrf-name;
            description
              "VRF name or all";
          }
          leaf afi-safi-name {
            mandatory true;
            type afi-safi-type;
            description
              "AFI and SAFI";
          }
          leaf ipv4-prefix {
            mandatory true;
            type inet:ipv4-prefix;
            description
              "IPv4 Network and mask or masklength to clear flap statistics";
          }
        }
      }
    }
  }
  augment "/ncs:devices/ncs:device/ncs:rpc" {
    container rpc-clear-bgp-vrf-afi-safi-flap-statistics-ip-addr {
      tailf:ncs-device-type "netconf";
      tailf:display-when "not(../../ncs:module) or ../../ncs:module[ncs:name='Cisco-IOS-XR-ipv4-bgp-act']";
      tailf:action clear-bgp-vrf-afi-safi-flap-statistics-ip-addr {
        tailf:actionpoint ncsproxy {
          tailf:internal;
        }
        csc:xr-task "bgp";
        csc:cli-command "clear bgp vrf <vrf-all> <afi-safi-name> flap-statistics <ip-addr>";
        description
          "Specify a VRF.
           Clear flap statistics.
          ";
        input {
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device-group/ncs:ned-id/ncs:rpc" {
    container rpc-clear-bgp-vrf-afi-safi-flap-statistics-ip-addr {
      tailf:ncs-device-type "netconf";
      tailf:display-when "/ncs:devices/ncs:device[ncs:name=current()/../../../ncs:member]/ncs:module[ncs:name='Cisco-IOS-XR-ipv4-bgp-act']";
      tailf:action clear-bgp-vrf-afi-safi-flap-statistics-ip-addr {
        tailf:actionpoint ncsproxy {
          tailf:internal;
        }
        csc:xr-task "bgp";
        csc:cli-command "clear bgp vrf <vrf-all> <afi-safi-name> flap-statistics <ip-addr>";
        description
          "Specify a VRF.
           Clear flap statistics.
          ";
        input {
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device/ncs:rpc" {
    container rpc-clear-bgp-vrf-afi-safi-flap-statistics-ip-addr-ipv4-mask {
      tailf:ncs-device-type "netconf";
      tailf:display-when "not(../../ncs:module) or ../../ncs:module[ncs:name='Cisco-IOS-XR-ipv4-bgp-act']";
      tailf:action clear-bgp-vrf-afi-safi-flap-statistics-ip-addr-ipv4-mask {
        tailf:actionpoint ncsproxy {
          tailf:internal;
        }
        csc:xr-task "bgp";
        csc:cli-command "clear bgp vrf <vrf-all> <afi-safi-name> flap-statistics <ip-addr> <ipv4-mask>";
        description
          "Specify a VRF.
           Clear flap statistics.
          ";
        input {
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "BGP neighbor address to clear";
          }
          leaf ipv4-mask {
            mandatory true;
            type ipv4-netmask;
            description
              "IPv4 Network and mask or masklength to clear flap statistics";
          }
        }
      }
    }
  }
  augment "/ncs:devices/ncs:device-group/ncs:ned-id/ncs:rpc" {
    container rpc-clear-bgp-vrf-afi-safi-flap-statistics-ip-addr-ipv4-mask {
      tailf:ncs-device-type "netconf";
      tailf:display-when "/ncs:devices/ncs:device[ncs:name=current()/../../../ncs:member]/ncs:module[ncs:name='Cisco-IOS-XR-ipv4-bgp-act']";
      tailf:action clear-bgp-vrf-afi-safi-flap-statistics-ip-addr-ipv4-mask {
        tailf:actionpoint ncsproxy {
          tailf:internal;
        }
        csc:xr-task "bgp";
        csc:cli-command "clear bgp vrf <vrf-all> <afi-safi-name> flap-statistics <ip-addr> <ipv4-mask>";
        description
          "Specify a VRF.
           Clear flap statistics.
          ";
        input {
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "BGP neighbor address to clear";
          }
          leaf ipv4-mask {
            mandatory true;
            type ipv4-netmask;
            description
              "IPv4 Network and mask or masklength to clear flap statistics";
          }
        }
      }
    }
  }
  augment "/ncs:devices/ncs:device/ncs:rpc" {
    container rpc-clear-bgp-vrf-afi-safi-external-soft {
      tailf:ncs-device-type "netconf";
      tailf:display-when "not(../../ncs:module) or ../../ncs:module[ncs:name='Cisco-IOS-XR-ipv4-bgp-act']";
      tailf:action clear-bgp-vrf-afi-safi-external-soft {
        tailf:actionpoint ncsproxy {
          tailf:internal;
        }
        csc:xr-task "bgp";
        csc:cli-command "clear bgp vrf <vrf-all> <afi-safi-name> external soft";
        description
          "Specify a VRF.
           Clear all external peers.
           Soft reconfig.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-vrf-afi-safi-external-soft {
      tailf:ncs-device-type "netconf";
      tailf:display-when "/ncs:devices/ncs:device[ncs:name=current()/../../../ncs:member]/ncs:module[ncs:name='Cisco-IOS-XR-ipv4-bgp-act']";
      tailf:action clear-bgp-vrf-afi-safi-external-soft {
        tailf:actionpoint ncsproxy {
          tailf:internal;
        }
        csc:xr-task "bgp";
        csc:cli-command "clear bgp vrf <vrf-all> <afi-safi-name> external soft";
        description
          "Specify a VRF.
           Clear all external peers.
           Soft reconfig.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-vrf-afi-safi-external-soft-out {
      tailf:ncs-device-type "netconf";
      tailf:display-when "not(../../ncs:module) or ../../ncs:module[ncs:name='Cisco-IOS-XR-ipv4-bgp-act']";
      tailf:action clear-bgp-vrf-afi-safi-external-soft-out {
        tailf:actionpoint ncsproxy {
          tailf:internal;
        }
        csc:xr-task "bgp";
        csc:cli-command "clear bgp vrf <vrf-all> <afi-safi-name> external soft out";
        description
          "Specify a VRF.
           Clear all external peers.
           Soft reconfig.
           Soft reconfig outbound update.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-vrf-afi-safi-external-soft-out {
      tailf:ncs-device-type "netconf";
      tailf:display-when "/ncs:devices/ncs:device[ncs:name=current()/../../../ncs:member]/ncs:module[ncs:name='Cisco-IOS-XR-ipv4-bgp-act']";
      tailf:action clear-bgp-vrf-afi-safi-external-soft-out {
        tailf:actionpoint ncsproxy {
          tailf:internal;
        }
        csc:xr-task "bgp";
        csc:cli-command "clear bgp vrf <vrf-all> <afi-safi-name> external soft out";
        description
          "Specify a VRF.
           Clear all external peers.
           Soft reconfig.
           Soft reconfig outbound update.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-vrf-afi-safi-external-soft-in {
      tailf:ncs-device-type "netconf";
      tailf:display-when "not(../../ncs:module) or ../../ncs:module[ncs:name='Cisco-IOS-XR-ipv4-bgp-act']";
      tailf:action clear-bgp-vrf-afi-safi-external-soft-in {
        tailf:actionpoint ncsproxy {
          tailf:internal;
        }
        csc:xr-task "bgp";
        csc:cli-command "clear bgp vrf <vrf-all> <afi-safi-name> external soft in";
        description
          "Specify a VRF.
           Clear all external peers.
           Soft reconfig.
           Soft reconfig inbound update.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-vrf-afi-safi-external-soft-in {
      tailf:ncs-device-type "netconf";
      tailf:display-when "/ncs:devices/ncs:device[ncs:name=current()/../../../ncs:member]/ncs:module[ncs:name='Cisco-IOS-XR-ipv4-bgp-act']";
      tailf:action clear-bgp-vrf-afi-safi-external-soft-in {
        tailf:actionpoint ncsproxy {
          tailf:internal;
        }
        csc:xr-task "bgp";
        csc:cli-command "clear bgp vrf <vrf-all> <afi-safi-name> external soft in";
        description
          "Specify a VRF.
           Clear all external peers.
           Soft reconfig.
           Soft reconfig inbound update.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-vrf-afi-safi-external-soft-in-prefix-filter {
      tailf:ncs-device-type "netconf";
      tailf:display-when "not(../../ncs:module) or ../../ncs:module[ncs:name='Cisco-IOS-XR-ipv4-bgp-act']";
      tailf:action clear-bgp-vrf-afi-safi-external-soft-in-prefix-filter {
        tailf:actionpoint ncsproxy {
          tailf:internal;
        }
        csc:xr-task "bgp";
        csc:cli-command "clear bgp vrf <vrf-all> <afi-safi-name> external soft in prefix-filter";
        description
          "Specify a VRF.
           Clear all external peers.
           Soft reconfig.
           Soft reconfig inbound update.
           Push out prefix ORF and do inbound soft reconfig.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-vrf-afi-safi-external-soft-in-prefix-filter {
      tailf:ncs-device-type "netconf";
      tailf:display-when "/ncs:devices/ncs:device[ncs:name=current()/../../../ncs:member]/ncs:module[ncs:name='Cisco-IOS-XR-ipv4-bgp-act']";
      tailf:action clear-bgp-vrf-afi-safi-external-soft-in-prefix-filter {
        tailf:actionpoint ncsproxy {
          tailf:internal;
        }
        csc:xr-task "bgp";
        csc:cli-command "clear bgp vrf <vrf-all> <afi-safi-name> external soft in prefix-filter";
        description
          "Specify a VRF.
           Clear all external peers.
           Soft reconfig.
           Soft reconfig inbound update.
           Push out prefix ORF and do inbound soft reconfig.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-vrf-afi-safi-dampening {
      tailf:ncs-device-type "netconf";
      tailf:display-when "not(../../ncs:module) or ../../ncs:module[ncs:name='Cisco-IOS-XR-ipv4-bgp-act']";
      tailf:action clear-bgp-vrf-afi-safi-dampening {
        tailf:actionpoint ncsproxy {
          tailf:internal;
        }
        csc:xr-task "bgp";
        csc:cli-command "clear bgp vrf <vrf-all> <afi-safi-name> dampening";
        description
          "Specify a VRF.
           Clear route flap dampening information.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-vrf-afi-safi-dampening {
      tailf:ncs-device-type "netconf";
      tailf:display-when "/ncs:devices/ncs:device[ncs:name=current()/../../../ncs:member]/ncs:module[ncs:name='Cisco-IOS-XR-ipv4-bgp-act']";
      tailf:action clear-bgp-vrf-afi-safi-dampening {
        tailf:actionpoint ncsproxy {
          tailf:internal;
        }
        csc:xr-task "bgp";
        csc:cli-command "clear bgp vrf <vrf-all> <afi-safi-name> dampening";
        description
          "Specify a VRF.
           Clear route flap dampening information.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-vrf-afi-safi-dampening-ipv4-prefix {
      tailf:ncs-device-type "netconf";
      tailf:display-when "not(../../ncs:module) or ../../ncs:module[ncs:name='Cisco-IOS-XR-ipv4-bgp-act']";
      tailf:action clear-bgp-vrf-afi-safi-dampening-ipv4-prefix {
        tailf:actionpoint ncsproxy {
          tailf:internal;
        }
        csc:xr-task "bgp";
        csc:cli-command "clear bgp vrf <vrf-all> <afi-safi-name> dampening <ipv4-prefix>";
        description
          "Specify a VRF.
           Clear route flap dampening information.
          ";
        input {
          leaf vrf-all {
            mandatory true;
            type vrf-name;
            description
              "VRF name or all";
          }
          leaf afi-safi-name {
            mandatory true;
            type afi-safi-type;
            description
              "AFI and SAFI";
          }
          leaf ipv4-prefix {
            mandatory true;
            type inet:ipv4-prefix;
            description
              "IPv4 Network and mask or masklength to clear dampening information";
          }
        }
      }
    }
  }
  augment "/ncs:devices/ncs:device-group/ncs:ned-id/ncs:rpc" {
    container rpc-clear-bgp-vrf-afi-safi-dampening-ipv4-prefix {
      tailf:ncs-device-type "netconf";
      tailf:display-when "/ncs:devices/ncs:device[ncs:name=current()/../../../ncs:member]/ncs:module[ncs:name='Cisco-IOS-XR-ipv4-bgp-act']";
      tailf:action clear-bgp-vrf-afi-safi-dampening-ipv4-prefix {
        tailf:actionpoint ncsproxy {
          tailf:internal;
        }
        csc:xr-task "bgp";
        csc:cli-command "clear bgp vrf <vrf-all> <afi-safi-name> dampening <ipv4-prefix>";
        description
          "Specify a VRF.
           Clear route flap dampening information.
          ";
        input {
          leaf vrf-all {
            mandatory true;
            type vrf-name;
            description
              "VRF name or all";
          }
          leaf afi-safi-name {
            mandatory true;
            type afi-safi-type;
            description
              "AFI and SAFI";
          }
          leaf ipv4-prefix {
            mandatory true;
            type inet:ipv4-prefix;
            description
              "IPv4 Network and mask or masklength to clear dampening information";
          }
        }
      }
    }
  }
  augment "/ncs:devices/ncs:device/ncs:rpc" {
    container rpc-clear-bgp-vrf-afi-safi-as-soft {
      tailf:ncs-device-type "netconf";
      tailf:display-when "not(../../ncs:module) or ../../ncs:module[ncs:name='Cisco-IOS-XR-ipv4-bgp-act']";
      tailf:action clear-bgp-vrf-afi-safi-as-soft {
        tailf:actionpoint ncsproxy {
          tailf:internal;
        }
        csc:xr-task "bgp";
        csc:cli-command "clear bgp vrf <vrf-all> <afi-safi-name> as <as-number> soft";
        description
          "Specify a VRF.
           Clear peers in a specific AS.
           Soft reconfig.
          ";
        input {
          leaf vrf-all {
            mandatory true;
            type vrf-name;
            description
              "VRF name or all";
          }
          leaf afi-safi-name {
            mandatory true;
            type afi-safi-type;
            description
              "AFI and SAFI";
          }
          leaf as-number {
            mandatory true;
            type as-number;
            description
              "AS number";
          }
        }
      }
    }
  }
  augment "/ncs:devices/ncs:device-group/ncs:ned-id/ncs:rpc" {
    container rpc-clear-bgp-vrf-afi-safi-as-soft {
      tailf:ncs-device-type "netconf";
      tailf:display-when "/ncs:devices/ncs:device[ncs:name=current()/../../../ncs:member]/ncs:module[ncs:name='Cisco-IOS-XR-ipv4-bgp-act']";
      tailf:action clear-bgp-vrf-afi-safi-as-soft {
        tailf:actionpoint ncsproxy {
          tailf:internal;
        }
        csc:xr-task "bgp";
        csc:cli-command "clear bgp vrf <vrf-all> <afi-safi-name> as <as-number> soft";
        description
          "Specify a VRF.
           Clear peers in a specific AS.
           Soft reconfig.
          ";
        input {
          leaf vrf-all {
            mandatory true;
            type vrf-name;
            description
              "VRF name or all";
          }
          leaf afi-safi-name {
            mandatory true;
            type afi-safi-type;
            description
              "AFI and SAFI";
          }
          leaf as-number {
            mandatory true;
            type as-number;
            description
              "AS number";
          }
        }
      }
    }
  }
  augment "/ncs:devices/ncs:device/ncs:rpc" {
    container rpc-clear-bgp-vrf-afi-safi-as-soft-out {
      tailf:ncs-device-type "netconf";
      tailf:display-when "not(../../ncs:module) or ../../ncs:module[ncs:name='Cisco-IOS-XR-ipv4-bgp-act']";
      tailf:action clear-bgp-vrf-afi-safi-as-soft-out {
        tailf:actionpoint ncsproxy {
          tailf:internal;
        }
        csc:xr-task "bgp";
        csc:cli-command "clear bgp vrf <vrf-all> <afi-safi-name> as <as-number> soft out";
        description
          "Specify a VRF.
           Clear peers in a specific AS.
           Soft reconfig.
           Soft reconfig outbound update.
          ";
        input {
          leaf vrf-all {
            mandatory true;
            type vrf-name;
            description
              "VRF name or all";
          }
          leaf afi-safi-name {
            mandatory true;
            type afi-safi-type;
            description
              "AFI and SAFI";
          }
          leaf as-number {
            mandatory true;
            type as-number;
            description
              "AS number";
          }
        }
      }
    }
  }
  augment "/ncs:devices/ncs:device-group/ncs:ned-id/ncs:rpc" {
    container rpc-clear-bgp-vrf-afi-safi-as-soft-out {
      tailf:ncs-device-type "netconf";
      tailf:display-when "/ncs:devices/ncs:device[ncs:name=current()/../../../ncs:member]/ncs:module[ncs:name='Cisco-IOS-XR-ipv4-bgp-act']";
      tailf:action clear-bgp-vrf-afi-safi-as-soft-out {
        tailf:actionpoint ncsproxy {
          tailf:internal;
        }
        csc:xr-task "bgp";
        csc:cli-command "clear bgp vrf <vrf-all> <afi-safi-name> as <as-number> soft out";
        description
          "Specify a VRF.
           Clear peers in a specific AS.
           Soft reconfig.
           Soft reconfig outbound update.
          ";
        input {
          leaf vrf-all {
            mandatory true;
            type vrf-name;
            description
              "VRF name or all";
          }
          leaf afi-safi-name {
            mandatory true;
            type afi-safi-type;
            description
              "AFI and SAFI";
          }
          leaf as-number {
            mandatory true;
            type as-number;
            description
              "AS number";
          }
        }
      }
    }
  }
  augment "/ncs:devices/ncs:device/ncs:rpc" {
    container rpc-clear-bgp-vrf-afi-safi-as-soft-in {
      tailf:ncs-device-type "netconf";
      tailf:display-when "not(../../ncs:module) or ../../ncs:module[ncs:name='Cisco-IOS-XR-ipv4-bgp-act']";
      tailf:action clear-bgp-vrf-afi-safi-as-soft-in {
        tailf:actionpoint ncsproxy {
          tailf:internal;
        }
        csc:xr-task "bgp";
        csc:cli-command "clear bgp vrf <vrf-all> <afi-safi-name> as <as-number> soft in";
        description
          "Specify a VRF.
           Clear peers in a specific AS.
           Soft reconfig.
           Soft reconfig inbound update.
          ";
        input {
          leaf vrf-all {
            mandatory true;
            type vrf-name;
            description
              "VRF name or all";
          }
          leaf afi-safi-name {
            mandatory true;
            type afi-safi-type;
            description
              "AFI and SAFI";
          }
          leaf as-number {
            mandatory true;
            type as-number;
            description
              "AS number";
          }
        }
      }
    }
  }
  augment "/ncs:devices/ncs:device-group/ncs:ned-id/ncs:rpc" {
    container rpc-clear-bgp-vrf-afi-safi-as-soft-in {
      tailf:ncs-device-type "netconf";
      tailf:display-when "/ncs:devices/ncs:device[ncs:name=current()/../../../ncs:member]/ncs:module[ncs:name='Cisco-IOS-XR-ipv4-bgp-act']";
      tailf:action clear-bgp-vrf-afi-safi-as-soft-in {
        tailf:actionpoint ncsproxy {
          tailf:internal;
        }
        csc:xr-task "bgp";
        csc:cli-command "clear bgp vrf <vrf-all> <afi-safi-name> as <as-number> soft in";
        description
          "Specify a VRF.
           Clear peers in a specific AS.
           Soft reconfig.
           Soft reconfig inbound update.
          ";
        input {
          leaf vrf-all {
            mandatory true;
            type vrf-name;
            description
              "VRF name or all";
          }
          leaf afi-safi-name {
            mandatory true;
            type afi-safi-type;
            description
              "AFI and SAFI";
          }
          leaf as-number {
            mandatory true;
            type as-number;
            description
              "AS number";
          }
        }
      }
    }
  }
  augment "/ncs:devices/ncs:device/ncs:rpc" {
    container rpc-clear-bgp-vrf-afi-safi-as-soft-in-prefix-filter {
      tailf:ncs-device-type "netconf";
      tailf:display-when "not(../../ncs:module) or ../../ncs:module[ncs:name='Cisco-IOS-XR-ipv4-bgp-act']";
      tailf:action clear-bgp-vrf-afi-safi-as-soft-in-prefix-filter {
        tailf:actionpoint ncsproxy {
          tailf:internal;
        }
        csc:xr-task "bgp";
        csc:cli-command "clear bgp vrf <vrf-all> <afi-safi-name> as <as-number> soft in prefix-filter";
        description
          "Specify a VRF.
           Clear peers in a specific AS.
           Soft reconfig.
           Soft reconfig inbound update.
           Push out prefix ORF and do inbound soft reconfig.
          ";
        input {
          leaf vrf-all {
            mandatory true;
            type vrf-name;
            description
              "VRF name or all";
          }
          leaf afi-safi-name {
            mandatory true;
            type afi-safi-type;
            description
              "AFI and SAFI";
          }
          leaf as-number {
            mandatory true;
            type as-number;
            description
              "AS number";
          }
        }
      }
    }
  }
  augment "/ncs:devices/ncs:device-group/ncs:ned-id/ncs:rpc" {
    container rpc-clear-bgp-vrf-afi-safi-as-soft-in-prefix-filter {
      tailf:ncs-device-type "netconf";
      tailf:display-when "/ncs:devices/ncs:device[ncs:name=current()/../../../ncs:member]/ncs:module[ncs:name='Cisco-IOS-XR-ipv4-bgp-act']";
      tailf:action clear-bgp-vrf-afi-safi-as-soft-in-prefix-filter {
        tailf:actionpoint ncsproxy {
          tailf:internal;
        }
        csc:xr-task "bgp";
        csc:cli-command "clear bgp vrf <vrf-all> <afi-safi-name> as <as-number> soft in prefix-filter";
        description
          "Specify a VRF.
           Clear peers in a specific AS.
           Soft reconfig.
           Soft reconfig inbound update.
           Push out prefix ORF and do inbound soft reconfig.
          ";
        input {
          leaf vrf-all {
            mandatory true;
            type vrf-name;
            description
              "VRF name or all";
          }
          leaf afi-safi-name {
            mandatory true;
            type afi-safi-type;
            description
              "AFI and SAFI";
          }
          leaf as-number {
            mandatory true;
            type as-number;
            description
              "AS number";
          }
        }
      }
    }
  }
  augment "/ncs:devices/ncs:device/ncs:rpc" {
    container rpc-clear-bgp-vrf-afi-safi-ip-addr-soft {
      tailf:ncs-device-type "netconf";
      tailf:display-when "not(../../ncs:module) or ../../ncs:module[ncs:name='Cisco-IOS-XR-ipv4-bgp-act']";
      tailf:action clear-bgp-vrf-afi-safi-ip-addr-soft {
        tailf:actionpoint ncsproxy {
          tailf:internal;
        }
        csc:xr-task "bgp";
        csc:cli-command "clear bgp vrf <vrf-all> <afi-safi-name> <ip-addr> soft";
        description
          "Specify a VRF.
           Soft reconfig.
          ";
        input {
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device-group/ncs:ned-id/ncs:rpc" {
    container rpc-clear-bgp-vrf-afi-safi-ip-addr-soft {
      tailf:ncs-device-type "netconf";
      tailf:display-when "/ncs:devices/ncs:device[ncs:name=current()/../../../ncs:member]/ncs:module[ncs:name='Cisco-IOS-XR-ipv4-bgp-act']";
      tailf:action clear-bgp-vrf-afi-safi-ip-addr-soft {
        tailf:actionpoint ncsproxy {
          tailf:internal;
        }
        csc:xr-task "bgp";
        csc:cli-command "clear bgp vrf <vrf-all> <afi-safi-name> <ip-addr> soft";
        description
          "Specify a VRF.
           Soft reconfig.
          ";
        input {
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device/ncs:rpc" {
    container rpc-clear-bgp-vrf-afi-safi-ip-addr-soft-out {
      tailf:ncs-device-type "netconf";
      tailf:display-when "not(../../ncs:module) or ../../ncs:module[ncs:name='Cisco-IOS-XR-ipv4-bgp-act']";
      tailf:action clear-bgp-vrf-afi-safi-ip-addr-soft-out {
        tailf:actionpoint ncsproxy {
          tailf:internal;
        }
        csc:xr-task "bgp";
        csc:cli-command "clear bgp vrf <vrf-all> <afi-safi-name> <ip-addr> soft out";
        description
          "Specify a VRF.
           Soft reconfig.
           Soft reconfig outbound update.
          ";
        input {
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device-group/ncs:ned-id/ncs:rpc" {
    container rpc-clear-bgp-vrf-afi-safi-ip-addr-soft-out {
      tailf:ncs-device-type "netconf";
      tailf:display-when "/ncs:devices/ncs:device[ncs:name=current()/../../../ncs:member]/ncs:module[ncs:name='Cisco-IOS-XR-ipv4-bgp-act']";
      tailf:action clear-bgp-vrf-afi-safi-ip-addr-soft-out {
        tailf:actionpoint ncsproxy {
          tailf:internal;
        }
        csc:xr-task "bgp";
        csc:cli-command "clear bgp vrf <vrf-all> <afi-safi-name> <ip-addr> soft out";
        description
          "Specify a VRF.
           Soft reconfig.
           Soft reconfig outbound update.
          ";
        input {
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device/ncs:rpc" {
    container rpc-clear-bgp-vrf-afi-safi-ip-addr-soft-in {
      tailf:ncs-device-type "netconf";
      tailf:display-when "not(../../ncs:module) or ../../ncs:module[ncs:name='Cisco-IOS-XR-ipv4-bgp-act']";
      tailf:action clear-bgp-vrf-afi-safi-ip-addr-soft-in {
        tailf:actionpoint ncsproxy {
          tailf:internal;
        }
        csc:xr-task "bgp";
        csc:cli-command "clear bgp vrf <vrf-all> <afi-safi-name> <ip-addr> soft in";
        description
          "Specify a VRF.
           Soft reconfig.
           Soft reconfig inbound update.
          ";
        input {
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device-group/ncs:ned-id/ncs:rpc" {
    container rpc-clear-bgp-vrf-afi-safi-ip-addr-soft-in {
      tailf:ncs-device-type "netconf";
      tailf:display-when "/ncs:devices/ncs:device[ncs:name=current()/../../../ncs:member]/ncs:module[ncs:name='Cisco-IOS-XR-ipv4-bgp-act']";
      tailf:action clear-bgp-vrf-afi-safi-ip-addr-soft-in {
        tailf:actionpoint ncsproxy {
          tailf:internal;
        }
        csc:xr-task "bgp";
        csc:cli-command "clear bgp vrf <vrf-all> <afi-safi-name> <ip-addr> soft in";
        description
          "Specify a VRF.
           Soft reconfig.
           Soft reconfig inbound update.
          ";
        input {
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device/ncs:rpc" {
    container rpc-clear-bgp-vrf-afi-safi-ip-addr-soft-in-prefix-filter {
      tailf:ncs-device-type "netconf";
      tailf:display-when "not(../../ncs:module) or ../../ncs:module[ncs:name='Cisco-IOS-XR-ipv4-bgp-act']";
      tailf:action clear-bgp-vrf-afi-safi-ip-addr-soft-in-prefix-filter {
        tailf:actionpoint ncsproxy {
          tailf:internal;
        }
        csc:xr-task "bgp";
        csc:cli-command "clear bgp vrf <vrf-all> <afi-safi-name> <ip-addr> soft in prefix-filter";
        description
          "Specify a VRF.
           Soft reconfig.
           Soft reconfig inbound update.
           Push out prefix ORF and do inbound soft reconfig.
          ";
        input {
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device-group/ncs:ned-id/ncs:rpc" {
    container rpc-clear-bgp-vrf-afi-safi-ip-addr-soft-in-prefix-filter {
      tailf:ncs-device-type "netconf";
      tailf:display-when "/ncs:devices/ncs:device[ncs:name=current()/../../../ncs:member]/ncs:module[ncs:name='Cisco-IOS-XR-ipv4-bgp-act']";
      tailf:action clear-bgp-vrf-afi-safi-ip-addr-soft-in-prefix-filter {
        tailf:actionpoint ncsproxy {
          tailf:internal;
        }
        csc:xr-task "bgp";
        csc:cli-command "clear bgp vrf <vrf-all> <afi-safi-name> <ip-addr> soft in prefix-filter";
        description
          "Specify a VRF.
           Soft reconfig.
           Soft reconfig inbound update.
           Push out prefix ORF and do inbound soft reconfig.
          ";
        input {
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device/ncs:rpc" {
    container rpc-clear-bgp-vrf-afi-safi-ip-addr-long-lived-stale {
      tailf:ncs-device-type "netconf";
      tailf:display-when "not(../../ncs:module) or ../../ncs:module[ncs:name='Cisco-IOS-XR-ipv4-bgp-act']";
      tailf:action clear-bgp-vrf-afi-safi-ip-addr-long-lived-stale {
        tailf:actionpoint ncsproxy {
          tailf:internal;
        }
        csc:xr-task "bgp";
        csc:cli-command "clear bgp vrf <vrf-all> <afi-safi-name> <ip-addr> long-lived-stale";
        description
          "Specify a VRF.
           Clear long-lived-stale routes.
          ";
        input {
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device-group/ncs:ned-id/ncs:rpc" {
    container rpc-clear-bgp-vrf-afi-safi-ip-addr-long-lived-stale {
      tailf:ncs-device-type "netconf";
      tailf:display-when "/ncs:devices/ncs:device[ncs:name=current()/../../../ncs:member]/ncs:module[ncs:name='Cisco-IOS-XR-ipv4-bgp-act']";
      tailf:action clear-bgp-vrf-afi-safi-ip-addr-long-lived-stale {
        tailf:actionpoint ncsproxy {
          tailf:internal;
        }
        csc:xr-task "bgp";
        csc:cli-command "clear bgp vrf <vrf-all> <afi-safi-name> <ip-addr> long-lived-stale";
        description
          "Specify a VRF.
           Clear long-lived-stale routes.
          ";
        input {
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device/ncs:rpc" {
    container rpc-clear-bgp-vrf-afi-safi-all-soft {
      tailf:ncs-device-type "netconf";
      tailf:display-when "not(../../ncs:module) or ../../ncs:module[ncs:name='Cisco-IOS-XR-ipv4-bgp-act']";
      tailf:action clear-bgp-vrf-afi-safi-all-soft {
        tailf:actionpoint ncsproxy {
          tailf:internal;
        }
        csc:xr-task "bgp";
        csc:cli-command "clear bgp vrf <vrf-all> <afi-safi-name> * soft";
        description
          "Specify a VRF.
           Clear all peers and all routes from the BGP table.
           Soft reconfig.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-vrf-afi-safi-all-soft {
      tailf:ncs-device-type "netconf";
      tailf:display-when "/ncs:devices/ncs:device[ncs:name=current()/../../../ncs:member]/ncs:module[ncs:name='Cisco-IOS-XR-ipv4-bgp-act']";
      tailf:action clear-bgp-vrf-afi-safi-all-soft {
        tailf:actionpoint ncsproxy {
          tailf:internal;
        }
        csc:xr-task "bgp";
        csc:cli-command "clear bgp vrf <vrf-all> <afi-safi-name> * soft";
        description
          "Specify a VRF.
           Clear all peers and all routes from the BGP table.
           Soft reconfig.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-vrf-afi-safi-all-soft-out {
      tailf:ncs-device-type "netconf";
      tailf:display-when "not(../../ncs:module) or ../../ncs:module[ncs:name='Cisco-IOS-XR-ipv4-bgp-act']";
      tailf:action clear-bgp-vrf-afi-safi-all-soft-out {
        tailf:actionpoint ncsproxy {
          tailf:internal;
        }
        csc:xr-task "bgp";
        csc:cli-command "clear bgp vrf <vrf-all> <afi-safi-name> * soft out";
        description
          "Specify a VRF.
           Clear all peers and all routes from the BGP table.
           Soft reconfig.
           Soft reconfig outbound update.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-vrf-afi-safi-all-soft-out {
      tailf:ncs-device-type "netconf";
      tailf:display-when "/ncs:devices/ncs:device[ncs:name=current()/../../../ncs:member]/ncs:module[ncs:name='Cisco-IOS-XR-ipv4-bgp-act']";
      tailf:action clear-bgp-vrf-afi-safi-all-soft-out {
        tailf:actionpoint ncsproxy {
          tailf:internal;
        }
        csc:xr-task "bgp";
        csc:cli-command "clear bgp vrf <vrf-all> <afi-safi-name> * soft out";
        description
          "Specify a VRF.
           Clear all peers and all routes from the BGP table.
           Soft reconfig.
           Soft reconfig outbound update.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-vrf-afi-safi-all-soft-in {
      tailf:ncs-device-type "netconf";
      tailf:display-when "not(../../ncs:module) or ../../ncs:module[ncs:name='Cisco-IOS-XR-ipv4-bgp-act']";
      tailf:action clear-bgp-vrf-afi-safi-all-soft-in {
        tailf:actionpoint ncsproxy {
          tailf:internal;
        }
        csc:xr-task "bgp";
        csc:cli-command "clear bgp vrf <vrf-all> <afi-safi-name> * soft in";
        description
          "Specify a VRF.
           Clear all peers and all routes from the BGP table.
           Soft reconfig.
           Soft reconfig inbound update.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-vrf-afi-safi-all-soft-in {
      tailf:ncs-device-type "netconf";
      tailf:display-when "/ncs:devices/ncs:device[ncs:name=current()/../../../ncs:member]/ncs:module[ncs:name='Cisco-IOS-XR-ipv4-bgp-act']";
      tailf:action clear-bgp-vrf-afi-safi-all-soft-in {
        tailf:actionpoint ncsproxy {
          tailf:internal;
        }
        csc:xr-task "bgp";
        csc:cli-command "clear bgp vrf <vrf-all> <afi-safi-name> * soft in";
        description
          "Specify a VRF.
           Clear all peers and all routes from the BGP table.
           Soft reconfig.
           Soft reconfig inbound update.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-vrf-afi-safi-all-soft-in-prefix-filter {
      tailf:ncs-device-type "netconf";
      tailf:display-when "not(../../ncs:module) or ../../ncs:module[ncs:name='Cisco-IOS-XR-ipv4-bgp-act']";
      tailf:action clear-bgp-vrf-afi-safi-all-soft-in-prefix-filter {
        tailf:actionpoint ncsproxy {
          tailf:internal;
        }
        csc:xr-task "bgp";
        csc:cli-command "clear bgp vrf <vrf-all> <afi-safi-name> * soft in prefix-filter";
        description
          "Specify a VRF.
           Clear all peers and all routes from the BGP table.
           Soft reconfig.
           Soft reconfig inbound update.
           Push out prefix ORF and do inbound soft reconfig.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-vrf-afi-safi-all-soft-in-prefix-filter {
      tailf:ncs-device-type "netconf";
      tailf:display-when "/ncs:devices/ncs:device[ncs:name=current()/../../../ncs:member]/ncs:module[ncs:name='Cisco-IOS-XR-ipv4-bgp-act']";
      tailf:action clear-bgp-vrf-afi-safi-all-soft-in-prefix-filter {
        tailf:actionpoint ncsproxy {
          tailf:internal;
        }
        csc:xr-task "bgp";
        csc:cli-command "clear bgp vrf <vrf-all> <afi-safi-name> * soft in prefix-filter";
        description
          "Specify a VRF.
           Clear all peers and all routes from the BGP table.
           Soft reconfig.
           Soft reconfig inbound update.
           Push out prefix ORF and do inbound soft reconfig.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-vrf-external {
      tailf:ncs-device-type "netconf";
      tailf:display-when "not(../../ncs:module) or ../../ncs:module[ncs:name='Cisco-IOS-XR-ipv4-bgp-act']";
      tailf:action clear-bgp-vrf-external {
        tailf:actionpoint ncsproxy {
          tailf:internal;
        }
        csc:xr-task "bgp";
        csc:cli-command "clear bgp vrf <vrf-all> external";
        description
          "Specify a VRF.
           Clear all external peers.
          ";
        input {
          leaf vrf-all {
            mandatory true;
            type vrf-name;
            description
              "VRF name or all";
          }
        }
      }
    }
  }
  augment "/ncs:devices/ncs:device-group/ncs:ned-id/ncs:rpc" {
    container rpc-clear-bgp-vrf-external {
      tailf:ncs-device-type "netconf";
      tailf:display-when "/ncs:devices/ncs:device[ncs:name=current()/../../../ncs:member]/ncs:module[ncs:name='Cisco-IOS-XR-ipv4-bgp-act']";
      tailf:action clear-bgp-vrf-external {
        tailf:actionpoint ncsproxy {
          tailf:internal;
        }
        csc:xr-task "bgp";
        csc:cli-command "clear bgp vrf <vrf-all> external";
        description
          "Specify a VRF.
           Clear all external peers.
          ";
        input {
          leaf vrf-all {
            mandatory true;
            type vrf-name;
            description
              "VRF name or all";
          }
        }
      }
    }
  }
  augment "/ncs:devices/ncs:device/ncs:rpc" {
    container rpc-clear-bgp-vrf-external-graceful {
      tailf:ncs-device-type "netconf";
      tailf:display-when "not(../../ncs:module) or ../../ncs:module[ncs:name='Cisco-IOS-XR-ipv4-bgp-act']";
      tailf:action clear-bgp-vrf-external-graceful {
        tailf:actionpoint ncsproxy {
          tailf:internal;
        }
        csc:xr-task "bgp";
        csc:cli-command "clear bgp vrf <vrf-all> external graceful";
        description
          "Specify a VRF.
           Clear all external peers.
           Clear with a hard reset and a graceful restart.
          ";
        input {
          leaf vrf-all {
            mandatory true;
            type vrf-name;
            description
              "VRF name or all";
          }
        }
      }
    }
  }
  augment "/ncs:devices/ncs:device-group/ncs:ned-id/ncs:rpc" {
    container rpc-clear-bgp-vrf-external-graceful {
      tailf:ncs-device-type "netconf";
      tailf:display-when "/ncs:devices/ncs:device[ncs:name=current()/../../../ncs:member]/ncs:module[ncs:name='Cisco-IOS-XR-ipv4-bgp-act']";
      tailf:action clear-bgp-vrf-external-graceful {
        tailf:actionpoint ncsproxy {
          tailf:internal;
        }
        csc:xr-task "bgp";
        csc:cli-command "clear bgp vrf <vrf-all> external graceful";
        description
          "Specify a VRF.
           Clear all external peers.
           Clear with a hard reset and a graceful restart.
          ";
        input {
          leaf vrf-all {
            mandatory true;
            type vrf-name;
            description
              "VRF name or all";
          }
        }
      }
    }
  }
  augment "/ncs:devices/ncs:device/ncs:rpc" {
    container rpc-clear-bgp-vrf-as {
      tailf:ncs-device-type "netconf";
      tailf:display-when "not(../../ncs:module) or ../../ncs:module[ncs:name='Cisco-IOS-XR-ipv4-bgp-act']";
      tailf:action clear-bgp-vrf-as {
        tailf:actionpoint ncsproxy {
          tailf:internal;
        }
        csc:xr-task "bgp";
        csc:cli-command "clear bgp vrf <vrf-all> as <as-number>";
        description
          "Specify a VRF.
           Clear peers in a specific AS.
          ";
        input {
          leaf vrf-all {
            mandatory true;
            type vrf-name;
            description
              "VRF name or all";
          }
          leaf as-number {
            mandatory true;
            type as-number;
            description
              "AS number";
          }
        }
      }
    }
  }
  augment "/ncs:devices/ncs:device-group/ncs:ned-id/ncs:rpc" {
    container rpc-clear-bgp-vrf-as {
      tailf:ncs-device-type "netconf";
      tailf:display-when "/ncs:devices/ncs:device[ncs:name=current()/../../../ncs:member]/ncs:module[ncs:name='Cisco-IOS-XR-ipv4-bgp-act']";
      tailf:action clear-bgp-vrf-as {
        tailf:actionpoint ncsproxy {
          tailf:internal;
        }
        csc:xr-task "bgp";
        csc:cli-command "clear bgp vrf <vrf-all> as <as-number>";
        description
          "Specify a VRF.
           Clear peers in a specific AS.
          ";
        input {
          leaf vrf-all {
            mandatory true;
            type vrf-name;
            description
              "VRF name or all";
          }
          leaf as-number {
            mandatory true;
            type as-number;
            description
              "AS number";
          }
        }
      }
    }
  }
  augment "/ncs:devices/ncs:device/ncs:rpc" {
    container rpc-clear-bgp-vrf-as-graceful {
      tailf:ncs-device-type "netconf";
      tailf:display-when "not(../../ncs:module) or ../../ncs:module[ncs:name='Cisco-IOS-XR-ipv4-bgp-act']";
      tailf:action clear-bgp-vrf-as-graceful {
        tailf:actionpoint ncsproxy {
          tailf:internal;
        }
        csc:xr-task "bgp";
        csc:cli-command "clear bgp vrf <vrf-all> as <as-number> graceful";
        description
          "Specify a VRF.
           Clear peers in a specific AS.
           Clear with a hard reset and a graceful restart.
          ";
        input {
          leaf vrf-all {
            mandatory true;
            type vrf-name;
            description
              "VRF name or all";
          }
          leaf as-number {
            mandatory true;
            type as-number;
            description
              "AS number";
          }
        }
      }
    }
  }
  augment "/ncs:devices/ncs:device-group/ncs:ned-id/ncs:rpc" {
    container rpc-clear-bgp-vrf-as-graceful {
      tailf:ncs-device-type "netconf";
      tailf:display-when "/ncs:devices/ncs:device[ncs:name=current()/../../../ncs:member]/ncs:module[ncs:name='Cisco-IOS-XR-ipv4-bgp-act']";
      tailf:action clear-bgp-vrf-as-graceful {
        tailf:actionpoint ncsproxy {
          tailf:internal;
        }
        csc:xr-task "bgp";
        csc:cli-command "clear bgp vrf <vrf-all> as <as-number> graceful";
        description
          "Specify a VRF.
           Clear peers in a specific AS.
           Clear with a hard reset and a graceful restart.
          ";
        input {
          leaf vrf-all {
            mandatory true;
            type vrf-name;
            description
              "VRF name or all";
          }
          leaf as-number {
            mandatory true;
            type as-number;
            description
              "AS number";
          }
        }
      }
    }
  }
  augment "/ncs:devices/ncs:device/ncs:rpc" {
    container rpc-clear-bgp-vrf-ip-addr {
      tailf:ncs-device-type "netconf";
      tailf:display-when "not(../../ncs:module) or ../../ncs:module[ncs:name='Cisco-IOS-XR-ipv4-bgp-act']";
      tailf:action clear-bgp-vrf-ip-addr {
        tailf:actionpoint ncsproxy {
          tailf:internal;
        }
        csc:xr-task "bgp";
        csc:cli-command "clear bgp vrf <vrf-all> <ip-addr>";
        description
          "Specify a VRF.
          ";
        input {
          leaf vrf-all {
            mandatory true;
            type vrf-name;
            description
              "VRF name or all";
          }
          leaf ip-addr {
            mandatory true;
            type inet:ip-address;
            description
              "BGP neighbor address to clear";
          }
        }
      }
    }
  }
  augment "/ncs:devices/ncs:device-group/ncs:ned-id/ncs:rpc" {
    container rpc-clear-bgp-vrf-ip-addr {
      tailf:ncs-device-type "netconf";
      tailf:display-when "/ncs:devices/ncs:device[ncs:name=current()/../../../ncs:member]/ncs:module[ncs:name='Cisco-IOS-XR-ipv4-bgp-act']";
      tailf:action clear-bgp-vrf-ip-addr {
        tailf:actionpoint ncsproxy {
          tailf:internal;
        }
        csc:xr-task "bgp";
        csc:cli-command "clear bgp vrf <vrf-all> <ip-addr>";
        description
          "Specify a VRF.
          ";
        input {
          leaf vrf-all {
            mandatory true;
            type vrf-name;
            description
              "VRF name or all";
          }
          leaf ip-addr {
            mandatory true;
            type inet:ip-address;
            description
              "BGP neighbor address to clear";
          }
        }
      }
    }
  }
  augment "/ncs:devices/ncs:device/ncs:rpc" {
    container rpc-clear-bgp-vrf-ip-addr-long-lived-stale {
      tailf:ncs-device-type "netconf";
      tailf:display-when "not(../../ncs:module) or ../../ncs:module[ncs:name='Cisco-IOS-XR-ipv4-bgp-act']";
      tailf:action clear-bgp-vrf-ip-addr-long-lived-stale {
        tailf:actionpoint ncsproxy {
          tailf:internal;
        }
        csc:xr-task "bgp";
        csc:cli-command "clear bgp vrf <vrf-all> <ip-addr> long-lived-stale";
        description
          "Specify a VRF.
           Clear long-lived-stale routes.
          ";
        input {
          leaf vrf-all {
            mandatory true;
            type vrf-name;
            description
              "VRF name or all";
          }
          leaf ip-addr {
            mandatory true;
            type inet:ip-address;
            description
              "BGP neighbor address to clear";
          }
        }
      }
    }
  }
  augment "/ncs:devices/ncs:device-group/ncs:ned-id/ncs:rpc" {
    container rpc-clear-bgp-vrf-ip-addr-long-lived-stale {
      tailf:ncs-device-type "netconf";
      tailf:display-when "/ncs:devices/ncs:device[ncs:name=current()/../../../ncs:member]/ncs:module[ncs:name='Cisco-IOS-XR-ipv4-bgp-act']";
      tailf:action clear-bgp-vrf-ip-addr-long-lived-stale {
        tailf:actionpoint ncsproxy {
          tailf:internal;
        }
        csc:xr-task "bgp";
        csc:cli-command "clear bgp vrf <vrf-all> <ip-addr> long-lived-stale";
        description
          "Specify a VRF.
           Clear long-lived-stale routes.
          ";
        input {
          leaf vrf-all {
            mandatory true;
            type vrf-name;
            description
              "VRF name or all";
          }
          leaf ip-addr {
            mandatory true;
            type inet:ip-address;
            description
              "BGP neighbor address to clear";
          }
        }
      }
    }
  }
  augment "/ncs:devices/ncs:device/ncs:rpc" {
    container rpc-clear-bgp-vrf-ip-addr-graceful {
      tailf:ncs-device-type "netconf";
      tailf:display-when "not(../../ncs:module) or ../../ncs:module[ncs:name='Cisco-IOS-XR-ipv4-bgp-act']";
      tailf:action clear-bgp-vrf-ip-addr-graceful {
        tailf:actionpoint ncsproxy {
          tailf:internal;
        }
        csc:xr-task "bgp";
        csc:cli-command "clear bgp vrf <vrf-all> <ip-addr> graceful";
        description
          "Specify a VRF.
           Clear with a hard reset and a graceful restart.
          ";
        input {
          leaf vrf-all {
            mandatory true;
            type vrf-name;
            description
              "VRF name or all";
          }
          leaf ip-addr {
            mandatory true;
            type inet:ip-address;
            description
              "BGP neighbor address to clear";
          }
        }
      }
    }
  }
  augment "/ncs:devices/ncs:device-group/ncs:ned-id/ncs:rpc" {
    container rpc-clear-bgp-vrf-ip-addr-graceful {
      tailf:ncs-device-type "netconf";
      tailf:display-when "/ncs:devices/ncs:device[ncs:name=current()/../../../ncs:member]/ncs:module[ncs:name='Cisco-IOS-XR-ipv4-bgp-act']";
      tailf:action clear-bgp-vrf-ip-addr-graceful {
        tailf:actionpoint ncsproxy {
          tailf:internal;
        }
        csc:xr-task "bgp";
        csc:cli-command "clear bgp vrf <vrf-all> <ip-addr> graceful";
        description
          "Specify a VRF.
           Clear with a hard reset and a graceful restart.
          ";
        input {
          leaf vrf-all {
            mandatory true;
            type vrf-name;
            description
              "VRF name or all";
          }
          leaf ip-addr {
            mandatory true;
            type inet:ip-address;
            description
              "BGP neighbor address to clear";
          }
        }
      }
    }
  }
  augment "/ncs:devices/ncs:device/ncs:rpc" {
    container rpc-clear-bgp-vrf-all {
      tailf:ncs-device-type "netconf";
      tailf:display-when "not(../../ncs:module) or ../../ncs:module[ncs:name='Cisco-IOS-XR-ipv4-bgp-act']";
      tailf:action clear-bgp-vrf-all {
        tailf:actionpoint ncsproxy {
          tailf:internal;
        }
        csc:xr-task "bgp";
        csc:cli-command "clear bgp vrf <vrf-all> *";
        description
          "Specify a VRF.
           Clear all peers and all routes from the BGP table.
          ";
        input {
          leaf vrf-all {
            mandatory true;
            type vrf-name;
            description
              "VRF name or all";
          }
        }
      }
    }
  }
  augment "/ncs:devices/ncs:device-group/ncs:ned-id/ncs:rpc" {
    container rpc-clear-bgp-vrf-all {
      tailf:ncs-device-type "netconf";
      tailf:display-when "/ncs:devices/ncs:device[ncs:name=current()/../../../ncs:member]/ncs:module[ncs:name='Cisco-IOS-XR-ipv4-bgp-act']";
      tailf:action clear-bgp-vrf-all {
        tailf:actionpoint ncsproxy {
          tailf:internal;
        }
        csc:xr-task "bgp";
        csc:cli-command "clear bgp vrf <vrf-all> *";
        description
          "Specify a VRF.
           Clear all peers and all routes from the BGP table.
          ";
        input {
          leaf vrf-all {
            mandatory true;
            type vrf-name;
            description
              "VRF name or all";
          }
        }
      }
    }
  }
  augment "/ncs:devices/ncs:device/ncs:rpc" {
    container rpc-clear-bgp-vrf-rpki-validation {
      tailf:ncs-device-type "netconf";
      tailf:display-when "not(../../ncs:module) or ../../ncs:module[ncs:name='Cisco-IOS-XR-ipv4-bgp-act']";
      tailf:action clear-bgp-vrf-rpki-validation {
        tailf:actionpoint ncsproxy {
          tailf:internal;
        }
        csc:xr-task "bgp";
        csc:cli-command "clear bgp vrf <vrf-all> rpki validation";
        description
          "RPKI clear command.
           clear RPKI origin-validation (trigger origin validation).
          ";
        input {
          leaf vrf-all {
            mandatory true;
            type vrf-name;
            description
              "VRF name or all";
          }
        }
      }
    }
  }
  augment "/ncs:devices/ncs:device-group/ncs:ned-id/ncs:rpc" {
    container rpc-clear-bgp-vrf-rpki-validation {
      tailf:ncs-device-type "netconf";
      tailf:display-when "/ncs:devices/ncs:device[ncs:name=current()/../../../ncs:member]/ncs:module[ncs:name='Cisco-IOS-XR-ipv4-bgp-act']";
      tailf:action clear-bgp-vrf-rpki-validation {
        tailf:actionpoint ncsproxy {
          tailf:internal;
        }
        csc:xr-task "bgp";
        csc:cli-command "clear bgp vrf <vrf-all> rpki validation";
        description
          "RPKI clear command.
           clear RPKI origin-validation (trigger origin validation).
          ";
        input {
          leaf vrf-all {
            mandatory true;
            type vrf-name;
            description
              "VRF name or all";
          }
        }
      }
    }
  }
  augment "/ncs:devices/ncs:device/ncs:rpc" {
    container rpc-clear-bgp-vrf-rpki-validation-ipv6 {
      tailf:ncs-device-type "netconf";
      tailf:display-when "not(../../ncs:module) or ../../ncs:module[ncs:name='Cisco-IOS-XR-ipv4-bgp-act']";
      tailf:action clear-bgp-vrf-rpki-validation-ipv6 {
        tailf:actionpoint ncsproxy {
          tailf:internal;
        }
        csc:xr-task "bgp";
        csc:cli-command "clear bgp vrf <vrf-all> rpki validation ipv6";
        description
          "RPKI clear command.
           clear RPKI origin-validation (trigger origin validation).
           trigger origin validation walk for the IPv6 table.
          ";
        input {
          leaf vrf-all {
            mandatory true;
            type vrf-name;
            description
              "VRF name or all";
          }
        }
      }
    }
  }
  augment "/ncs:devices/ncs:device-group/ncs:ned-id/ncs:rpc" {
    container rpc-clear-bgp-vrf-rpki-validation-ipv6 {
      tailf:ncs-device-type "netconf";
      tailf:display-when "/ncs:devices/ncs:device[ncs:name=current()/../../../ncs:member]/ncs:module[ncs:name='Cisco-IOS-XR-ipv4-bgp-act']";
      tailf:action clear-bgp-vrf-rpki-validation-ipv6 {
        tailf:actionpoint ncsproxy {
          tailf:internal;
        }
        csc:xr-task "bgp";
        csc:cli-command "clear bgp vrf <vrf-all> rpki validation ipv6";
        description
          "RPKI clear command.
           clear RPKI origin-validation (trigger origin validation).
           trigger origin validation walk for the IPv6 table.
          ";
        input {
          leaf vrf-all {
            mandatory true;
            type vrf-name;
            description
              "VRF name or all";
          }
        }
      }
    }
  }
  augment "/ncs:devices/ncs:device/ncs:rpc" {
    container rpc-clear-bgp-vrf-rpki-validation-ipv4 {
      tailf:ncs-device-type "netconf";
      tailf:display-when "not(../../ncs:module) or ../../ncs:module[ncs:name='Cisco-IOS-XR-ipv4-bgp-act']";
      tailf:action clear-bgp-vrf-rpki-validation-ipv4 {
        tailf:actionpoint ncsproxy {
          tailf:internal;
        }
        csc:xr-task "bgp";
        csc:cli-command "clear bgp vrf <vrf-all> rpki validation ipv4";
        description
          "RPKI clear command.
           clear RPKI origin-validation (trigger origin validation).
           trigger origin validation walk for the IPv4 table.
          ";
        input {
          leaf vrf-all {
            mandatory true;
            type vrf-name;
            description
              "VRF name or all";
          }
        }
      }
    }
  }
  augment "/ncs:devices/ncs:device-group/ncs:ned-id/ncs:rpc" {
    container rpc-clear-bgp-vrf-rpki-validation-ipv4 {
      tailf:ncs-device-type "netconf";
      tailf:display-when "/ncs:devices/ncs:device[ncs:name=current()/../../../ncs:member]/ncs:module[ncs:name='Cisco-IOS-XR-ipv4-bgp-act']";
      tailf:action clear-bgp-vrf-rpki-validation-ipv4 {
        tailf:actionpoint ncsproxy {
          tailf:internal;
        }
        csc:xr-task "bgp";
        csc:cli-command "clear bgp vrf <vrf-all> rpki validation ipv4";
        description
          "RPKI clear command.
           clear RPKI origin-validation (trigger origin validation).
           trigger origin validation walk for the IPv4 table.
          ";
        input {
          leaf vrf-all {
            mandatory true;
            type vrf-name;
            description
              "VRF name or all";
          }
        }
      }
    }
  }
  augment "/ncs:devices/ncs:device/ncs:rpc" {
    container rpc-clear-bgp-instance-vrf-rpki-validation {
      tailf:ncs-device-type "netconf";
      tailf:display-when "not(../../ncs:module) or ../../ncs:module[ncs:name='Cisco-IOS-XR-ipv4-bgp-act']";
      tailf:action clear-bgp-instance-vrf-rpki-validation {
        tailf:actionpoint ncsproxy {
          tailf:internal;
        }
        csc:xr-task "bgp";
        csc:cli-command "clear bgp instance <instance-name> vrf <vrf-all> rpki validation";
        description
          "Choose a particular BGP instance and VRF.
           RPKI clear command.
           clear RPKI origin-validation (trigger origin validation).
          ";
        input {
          leaf instance-name {
            mandatory true;
            type instance-name;
            description
              "instance name or all";
          }
          leaf vrf-all {
            mandatory true;
            type vrf-name;
            description
              "VRF name or all";
          }
        }
      }
    }
  }
  augment "/ncs:devices/ncs:device-group/ncs:ned-id/ncs:rpc" {
    container rpc-clear-bgp-instance-vrf-rpki-validation {
      tailf:ncs-device-type "netconf";
      tailf:display-when "/ncs:devices/ncs:device[ncs:name=current()/../../../ncs:member]/ncs:module[ncs:name='Cisco-IOS-XR-ipv4-bgp-act']";
      tailf:action clear-bgp-instance-vrf-rpki-validation {
        tailf:actionpoint ncsproxy {
          tailf:internal;
        }
        csc:xr-task "bgp";
        csc:cli-command "clear bgp instance <instance-name> vrf <vrf-all> rpki validation";
        description
          "Choose a particular BGP instance and VRF.
           RPKI clear command.
           clear RPKI origin-validation (trigger origin validation).
          ";
        input {
          leaf instance-name {
            mandatory true;
            type instance-name;
            description
              "instance name or all";
          }
          leaf vrf-all {
            mandatory true;
            type vrf-name;
            description
              "VRF name or all";
          }
        }
      }
    }
  }
  augment "/ncs:devices/ncs:device/ncs:rpc" {
    container rpc-clear-bgp-instance-vrf-rpki-validation-ipv6 {
      tailf:ncs-device-type "netconf";
      tailf:display-when "not(../../ncs:module) or ../../ncs:module[ncs:name='Cisco-IOS-XR-ipv4-bgp-act']";
      tailf:action clear-bgp-instance-vrf-rpki-validation-ipv6 {
        tailf:actionpoint ncsproxy {
          tailf:internal;
        }
        csc:xr-task "bgp";
        csc:cli-command "clear bgp instance <instance-name> vrf <vrf-all> rpki validation ipv6";
        description
          "Choose a particular BGP instance and VRF.
           RPKI clear command.
           clear RPKI origin-validation (trigger origin validation).
           trigger origin validation walk for the IPv6 table.
          ";
        input {
          leaf instance-name {
            mandatory true;
            type instance-name;
            description
              "instance name or all";
          }
          leaf vrf-all {
            mandatory true;
            type vrf-name;
            description
              "VRF name or all";
          }
        }
      }
    }
  }
  augment "/ncs:devices/ncs:device-group/ncs:ned-id/ncs:rpc" {
    container rpc-clear-bgp-instance-vrf-rpki-validation-ipv6 {
      tailf:ncs-device-type "netconf";
      tailf:display-when "/ncs:devices/ncs:device[ncs:name=current()/../../../ncs:member]/ncs:module[ncs:name='Cisco-IOS-XR-ipv4-bgp-act']";
      tailf:action clear-bgp-instance-vrf-rpki-validation-ipv6 {
        tailf:actionpoint ncsproxy {
          tailf:internal;
        }
        csc:xr-task "bgp";
        csc:cli-command "clear bgp instance <instance-name> vrf <vrf-all> rpki validation ipv6";
        description
          "Choose a particular BGP instance and VRF.
           RPKI clear command.
           clear RPKI origin-validation (trigger origin validation).
           trigger origin validation walk for the IPv6 table.
          ";
        input {
          leaf instance-name {
            mandatory true;
            type instance-name;
            description
              "instance name or all";
          }
          leaf vrf-all {
            mandatory true;
            type vrf-name;
            description
              "VRF name or all";
          }
        }
      }
    }
  }
  augment "/ncs:devices/ncs:device/ncs:rpc" {
    container rpc-clear-bgp-instance-vrf-rpki-validation-ipv4 {
      tailf:ncs-device-type "netconf";
      tailf:display-when "not(../../ncs:module) or ../../ncs:module[ncs:name='Cisco-IOS-XR-ipv4-bgp-act']";
      tailf:action clear-bgp-instance-vrf-rpki-validation-ipv4 {
        tailf:actionpoint ncsproxy {
          tailf:internal;
        }
        csc:xr-task "bgp";
        csc:cli-command "clear bgp instance <instance-name> vrf <vrf-all> rpki validation ipv4";
        description
          "Choose a particular BGP instance and VRF.
           RPKI clear command.
           clear RPKI origin-validation (trigger origin validation).
           trigger origin validation walk for the IPv4 table.
          ";
        input {
          leaf instance-name {
            mandatory true;
            type instance-name;
            description
              "instance name or all";
          }
          leaf vrf-all {
            mandatory true;
            type vrf-name;
            description
              "VRF name or all";
          }
        }
      }
    }
  }
  augment "/ncs:devices/ncs:device-group/ncs:ned-id/ncs:rpc" {
    container rpc-clear-bgp-instance-vrf-rpki-validation-ipv4 {
      tailf:ncs-device-type "netconf";
      tailf:display-when "/ncs:devices/ncs:device[ncs:name=current()/../../../ncs:member]/ncs:module[ncs:name='Cisco-IOS-XR-ipv4-bgp-act']";
      tailf:action clear-bgp-instance-vrf-rpki-validation-ipv4 {
        tailf:actionpoint ncsproxy {
          tailf:internal;
        }
        csc:xr-task "bgp";
        csc:cli-command "clear bgp instance <instance-name> vrf <vrf-all> rpki validation ipv4";
        description
          "Choose a particular BGP instance and VRF.
           RPKI clear command.
           clear RPKI origin-validation (trigger origin validation).
           trigger origin validation walk for the IPv4 table.
          ";
        input {
          leaf instance-name {
            mandatory true;
            type instance-name;
            description
              "instance name or all";
          }
          leaf vrf-all {
            mandatory true;
            type vrf-name;
            description
              "VRF name or all";
          }
        }
      }
    }
  }
  augment "/ncs:devices/ncs:device/ncs:rpc" {
    container rpc-clear-bgp-vrf-all-graceful {
      tailf:ncs-device-type "netconf";
      tailf:display-when "not(../../ncs:module) or ../../ncs:module[ncs:name='Cisco-IOS-XR-ipv4-bgp-act']";
      tailf:action clear-bgp-vrf-all-graceful {
        tailf:actionpoint ncsproxy {
          tailf:internal;
        }
        csc:xr-task "bgp";
        csc:cli-command "clear bgp vrf <vrf-all> * graceful";
        description
          "Specify a VRF.
           Clear all peers and all routes from the BGP table.
           Clear with a hard reset and a graceful restart.
          ";
        input {
          leaf vrf-all {
            mandatory true;
            type vrf-name;
            description
              "VRF name or all";
          }
        }
      }
    }
  }
  augment "/ncs:devices/ncs:device-group/ncs:ned-id/ncs:rpc" {
    container rpc-clear-bgp-vrf-all-graceful {
      tailf:ncs-device-type "netconf";
      tailf:display-when "/ncs:devices/ncs:device[ncs:name=current()/../../../ncs:member]/ncs:module[ncs:name='Cisco-IOS-XR-ipv4-bgp-act']";
      tailf:action clear-bgp-vrf-all-graceful {
        tailf:actionpoint ncsproxy {
          tailf:internal;
        }
        csc:xr-task "bgp";
        csc:cli-command "clear bgp vrf <vrf-all> * graceful";
        description
          "Specify a VRF.
           Clear all peers and all routes from the BGP table.
           Clear with a hard reset and a graceful restart.
          ";
        input {
          leaf vrf-all {
            mandatory true;
            type vrf-name;
            description
              "VRF name or all";
          }
        }
      }
    }
  }
  augment "/ncs:devices/ncs:device/ncs:rpc" {
    container rpc-clear-bgp-version-vrf-afi-safi {
      tailf:ncs-device-type "netconf";
      tailf:display-when "not(../../ncs:module) or ../../ncs:module[ncs:name='Cisco-IOS-XR-ipv4-bgp-act']";
      tailf:action clear-bgp-version-vrf-afi-safi {
        tailf:actionpoint ncsproxy {
          tailf:internal;
        }
        csc:xr-task "bgp";
        csc:cli-command "clear bgp version vrf <vrf-all> <afi-safi-name>";
        description
          "clear BGP prefix version.
           Specify a VRF.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-version-vrf-afi-safi {
      tailf:ncs-device-type "netconf";
      tailf:display-when "/ncs:devices/ncs:device[ncs:name=current()/../../../ncs:member]/ncs:module[ncs:name='Cisco-IOS-XR-ipv4-bgp-act']";
      tailf:action clear-bgp-version-vrf-afi-safi {
        tailf:actionpoint ncsproxy {
          tailf:internal;
        }
        csc:xr-task "bgp";
        csc:cli-command "clear bgp version vrf <vrf-all> <afi-safi-name>";
        description
          "clear BGP prefix version.
           Specify a VRF.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-version-vrf-afi-safi-vrf {
      tailf:ncs-device-type "netconf";
      tailf:display-when "not(../../ncs:module) or ../../ncs:module[ncs:name='Cisco-IOS-XR-ipv4-bgp-act']";
      tailf:action clear-bgp-version-vrf-afi-safi-vrf {
        tailf:actionpoint ncsproxy {
          tailf:internal;
        }
        csc:xr-task "bgp";
        csc:cli-command "clear bgp version vrf <vrf-all> <afi-safi-name> vrf <vrf-name>";
        description
          "clear BGP prefix version.
           Specify a VRF.
           Display routes for a specified VRF.
          ";
        input {
          leaf vrf-all {
            mandatory true;
            type vrf-name;
            description
              "VRF name or all";
          }
          leaf afi-safi-name {
            mandatory true;
            type afi-safi-type;
            description
              "AFI and SAFI";
          }
          leaf vrf-name {
            mandatory true;
            type string;
            description
              "VRF name";
          }
        }
      }
    }
  }
  augment "/ncs:devices/ncs:device-group/ncs:ned-id/ncs:rpc" {
    container rpc-clear-bgp-version-vrf-afi-safi-vrf {
      tailf:ncs-device-type "netconf";
      tailf:display-when "/ncs:devices/ncs:device[ncs:name=current()/../../../ncs:member]/ncs:module[ncs:name='Cisco-IOS-XR-ipv4-bgp-act']";
      tailf:action clear-bgp-version-vrf-afi-safi-vrf {
        tailf:actionpoint ncsproxy {
          tailf:internal;
        }
        csc:xr-task "bgp";
        csc:cli-command "clear bgp version vrf <vrf-all> <afi-safi-name> vrf <vrf-name>";
        description
          "clear BGP prefix version.
           Specify a VRF.
           Display routes for a specified VRF.
          ";
        input {
          leaf vrf-all {
            mandatory true;
            type vrf-name;
            description
              "VRF name or all";
          }
          leaf afi-safi-name {
            mandatory true;
            type afi-safi-type;
            description
              "AFI and SAFI";
          }
          leaf vrf-name {
            mandatory true;
            type string;
            description
              "VRF name";
          }
        }
      }
    }
  }
  augment "/ncs:devices/ncs:device/ncs:rpc" {
    container rpc-clear-bgp-version-vrf-afi-safi-rd {
      tailf:ncs-device-type "netconf";
      tailf:display-when "not(../../ncs:module) or ../../ncs:module[ncs:name='Cisco-IOS-XR-ipv4-bgp-act']";
      tailf:action clear-bgp-version-vrf-afi-safi-rd {
        tailf:actionpoint ncsproxy {
          tailf:internal;
        }
        csc:xr-task "bgp";
        csc:cli-command "clear bgp version vrf <vrf-all> <afi-safi-name> rd <rd>";
        description
          "clear BGP prefix version.
           Specify a VRF.
           Display routes with a specific route distinguisher.
          ";
        input {
          leaf vrf-all {
            mandatory true;
            type vrf-name;
            description
              "VRF name or all";
          }
          leaf afi-safi-name {
            mandatory true;
            type afi-safi-type;
            description
              "AFI and SAFI";
          }
          leaf rd {
            mandatory true;
            type rd;
            description
              "Route distinguisher";
          }
        }
      }
    }
  }
  augment "/ncs:devices/ncs:device-group/ncs:ned-id/ncs:rpc" {
    container rpc-clear-bgp-version-vrf-afi-safi-rd {
      tailf:ncs-device-type "netconf";
      tailf:display-when "/ncs:devices/ncs:device[ncs:name=current()/../../../ncs:member]/ncs:module[ncs:name='Cisco-IOS-XR-ipv4-bgp-act']";
      tailf:action clear-bgp-version-vrf-afi-safi-rd {
        tailf:actionpoint ncsproxy {
          tailf:internal;
        }
        csc:xr-task "bgp";
        csc:cli-command "clear bgp version vrf <vrf-all> <afi-safi-name> rd <rd>";
        description
          "clear BGP prefix version.
           Specify a VRF.
           Display routes with a specific route distinguisher.
          ";
        input {
          leaf vrf-all {
            mandatory true;
            type vrf-name;
            description
              "VRF name or all";
          }
          leaf afi-safi-name {
            mandatory true;
            type afi-safi-type;
            description
              "AFI and SAFI";
          }
          leaf rd {
            mandatory true;
            type rd;
            description
              "Route distinguisher";
          }
        }
      }
    }
  }
  augment "/ncs:devices/ncs:device/ncs:rpc" {
    container rpc-clear-bgp-version-vrf-afi-safi-ipv6-prefix {
      tailf:ncs-device-type "netconf";
      tailf:display-when "not(../../ncs:module) or ../../ncs:module[ncs:name='Cisco-IOS-XR-ipv4-bgp-act']";
      tailf:action clear-bgp-version-vrf-afi-safi-ipv6-prefix {
        tailf:actionpoint ncsproxy {
          tailf:internal;
        }
        csc:xr-task "bgp";
        csc:cli-command "clear bgp version vrf <vrf-all> <afi-safi-name> <ipv6-prefix>";
        description
          "clear BGP prefix version.
           Specify a VRF.
          ";
        input {
          leaf vrf-all {
            mandatory true;
            type vrf-name;
            description
              "VRF name or all";
          }
          leaf afi-safi-name {
            mandatory true;
            type afi-safi-type;
            description
              "AFI and SAFI";
          }
          leaf ipv6-prefix {
            mandatory true;
            type inet:ipv6-prefix;
            description
              "IPv6 network and masklength";
          }
        }
      }
    }
  }
  augment "/ncs:devices/ncs:device-group/ncs:ned-id/ncs:rpc" {
    container rpc-clear-bgp-version-vrf-afi-safi-ipv6-prefix {
      tailf:ncs-device-type "netconf";
      tailf:display-when "/ncs:devices/ncs:device[ncs:name=current()/../../../ncs:member]/ncs:module[ncs:name='Cisco-IOS-XR-ipv4-bgp-act']";
      tailf:action clear-bgp-version-vrf-afi-safi-ipv6-prefix {
        tailf:actionpoint ncsproxy {
          tailf:internal;
        }
        csc:xr-task "bgp";
        csc:cli-command "clear bgp version vrf <vrf-all> <afi-safi-name> <ipv6-prefix>";
        description
          "clear BGP prefix version.
           Specify a VRF.
          ";
        input {
          leaf vrf-all {
            mandatory true;
            type vrf-name;
            description
              "VRF name or all";
          }
          leaf afi-safi-name {
            mandatory true;
            type afi-safi-type;
            description
              "AFI and SAFI";
          }
          leaf ipv6-prefix {
            mandatory true;
            type inet:ipv6-prefix;
            description
              "IPv6 network and masklength";
          }
        }
      }
    }
  }
  augment "/ncs:devices/ncs:device/ncs:rpc" {
    container rpc-clear-bgp-version-vrf-afi-safi-ipv6-addr {
      tailf:ncs-device-type "netconf";
      tailf:display-when "not(../../ncs:module) or ../../ncs:module[ncs:name='Cisco-IOS-XR-ipv4-bgp-act']";
      tailf:action clear-bgp-version-vrf-afi-safi-ipv6-addr {
        tailf:actionpoint ncsproxy {
          tailf:internal;
        }
        csc:xr-task "bgp";
        csc:cli-command "clear bgp version vrf <vrf-all> <afi-safi-name> <ipv6-addr>";
        description
          "clear BGP prefix version.
           Specify a VRF.
          ";
        input {
          leaf vrf-all {
            mandatory true;
            type vrf-name;
            description
              "VRF name or all";
          }
          leaf afi-safi-name {
            mandatory true;
            type afi-safi-type;
            description
              "AFI and SAFI";
          }
          leaf ipv6-addr {
            mandatory true;
            type inet:ipv6-address;
            description
              "IPv6 network";
          }
        }
      }
    }
  }
  augment "/ncs:devices/ncs:device-group/ncs:ned-id/ncs:rpc" {
    container rpc-clear-bgp-version-vrf-afi-safi-ipv6-addr {
      tailf:ncs-device-type "netconf";
      tailf:display-when "/ncs:devices/ncs:device[ncs:name=current()/../../../ncs:member]/ncs:module[ncs:name='Cisco-IOS-XR-ipv4-bgp-act']";
      tailf:action clear-bgp-version-vrf-afi-safi-ipv6-addr {
        tailf:actionpoint ncsproxy {
          tailf:internal;
        }
        csc:xr-task "bgp";
        csc:cli-command "clear bgp version vrf <vrf-all> <afi-safi-name> <ipv6-addr>";
        description
          "clear BGP prefix version.
           Specify a VRF.
          ";
        input {
          leaf vrf-all {
            mandatory true;
            type vrf-name;
            description
              "VRF name or all";
          }
          leaf afi-safi-name {
            mandatory true;
            type afi-safi-type;
            description
              "AFI and SAFI";
          }
          leaf ipv6-addr {
            mandatory true;
            type inet:ipv6-address;
            description
              "IPv6 network";
          }
        }
      }
    }
  }
  augment "/ncs:devices/ncs:device/ncs:rpc" {
    container rpc-clear-bgp-version-vrf-afi-safi-ipv6-addr-ipv6-netmask {
      tailf:ncs-device-type "netconf";
      tailf:display-when "not(../../ncs:module) or ../../ncs:module[ncs:name='Cisco-IOS-XR-ipv4-bgp-act']";
      tailf:action clear-bgp-version-vrf-afi-safi-ipv6-addr-ipv6-netmask {
        tailf:actionpoint ncsproxy {
          tailf:internal;
        }
        csc:xr-task "bgp";
        csc:cli-command "clear bgp version vrf <vrf-all> <afi-safi-name> <ipv6-addr> <ipv6-netmask>";
        description
          "clear BGP prefix version.
           Specify a VRF.
          ";
        input {
          leaf vrf-all {
            mandatory true;
            type vrf-name;
            description
              "VRF name or all";
          }
          leaf afi-safi-name {
            mandatory true;
            type afi-safi-type;
            description
              "AFI and SAFI";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device-group/ncs:ned-id/ncs:rpc" {
    container rpc-clear-bgp-version-vrf-afi-safi-ipv6-addr-ipv6-netmask {
      tailf:ncs-device-type "netconf";
      tailf:display-when "/ncs:devices/ncs:device[ncs:name=current()/../../../ncs:member]/ncs:module[ncs:name='Cisco-IOS-XR-ipv4-bgp-act']";
      tailf:action clear-bgp-version-vrf-afi-safi-ipv6-addr-ipv6-netmask {
        tailf:actionpoint ncsproxy {
          tailf:internal;
        }
        csc:xr-task "bgp";
        csc:cli-command "clear bgp version vrf <vrf-all> <afi-safi-name> <ipv6-addr> <ipv6-netmask>";
        description
          "clear BGP prefix version.
           Specify a VRF.
          ";
        input {
          leaf vrf-all {
            mandatory true;
            type vrf-name;
            description
              "VRF name or all";
          }
          leaf afi-safi-name {
            mandatory true;
            type afi-safi-type;
            description
              "AFI and SAFI";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device/ncs:rpc" {
    container rpc-clear-bgp-version-vrf-afi-safi-vrf-network {
      tailf:ncs-device-type "netconf";
      tailf:display-when "not(../../ncs:module) or ../../ncs:module[ncs:name='Cisco-IOS-XR-ipv4-bgp-act']";
      tailf:action clear-bgp-version-vrf-afi-safi-vrf-network {
        tailf:actionpoint ncsproxy {
          tailf:internal;
        }
        csc:xr-task "bgp";
        csc:cli-command "clear bgp version vrf <vrf-all> <afi-safi-name> vrf <vrf-name> <network>";
        description
          "clear BGP prefix version.
           Specify a VRF.
           Display routes for a specified VRF.
          ";
        input {
          leaf vrf-all {
            mandatory true;
            type vrf-name;
            description
              "VRF name or all";
          }
          leaf afi-safi-name {
            mandatory true;
            type afi-safi-type;
            description
              "AFI and SAFI";
          }
          leaf vrf-name {
            mandatory true;
            type string;
            description
              "VRF name";
          }
          leaf network {
            mandatory true;
            type string;
            description
              "Address family modifier specific network";
          }
        }
      }
    }
  }
  augment "/ncs:devices/ncs:device-group/ncs:ned-id/ncs:rpc" {
    container rpc-clear-bgp-version-vrf-afi-safi-vrf-network {
      tailf:ncs-device-type "netconf";
      tailf:display-when "/ncs:devices/ncs:device[ncs:name=current()/../../../ncs:member]/ncs:module[ncs:name='Cisco-IOS-XR-ipv4-bgp-act']";
      tailf:action clear-bgp-version-vrf-afi-safi-vrf-network {
        tailf:actionpoint ncsproxy {
          tailf:internal;
        }
        csc:xr-task "bgp";
        csc:cli-command "clear bgp version vrf <vrf-all> <afi-safi-name> vrf <vrf-name> <network>";
        description
          "clear BGP prefix version.
           Specify a VRF.
           Display routes for a specified VRF.
          ";
        input {
          leaf vrf-all {
            mandatory true;
            type vrf-name;
            description
              "VRF name or all";
          }
          leaf afi-safi-name {
            mandatory true;
            type afi-safi-type;
            description
              "AFI and SAFI";
          }
          leaf vrf-name {
            mandatory true;
            type string;
            description
              "VRF name";
          }
          leaf network {
            mandatory true;
            type string;
            description
              "Address family modifier specific network";
          }
        }
      }
    }
  }
  augment "/ncs:devices/ncs:device/ncs:rpc" {
    container rpc-clear-bgp-version-vrf-afi-safi-rd-network {
      tailf:ncs-device-type "netconf";
      tailf:display-when "not(../../ncs:module) or ../../ncs:module[ncs:name='Cisco-IOS-XR-ipv4-bgp-act']";
      tailf:action clear-bgp-version-vrf-afi-safi-rd-network {
        tailf:actionpoint ncsproxy {
          tailf:internal;
        }
        csc:xr-task "bgp";
        csc:cli-command "clear bgp version vrf <vrf-all> <afi-safi-name> rd <rd> <network>";
        description
          "clear BGP prefix version.
           Specify a VRF.
           Display routes with a specific route distinguisher.
          ";
        input {
          leaf vrf-all {
            mandatory true;
            type vrf-name;
            description
              "VRF name or all";
          }
          leaf afi-safi-name {
            mandatory true;
            type afi-safi-type;
            description
              "AFI and SAFI";
          }
          leaf rd {
            mandatory true;
            type rd;
            description
              "Route distinguisher";
          }
          leaf network {
            mandatory true;
            type string;
            description
              "Address family modifier specific network";
          }
        }
      }
    }
  }
  augment "/ncs:devices/ncs:device-group/ncs:ned-id/ncs:rpc" {
    container rpc-clear-bgp-version-vrf-afi-safi-rd-network {
      tailf:ncs-device-type "netconf";
      tailf:display-when "/ncs:devices/ncs:device[ncs:name=current()/../../../ncs:member]/ncs:module[ncs:name='Cisco-IOS-XR-ipv4-bgp-act']";
      tailf:action clear-bgp-version-vrf-afi-safi-rd-network {
        tailf:actionpoint ncsproxy {
          tailf:internal;
        }
        csc:xr-task "bgp";
        csc:cli-command "clear bgp version vrf <vrf-all> <afi-safi-name> rd <rd> <network>";
        description
          "clear BGP prefix version.
           Specify a VRF.
           Display routes with a specific route distinguisher.
          ";
        input {
          leaf vrf-all {
            mandatory true;
            type vrf-name;
            description
              "VRF name or all";
          }
          leaf afi-safi-name {
            mandatory true;
            type afi-safi-type;
            description
              "AFI and SAFI";
          }
          leaf rd {
            mandatory true;
            type rd;
            description
              "Route distinguisher";
          }
          leaf network {
            mandatory true;
            type string;
            description
              "Address family modifier specific network";
          }
        }
      }
    }
  }
  augment "/ncs:devices/ncs:device/ncs:rpc" {
    container rpc-clear-bgp-version-vrf-afi-safi-network {
      tailf:ncs-device-type "netconf";
      tailf:display-when "not(../../ncs:module) or ../../ncs:module[ncs:name='Cisco-IOS-XR-ipv4-bgp-act']";
      tailf:action clear-bgp-version-vrf-afi-safi-network {
        tailf:actionpoint ncsproxy {
          tailf:internal;
        }
        csc:xr-task "bgp";
        csc:cli-command "clear bgp version vrf <vrf-all> <afi-safi-name> <network>";
        description
          "clear BGP prefix version.
           Specify a VRF.
          ";
        input {
          leaf vrf-all {
            mandatory true;
            type vrf-name;
            description
              "VRF name or all";
          }
          leaf afi-safi-name {
            mandatory true;
            type afi-safi-type;
            description
              "AFI and SAFI";
          }
          leaf network {
            mandatory true;
            type string;
            description
              "Address family modifier specific network";
          }
        }
      }
    }
  }
  augment "/ncs:devices/ncs:device-group/ncs:ned-id/ncs:rpc" {
    container rpc-clear-bgp-version-vrf-afi-safi-network {
      tailf:ncs-device-type "netconf";
      tailf:display-when "/ncs:devices/ncs:device[ncs:name=current()/../../../ncs:member]/ncs:module[ncs:name='Cisco-IOS-XR-ipv4-bgp-act']";
      tailf:action clear-bgp-version-vrf-afi-safi-network {
        tailf:actionpoint ncsproxy {
          tailf:internal;
        }
        csc:xr-task "bgp";
        csc:cli-command "clear bgp version vrf <vrf-all> <afi-safi-name> <network>";
        description
          "clear BGP prefix version.
           Specify a VRF.
          ";
        input {
          leaf vrf-all {
            mandatory true;
            type vrf-name;
            description
              "VRF name or all";
          }
          leaf afi-safi-name {
            mandatory true;
            type afi-safi-type;
            description
              "AFI and SAFI";
          }
          leaf network {
            mandatory true;
            type string;
            description
              "Address family modifier specific network";
          }
        }
      }
    }
  }
  augment "/ncs:devices/ncs:device/ncs:rpc" {
    container rpc-clear-bgp-version-vrf-afi-safi-ipv4-addr {
      tailf:ncs-device-type "netconf";
      tailf:display-when "not(../../ncs:module) or ../../ncs:module[ncs:name='Cisco-IOS-XR-ipv4-bgp-act']";
      tailf:action clear-bgp-version-vrf-afi-safi-ipv4-addr {
        tailf:actionpoint ncsproxy {
          tailf:internal;
        }
        csc:xr-task "bgp";
        csc:cli-command "clear bgp version vrf <vrf-all> <afi-safi-name> <ipv4-addr>";
        description
          "clear BGP prefix version.
           Specify a VRF.
          ";
        input {
          leaf vrf-all {
            mandatory true;
            type vrf-name;
            description
              "VRF name or all";
          }
          leaf afi-safi-name {
            mandatory true;
            type afi-safi-type;
            description
              "AFI and SAFI";
          }
          leaf ipv4-addr {
            mandatory true;
            type inet:ipv4-address;
            description
              "IPv4 network";
          }
        }
      }
    }
  }
  augment "/ncs:devices/ncs:device-group/ncs:ned-id/ncs:rpc" {
    container rpc-clear-bgp-version-vrf-afi-safi-ipv4-addr {
      tailf:ncs-device-type "netconf";
      tailf:display-when "/ncs:devices/ncs:device[ncs:name=current()/../../../ncs:member]/ncs:module[ncs:name='Cisco-IOS-XR-ipv4-bgp-act']";
      tailf:action clear-bgp-version-vrf-afi-safi-ipv4-addr {
        tailf:actionpoint ncsproxy {
          tailf:internal;
        }
        csc:xr-task "bgp";
        csc:cli-command "clear bgp version vrf <vrf-all> <afi-safi-name> <ipv4-addr>";
        description
          "clear BGP prefix version.
           Specify a VRF.
          ";
        input {
          leaf vrf-all {
            mandatory true;
            type vrf-name;
            description
              "VRF name or all";
          }
          leaf afi-safi-name {
            mandatory true;
            type afi-safi-type;
            description
              "AFI and SAFI";
          }
          leaf ipv4-addr {
            mandatory true;
            type inet:ipv4-address;
            description
              "IPv4 network";
          }
        }
      }
    }
  }
  augment "/ncs:devices/ncs:device/ncs:rpc" {
    container rpc-clear-bgp-version-vrf-afi-safi-ipv4-addr-ipv4-mask {
      tailf:ncs-device-type "netconf";
      tailf:display-when "not(../../ncs:module) or ../../ncs:module[ncs:name='Cisco-IOS-XR-ipv4-bgp-act']";
      tailf:action clear-bgp-version-vrf-afi-safi-ipv4-addr-ipv4-mask {
        tailf:actionpoint ncsproxy {
          tailf:internal;
        }
        csc:xr-task "bgp";
        csc:cli-command "clear bgp version vrf <vrf-all> <afi-safi-name> <ipv4-addr> <ipv4-mask>";
        description
          "clear BGP prefix version.
           Specify a VRF.
          ";
        input {
          leaf vrf-all {
            mandatory true;
            type vrf-name;
            description
              "VRF name or all";
          }
          leaf afi-safi-name {
            mandatory true;
            type afi-safi-type;
            description
              "AFI and SAFI";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device-group/ncs:ned-id/ncs:rpc" {
    container rpc-clear-bgp-version-vrf-afi-safi-ipv4-addr-ipv4-mask {
      tailf:ncs-device-type "netconf";
      tailf:display-when "/ncs:devices/ncs:device[ncs:name=current()/../../../ncs:member]/ncs:module[ncs:name='Cisco-IOS-XR-ipv4-bgp-act']";
      tailf:action clear-bgp-version-vrf-afi-safi-ipv4-addr-ipv4-mask {
        tailf:actionpoint ncsproxy {
          tailf:internal;
        }
        csc:xr-task "bgp";
        csc:cli-command "clear bgp version vrf <vrf-all> <afi-safi-name> <ipv4-addr> <ipv4-mask>";
        description
          "clear BGP prefix version.
           Specify a VRF.
          ";
        input {
          leaf vrf-all {
            mandatory true;
            type vrf-name;
            description
              "VRF name or all";
          }
          leaf afi-safi-name {
            mandatory true;
            type afi-safi-type;
            description
              "AFI and SAFI";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device/ncs:rpc" {
    container rpc-clear-bgp-version-vrf-afi-safi-ipv4-prefix {
      tailf:ncs-device-type "netconf";
      tailf:display-when "not(../../ncs:module) or ../../ncs:module[ncs:name='Cisco-IOS-XR-ipv4-bgp-act']";
      tailf:action clear-bgp-version-vrf-afi-safi-ipv4-prefix {
        tailf:actionpoint ncsproxy {
          tailf:internal;
        }
        csc:xr-task "bgp";
        csc:cli-command "clear bgp version vrf <vrf-all> <afi-safi-name> <ipv4-prefix>";
        description
          "clear BGP prefix version.
           Specify a VRF.
          ";
        input {
          leaf vrf-all {
            mandatory true;
            type vrf-name;
            description
              "VRF name or all";
          }
          leaf afi-safi-name {
            mandatory true;
            type afi-safi-type;
            description
              "AFI and SAFI";
          }
          leaf ipv4-prefix {
            mandatory true;
            type inet:ipv4-prefix;
            description
              "Fspec IPv4 Prefix";
          }
        }
      }
    }
  }
  augment "/ncs:devices/ncs:device-group/ncs:ned-id/ncs:rpc" {
    container rpc-clear-bgp-version-vrf-afi-safi-ipv4-prefix {
      tailf:ncs-device-type "netconf";
      tailf:display-when "/ncs:devices/ncs:device[ncs:name=current()/../../../ncs:member]/ncs:module[ncs:name='Cisco-IOS-XR-ipv4-bgp-act']";
      tailf:action clear-bgp-version-vrf-afi-safi-ipv4-prefix {
        tailf:actionpoint ncsproxy {
          tailf:internal;
        }
        csc:xr-task "bgp";
        csc:cli-command "clear bgp version vrf <vrf-all> <afi-safi-name> <ipv4-prefix>";
        description
          "clear BGP prefix version.
           Specify a VRF.
          ";
        input {
          leaf vrf-all {
            mandatory true;
            type vrf-name;
            description
              "VRF name or all";
          }
          leaf afi-safi-name {
            mandatory true;
            type afi-safi-type;
            description
              "AFI and SAFI";
          }
          leaf ipv4-prefix {
            mandatory true;
            type inet:ipv4-prefix;
            description
              "Fspec IPv4 Prefix";
          }
        }
      }
    }
  }
  augment "/ncs:devices/ncs:device/ncs:rpc" {
    container rpc-clear-bgp-version-vrf-ip-prefix {
      tailf:ncs-device-type "netconf";
      tailf:display-when "not(../../ncs:module) or ../../ncs:module[ncs:name='Cisco-IOS-XR-ipv4-bgp-act']";
      tailf:action clear-bgp-version-vrf-ip-prefix {
        tailf:actionpoint ncsproxy {
          tailf:internal;
        }
        csc:xr-task "bgp";
        csc:cli-command "clear bgp version vrf <vrf-all> <ip-prefix>";
        description
          "clear BGP prefix version.
           Specify a VRF.
          ";
        input {
          leaf vrf-all {
            mandatory true;
            type vrf-name;
            description
              "VRF name or all";
          }
          leaf ip-prefix {
            mandatory true;
            type inet:ip-prefix;
            description
              "Network and masklength";
          }
        }
      }
    }
  }
  augment "/ncs:devices/ncs:device-group/ncs:ned-id/ncs:rpc" {
    container rpc-clear-bgp-version-vrf-ip-prefix {
      tailf:ncs-device-type "netconf";
      tailf:display-when "/ncs:devices/ncs:device[ncs:name=current()/../../../ncs:member]/ncs:module[ncs:name='Cisco-IOS-XR-ipv4-bgp-act']";
      tailf:action clear-bgp-version-vrf-ip-prefix {
        tailf:actionpoint ncsproxy {
          tailf:internal;
        }
        csc:xr-task "bgp";
        csc:cli-command "clear bgp version vrf <vrf-all> <ip-prefix>";
        description
          "clear BGP prefix version.
           Specify a VRF.
          ";
        input {
          leaf vrf-all {
            mandatory true;
            type vrf-name;
            description
              "VRF name or all";
          }
          leaf ip-prefix {
            mandatory true;
            type inet:ip-prefix;
            description
              "Network and masklength";
          }
        }
      }
    }
  }
  augment "/ncs:devices/ncs:device/ncs:rpc" {
    container rpc-clear-bgp-version-vrf-ip-addr {
      tailf:ncs-device-type "netconf";
      tailf:display-when "not(../../ncs:module) or ../../ncs:module[ncs:name='Cisco-IOS-XR-ipv4-bgp-act']";
      tailf:action clear-bgp-version-vrf-ip-addr {
        tailf:actionpoint ncsproxy {
          tailf:internal;
        }
        csc:xr-task "bgp";
        csc:cli-command "clear bgp version vrf <vrf-all> <ip-addr>";
        description
          "clear BGP prefix version.
           Specify a VRF.
          ";
        input {
          leaf vrf-all {
            mandatory true;
            type vrf-name;
            description
              "VRF name or all";
          }
          leaf ip-addr {
            mandatory true;
            type inet:ip-address;
            description
              "Network";
          }
        }
      }
    }
  }
  augment "/ncs:devices/ncs:device-group/ncs:ned-id/ncs:rpc" {
    container rpc-clear-bgp-version-vrf-ip-addr {
      tailf:ncs-device-type "netconf";
      tailf:display-when "/ncs:devices/ncs:device[ncs:name=current()/../../../ncs:member]/ncs:module[ncs:name='Cisco-IOS-XR-ipv4-bgp-act']";
      tailf:action clear-bgp-version-vrf-ip-addr {
        tailf:actionpoint ncsproxy {
          tailf:internal;
        }
        csc:xr-task "bgp";
        csc:cli-command "clear bgp version vrf <vrf-all> <ip-addr>";
        description
          "clear BGP prefix version.
           Specify a VRF.
          ";
        input {
          leaf vrf-all {
            mandatory true;
            type vrf-name;
            description
              "VRF name or all";
          }
          leaf ip-addr {
            mandatory true;
            type inet:ip-address;
            description
              "Network";
          }
        }
      }
    }
  }
  augment "/ncs:devices/ncs:device/ncs:rpc" {
    container rpc-clear-bgp-version-vrf-ip-addr-ip-netmask {
      tailf:ncs-device-type "netconf";
      tailf:display-when "not(../../ncs:module) or ../../ncs:module[ncs:name='Cisco-IOS-XR-ipv4-bgp-act']";
      tailf:action clear-bgp-version-vrf-ip-addr-ip-netmask {
        tailf:actionpoint ncsproxy {
          tailf:internal;
        }
        csc:xr-task "bgp";
        csc:cli-command "clear bgp version vrf <vrf-all> <ip-addr> <ip-netmask>";
        description
          "clear BGP prefix version.
           Specify a VRF.
          ";
        input {
          leaf vrf-all {
            mandatory true;
            type vrf-name;
            description
              "VRF name or all";
          }
          leaf ip-addr {
            mandatory true;
            type inet:ip-address;
            description
              "Network";
          }
          leaf ip-netmask {
            mandatory true;
            type ip-netmask;
            description
              "Mask";
          }
        }
      }
    }
  }
  augment "/ncs:devices/ncs:device-group/ncs:ned-id/ncs:rpc" {
    container rpc-clear-bgp-version-vrf-ip-addr-ip-netmask {
      tailf:ncs-device-type "netconf";
      tailf:display-when "/ncs:devices/ncs:device[ncs:name=current()/../../../ncs:member]/ncs:module[ncs:name='Cisco-IOS-XR-ipv4-bgp-act']";
      tailf:action clear-bgp-version-vrf-ip-addr-ip-netmask {
        tailf:actionpoint ncsproxy {
          tailf:internal;
        }
        csc:xr-task "bgp";
        csc:cli-command "clear bgp version vrf <vrf-all> <ip-addr> <ip-netmask>";
        description
          "clear BGP prefix version.
           Specify a VRF.
          ";
        input {
          leaf vrf-all {
            mandatory true;
            type vrf-name;
            description
              "VRF name or all";
          }
          leaf ip-addr {
            mandatory true;
            type inet:ip-address;
            description
              "Network";
          }
          leaf ip-netmask {
            mandatory true;
            type ip-netmask;
            description
              "Mask";
          }
        }
      }
    }
  }
  augment "/ncs:devices/ncs:device/ncs:rpc" {
    container rpc-clear-bgp-version-afi-safi-vrf-ipv6-prefix {
      tailf:ncs-device-type "netconf";
      tailf:display-when "not(../../ncs:module) or ../../ncs:module[ncs:name='Cisco-IOS-XR-ipv4-bgp-act']";
      tailf:action clear-bgp-version-afi-safi-vrf-ipv6-prefix {
        tailf:actionpoint ncsproxy {
          tailf:internal;
        }
        csc:xr-task "bgp";
        csc:cli-command "clear bgp version <afi-safi-name> vrf <vrf-name> <ipv6-prefix>";
        description
          "clear BGP prefix version.
           Display routes for a specified VRF.
          ";
        input {
          leaf afi-safi-name {
            mandatory true;
            type afi-safi-type;
            description
              "AFI and SAFI";
          }
          leaf vrf-name {
            mandatory true;
            type string;
            description
              "VRF name";
          }
          leaf ipv6-prefix {
            mandatory true;
            type inet:ipv6-prefix;
            description
              "IPv6 network and masklength";
          }
        }
      }
    }
  }
  augment "/ncs:devices/ncs:device-group/ncs:ned-id/ncs:rpc" {
    container rpc-clear-bgp-version-afi-safi-vrf-ipv6-prefix {
      tailf:ncs-device-type "netconf";
      tailf:display-when "/ncs:devices/ncs:device[ncs:name=current()/../../../ncs:member]/ncs:module[ncs:name='Cisco-IOS-XR-ipv4-bgp-act']";
      tailf:action clear-bgp-version-afi-safi-vrf-ipv6-prefix {
        tailf:actionpoint ncsproxy {
          tailf:internal;
        }
        csc:xr-task "bgp";
        csc:cli-command "clear bgp version <afi-safi-name> vrf <vrf-name> <ipv6-prefix>";
        description
          "clear BGP prefix version.
           Display routes for a specified VRF.
          ";
        input {
          leaf afi-safi-name {
            mandatory true;
            type afi-safi-type;
            description
              "AFI and SAFI";
          }
          leaf vrf-name {
            mandatory true;
            type string;
            description
              "VRF name";
          }
          leaf ipv6-prefix {
            mandatory true;
            type inet:ipv6-prefix;
            description
              "IPv6 network and masklength";
          }
        }
      }
    }
  }
  augment "/ncs:devices/ncs:device/ncs:rpc" {
    container rpc-clear-bgp-version-afi-safi-vrf-ipv6-addr {
      tailf:ncs-device-type "netconf";
      tailf:display-when "not(../../ncs:module) or ../../ncs:module[ncs:name='Cisco-IOS-XR-ipv4-bgp-act']";
      tailf:action clear-bgp-version-afi-safi-vrf-ipv6-addr {
        tailf:actionpoint ncsproxy {
          tailf:internal;
        }
        csc:xr-task "bgp";
        csc:cli-command "clear bgp version <afi-safi-name> vrf <vrf-name> <ipv6-addr>";
        description
          "clear BGP prefix version.
           Display routes for a specified VRF.
          ";
        input {
          leaf afi-safi-name {
            mandatory true;
            type afi-safi-type;
            description
              "AFI and SAFI";
          }
          leaf vrf-name {
            mandatory true;
            type string;
            description
              "VRF name";
          }
          leaf ipv6-addr {
            mandatory true;
            type inet:ipv6-address;
            description
              "IPv6 network";
          }
        }
      }
    }
  }
  augment "/ncs:devices/ncs:device-group/ncs:ned-id/ncs:rpc" {
    container rpc-clear-bgp-version-afi-safi-vrf-ipv6-addr {
      tailf:ncs-device-type "netconf";
      tailf:display-when "/ncs:devices/ncs:device[ncs:name=current()/../../../ncs:member]/ncs:module[ncs:name='Cisco-IOS-XR-ipv4-bgp-act']";
      tailf:action clear-bgp-version-afi-safi-vrf-ipv6-addr {
        tailf:actionpoint ncsproxy {
          tailf:internal;
        }
        csc:xr-task "bgp";
        csc:cli-command "clear bgp version <afi-safi-name> vrf <vrf-name> <ipv6-addr>";
        description
          "clear BGP prefix version.
           Display routes for a specified VRF.
          ";
        input {
          leaf afi-safi-name {
            mandatory true;
            type afi-safi-type;
            description
              "AFI and SAFI";
          }
          leaf vrf-name {
            mandatory true;
            type string;
            description
              "VRF name";
          }
          leaf ipv6-addr {
            mandatory true;
            type inet:ipv6-address;
            description
              "IPv6 network";
          }
        }
      }
    }
  }
  augment "/ncs:devices/ncs:device/ncs:rpc" {
    container rpc-clear-bgp-version-afi-safi-vrf-ipv6-addr-ipv6-netmask {
      tailf:ncs-device-type "netconf";
      tailf:display-when "not(../../ncs:module) or ../../ncs:module[ncs:name='Cisco-IOS-XR-ipv4-bgp-act']";
      tailf:action clear-bgp-version-afi-safi-vrf-ipv6-addr-ipv6-netmask {
        tailf:actionpoint ncsproxy {
          tailf:internal;
        }
        csc:xr-task "bgp";
        csc:cli-command "clear bgp version <afi-safi-name> vrf <vrf-name> <ipv6-addr> <ipv6-netmask>";
        description
          "clear BGP prefix version.
           Display routes for a specified VRF.
          ";
        input {
          leaf afi-safi-name {
            mandatory true;
            type afi-safi-type;
            description
              "AFI and SAFI";
          }
          leaf vrf-name {
            mandatory true;
            type string;
            description
              "VRF name";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device-group/ncs:ned-id/ncs:rpc" {
    container rpc-clear-bgp-version-afi-safi-vrf-ipv6-addr-ipv6-netmask {
      tailf:ncs-device-type "netconf";
      tailf:display-when "/ncs:devices/ncs:device[ncs:name=current()/../../../ncs:member]/ncs:module[ncs:name='Cisco-IOS-XR-ipv4-bgp-act']";
      tailf:action clear-bgp-version-afi-safi-vrf-ipv6-addr-ipv6-netmask {
        tailf:actionpoint ncsproxy {
          tailf:internal;
        }
        csc:xr-task "bgp";
        csc:cli-command "clear bgp version <afi-safi-name> vrf <vrf-name> <ipv6-addr> <ipv6-netmask>";
        description
          "clear BGP prefix version.
           Display routes for a specified VRF.
          ";
        input {
          leaf afi-safi-name {
            mandatory true;
            type afi-safi-type;
            description
              "AFI and SAFI";
          }
          leaf vrf-name {
            mandatory true;
            type string;
            description
              "VRF name";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device/ncs:rpc" {
    container rpc-clear-bgp-version-afi-safi-rd-ipv6-prefix {
      tailf:ncs-device-type "netconf";
      tailf:display-when "not(../../ncs:module) or ../../ncs:module[ncs:name='Cisco-IOS-XR-ipv4-bgp-act']";
      tailf:action clear-bgp-version-afi-safi-rd-ipv6-prefix {
        tailf:actionpoint ncsproxy {
          tailf:internal;
        }
        csc:xr-task "bgp";
        csc:cli-command "clear bgp version <afi-safi-name> rd <rd> <ipv6-prefix>";
        description
          "clear BGP prefix version.
           Display routes with a specific route distinguisher.
          ";
        input {
          leaf afi-safi-name {
            mandatory true;
            type afi-safi-type;
            description
              "AFI and SAFI";
          }
          leaf rd {
            mandatory true;
            type rd;
            description
              "Route distinguisher";
          }
          leaf ipv6-prefix {
            mandatory true;
            type inet:ipv6-prefix;
            description
              "IPv6 network and masklength";
          }
        }
      }
    }
  }
  augment "/ncs:devices/ncs:device-group/ncs:ned-id/ncs:rpc" {
    container rpc-clear-bgp-version-afi-safi-rd-ipv6-prefix {
      tailf:ncs-device-type "netconf";
      tailf:display-when "/ncs:devices/ncs:device[ncs:name=current()/../../../ncs:member]/ncs:module[ncs:name='Cisco-IOS-XR-ipv4-bgp-act']";
      tailf:action clear-bgp-version-afi-safi-rd-ipv6-prefix {
        tailf:actionpoint ncsproxy {
          tailf:internal;
        }
        csc:xr-task "bgp";
        csc:cli-command "clear bgp version <afi-safi-name> rd <rd> <ipv6-prefix>";
        description
          "clear BGP prefix version.
           Display routes with a specific route distinguisher.
          ";
        input {
          leaf afi-safi-name {
            mandatory true;
            type afi-safi-type;
            description
              "AFI and SAFI";
          }
          leaf rd {
            mandatory true;
            type rd;
            description
              "Route distinguisher";
          }
          leaf ipv6-prefix {
            mandatory true;
            type inet:ipv6-prefix;
            description
              "IPv6 network and masklength";
          }
        }
      }
    }
  }
  augment "/ncs:devices/ncs:device/ncs:rpc" {
    container rpc-clear-bgp-version-afi-safi-rd-ipv6-addr {
      tailf:ncs-device-type "netconf";
      tailf:display-when "not(../../ncs:module) or ../../ncs:module[ncs:name='Cisco-IOS-XR-ipv4-bgp-act']";
      tailf:action clear-bgp-version-afi-safi-rd-ipv6-addr {
        tailf:actionpoint ncsproxy {
          tailf:internal;
        }
        csc:xr-task "bgp";
        csc:cli-command "clear bgp version <afi-safi-name> rd <rd> <ipv6-addr>";
        description
          "clear BGP prefix version.
           Display routes with a specific route distinguisher.
          ";
        input {
          leaf afi-safi-name {
            mandatory true;
            type afi-safi-type;
            description
              "AFI and SAFI";
          }
          leaf rd {
            mandatory true;
            type rd;
            description
              "Route distinguisher";
          }
          leaf ipv6-addr {
            mandatory true;
            type inet:ipv6-address;
            description
              "IPv6 network";
          }
        }
      }
    }
  }
  augment "/ncs:devices/ncs:device-group/ncs:ned-id/ncs:rpc" {
    container rpc-clear-bgp-version-afi-safi-rd-ipv6-addr {
      tailf:ncs-device-type "netconf";
      tailf:display-when "/ncs:devices/ncs:device[ncs:name=current()/../../../ncs:member]/ncs:module[ncs:name='Cisco-IOS-XR-ipv4-bgp-act']";
      tailf:action clear-bgp-version-afi-safi-rd-ipv6-addr {
        tailf:actionpoint ncsproxy {
          tailf:internal;
        }
        csc:xr-task "bgp";
        csc:cli-command "clear bgp version <afi-safi-name> rd <rd> <ipv6-addr>";
        description
          "clear BGP prefix version.
           Display routes with a specific route distinguisher.
          ";
        input {
          leaf afi-safi-name {
            mandatory true;
            type afi-safi-type;
            description
              "AFI and SAFI";
          }
          leaf rd {
            mandatory true;
            type rd;
            description
              "Route distinguisher";
          }
          leaf ipv6-addr {
            mandatory true;
            type inet:ipv6-address;
            description
              "IPv6 network";
          }
        }
      }
    }
  }
  augment "/ncs:devices/ncs:device/ncs:rpc" {
    container rpc-clear-bgp-version-afi-safi-rd-ipv6-addr-ipv6-netmask {
      tailf:ncs-device-type "netconf";
      tailf:display-when "not(../../ncs:module) or ../../ncs:module[ncs:name='Cisco-IOS-XR-ipv4-bgp-act']";
      tailf:action clear-bgp-version-afi-safi-rd-ipv6-addr-ipv6-netmask {
        tailf:actionpoint ncsproxy {
          tailf:internal;
        }
        csc:xr-task "bgp";
        csc:cli-command "clear bgp version <afi-safi-name> rd <rd> <ipv6-addr> <ipv6-netmask>";
        description
          "clear BGP prefix version.
           Display routes with a specific route distinguisher.
          ";
        input {
          leaf afi-safi-name {
            mandatory true;
            type afi-safi-type;
            description
              "AFI and SAFI";
          }
          leaf rd {
            mandatory true;
            type rd;
            description
              "Route distinguisher";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device-group/ncs:ned-id/ncs:rpc" {
    container rpc-clear-bgp-version-afi-safi-rd-ipv6-addr-ipv6-netmask {
      tailf:ncs-device-type "netconf";
      tailf:display-when "/ncs:devices/ncs:device[ncs:name=current()/../../../ncs:member]/ncs:module[ncs:name='Cisco-IOS-XR-ipv4-bgp-act']";
      tailf:action clear-bgp-version-afi-safi-rd-ipv6-addr-ipv6-netmask {
        tailf:actionpoint ncsproxy {
          tailf:internal;
        }
        csc:xr-task "bgp";
        csc:cli-command "clear bgp version <afi-safi-name> rd <rd> <ipv6-addr> <ipv6-netmask>";
        description
          "clear BGP prefix version.
           Display routes with a specific route distinguisher.
          ";
        input {
          leaf afi-safi-name {
            mandatory true;
            type afi-safi-type;
            description
              "AFI and SAFI";
          }
          leaf rd {
            mandatory true;
            type rd;
            description
              "Route distinguisher";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device/ncs:rpc" {
    container rpc-clear-bgp-version-afi-safi-vrf-ipv4-addr-ipv4-mask {
      tailf:ncs-device-type "netconf";
      tailf:display-when "not(../../ncs:module) or ../../ncs:module[ncs:name='Cisco-IOS-XR-ipv4-bgp-act']";
      tailf:action clear-bgp-version-afi-safi-vrf-ipv4-addr-ipv4-mask {
        tailf:actionpoint ncsproxy {
          tailf:internal;
        }
        csc:xr-task "bgp";
        csc:cli-command "clear bgp version <afi-safi-name> vrf <vrf-name> <ipv4-addr> <ipv4-mask>";
        description
          "clear BGP prefix version.
           Display routes for a specified VRF.
          ";
        input {
          leaf afi-safi-name {
            mandatory true;
            type afi-safi-type;
            description
              "AFI and SAFI";
          }
          leaf vrf-name {
            mandatory true;
            type string;
            description
              "VRF name";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device-group/ncs:ned-id/ncs:rpc" {
    container rpc-clear-bgp-version-afi-safi-vrf-ipv4-addr-ipv4-mask {
      tailf:ncs-device-type "netconf";
      tailf:display-when "/ncs:devices/ncs:device[ncs:name=current()/../../../ncs:member]/ncs:module[ncs:name='Cisco-IOS-XR-ipv4-bgp-act']";
      tailf:action clear-bgp-version-afi-safi-vrf-ipv4-addr-ipv4-mask {
        tailf:actionpoint ncsproxy {
          tailf:internal;
        }
        csc:xr-task "bgp";
        csc:cli-command "clear bgp version <afi-safi-name> vrf <vrf-name> <ipv4-addr> <ipv4-mask>";
        description
          "clear BGP prefix version.
           Display routes for a specified VRF.
          ";
        input {
          leaf afi-safi-name {
            mandatory true;
            type afi-safi-type;
            description
              "AFI and SAFI";
          }
          leaf vrf-name {
            mandatory true;
            type string;
            description
              "VRF name";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device/ncs:rpc" {
    container rpc-clear-bgp-version-afi-safi-rd-ipv4-addr-ipv4-mask {
      tailf:ncs-device-type "netconf";
      tailf:display-when "not(../../ncs:module) or ../../ncs:module[ncs:name='Cisco-IOS-XR-ipv4-bgp-act']";
      tailf:action clear-bgp-version-afi-safi-rd-ipv4-addr-ipv4-mask {
        tailf:actionpoint ncsproxy {
          tailf:internal;
        }
        csc:xr-task "bgp";
        csc:cli-command "clear bgp version <afi-safi-name> rd <rd> <ipv4-addr> <ipv4-mask>";
        description
          "clear BGP prefix version.
           Display routes with a specific route distinguisher.
          ";
        input {
          leaf afi-safi-name {
            mandatory true;
            type afi-safi-type;
            description
              "AFI and SAFI";
          }
          leaf rd {
            mandatory true;
            type rd;
            description
              "Route distinguisher";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device-group/ncs:ned-id/ncs:rpc" {
    container rpc-clear-bgp-version-afi-safi-rd-ipv4-addr-ipv4-mask {
      tailf:ncs-device-type "netconf";
      tailf:display-when "/ncs:devices/ncs:device[ncs:name=current()/../../../ncs:member]/ncs:module[ncs:name='Cisco-IOS-XR-ipv4-bgp-act']";
      tailf:action clear-bgp-version-afi-safi-rd-ipv4-addr-ipv4-mask {
        tailf:actionpoint ncsproxy {
          tailf:internal;
        }
        csc:xr-task "bgp";
        csc:cli-command "clear bgp version <afi-safi-name> rd <rd> <ipv4-addr> <ipv4-mask>";
        description
          "clear BGP prefix version.
           Display routes with a specific route distinguisher.
          ";
        input {
          leaf afi-safi-name {
            mandatory true;
            type afi-safi-type;
            description
              "AFI and SAFI";
          }
          leaf rd {
            mandatory true;
            type rd;
            description
              "Route distinguisher";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device/ncs:rpc" {
    container rpc-clear-bgp-version-afi-safi-vrf-ipv4-prefix {
      tailf:ncs-device-type "netconf";
      tailf:display-when "not(../../ncs:module) or ../../ncs:module[ncs:name='Cisco-IOS-XR-ipv4-bgp-act']";
      tailf:action clear-bgp-version-afi-safi-vrf-ipv4-prefix {
        tailf:actionpoint ncsproxy {
          tailf:internal;
        }
        csc:xr-task "bgp";
        csc:cli-command "clear bgp version <afi-safi-name> vrf <vrf-name> <ipv4-prefix>";
        description
          "clear BGP prefix version.
           Display routes for a specified VRF.
          ";
        input {
          leaf afi-safi-name {
            mandatory true;
            type afi-safi-type;
            description
              "AFI and SAFI";
          }
          leaf vrf-name {
            mandatory true;
            type string;
            description
              "VRF name";
          }
          leaf ipv4-prefix {
            mandatory true;
            type inet:ipv4-prefix;
            description
              "VPN Fspec Prefix";
          }
        }
      }
    }
  }
  augment "/ncs:devices/ncs:device-group/ncs:ned-id/ncs:rpc" {
    container rpc-clear-bgp-version-afi-safi-vrf-ipv4-prefix {
      tailf:ncs-device-type "netconf";
      tailf:display-when "/ncs:devices/ncs:device[ncs:name=current()/../../../ncs:member]/ncs:module[ncs:name='Cisco-IOS-XR-ipv4-bgp-act']";
      tailf:action clear-bgp-version-afi-safi-vrf-ipv4-prefix {
        tailf:actionpoint ncsproxy {
          tailf:internal;
        }
        csc:xr-task "bgp";
        csc:cli-command "clear bgp version <afi-safi-name> vrf <vrf-name> <ipv4-prefix>";
        description
          "clear BGP prefix version.
           Display routes for a specified VRF.
          ";
        input {
          leaf afi-safi-name {
            mandatory true;
            type afi-safi-type;
            description
              "AFI and SAFI";
          }
          leaf vrf-name {
            mandatory true;
            type string;
            description
              "VRF name";
          }
          leaf ipv4-prefix {
            mandatory true;
            type inet:ipv4-prefix;
            description
              "VPN Fspec Prefix";
          }
        }
      }
    }
  }
  augment "/ncs:devices/ncs:device/ncs:rpc" {
    container rpc-clear-bgp-version-afi-safi-mp2mp-ipv4-prefix {
      tailf:ncs-device-type "netconf";
      tailf:display-when "not(../../ncs:module) or ../../ncs:module[ncs:name='Cisco-IOS-XR-ipv4-bgp-act']";
      tailf:action clear-bgp-version-afi-safi-mp2mp-ipv4-prefix {
        tailf:actionpoint ncsproxy {
          tailf:internal;
        }
        csc:xr-task "bgp";
        csc:cli-command "clear bgp version <afi-safi-name> mp2mp <mp2mp> <ipv4-prefix>";
        description
          "clear BGP prefix version.
           Display routes for a specified Xconnect group:MP2MP.
          ";
        input {
          leaf afi-safi-name {
            mandatory true;
            type afi-safi-type;
            description
              "AFI and SAFI";
          }
          leaf mp2mp {
            mandatory true;
            type string;
            description
              "Xconnect Group:mp2mp";
          }
          leaf ipv4-prefix {
            mandatory true;
            type inet:ipv4-prefix;
            description
              "L2VPN VPWS Prefix";
          }
        }
      }
    }
  }
  augment "/ncs:devices/ncs:device-group/ncs:ned-id/ncs:rpc" {
    container rpc-clear-bgp-version-afi-safi-mp2mp-ipv4-prefix {
      tailf:ncs-device-type "netconf";
      tailf:display-when "/ncs:devices/ncs:device[ncs:name=current()/../../../ncs:member]/ncs:module[ncs:name='Cisco-IOS-XR-ipv4-bgp-act']";
      tailf:action clear-bgp-version-afi-safi-mp2mp-ipv4-prefix {
        tailf:actionpoint ncsproxy {
          tailf:internal;
        }
        csc:xr-task "bgp";
        csc:cli-command "clear bgp version <afi-safi-name> mp2mp <mp2mp> <ipv4-prefix>";
        description
          "clear BGP prefix version.
           Display routes for a specified Xconnect group:MP2MP.
          ";
        input {
          leaf afi-safi-name {
            mandatory true;
            type afi-safi-type;
            description
              "AFI and SAFI";
          }
          leaf mp2mp {
            mandatory true;
            type string;
            description
              "Xconnect Group:mp2mp";
          }
          leaf ipv4-prefix {
            mandatory true;
            type inet:ipv4-prefix;
            description
              "L2VPN VPWS Prefix";
          }
        }
      }
    }
  }
  augment "/ncs:devices/ncs:device/ncs:rpc" {
    container rpc-clear-bgp-version-afi-safi-rd-ipv4-prefix {
      tailf:ncs-device-type "netconf";
      tailf:display-when "not(../../ncs:module) or ../../ncs:module[ncs:name='Cisco-IOS-XR-ipv4-bgp-act']";
      tailf:action clear-bgp-version-afi-safi-rd-ipv4-prefix {
        tailf:actionpoint ncsproxy {
          tailf:internal;
        }
        csc:xr-task "bgp";
        csc:cli-command "clear bgp version <afi-safi-name> rd <rd> <ipv4-prefix>";
        description
          "clear BGP prefix version.
           Display routes with a specific route distinguisher.
          ";
        input {
          leaf afi-safi-name {
            mandatory true;
            type afi-safi-type;
            description
              "AFI and SAFI";
          }
          leaf rd {
            mandatory true;
            type rd;
            description
              "Route distinguisher";
          }
          leaf ipv4-prefix {
            mandatory true;
            type inet:ipv4-prefix;
            description
              "L2VPN EVPN Prefix";
          }
        }
      }
    }
  }
  augment "/ncs:devices/ncs:device-group/ncs:ned-id/ncs:rpc" {
    container rpc-clear-bgp-version-afi-safi-rd-ipv4-prefix {
      tailf:ncs-device-type "netconf";
      tailf:display-when "/ncs:devices/ncs:device[ncs:name=current()/../../../ncs:member]/ncs:module[ncs:name='Cisco-IOS-XR-ipv4-bgp-act']";
      tailf:action clear-bgp-version-afi-safi-rd-ipv4-prefix {
        tailf:actionpoint ncsproxy {
          tailf:internal;
        }
        csc:xr-task "bgp";
        csc:cli-command "clear bgp version <afi-safi-name> rd <rd> <ipv4-prefix>";
        description
          "clear BGP prefix version.
           Display routes with a specific route distinguisher.
          ";
        input {
          leaf afi-safi-name {
            mandatory true;
            type afi-safi-type;
            description
              "AFI and SAFI";
          }
          leaf rd {
            mandatory true;
            type rd;
            description
              "Route distinguisher";
          }
          leaf ipv4-prefix {
            mandatory true;
            type inet:ipv4-prefix;
            description
              "L2VPN EVPN Prefix";
          }
        }
      }
    }
  }
  augment "/ncs:devices/ncs:device/ncs:rpc" {
    container rpc-clear-bgp-version-afi-safi-bridge-domain-ipv4-prefix {
      tailf:ncs-device-type "netconf";
      tailf:display-when "not(../../ncs:module) or ../../ncs:module[ncs:name='Cisco-IOS-XR-ipv4-bgp-act']";
      tailf:action clear-bgp-version-afi-safi-bridge-domain-ipv4-prefix {
        tailf:actionpoint ncsproxy {
          tailf:internal;
        }
        csc:xr-task "bgp";
        csc:cli-command "clear bgp version <afi-safi-name> bridge-domain <bridge-domain-name> <ipv4-prefix>";
        description
          "clear BGP prefix version.
           Display routes for a specified Bridge Domain.
          ";
        input {
          leaf afi-safi-name {
            mandatory true;
            type afi-safi-type;
            description
              "AFI and SAFI";
          }
          leaf bridge-domain-name {
            mandatory true;
            type string;
            description
              "Bridge Domain";
          }
          leaf ipv4-prefix {
            mandatory true;
            type inet:ipv4-prefix;
            description
              "L2VPN EVPN Prefix";
          }
        }
      }
    }
  }
  augment "/ncs:devices/ncs:device-group/ncs:ned-id/ncs:rpc" {
    container rpc-clear-bgp-version-afi-safi-bridge-domain-ipv4-prefix {
      tailf:ncs-device-type "netconf";
      tailf:display-when "/ncs:devices/ncs:device[ncs:name=current()/../../../ncs:member]/ncs:module[ncs:name='Cisco-IOS-XR-ipv4-bgp-act']";
      tailf:action clear-bgp-version-afi-safi-bridge-domain-ipv4-prefix {
        tailf:actionpoint ncsproxy {
          tailf:internal;
        }
        csc:xr-task "bgp";
        csc:cli-command "clear bgp version <afi-safi-name> bridge-domain <bridge-domain-name> <ipv4-prefix>";
        description
          "clear BGP prefix version.
           Display routes for a specified Bridge Domain.
          ";
        input {
          leaf afi-safi-name {
            mandatory true;
            type afi-safi-type;
            description
              "AFI and SAFI";
          }
          leaf bridge-domain-name {
            mandatory true;
            type string;
            description
              "Bridge Domain";
          }
          leaf ipv4-prefix {
            mandatory true;
            type inet:ipv4-prefix;
            description
              "L2VPN EVPN Prefix";
          }
        }
      }
    }
  }
  augment "/ncs:devices/ncs:device/ncs:rpc" {
    container rpc-clear-bgp-version-afi-safi-sr-policy-prefix {
      tailf:ncs-device-type "netconf";
      tailf:display-when "not(../../ncs:module) or ../../ncs:module[ncs:name='Cisco-IOS-XR-ipv4-bgp-act']";
      tailf:action clear-bgp-version-afi-safi-sr-policy-prefix {
        tailf:actionpoint ncsproxy {
          tailf:internal;
        }
        csc:xr-task "bgp";
        csc:cli-command "clear bgp version <afi-safi-name> <sr-policy-prefix>";
        description
          "clear BGP prefix version.
          ";
        input {
          leaf afi-safi-name {
            mandatory true;
            type afi-safi-type;
            description
              "AFI and SAFI";
          }
          leaf sr-policy-prefix {
            mandatory true;
            type string;
            description
              "SR Policy prefix";
          }
        }
      }
    }
  }
  augment "/ncs:devices/ncs:device-group/ncs:ned-id/ncs:rpc" {
    container rpc-clear-bgp-version-afi-safi-sr-policy-prefix {
      tailf:ncs-device-type "netconf";
      tailf:display-when "/ncs:devices/ncs:device[ncs:name=current()/../../../ncs:member]/ncs:module[ncs:name='Cisco-IOS-XR-ipv4-bgp-act']";
      tailf:action clear-bgp-version-afi-safi-sr-policy-prefix {
        tailf:actionpoint ncsproxy {
          tailf:internal;
        }
        csc:xr-task "bgp";
        csc:cli-command "clear bgp version <afi-safi-name> <sr-policy-prefix>";
        description
          "clear BGP prefix version.
          ";
        input {
          leaf afi-safi-name {
            mandatory true;
            type afi-safi-type;
            description
              "AFI and SAFI";
          }
          leaf sr-policy-prefix {
            mandatory true;
            type string;
            description
              "SR Policy prefix";
          }
        }
      }
    }
  }
  augment "/ncs:devices/ncs:device/ncs:rpc" {
    container rpc-clear-bgp-version-afi-safi {
      tailf:ncs-device-type "netconf";
      tailf:display-when "not(../../ncs:module) or ../../ncs:module[ncs:name='Cisco-IOS-XR-ipv4-bgp-act']";
      tailf:action clear-bgp-version-afi-safi {
        tailf:actionpoint ncsproxy {
          tailf:internal;
        }
        csc:xr-task "bgp";
        csc:cli-command "clear bgp version <afi-safi-name>";
        description
          "clear BGP prefix version.
          ";
        input {
          leaf afi-safi-name {
            mandatory true;
            type afi-safi-type;
            description
              "AFI and SAFI";
          }
        }
      }
    }
  }
  augment "/ncs:devices/ncs:device-group/ncs:ned-id/ncs:rpc" {
    container rpc-clear-bgp-version-afi-safi {
      tailf:ncs-device-type "netconf";
      tailf:display-when "/ncs:devices/ncs:device[ncs:name=current()/../../../ncs:member]/ncs:module[ncs:name='Cisco-IOS-XR-ipv4-bgp-act']";
      tailf:action clear-bgp-version-afi-safi {
        tailf:actionpoint ncsproxy {
          tailf:internal;
        }
        csc:xr-task "bgp";
        csc:cli-command "clear bgp version <afi-safi-name>";
        description
          "clear BGP prefix version.
          ";
        input {
          leaf afi-safi-name {
            mandatory true;
            type afi-safi-type;
            description
              "AFI and SAFI";
          }
        }
      }
    }
  }
  augment "/ncs:devices/ncs:device/ncs:rpc" {
    container rpc-clear-bgp-version-afi-safi-vrf {
      tailf:ncs-device-type "netconf";
      tailf:display-when "not(../../ncs:module) or ../../ncs:module[ncs:name='Cisco-IOS-XR-ipv4-bgp-act']";
      tailf:action clear-bgp-version-afi-safi-vrf {
        tailf:actionpoint ncsproxy {
          tailf:internal;
        }
        csc:xr-task "bgp";
        csc:cli-command "clear bgp version <afi-safi-name> vrf <vrf-name>";
        description
          "clear BGP prefix version.
           Display routes for a specified VRF.
          ";
        input {
          leaf afi-safi-name {
            mandatory true;
            type afi-safi-type;
            description
              "AFI and SAFI";
          }
          leaf vrf-name {
            mandatory true;
            type string;
            description
              "VRF name";
          }
        }
      }
    }
  }
  augment "/ncs:devices/ncs:device-group/ncs:ned-id/ncs:rpc" {
    container rpc-clear-bgp-version-afi-safi-vrf {
      tailf:ncs-device-type "netconf";
      tailf:display-when "/ncs:devices/ncs:device[ncs:name=current()/../../../ncs:member]/ncs:module[ncs:name='Cisco-IOS-XR-ipv4-bgp-act']";
      tailf:action clear-bgp-version-afi-safi-vrf {
        tailf:actionpoint ncsproxy {
          tailf:internal;
        }
        csc:xr-task "bgp";
        csc:cli-command "clear bgp version <afi-safi-name> vrf <vrf-name>";
        description
          "clear BGP prefix version.
           Display routes for a specified VRF.
          ";
        input {
          leaf afi-safi-name {
            mandatory true;
            type afi-safi-type;
            description
              "AFI and SAFI";
          }
          leaf vrf-name {
            mandatory true;
            type string;
            description
              "VRF name";
          }
        }
      }
    }
  }
  augment "/ncs:devices/ncs:device/ncs:rpc" {
    container rpc-clear-bgp-version-afi-safi-rd {
      tailf:ncs-device-type "netconf";
      tailf:display-when "not(../../ncs:module) or ../../ncs:module[ncs:name='Cisco-IOS-XR-ipv4-bgp-act']";
      tailf:action clear-bgp-version-afi-safi-rd {
        tailf:actionpoint ncsproxy {
          tailf:internal;
        }
        csc:xr-task "bgp";
        csc:cli-command "clear bgp version <afi-safi-name> rd <rd>";
        description
          "clear BGP prefix version.
           Display routes with a specific route distinguisher.
          ";
        input {
          leaf afi-safi-name {
            mandatory true;
            type afi-safi-type;
            description
              "AFI and SAFI";
          }
          leaf rd {
            mandatory true;
            type rd;
            description
              "Route distinguisher";
          }
        }
      }
    }
  }
  augment "/ncs:devices/ncs:device-group/ncs:ned-id/ncs:rpc" {
    container rpc-clear-bgp-version-afi-safi-rd {
      tailf:ncs-device-type "netconf";
      tailf:display-when "/ncs:devices/ncs:device[ncs:name=current()/../../../ncs:member]/ncs:module[ncs:name='Cisco-IOS-XR-ipv4-bgp-act']";
      tailf:action clear-bgp-version-afi-safi-rd {
        tailf:actionpoint ncsproxy {
          tailf:internal;
        }
        csc:xr-task "bgp";
        csc:cli-command "clear bgp version <afi-safi-name> rd <rd>";
        description
          "clear BGP prefix version.
           Display routes with a specific route distinguisher.
          ";
        input {
          leaf afi-safi-name {
            mandatory true;
            type afi-safi-type;
            description
              "AFI and SAFI";
          }
          leaf rd {
            mandatory true;
            type rd;
            description
              "Route distinguisher";
          }
        }
      }
    }
  }
  augment "/ncs:devices/ncs:device/ncs:rpc" {
    container rpc-clear-bgp-version-afi-safi-ipv6-prefix {
      tailf:ncs-device-type "netconf";
      tailf:display-when "not(../../ncs:module) or ../../ncs:module[ncs:name='Cisco-IOS-XR-ipv4-bgp-act']";
      tailf:action clear-bgp-version-afi-safi-ipv6-prefix {
        tailf:actionpoint ncsproxy {
          tailf:internal;
        }
        csc:xr-task "bgp";
        csc:cli-command "clear bgp version <afi-safi-name> <ipv6-prefix>";
        description
          "clear BGP prefix version.
          ";
        input {
          leaf afi-safi-name {
            mandatory true;
            type afi-safi-type;
            description
              "AFI and SAFI";
          }
          leaf ipv6-prefix {
            mandatory true;
            type inet:ipv6-prefix;
            description
              "IPv6 network and masklength";
          }
        }
      }
    }
  }
  augment "/ncs:devices/ncs:device-group/ncs:ned-id/ncs:rpc" {
    container rpc-clear-bgp-version-afi-safi-ipv6-prefix {
      tailf:ncs-device-type "netconf";
      tailf:display-when "/ncs:devices/ncs:device[ncs:name=current()/../../../ncs:member]/ncs:module[ncs:name='Cisco-IOS-XR-ipv4-bgp-act']";
      tailf:action clear-bgp-version-afi-safi-ipv6-prefix {
        tailf:actionpoint ncsproxy {
          tailf:internal;
        }
        csc:xr-task "bgp";
        csc:cli-command "clear bgp version <afi-safi-name> <ipv6-prefix>";
        description
          "clear BGP prefix version.
          ";
        input {
          leaf afi-safi-name {
            mandatory true;
            type afi-safi-type;
            description
              "AFI and SAFI";
          }
          leaf ipv6-prefix {
            mandatory true;
            type inet:ipv6-prefix;
            description
              "IPv6 network and masklength";
          }
        }
      }
    }
  }
  augment "/ncs:devices/ncs:device/ncs:rpc" {
    container rpc-clear-bgp-version-afi-safi-ipv6-addr {
      tailf:ncs-device-type "netconf";
      tailf:display-when "not(../../ncs:module) or ../../ncs:module[ncs:name='Cisco-IOS-XR-ipv4-bgp-act']";
      tailf:action clear-bgp-version-afi-safi-ipv6-addr {
        tailf:actionpoint ncsproxy {
          tailf:internal;
        }
        csc:xr-task "bgp";
        csc:cli-command "clear bgp version <afi-safi-name> <ipv6-addr>";
        description
          "clear BGP prefix version.
          ";
        input {
          leaf afi-safi-name {
            mandatory true;
            type afi-safi-type;
            description
              "AFI and SAFI";
          }
          leaf ipv6-addr {
            mandatory true;
            type inet:ipv6-address;
            description
              "IPv6 network";
          }
        }
      }
    }
  }
  augment "/ncs:devices/ncs:device-group/ncs:ned-id/ncs:rpc" {
    container rpc-clear-bgp-version-afi-safi-ipv6-addr {
      tailf:ncs-device-type "netconf";
      tailf:display-when "/ncs:devices/ncs:device[ncs:name=current()/../../../ncs:member]/ncs:module[ncs:name='Cisco-IOS-XR-ipv4-bgp-act']";
      tailf:action clear-bgp-version-afi-safi-ipv6-addr {
        tailf:actionpoint ncsproxy {
          tailf:internal;
        }
        csc:xr-task "bgp";
        csc:cli-command "clear bgp version <afi-safi-name> <ipv6-addr>";
        description
          "clear BGP prefix version.
          ";
        input {
          leaf afi-safi-name {
            mandatory true;
            type afi-safi-type;
            description
              "AFI and SAFI";
          }
          leaf ipv6-addr {
            mandatory true;
            type inet:ipv6-address;
            description
              "IPv6 network";
          }
        }
      }
    }
  }
  augment "/ncs:devices/ncs:device/ncs:rpc" {
    container rpc-clear-bgp-version-afi-safi-ipv6-addr-ipv6-netmask {
      tailf:ncs-device-type "netconf";
      tailf:display-when "not(../../ncs:module) or ../../ncs:module[ncs:name='Cisco-IOS-XR-ipv4-bgp-act']";
      tailf:action clear-bgp-version-afi-safi-ipv6-addr-ipv6-netmask {
        tailf:actionpoint ncsproxy {
          tailf:internal;
        }
        csc:xr-task "bgp";
        csc:cli-command "clear bgp version <afi-safi-name> <ipv6-addr> <ipv6-netmask>";
        description
          "clear BGP prefix version.
          ";
        input {
          leaf afi-safi-name {
            mandatory true;
            type afi-safi-type;
            description
              "AFI and SAFI";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device-group/ncs:ned-id/ncs:rpc" {
    container rpc-clear-bgp-version-afi-safi-ipv6-addr-ipv6-netmask {
      tailf:ncs-device-type "netconf";
      tailf:display-when "/ncs:devices/ncs:device[ncs:name=current()/../../../ncs:member]/ncs:module[ncs:name='Cisco-IOS-XR-ipv4-bgp-act']";
      tailf:action clear-bgp-version-afi-safi-ipv6-addr-ipv6-netmask {
        tailf:actionpoint ncsproxy {
          tailf:internal;
        }
        csc:xr-task "bgp";
        csc:cli-command "clear bgp version <afi-safi-name> <ipv6-addr> <ipv6-netmask>";
        description
          "clear BGP prefix version.
          ";
        input {
          leaf afi-safi-name {
            mandatory true;
            type afi-safi-type;
            description
              "AFI and SAFI";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device/ncs:rpc" {
    container rpc-clear-bgp-version-afi-safi-ipv4-tunnel-network {
      tailf:ncs-device-type "netconf";
      tailf:display-when "not(../../ncs:module) or ../../ncs:module[ncs:name='Cisco-IOS-XR-ipv4-bgp-act']";
      tailf:action clear-bgp-version-afi-safi-ipv4-tunnel-network {
        tailf:actionpoint ncsproxy {
          tailf:internal;
        }
        csc:xr-task "bgp";
        csc:cli-command "clear bgp version <afi-safi-name> <ipv4-tunnel-network>";
        description
          "clear BGP prefix version.
          ";
        input {
          leaf afi-safi-name {
            mandatory true;
            type afi-safi-type;
            description
              "AFI and SAFI";
          }
          leaf ipv4-tunnel-network {
            mandatory true;
            type string;
            description
              "IPv4 Tunnel network <Tunnel-ID>:<IPv4 Address>";
          }
        }
      }
    }
  }
  augment "/ncs:devices/ncs:device-group/ncs:ned-id/ncs:rpc" {
    container rpc-clear-bgp-version-afi-safi-ipv4-tunnel-network {
      tailf:ncs-device-type "netconf";
      tailf:display-when "/ncs:devices/ncs:device[ncs:name=current()/../../../ncs:member]/ncs:module[ncs:name='Cisco-IOS-XR-ipv4-bgp-act']";
      tailf:action clear-bgp-version-afi-safi-ipv4-tunnel-network {
        tailf:actionpoint ncsproxy {
          tailf:internal;
        }
        csc:xr-task "bgp";
        csc:cli-command "clear bgp version <afi-safi-name> <ipv4-tunnel-network>";
        description
          "clear BGP prefix version.
          ";
        input {
          leaf afi-safi-name {
            mandatory true;
            type afi-safi-type;
            description
              "AFI and SAFI";
          }
          leaf ipv4-tunnel-network {
            mandatory true;
            type string;
            description
              "IPv4 Tunnel network <Tunnel-ID>:<IPv4 Address>";
          }
        }
      }
    }
  }
  augment "/ncs:devices/ncs:device/ncs:rpc" {
    container rpc-clear-bgp-version-afi-safi-rt-constraint-network {
      tailf:ncs-device-type "netconf";
      tailf:display-when "not(../../ncs:module) or ../../ncs:module[ncs:name='Cisco-IOS-XR-ipv4-bgp-act']";
      tailf:action clear-bgp-version-afi-safi-rt-constraint-network {
        tailf:actionpoint ncsproxy {
          tailf:internal;
        }
        csc:xr-task "bgp";
        csc:cli-command "clear bgp version <afi-safi-name> <rt-constraint-network>";
        description
          "clear BGP prefix version.
          ";
        input {
          leaf afi-safi-name {
            mandatory true;
            type afi-safi-type;
            description
              "AFI and SAFI";
          }
          leaf rt-constraint-network {
            mandatory true;
            type string;
            description
              "RT-Constraint network";
          }
        }
      }
    }
  }
  augment "/ncs:devices/ncs:device-group/ncs:ned-id/ncs:rpc" {
    container rpc-clear-bgp-version-afi-safi-rt-constraint-network {
      tailf:ncs-device-type "netconf";
      tailf:display-when "/ncs:devices/ncs:device[ncs:name=current()/../../../ncs:member]/ncs:module[ncs:name='Cisco-IOS-XR-ipv4-bgp-act']";
      tailf:action clear-bgp-version-afi-safi-rt-constraint-network {
        tailf:actionpoint ncsproxy {
          tailf:internal;
        }
        csc:xr-task "bgp";
        csc:cli-command "clear bgp version <afi-safi-name> <rt-constraint-network>";
        description
          "clear BGP prefix version.
          ";
        input {
          leaf afi-safi-name {
            mandatory true;
            type afi-safi-type;
            description
              "AFI and SAFI";
          }
          leaf rt-constraint-network {
            mandatory true;
            type string;
            description
              "RT-Constraint network";
          }
        }
      }
    }
  }
  augment "/ncs:devices/ncs:device/ncs:rpc" {
    container rpc-clear-bgp-version-afi-safi-vrf-network {
      tailf:ncs-device-type "netconf";
      tailf:display-when "not(../../ncs:module) or ../../ncs:module[ncs:name='Cisco-IOS-XR-ipv4-bgp-act']";
      tailf:action clear-bgp-version-afi-safi-vrf-network {
        tailf:actionpoint ncsproxy {
          tailf:internal;
        }
        csc:xr-task "bgp";
        csc:cli-command "clear bgp version <afi-safi-name> vrf <vrf-name> <network>";
        description
          "clear BGP prefix version.
           Display routes for a specified VRF.
          ";
        input {
          leaf afi-safi-name {
            mandatory true;
            type afi-safi-type;
            description
              "AFI and SAFI";
          }
          leaf vrf-name {
            mandatory true;
            type string;
            description
              "VRF name";
          }
          leaf network {
            mandatory true;
            type string;
            description
              "Address family modifier specific network";
          }
        }
      }
    }
  }
  augment "/ncs:devices/ncs:device-group/ncs:ned-id/ncs:rpc" {
    container rpc-clear-bgp-version-afi-safi-vrf-network {
      tailf:ncs-device-type "netconf";
      tailf:display-when "/ncs:devices/ncs:device[ncs:name=current()/../../../ncs:member]/ncs:module[ncs:name='Cisco-IOS-XR-ipv4-bgp-act']";
      tailf:action clear-bgp-version-afi-safi-vrf-network {
        tailf:actionpoint ncsproxy {
          tailf:internal;
        }
        csc:xr-task "bgp";
        csc:cli-command "clear bgp version <afi-safi-name> vrf <vrf-name> <network>";
        description
          "clear BGP prefix version.
           Display routes for a specified VRF.
          ";
        input {
          leaf afi-safi-name {
            mandatory true;
            type afi-safi-type;
            description
              "AFI and SAFI";
          }
          leaf vrf-name {
            mandatory true;
            type string;
            description
              "VRF name";
          }
          leaf network {
            mandatory true;
            type string;
            description
              "Address family modifier specific network";
          }
        }
      }
    }
  }
  augment "/ncs:devices/ncs:device/ncs:rpc" {
    container rpc-clear-bgp-version-afi-safi-rd-network {
      tailf:ncs-device-type "netconf";
      tailf:display-when "not(../../ncs:module) or ../../ncs:module[ncs:name='Cisco-IOS-XR-ipv4-bgp-act']";
      tailf:action clear-bgp-version-afi-safi-rd-network {
        tailf:actionpoint ncsproxy {
          tailf:internal;
        }
        csc:xr-task "bgp";
        csc:cli-command "clear bgp version <afi-safi-name> rd <rd> <network>";
        description
          "clear BGP prefix version.
           Display routes with a specific route distinguisher.
          ";
        input {
          leaf afi-safi-name {
            mandatory true;
            type afi-safi-type;
            description
              "AFI and SAFI";
          }
          leaf rd {
            mandatory true;
            type rd;
            description
              "Route distinguisher";
          }
          leaf network {
            mandatory true;
            type string;
            description
              "Address family modifier specific network";
          }
        }
      }
    }
  }
  augment "/ncs:devices/ncs:device-group/ncs:ned-id/ncs:rpc" {
    container rpc-clear-bgp-version-afi-safi-rd-network {
      tailf:ncs-device-type "netconf";
      tailf:display-when "/ncs:devices/ncs:device[ncs:name=current()/../../../ncs:member]/ncs:module[ncs:name='Cisco-IOS-XR-ipv4-bgp-act']";
      tailf:action clear-bgp-version-afi-safi-rd-network {
        tailf:actionpoint ncsproxy {
          tailf:internal;
        }
        csc:xr-task "bgp";
        csc:cli-command "clear bgp version <afi-safi-name> rd <rd> <network>";
        description
          "clear BGP prefix version.
           Display routes with a specific route distinguisher.
          ";
        input {
          leaf afi-safi-name {
            mandatory true;
            type afi-safi-type;
            description
              "AFI and SAFI";
          }
          leaf rd {
            mandatory true;
            type rd;
            description
              "Route distinguisher";
          }
          leaf network {
            mandatory true;
            type string;
            description
              "Address family modifier specific network";
          }
        }
      }
    }
  }
  augment "/ncs:devices/ncs:device/ncs:rpc" {
    container rpc-clear-bgp-version-afi-safi-network {
      tailf:ncs-device-type "netconf";
      tailf:display-when "not(../../ncs:module) or ../../ncs:module[ncs:name='Cisco-IOS-XR-ipv4-bgp-act']";
      tailf:action clear-bgp-version-afi-safi-network {
        tailf:actionpoint ncsproxy {
          tailf:internal;
        }
        csc:xr-task "bgp";
        csc:cli-command "clear bgp version <afi-safi-name> <network>";
        description
          "clear BGP prefix version.
          ";
        input {
          leaf afi-safi-name {
            mandatory true;
            type afi-safi-type;
            description
              "AFI and SAFI";
          }
          leaf network {
            mandatory true;
            type string;
            description
              "Address family modifier specific network";
          }
        }
      }
    }
  }
  augment "/ncs:devices/ncs:device-group/ncs:ned-id/ncs:rpc" {
    container rpc-clear-bgp-version-afi-safi-network {
      tailf:ncs-device-type "netconf";
      tailf:display-when "/ncs:devices/ncs:device[ncs:name=current()/../../../ncs:member]/ncs:module[ncs:name='Cisco-IOS-XR-ipv4-bgp-act']";
      tailf:action clear-bgp-version-afi-safi-network {
        tailf:actionpoint ncsproxy {
          tailf:internal;
        }
        csc:xr-task "bgp";
        csc:cli-command "clear bgp version <afi-safi-name> <network>";
        description
          "clear BGP prefix version.
          ";
        input {
          leaf afi-safi-name {
            mandatory true;
            type afi-safi-type;
            description
              "AFI and SAFI";
          }
          leaf network {
            mandatory true;
            type string;
            description
              "Address family modifier specific network";
          }
        }
      }
    }
  }
  augment "/ncs:devices/ncs:device/ncs:rpc" {
    container rpc-clear-bgp-version-afi-safi-vrf-ipv4-addr {
      tailf:ncs-device-type "netconf";
      tailf:display-when "not(../../ncs:module) or ../../ncs:module[ncs:name='Cisco-IOS-XR-ipv4-bgp-act']";
      tailf:action clear-bgp-version-afi-safi-vrf-ipv4-addr {
        tailf:actionpoint ncsproxy {
          tailf:internal;
        }
        csc:xr-task "bgp";
        csc:cli-command "clear bgp version <afi-safi-name> vrf <vrf-name> <ipv4-addr>";
        description
          "clear BGP prefix version.
           Display routes for a specified VRF.
          ";
        input {
          leaf afi-safi-name {
            mandatory true;
            type afi-safi-type;
            description
              "AFI and SAFI";
          }
          leaf vrf-name {
            mandatory true;
            type string;
            description
              "VRF name";
          }
          leaf ipv4-addr {
            mandatory true;
            type inet:ipv4-address;
            description
              "IPv4 MDT network";
          }
        }
      }
    }
  }
  augment "/ncs:devices/ncs:device-group/ncs:ned-id/ncs:rpc" {
    container rpc-clear-bgp-version-afi-safi-vrf-ipv4-addr {
      tailf:ncs-device-type "netconf";
      tailf:display-when "/ncs:devices/ncs:device[ncs:name=current()/../../../ncs:member]/ncs:module[ncs:name='Cisco-IOS-XR-ipv4-bgp-act']";
      tailf:action clear-bgp-version-afi-safi-vrf-ipv4-addr {
        tailf:actionpoint ncsproxy {
          tailf:internal;
        }
        csc:xr-task "bgp";
        csc:cli-command "clear bgp version <afi-safi-name> vrf <vrf-name> <ipv4-addr>";
        description
          "clear BGP prefix version.
           Display routes for a specified VRF.
          ";
        input {
          leaf afi-safi-name {
            mandatory true;
            type afi-safi-type;
            description
              "AFI and SAFI";
          }
          leaf vrf-name {
            mandatory true;
            type string;
            description
              "VRF name";
          }
          leaf ipv4-addr {
            mandatory true;
            type inet:ipv4-address;
            description
              "IPv4 MDT network";
          }
        }
      }
    }
  }
  augment "/ncs:devices/ncs:device/ncs:rpc" {
    container rpc-clear-bgp-version-afi-safi-rd-ipv4-addr {
      tailf:ncs-device-type "netconf";
      tailf:display-when "not(../../ncs:module) or ../../ncs:module[ncs:name='Cisco-IOS-XR-ipv4-bgp-act']";
      tailf:action clear-bgp-version-afi-safi-rd-ipv4-addr {
        tailf:actionpoint ncsproxy {
          tailf:internal;
        }
        csc:xr-task "bgp";
        csc:cli-command "clear bgp version <afi-safi-name> rd <rd> <ipv4-addr>";
        description
          "clear BGP prefix version.
           Display routes with a specific route distinguisher.
          ";
        input {
          leaf afi-safi-name {
            mandatory true;
            type afi-safi-type;
            description
              "AFI and SAFI";
          }
          leaf rd {
            mandatory true;
            type rd;
            description
              "Route distinguisher";
          }
          leaf ipv4-addr {
            mandatory true;
            type inet:ipv4-address;
            description
              "IPv4 MDT network";
          }
        }
      }
    }
  }
  augment "/ncs:devices/ncs:device-group/ncs:ned-id/ncs:rpc" {
    container rpc-clear-bgp-version-afi-safi-rd-ipv4-addr {
      tailf:ncs-device-type "netconf";
      tailf:display-when "/ncs:devices/ncs:device[ncs:name=current()/../../../ncs:member]/ncs:module[ncs:name='Cisco-IOS-XR-ipv4-bgp-act']";
      tailf:action clear-bgp-version-afi-safi-rd-ipv4-addr {
        tailf:actionpoint ncsproxy {
          tailf:internal;
        }
        csc:xr-task "bgp";
        csc:cli-command "clear bgp version <afi-safi-name> rd <rd> <ipv4-addr>";
        description
          "clear BGP prefix version.
           Display routes with a specific route distinguisher.
          ";
        input {
          leaf afi-safi-name {
            mandatory true;
            type afi-safi-type;
            description
              "AFI and SAFI";
          }
          leaf rd {
            mandatory true;
            type rd;
            description
              "Route distinguisher";
          }
          leaf ipv4-addr {
            mandatory true;
            type inet:ipv4-address;
            description
              "IPv4 MDT network";
          }
        }
      }
    }
  }
  augment "/ncs:devices/ncs:device/ncs:rpc" {
    container rpc-clear-bgp-version-afi-safi-ipv4-prefix {
      tailf:ncs-device-type "netconf";
      tailf:display-when "not(../../ncs:module) or ../../ncs:module[ncs:name='Cisco-IOS-XR-ipv4-bgp-act']";
      tailf:action clear-bgp-version-afi-safi-ipv4-prefix {
        tailf:actionpoint ncsproxy {
          tailf:internal;
        }
        csc:xr-task "bgp";
        csc:cli-command "clear bgp version <afi-safi-name> <ipv4-prefix>";
        description
          "clear BGP prefix version.
          ";
        input {
          leaf afi-safi-name {
            mandatory true;
            type afi-safi-type;
            description
              "AFI and SAFI";
          }
          leaf ipv4-prefix {
            mandatory true;
            type inet:ipv4-prefix;
            description
              "IPv4 network and masklength";
          }
        }
      }
    }
  }
  augment "/ncs:devices/ncs:device-group/ncs:ned-id/ncs:rpc" {
    container rpc-clear-bgp-version-afi-safi-ipv4-prefix {
      tailf:ncs-device-type "netconf";
      tailf:display-when "/ncs:devices/ncs:device[ncs:name=current()/../../../ncs:member]/ncs:module[ncs:name='Cisco-IOS-XR-ipv4-bgp-act']";
      tailf:action clear-bgp-version-afi-safi-ipv4-prefix {
        tailf:actionpoint ncsproxy {
          tailf:internal;
        }
        csc:xr-task "bgp";
        csc:cli-command "clear bgp version <afi-safi-name> <ipv4-prefix>";
        description
          "clear BGP prefix version.
          ";
        input {
          leaf afi-safi-name {
            mandatory true;
            type afi-safi-type;
            description
              "AFI and SAFI";
          }
          leaf ipv4-prefix {
            mandatory true;
            type inet:ipv4-prefix;
            description
              "IPv4 network and masklength";
          }
        }
      }
    }
  }
  augment "/ncs:devices/ncs:device/ncs:rpc" {
    container rpc-clear-bgp-version-afi-safi-ipv4-addr {
      tailf:ncs-device-type "netconf";
      tailf:display-when "not(../../ncs:module) or ../../ncs:module[ncs:name='Cisco-IOS-XR-ipv4-bgp-act']";
      tailf:action clear-bgp-version-afi-safi-ipv4-addr {
        tailf:actionpoint ncsproxy {
          tailf:internal;
        }
        csc:xr-task "bgp";
        csc:cli-command "clear bgp version <afi-safi-name> <ipv4-addr>";
        description
          "clear BGP prefix version.
          ";
        input {
          leaf afi-safi-name {
            mandatory true;
            type afi-safi-type;
            description
              "AFI and SAFI";
          }
          leaf ipv4-addr {
            mandatory true;
            type inet:ipv4-address;
            description
              "IPv4 network";
          }
        }
      }
    }
  }
  augment "/ncs:devices/ncs:device-group/ncs:ned-id/ncs:rpc" {
    container rpc-clear-bgp-version-afi-safi-ipv4-addr {
      tailf:ncs-device-type "netconf";
      tailf:display-when "/ncs:devices/ncs:device[ncs:name=current()/../../../ncs:member]/ncs:module[ncs:name='Cisco-IOS-XR-ipv4-bgp-act']";
      tailf:action clear-bgp-version-afi-safi-ipv4-addr {
        tailf:actionpoint ncsproxy {
          tailf:internal;
        }
        csc:xr-task "bgp";
        csc:cli-command "clear bgp version <afi-safi-name> <ipv4-addr>";
        description
          "clear BGP prefix version.
          ";
        input {
          leaf afi-safi-name {
            mandatory true;
            type afi-safi-type;
            description
              "AFI and SAFI";
          }
          leaf ipv4-addr {
            mandatory true;
            type inet:ipv4-address;
            description
              "IPv4 network";
          }
        }
      }
    }
  }
  augment "/ncs:devices/ncs:device/ncs:rpc" {
    container rpc-clear-bgp-version-afi-safi-ipv4-addr-ipv4-mask {
      tailf:ncs-device-type "netconf";
      tailf:display-when "not(../../ncs:module) or ../../ncs:module[ncs:name='Cisco-IOS-XR-ipv4-bgp-act']";
      tailf:action clear-bgp-version-afi-safi-ipv4-addr-ipv4-mask {
        tailf:actionpoint ncsproxy {
          tailf:internal;
        }
        csc:xr-task "bgp";
        csc:cli-command "clear bgp version <afi-safi-name> <ipv4-addr> <ipv4-mask>";
        description
          "clear BGP prefix version.
          ";
        input {
          leaf afi-safi-name {
            mandatory true;
            type afi-safi-type;
            description
              "AFI and SAFI";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device-group/ncs:ned-id/ncs:rpc" {
    container rpc-clear-bgp-version-afi-safi-ipv4-addr-ipv4-mask {
      tailf:ncs-device-type "netconf";
      tailf:display-when "/ncs:devices/ncs:device[ncs:name=current()/../../../ncs:member]/ncs:module[ncs:name='Cisco-IOS-XR-ipv4-bgp-act']";
      tailf:action clear-bgp-version-afi-safi-ipv4-addr-ipv4-mask {
        tailf:actionpoint ncsproxy {
          tailf:internal;
        }
        csc:xr-task "bgp";
        csc:cli-command "clear bgp version <afi-safi-name> <ipv4-addr> <ipv4-mask>";
        description
          "clear BGP prefix version.
          ";
        input {
          leaf afi-safi-name {
            mandatory true;
            type afi-safi-type;
            description
              "AFI and SAFI";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device/ncs:rpc" {
    container rpc-clear-bgp-version-afi-safi-rd-ip-prefix {
      tailf:ncs-device-type "netconf";
      tailf:display-when "not(../../ncs:module) or ../../ncs:module[ncs:name='Cisco-IOS-XR-ipv4-bgp-act']";
      tailf:action clear-bgp-version-afi-safi-rd-ip-prefix {
        tailf:actionpoint ncsproxy {
          tailf:internal;
        }
        csc:xr-task "bgp";
        csc:cli-command "clear bgp version <afi-safi-name> rd <rd> <ip-prefix>";
        description
          "clear BGP prefix version.
           Display routes with a specific route distinguisher.
          ";
        input {
          leaf afi-safi-name {
            mandatory true;
            type afi-safi-type;
            description
              "AFI and SAFI";
          }
          leaf rd {
            mandatory true;
            type rd;
            description
              "Route distinguisher";
          }
          leaf ip-prefix {
            mandatory true;
            type inet:ip-prefix;
            description
              "Network and masklength";
          }
        }
      }
    }
  }
  augment "/ncs:devices/ncs:device-group/ncs:ned-id/ncs:rpc" {
    container rpc-clear-bgp-version-afi-safi-rd-ip-prefix {
      tailf:ncs-device-type "netconf";
      tailf:display-when "/ncs:devices/ncs:device[ncs:name=current()/../../../ncs:member]/ncs:module[ncs:name='Cisco-IOS-XR-ipv4-bgp-act']";
      tailf:action clear-bgp-version-afi-safi-rd-ip-prefix {
        tailf:actionpoint ncsproxy {
          tailf:internal;
        }
        csc:xr-task "bgp";
        csc:cli-command "clear bgp version <afi-safi-name> rd <rd> <ip-prefix>";
        description
          "clear BGP prefix version.
           Display routes with a specific route distinguisher.
          ";
        input {
          leaf afi-safi-name {
            mandatory true;
            type afi-safi-type;
            description
              "AFI and SAFI";
          }
          leaf rd {
            mandatory true;
            type rd;
            description
              "Route distinguisher";
          }
          leaf ip-prefix {
            mandatory true;
            type inet:ip-prefix;
            description
              "Network and masklength";
          }
        }
      }
    }
  }
  augment "/ncs:devices/ncs:device/ncs:rpc" {
    container rpc-clear-bgp-version-afi-safi-rd-ip-addr {
      tailf:ncs-device-type "netconf";
      tailf:display-when "not(../../ncs:module) or ../../ncs:module[ncs:name='Cisco-IOS-XR-ipv4-bgp-act']";
      tailf:action clear-bgp-version-afi-safi-rd-ip-addr {
        tailf:actionpoint ncsproxy {
          tailf:internal;
        }
        csc:xr-task "bgp";
        csc:cli-command "clear bgp version <afi-safi-name> rd <rd> <ip-addr>";
        description
          "clear BGP prefix version.
           Display routes with a specific route distinguisher.
          ";
        input {
          leaf afi-safi-name {
            mandatory true;
            type afi-safi-type;
            description
              "AFI and SAFI";
          }
          leaf rd {
            mandatory true;
            type rd;
            description
              "Route distinguisher";
          }
          leaf ip-addr {
            mandatory true;
            type inet:ip-address;
            description
              "Network";
          }
        }
      }
    }
  }
  augment "/ncs:devices/ncs:device-group/ncs:ned-id/ncs:rpc" {
    container rpc-clear-bgp-version-afi-safi-rd-ip-addr {
      tailf:ncs-device-type "netconf";
      tailf:display-when "/ncs:devices/ncs:device[ncs:name=current()/../../../ncs:member]/ncs:module[ncs:name='Cisco-IOS-XR-ipv4-bgp-act']";
      tailf:action clear-bgp-version-afi-safi-rd-ip-addr {
        tailf:actionpoint ncsproxy {
          tailf:internal;
        }
        csc:xr-task "bgp";
        csc:cli-command "clear bgp version <afi-safi-name> rd <rd> <ip-addr>";
        description
          "clear BGP prefix version.
           Display routes with a specific route distinguisher.
          ";
        input {
          leaf afi-safi-name {
            mandatory true;
            type afi-safi-type;
            description
              "AFI and SAFI";
          }
          leaf rd {
            mandatory true;
            type rd;
            description
              "Route distinguisher";
          }
          leaf ip-addr {
            mandatory true;
            type inet:ip-address;
            description
              "Network";
          }
        }
      }
    }
  }
  augment "/ncs:devices/ncs:device/ncs:rpc" {
    container rpc-clear-bgp-version-afi-safi-rd-ip-addr-ip-netmask {
      tailf:ncs-device-type "netconf";
      tailf:display-when "not(../../ncs:module) or ../../ncs:module[ncs:name='Cisco-IOS-XR-ipv4-bgp-act']";
      tailf:action clear-bgp-version-afi-safi-rd-ip-addr-ip-netmask {
        tailf:actionpoint ncsproxy {
          tailf:internal;
        }
        csc:xr-task "bgp";
        csc:cli-command "clear bgp version <afi-safi-name> rd <rd> <ip-addr> <ip-netmask>";
        description
          "clear BGP prefix version.
           Display routes with a specific route distinguisher.
          ";
        input {
          leaf afi-safi-name {
            mandatory true;
            type afi-safi-type;
            description
              "AFI and SAFI";
          }
          leaf rd {
            mandatory true;
            type rd;
            description
              "Route distinguisher";
          }
          leaf ip-addr {
            mandatory true;
            type inet:ip-address;
            description
              "Network";
          }
          leaf ip-netmask {
            mandatory true;
            type ip-netmask;
            description
              "Mask";
          }
        }
      }
    }
  }
  augment "/ncs:devices/ncs:device-group/ncs:ned-id/ncs:rpc" {
    container rpc-clear-bgp-version-afi-safi-rd-ip-addr-ip-netmask {
      tailf:ncs-device-type "netconf";
      tailf:display-when "/ncs:devices/ncs:device[ncs:name=current()/../../../ncs:member]/ncs:module[ncs:name='Cisco-IOS-XR-ipv4-bgp-act']";
      tailf:action clear-bgp-version-afi-safi-rd-ip-addr-ip-netmask {
        tailf:actionpoint ncsproxy {
          tailf:internal;
        }
        csc:xr-task "bgp";
        csc:cli-command "clear bgp version <afi-safi-name> rd <rd> <ip-addr> <ip-netmask>";
        description
          "clear BGP prefix version.
           Display routes with a specific route distinguisher.
          ";
        input {
          leaf afi-safi-name {
            mandatory true;
            type afi-safi-type;
            description
              "AFI and SAFI";
          }
          leaf rd {
            mandatory true;
            type rd;
            description
              "Route distinguisher";
          }
          leaf ip-addr {
            mandatory true;
            type inet:ip-address;
            description
              "Network";
          }
          leaf ip-netmask {
            mandatory true;
            type ip-netmask;
            description
              "Mask";
          }
        }
      }
    }
  }
  augment "/ncs:devices/ncs:device/ncs:rpc" {
    container rpc-clear-bgp-version-afi-safi-bridge-domain-ip-prefix {
      tailf:ncs-device-type "netconf";
      tailf:display-when "not(../../ncs:module) or ../../ncs:module[ncs:name='Cisco-IOS-XR-ipv4-bgp-act']";
      tailf:action clear-bgp-version-afi-safi-bridge-domain-ip-prefix {
        tailf:actionpoint ncsproxy {
          tailf:internal;
        }
        csc:xr-task "bgp";
        csc:cli-command "clear bgp version <afi-safi-name> bridge-domain <bridge-domain-name> <ip-prefix>";
        description
          "clear BGP prefix version.
           Display routes for a specified Bridge Domain.
          ";
        input {
          leaf afi-safi-name {
            mandatory true;
            type afi-safi-type;
            description
              "AFI and SAFI";
          }
          leaf bridge-domain-name {
            mandatory true;
            type string;
            description
              "Bridge Domain";
          }
          leaf ip-prefix {
            mandatory true;
            type inet:ip-prefix;
            description
              "Network and masklength";
          }
        }
      }
    }
  }
  augment "/ncs:devices/ncs:device-group/ncs:ned-id/ncs:rpc" {
    container rpc-clear-bgp-version-afi-safi-bridge-domain-ip-prefix {
      tailf:ncs-device-type "netconf";
      tailf:display-when "/ncs:devices/ncs:device[ncs:name=current()/../../../ncs:member]/ncs:module[ncs:name='Cisco-IOS-XR-ipv4-bgp-act']";
      tailf:action clear-bgp-version-afi-safi-bridge-domain-ip-prefix {
        tailf:actionpoint ncsproxy {
          tailf:internal;
        }
        csc:xr-task "bgp";
        csc:cli-command "clear bgp version <afi-safi-name> bridge-domain <bridge-domain-name> <ip-prefix>";
        description
          "clear BGP prefix version.
           Display routes for a specified Bridge Domain.
          ";
        input {
          leaf afi-safi-name {
            mandatory true;
            type afi-safi-type;
            description
              "AFI and SAFI";
          }
          leaf bridge-domain-name {
            mandatory true;
            type string;
            description
              "Bridge Domain";
          }
          leaf ip-prefix {
            mandatory true;
            type inet:ip-prefix;
            description
              "Network and masklength";
          }
        }
      }
    }
  }
  augment "/ncs:devices/ncs:device/ncs:rpc" {
    container rpc-clear-bgp-version-afi-safi-bridge-domain-ip-addr {
      tailf:ncs-device-type "netconf";
      tailf:display-when "not(../../ncs:module) or ../../ncs:module[ncs:name='Cisco-IOS-XR-ipv4-bgp-act']";
      tailf:action clear-bgp-version-afi-safi-bridge-domain-ip-addr {
        tailf:actionpoint ncsproxy {
          tailf:internal;
        }
        csc:xr-task "bgp";
        csc:cli-command "clear bgp version <afi-safi-name> bridge-domain <bridge-domain-name> <ip-addr>";
        description
          "clear BGP prefix version.
           Display routes for a specified Bridge Domain.
          ";
        input {
          leaf afi-safi-name {
            mandatory true;
            type afi-safi-type;
            description
              "AFI and SAFI";
          }
          leaf bridge-domain-name {
            mandatory true;
            type string;
            description
              "Bridge Domain";
          }
          leaf ip-addr {
            mandatory true;
            type inet:ip-address;
            description
              "Network";
          }
        }
      }
    }
  }
  augment "/ncs:devices/ncs:device-group/ncs:ned-id/ncs:rpc" {
    container rpc-clear-bgp-version-afi-safi-bridge-domain-ip-addr {
      tailf:ncs-device-type "netconf";
      tailf:display-when "/ncs:devices/ncs:device[ncs:name=current()/../../../ncs:member]/ncs:module[ncs:name='Cisco-IOS-XR-ipv4-bgp-act']";
      tailf:action clear-bgp-version-afi-safi-bridge-domain-ip-addr {
        tailf:actionpoint ncsproxy {
          tailf:internal;
        }
        csc:xr-task "bgp";
        csc:cli-command "clear bgp version <afi-safi-name> bridge-domain <bridge-domain-name> <ip-addr>";
        description
          "clear BGP prefix version.
           Display routes for a specified Bridge Domain.
          ";
        input {
          leaf afi-safi-name {
            mandatory true;
            type afi-safi-type;
            description
              "AFI and SAFI";
          }
          leaf bridge-domain-name {
            mandatory true;
            type string;
            description
              "Bridge Domain";
          }
          leaf ip-addr {
            mandatory true;
            type inet:ip-address;
            description
              "Network";
          }
        }
      }
    }
  }
  augment "/ncs:devices/ncs:device/ncs:rpc" {
    container rpc-clear-bgp-version-afi-safi-bridge-domain-ip-addr-ip-netmask {
      tailf:ncs-device-type "netconf";
      tailf:display-when "not(../../ncs:module) or ../../ncs:module[ncs:name='Cisco-IOS-XR-ipv4-bgp-act']";
      tailf:action clear-bgp-version-afi-safi-bridge-domain-ip-addr-ip-netmask {
        tailf:actionpoint ncsproxy {
          tailf:internal;
        }
        csc:xr-task "bgp";
        csc:cli-command "clear bgp version <afi-safi-name> bridge-domain <bridge-domain-name> <ip-addr> <ip-netmask>";
        description
          "clear BGP prefix version.
           Display routes for a specified Bridge Domain.
          ";
        input {
          leaf afi-safi-name {
            mandatory true;
            type afi-safi-type;
            description
              "AFI and SAFI";
          }
          leaf bridge-domain-name {
            mandatory true;
            type string;
            description
              "Bridge Domain";
          }
          leaf ip-addr {
            mandatory true;
            type inet:ip-address;
            description
              "Network";
          }
          leaf ip-netmask {
            mandatory true;
            type ip-netmask;
            description
              "Mask";
          }
        }
      }
    }
  }
  augment "/ncs:devices/ncs:device-group/ncs:ned-id/ncs:rpc" {
    container rpc-clear-bgp-version-afi-safi-bridge-domain-ip-addr-ip-netmask {
      tailf:ncs-device-type "netconf";
      tailf:display-when "/ncs:devices/ncs:device[ncs:name=current()/../../../ncs:member]/ncs:module[ncs:name='Cisco-IOS-XR-ipv4-bgp-act']";
      tailf:action clear-bgp-version-afi-safi-bridge-domain-ip-addr-ip-netmask {
        tailf:actionpoint ncsproxy {
          tailf:internal;
        }
        csc:xr-task "bgp";
        csc:cli-command "clear bgp version <afi-safi-name> bridge-domain <bridge-domain-name> <ip-addr> <ip-netmask>";
        description
          "clear BGP prefix version.
           Display routes for a specified Bridge Domain.
          ";
        input {
          leaf afi-safi-name {
            mandatory true;
            type afi-safi-type;
            description
              "AFI and SAFI";
          }
          leaf bridge-domain-name {
            mandatory true;
            type string;
            description
              "Bridge Domain";
          }
          leaf ip-addr {
            mandatory true;
            type inet:ip-address;
            description
              "Network";
          }
          leaf ip-netmask {
            mandatory true;
            type ip-netmask;
            description
              "Mask";
          }
        }
      }
    }
  }
  augment "/ncs:devices/ncs:device/ncs:rpc" {
    container rpc-clear-bgp-version-afi-safi-ip-prefix {
      tailf:ncs-device-type "netconf";
      tailf:display-when "not(../../ncs:module) or ../../ncs:module[ncs:name='Cisco-IOS-XR-ipv4-bgp-act']";
      tailf:action clear-bgp-version-afi-safi-ip-prefix {
        tailf:actionpoint ncsproxy {
          tailf:internal;
        }
        csc:xr-task "bgp";
        csc:cli-command "clear bgp version <afi-safi-name> <ip-prefix>";
        description
          "clear BGP prefix version.
          ";
        input {
          leaf afi-safi-name {
            mandatory true;
            type afi-safi-type;
            description
              "AFI and SAFI";
          }
          leaf ip-prefix {
            mandatory true;
            type inet:ip-prefix;
            description
              "Network and masklength";
          }
        }
      }
    }
  }
  augment "/ncs:devices/ncs:device-group/ncs:ned-id/ncs:rpc" {
    container rpc-clear-bgp-version-afi-safi-ip-prefix {
      tailf:ncs-device-type "netconf";
      tailf:display-when "/ncs:devices/ncs:device[ncs:name=current()/../../../ncs:member]/ncs:module[ncs:name='Cisco-IOS-XR-ipv4-bgp-act']";
      tailf:action clear-bgp-version-afi-safi-ip-prefix {
        tailf:actionpoint ncsproxy {
          tailf:internal;
        }
        csc:xr-task "bgp";
        csc:cli-command "clear bgp version <afi-safi-name> <ip-prefix>";
        description
          "clear BGP prefix version.
          ";
        input {
          leaf afi-safi-name {
            mandatory true;
            type afi-safi-type;
            description
              "AFI and SAFI";
          }
          leaf ip-prefix {
            mandatory true;
            type inet:ip-prefix;
            description
              "Network and masklength";
          }
        }
      }
    }
  }
  augment "/ncs:devices/ncs:device/ncs:rpc" {
    container rpc-clear-bgp-version-afi-safi-ip-addr {
      tailf:ncs-device-type "netconf";
      tailf:display-when "not(../../ncs:module) or ../../ncs:module[ncs:name='Cisco-IOS-XR-ipv4-bgp-act']";
      tailf:action clear-bgp-version-afi-safi-ip-addr {
        tailf:actionpoint ncsproxy {
          tailf:internal;
        }
        csc:xr-task "bgp";
        csc:cli-command "clear bgp version <afi-safi-name> <ip-addr>";
        description
          "clear BGP prefix version.
          ";
        input {
          leaf afi-safi-name {
            mandatory true;
            type afi-safi-type;
            description
              "AFI and SAFI";
          }
          leaf ip-addr {
            mandatory true;
            type inet:ip-address;
            description
              "Network";
          }
        }
      }
    }
  }
  augment "/ncs:devices/ncs:device-group/ncs:ned-id/ncs:rpc" {
    container rpc-clear-bgp-version-afi-safi-ip-addr {
      tailf:ncs-device-type "netconf";
      tailf:display-when "/ncs:devices/ncs:device[ncs:name=current()/../../../ncs:member]/ncs:module[ncs:name='Cisco-IOS-XR-ipv4-bgp-act']";
      tailf:action clear-bgp-version-afi-safi-ip-addr {
        tailf:actionpoint ncsproxy {
          tailf:internal;
        }
        csc:xr-task "bgp";
        csc:cli-command "clear bgp version <afi-safi-name> <ip-addr>";
        description
          "clear BGP prefix version.
          ";
        input {
          leaf afi-safi-name {
            mandatory true;
            type afi-safi-type;
            description
              "AFI and SAFI";
          }
          leaf ip-addr {
            mandatory true;
            type inet:ip-address;
            description
              "Network";
          }
        }
      }
    }
  }
  augment "/ncs:devices/ncs:device/ncs:rpc" {
    container rpc-clear-bgp-version-afi-safi-ip-addr-ip-netmask {
      tailf:ncs-device-type "netconf";
      tailf:display-when "not(../../ncs:module) or ../../ncs:module[ncs:name='Cisco-IOS-XR-ipv4-bgp-act']";
      tailf:action clear-bgp-version-afi-safi-ip-addr-ip-netmask {
        tailf:actionpoint ncsproxy {
          tailf:internal;
        }
        csc:xr-task "bgp";
        csc:cli-command "clear bgp version <afi-safi-name> <ip-addr> <ip-netmask>";
        description
          "clear BGP prefix version.
          ";
        input {
          leaf afi-safi-name {
            mandatory true;
            type afi-safi-type;
            description
              "AFI and SAFI";
          }
          leaf ip-addr {
            mandatory true;
            type inet:ip-address;
            description
              "Network";
          }
          leaf ip-netmask {
            mandatory true;
            type ip-netmask;
            description
              "Mask";
          }
        }
      }
    }
  }
  augment "/ncs:devices/ncs:device-group/ncs:ned-id/ncs:rpc" {
    container rpc-clear-bgp-version-afi-safi-ip-addr-ip-netmask {
      tailf:ncs-device-type "netconf";
      tailf:display-when "/ncs:devices/ncs:device[ncs:name=current()/../../../ncs:member]/ncs:module[ncs:name='Cisco-IOS-XR-ipv4-bgp-act']";
      tailf:action clear-bgp-version-afi-safi-ip-addr-ip-netmask {
        tailf:actionpoint ncsproxy {
          tailf:internal;
        }
        csc:xr-task "bgp";
        csc:cli-command "clear bgp version <afi-safi-name> <ip-addr> <ip-netmask>";
        description
          "clear BGP prefix version.
          ";
        input {
          leaf afi-safi-name {
            mandatory true;
            type afi-safi-type;
            description
              "AFI and SAFI";
          }
          leaf ip-addr {
            mandatory true;
            type inet:ip-address;
            description
              "Network";
          }
          leaf ip-netmask {
            mandatory true;
            type ip-netmask;
            description
              "Mask";
          }
        }
      }
    }
  }
  augment "/ncs:devices/ncs:device/ncs:rpc" {
    container rpc-clear-bgp-version-ip-prefix {
      tailf:ncs-device-type "netconf";
      tailf:display-when "not(../../ncs:module) or ../../ncs:module[ncs:name='Cisco-IOS-XR-ipv4-bgp-act']";
      tailf:action clear-bgp-version-ip-prefix {
        tailf:actionpoint ncsproxy {
          tailf:internal;
        }
        csc:xr-task "bgp";
        csc:cli-command "clear bgp version <ip-prefix>";
        description
          "clear BGP prefix version.
          ";
        input {
          leaf ip-prefix {
            mandatory true;
            type inet:ip-prefix;
            description
              "Network and masklength";
          }
        }
      }
    }
  }
  augment "/ncs:devices/ncs:device-group/ncs:ned-id/ncs:rpc" {
    container rpc-clear-bgp-version-ip-prefix {
      tailf:ncs-device-type "netconf";
      tailf:display-when "/ncs:devices/ncs:device[ncs:name=current()/../../../ncs:member]/ncs:module[ncs:name='Cisco-IOS-XR-ipv4-bgp-act']";
      tailf:action clear-bgp-version-ip-prefix {
        tailf:actionpoint ncsproxy {
          tailf:internal;
        }
        csc:xr-task "bgp";
        csc:cli-command "clear bgp version <ip-prefix>";
        description
          "clear BGP prefix version.
          ";
        input {
          leaf ip-prefix {
            mandatory true;
            type inet:ip-prefix;
            description
              "Network and masklength";
          }
        }
      }
    }
  }
  augment "/ncs:devices/ncs:device/ncs:rpc" {
    container rpc-clear-bgp-version-ip-addr {
      tailf:ncs-device-type "netconf";
      tailf:display-when "not(../../ncs:module) or ../../ncs:module[ncs:name='Cisco-IOS-XR-ipv4-bgp-act']";
      tailf:action clear-bgp-version-ip-addr {
        tailf:actionpoint ncsproxy {
          tailf:internal;
        }
        csc:xr-task "bgp";
        csc:cli-command "clear bgp version <ip-addr>";
        description
          "clear BGP prefix version.
          ";
        input {
          leaf ip-addr {
            mandatory true;
            type inet:ip-address;
            description
              "Network";
          }
        }
      }
    }
  }
  augment "/ncs:devices/ncs:device-group/ncs:ned-id/ncs:rpc" {
    container rpc-clear-bgp-version-ip-addr {
      tailf:ncs-device-type "netconf";
      tailf:display-when "/ncs:devices/ncs:device[ncs:name=current()/../../../ncs:member]/ncs:module[ncs:name='Cisco-IOS-XR-ipv4-bgp-act']";
      tailf:action clear-bgp-version-ip-addr {
        tailf:actionpoint ncsproxy {
          tailf:internal;
        }
        csc:xr-task "bgp";
        csc:cli-command "clear bgp version <ip-addr>";
        description
          "clear BGP prefix version.
          ";
        input {
          leaf ip-addr {
            mandatory true;
            type inet:ip-address;
            description
              "Network";
          }
        }
      }
    }
  }
  augment "/ncs:devices/ncs:device/ncs:rpc" {
    container rpc-clear-bgp-version-ip-addr-ip-netmask {
      tailf:ncs-device-type "netconf";
      tailf:display-when "not(../../ncs:module) or ../../ncs:module[ncs:name='Cisco-IOS-XR-ipv4-bgp-act']";
      tailf:action clear-bgp-version-ip-addr-ip-netmask {
        tailf:actionpoint ncsproxy {
          tailf:internal;
        }
        csc:xr-task "bgp";
        csc:cli-command "clear bgp version <ip-addr> <ip-netmask>";
        description
          "clear BGP prefix version.
          ";
        input {
          leaf ip-addr {
            mandatory true;
            type inet:ip-address;
            description
              "Network";
          }
          leaf ip-netmask {
            mandatory true;
            type ip-netmask;
            description
              "Mask";
          }
        }
      }
    }
  }
  augment "/ncs:devices/ncs:device-group/ncs:ned-id/ncs:rpc" {
    container rpc-clear-bgp-version-ip-addr-ip-netmask {
      tailf:ncs-device-type "netconf";
      tailf:display-when "/ncs:devices/ncs:device[ncs:name=current()/../../../ncs:member]/ncs:module[ncs:name='Cisco-IOS-XR-ipv4-bgp-act']";
      tailf:action clear-bgp-version-ip-addr-ip-netmask {
        tailf:actionpoint ncsproxy {
          tailf:internal;
        }
        csc:xr-task "bgp";
        csc:cli-command "clear bgp version <ip-addr> <ip-netmask>";
        description
          "clear BGP prefix version.
          ";
        input {
          leaf ip-addr {
            mandatory true;
            type inet:ip-address;
            description
              "Network";
          }
          leaf ip-netmask {
            mandatory true;
            type ip-netmask;
            description
              "Mask";
          }
        }
      }
    }
  }
  augment "/ncs:devices/ncs:device/ncs:rpc" {
    container rpc-clear-bgp-update-outq-update-group {
      tailf:ncs-device-type "netconf";
      tailf:display-when "not(../../ncs:module) or ../../ncs:module[ncs:name='Cisco-IOS-XR-ipv4-bgp-act']";
      tailf:action clear-bgp-update-outq-update-group {
        tailf:actionpoint ncsproxy {
          tailf:internal;
        }
        csc:xr-task "bgp";
        csc:cli-command "clear bgp update outq update-group <update-group>";
        description
          "Clear Update information (Do NOT execute without cisco support)(cisco-support).
           Clear Update generation OutQ counters (Do NOT execute without cisco support)(cisco-support).
           Update-group.
          ";
        input {
          leaf update-group {
            mandatory true;
            type update-group-id;
            description
              "Update-group process ID <x.y>";
          }
        }
      }
    }
  }
  augment "/ncs:devices/ncs:device-group/ncs:ned-id/ncs:rpc" {
    container rpc-clear-bgp-update-outq-update-group {
      tailf:ncs-device-type "netconf";
      tailf:display-when "/ncs:devices/ncs:device[ncs:name=current()/../../../ncs:member]/ncs:module[ncs:name='Cisco-IOS-XR-ipv4-bgp-act']";
      tailf:action clear-bgp-update-outq-update-group {
        tailf:actionpoint ncsproxy {
          tailf:internal;
        }
        csc:xr-task "bgp";
        csc:cli-command "clear bgp update outq update-group <update-group>";
        description
          "Clear Update information (Do NOT execute without cisco support)(cisco-support).
           Clear Update generation OutQ counters (Do NOT execute without cisco support)(cisco-support).
           Update-group.
          ";
        input {
          leaf update-group {
            mandatory true;
            type update-group-id;
            description
              "Update-group process ID <x.y>";
          }
        }
      }
    }
  }
  augment "/ncs:devices/ncs:device/ncs:rpc" {
    container rpc-clear-bgp-update-outq-update-group-update-parent {
      tailf:ncs-device-type "netconf";
      tailf:display-when "not(../../ncs:module) or ../../ncs:module[ncs:name='Cisco-IOS-XR-ipv4-bgp-act']";
      tailf:action clear-bgp-update-outq-update-group-update-parent {
        tailf:actionpoint ncsproxy {
          tailf:internal;
        }
        csc:xr-task "bgp";
        csc:cli-command "clear bgp update outq update-group <update-group> update-parent";
        description
          "Clear Update information (Do NOT execute without cisco support)(cisco-support).
           Clear Update generation OutQ counters (Do NOT execute without cisco support)(cisco-support).
           Update-group.
           Update parents' OutQ counters too.
          ";
        input {
          leaf update-group {
            mandatory true;
            type update-group-id;
            description
              "Update-group process ID <x.y>";
          }
        }
      }
    }
  }
  augment "/ncs:devices/ncs:device-group/ncs:ned-id/ncs:rpc" {
    container rpc-clear-bgp-update-outq-update-group-update-parent {
      tailf:ncs-device-type "netconf";
      tailf:display-when "/ncs:devices/ncs:device[ncs:name=current()/../../../ncs:member]/ncs:module[ncs:name='Cisco-IOS-XR-ipv4-bgp-act']";
      tailf:action clear-bgp-update-outq-update-group-update-parent {
        tailf:actionpoint ncsproxy {
          tailf:internal;
        }
        csc:xr-task "bgp";
        csc:cli-command "clear bgp update outq update-group <update-group> update-parent";
        description
          "Clear Update information (Do NOT execute without cisco support)(cisco-support).
           Clear Update generation OutQ counters (Do NOT execute without cisco support)(cisco-support).
           Update-group.
           Update parents' OutQ counters too.
          ";
        input {
          leaf update-group {
            mandatory true;
            type update-group-id;
            description
              "Update-group process ID <x.y>";
          }
        }
      }
    }
  }
  augment "/ncs:devices/ncs:device/ncs:rpc" {
    container rpc-clear-bgp-update-outq-update-group-sub-group-refresh-sub-group {
      tailf:ncs-device-type "netconf";
      tailf:display-when "not(../../ncs:module) or ../../ncs:module[ncs:name='Cisco-IOS-XR-ipv4-bgp-act']";
      tailf:action clear-bgp-update-outq-update-group-sub-group-refresh-sub-group {
        tailf:actionpoint ncsproxy {
          tailf:internal;
        }
        csc:xr-task "bgp";
        csc:cli-command "clear bgp update outq update-group <update-group> sub-group <refresh-sub-group>";
        description
          "Clear Update information (Do NOT execute without cisco support)(cisco-support).
           Clear Update generation OutQ counters (Do NOT execute without cisco support)(cisco-support).
           Update-group.
           Sub-group.
          ";
        input {
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device-group/ncs:ned-id/ncs:rpc" {
    container rpc-clear-bgp-update-outq-update-group-sub-group-refresh-sub-group {
      tailf:ncs-device-type "netconf";
      tailf:display-when "/ncs:devices/ncs:device[ncs:name=current()/../../../ncs:member]/ncs:module[ncs:name='Cisco-IOS-XR-ipv4-bgp-act']";
      tailf:action clear-bgp-update-outq-update-group-sub-group-refresh-sub-group {
        tailf:actionpoint ncsproxy {
          tailf:internal;
        }
        csc:xr-task "bgp";
        csc:cli-command "clear bgp update outq update-group <update-group> sub-group <refresh-sub-group>";
        description
          "Clear Update information (Do NOT execute without cisco support)(cisco-support).
           Clear Update generation OutQ counters (Do NOT execute without cisco support)(cisco-support).
           Update-group.
           Sub-group.
          ";
        input {
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device/ncs:rpc" {
    container rpc-clear-bgp-update-outq-update-group-sub-group-refresh-sub-group-update-parent {
      tailf:ncs-device-type "netconf";
      tailf:display-when "not(../../ncs:module) or ../../ncs:module[ncs:name='Cisco-IOS-XR-ipv4-bgp-act']";
      tailf:action clear-bgp-update-outq-update-group-sub-group-refresh-sub-group-update-parent {
        tailf:actionpoint ncsproxy {
          tailf:internal;
        }
        csc:xr-task "bgp";
        csc:cli-command "clear bgp update outq update-group <update-group> sub-group <refresh-sub-group> update-parent";
        description
          "Clear Update information (Do NOT execute without cisco support)(cisco-support).
           Clear Update generation OutQ counters (Do NOT execute without cisco support)(cisco-support).
           Update-group.
           Sub-group.
           Update parents' OutQ counters too.
          ";
        input {
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device-group/ncs:ned-id/ncs:rpc" {
    container rpc-clear-bgp-update-outq-update-group-sub-group-refresh-sub-group-update-parent {
      tailf:ncs-device-type "netconf";
      tailf:display-when "/ncs:devices/ncs:device[ncs:name=current()/../../../ncs:member]/ncs:module[ncs:name='Cisco-IOS-XR-ipv4-bgp-act']";
      tailf:action clear-bgp-update-outq-update-group-sub-group-refresh-sub-group-update-parent {
        tailf:actionpoint ncsproxy {
          tailf:internal;
        }
        csc:xr-task "bgp";
        csc:cli-command "clear bgp update outq update-group <update-group> sub-group <refresh-sub-group> update-parent";
        description
          "Clear Update information (Do NOT execute without cisco support)(cisco-support).
           Clear Update generation OutQ counters (Do NOT execute without cisco support)(cisco-support).
           Update-group.
           Sub-group.
           Update parents' OutQ counters too.
          ";
        input {
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device/ncs:rpc" {
    container rpc-clear-bgp-update-outq-update-group-sub-group {
      tailf:ncs-device-type "netconf";
      tailf:display-when "not(../../ncs:module) or ../../ncs:module[ncs:name='Cisco-IOS-XR-ipv4-bgp-act']";
      tailf:action clear-bgp-update-outq-update-group-sub-group {
        tailf:actionpoint ncsproxy {
          tailf:internal;
        }
        csc:xr-task "bgp";
        csc:cli-command "clear bgp update outq update-group <update-group> sub-group <sub-group>";
        description
          "Clear Update information (Do NOT execute without cisco support)(cisco-support).
           Clear Update generation OutQ counters (Do NOT execute without cisco support)(cisco-support).
           Update-group.
           Sub-group.
          ";
        input {
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device-group/ncs:ned-id/ncs:rpc" {
    container rpc-clear-bgp-update-outq-update-group-sub-group {
      tailf:ncs-device-type "netconf";
      tailf:display-when "/ncs:devices/ncs:device[ncs:name=current()/../../../ncs:member]/ncs:module[ncs:name='Cisco-IOS-XR-ipv4-bgp-act']";
      tailf:action clear-bgp-update-outq-update-group-sub-group {
        tailf:actionpoint ncsproxy {
          tailf:internal;
        }
        csc:xr-task "bgp";
        csc:cli-command "clear bgp update outq update-group <update-group> sub-group <sub-group>";
        description
          "Clear Update information (Do NOT execute without cisco support)(cisco-support).
           Clear Update generation OutQ counters (Do NOT execute without cisco support)(cisco-support).
           Update-group.
           Sub-group.
          ";
        input {
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device/ncs:rpc" {
    container rpc-clear-bgp-update-outq-update-group-sub-group-update-parent {
      tailf:ncs-device-type "netconf";
      tailf:display-when "not(../../ncs:module) or ../../ncs:module[ncs:name='Cisco-IOS-XR-ipv4-bgp-act']";
      tailf:action clear-bgp-update-outq-update-group-sub-group-update-parent {
        tailf:actionpoint ncsproxy {
          tailf:internal;
        }
        csc:xr-task "bgp";
        csc:cli-command "clear bgp update outq update-group <update-group> sub-group <sub-group> update-parent";
        description
          "Clear Update information (Do NOT execute without cisco support)(cisco-support).
           Clear Update generation OutQ counters (Do NOT execute without cisco support)(cisco-support).
           Update-group.
           Sub-group.
           Update parents' OutQ counters too.
          ";
        input {
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device-group/ncs:ned-id/ncs:rpc" {
    container rpc-clear-bgp-update-outq-update-group-sub-group-update-parent {
      tailf:ncs-device-type "netconf";
      tailf:display-when "/ncs:devices/ncs:device[ncs:name=current()/../../../ncs:member]/ncs:module[ncs:name='Cisco-IOS-XR-ipv4-bgp-act']";
      tailf:action clear-bgp-update-outq-update-group-sub-group-update-parent {
        tailf:actionpoint ncsproxy {
          tailf:internal;
        }
        csc:xr-task "bgp";
        csc:cli-command "clear bgp update outq update-group <update-group> sub-group <sub-group> update-parent";
        description
          "Clear Update information (Do NOT execute without cisco support)(cisco-support).
           Clear Update generation OutQ counters (Do NOT execute without cisco support)(cisco-support).
           Update-group.
           Sub-group.
           Update parents' OutQ counters too.
          ";
        input {
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device/ncs:rpc" {
    container rpc-clear-bgp-update-outq-process {
      tailf:ncs-device-type "netconf";
      tailf:display-when "not(../../ncs:module) or ../../ncs:module[ncs:name='Cisco-IOS-XR-ipv4-bgp-act']";
      tailf:action clear-bgp-update-outq-process {
        tailf:actionpoint ncsproxy {
          tailf:internal;
        }
        csc:xr-task "bgp";
        csc:cli-command "clear bgp update outq process";
        description
          "Clear Update information (Do NOT execute without cisco support)(cisco-support).
           Clear Update generation OutQ counters (Do NOT execute without cisco support)(cisco-support).
           Process.
          ";
      }
    }
  }
  augment "/ncs:devices/ncs:device-group/ncs:ned-id/ncs:rpc" {
    container rpc-clear-bgp-update-outq-process {
      tailf:ncs-device-type "netconf";
      tailf:display-when "/ncs:devices/ncs:device[ncs:name=current()/../../../ncs:member]/ncs:module[ncs:name='Cisco-IOS-XR-ipv4-bgp-act']";
      tailf:action clear-bgp-update-outq-process {
        tailf:actionpoint ncsproxy {
          tailf:internal;
        }
        csc:xr-task "bgp";
        csc:cli-command "clear bgp update outq process";
        description
          "Clear Update information (Do NOT execute without cisco support)(cisco-support).
           Clear Update generation OutQ counters (Do NOT execute without cisco support)(cisco-support).
           Process.
          ";
      }
    }
  }
  augment "/ncs:devices/ncs:device/ncs:rpc" {
    container rpc-clear-bgp-update-outq-neighbor-ip-addr {
      tailf:ncs-device-type "netconf";
      tailf:display-when "not(../../ncs:module) or ../../ncs:module[ncs:name='Cisco-IOS-XR-ipv4-bgp-act']";
      tailf:action clear-bgp-update-outq-neighbor-ip-addr {
        tailf:actionpoint ncsproxy {
          tailf:internal;
        }
        csc:xr-task "bgp";
        csc:cli-command "clear bgp update outq neighbor <ip-addr>";
        description
          "Clear Update information (Do NOT execute without cisco support)(cisco-support).
           Clear Update generation OutQ counters (Do NOT execute without cisco support)(cisco-support).
           Neighbor.
          ";
        input {
          leaf ip-addr {
            mandatory true;
            type inet:ip-address;
            description
              "Neighbor address";
          }
        }
      }
    }
  }
  augment "/ncs:devices/ncs:device-group/ncs:ned-id/ncs:rpc" {
    container rpc-clear-bgp-update-outq-neighbor-ip-addr {
      tailf:ncs-device-type "netconf";
      tailf:display-when "/ncs:devices/ncs:device[ncs:name=current()/../../../ncs:member]/ncs:module[ncs:name='Cisco-IOS-XR-ipv4-bgp-act']";
      tailf:action clear-bgp-update-outq-neighbor-ip-addr {
        tailf:actionpoint ncsproxy {
          tailf:internal;
        }
        csc:xr-task "bgp";
        csc:cli-command "clear bgp update outq neighbor <ip-addr>";
        description
          "Clear Update information (Do NOT execute without cisco support)(cisco-support).
           Clear Update generation OutQ counters (Do NOT execute without cisco support)(cisco-support).
           Neighbor.
          ";
        input {
          leaf ip-addr {
            mandatory true;
            type inet:ip-address;
            description
              "Neighbor address";
          }
        }
      }
    }
  }
  augment "/ncs:devices/ncs:device/ncs:rpc" {
    container rpc-clear-bgp-update-outq-neighbor-ip-addr-update-parent {
      tailf:ncs-device-type "netconf";
      tailf:display-when "not(../../ncs:module) or ../../ncs:module[ncs:name='Cisco-IOS-XR-ipv4-bgp-act']";
      tailf:action clear-bgp-update-outq-neighbor-ip-addr-update-parent {
        tailf:actionpoint ncsproxy {
          tailf:internal;
        }
        csc:xr-task "bgp";
        csc:cli-command "clear bgp update outq neighbor <ip-addr> update-parent";
        description
          "Clear Update information (Do NOT execute without cisco support)(cisco-support).
           Clear Update generation OutQ counters (Do NOT execute without cisco support)(cisco-support).
           Neighbor.
           Update parents' OutQ counters too.
          ";
        input {
          leaf ip-addr {
            mandatory true;
            type inet:ip-address;
            description
              "Neighbor address";
          }
        }
      }
    }
  }
  augment "/ncs:devices/ncs:device-group/ncs:ned-id/ncs:rpc" {
    container rpc-clear-bgp-update-outq-neighbor-ip-addr-update-parent {
      tailf:ncs-device-type "netconf";
      tailf:display-when "/ncs:devices/ncs:device[ncs:name=current()/../../../ncs:member]/ncs:module[ncs:name='Cisco-IOS-XR-ipv4-bgp-act']";
      tailf:action clear-bgp-update-outq-neighbor-ip-addr-update-parent {
        tailf:actionpoint ncsproxy {
          tailf:internal;
        }
        csc:xr-task "bgp";
        csc:cli-command "clear bgp update outq neighbor <ip-addr> update-parent";
        description
          "Clear Update information (Do NOT execute without cisco support)(cisco-support).
           Clear Update generation OutQ counters (Do NOT execute without cisco support)(cisco-support).
           Neighbor.
           Update parents' OutQ counters too.
          ";
        input {
          leaf ip-addr {
            mandatory true;
            type inet:ip-address;
            description
              "Neighbor address";
          }
        }
      }
    }
  }
  augment "/ncs:devices/ncs:device/ncs:rpc" {
    container rpc-clear-bgp-update-outq-neighbor-ip-addr-refresh {
      tailf:ncs-device-type "netconf";
      tailf:display-when "not(../../ncs:module) or ../../ncs:module[ncs:name='Cisco-IOS-XR-ipv4-bgp-act']";
      tailf:action clear-bgp-update-outq-neighbor-ip-addr-refresh {
        tailf:actionpoint ncsproxy {
          tailf:internal;
        }
        csc:xr-task "bgp";
        csc:cli-command "clear bgp update outq neighbor <ip-addr> refresh";
        description
          "Clear Update information (Do NOT execute without cisco support)(cisco-support).
           Clear Update generation OutQ counters (Do NOT execute without cisco support)(cisco-support).
           Neighbor.
           Refresh OutQ.
          ";
        input {
          leaf ip-addr {
            mandatory true;
            type inet:ip-address;
            description
              "Neighbor address";
          }
        }
      }
    }
  }
  augment "/ncs:devices/ncs:device-group/ncs:ned-id/ncs:rpc" {
    container rpc-clear-bgp-update-outq-neighbor-ip-addr-refresh {
      tailf:ncs-device-type "netconf";
      tailf:display-when "/ncs:devices/ncs:device[ncs:name=current()/../../../ncs:member]/ncs:module[ncs:name='Cisco-IOS-XR-ipv4-bgp-act']";
      tailf:action clear-bgp-update-outq-neighbor-ip-addr-refresh {
        tailf:actionpoint ncsproxy {
          tailf:internal;
        }
        csc:xr-task "bgp";
        csc:cli-command "clear bgp update outq neighbor <ip-addr> refresh";
        description
          "Clear Update information (Do NOT execute without cisco support)(cisco-support).
           Clear Update generation OutQ counters (Do NOT execute without cisco support)(cisco-support).
           Neighbor.
           Refresh OutQ.
          ";
        input {
          leaf ip-addr {
            mandatory true;
            type inet:ip-address;
            description
              "Neighbor address";
          }
        }
      }
    }
  }
  augment "/ncs:devices/ncs:device/ncs:rpc" {
    container rpc-clear-bgp-update-outq-neighbor-ip-addr-refresh-update-parent {
      tailf:ncs-device-type "netconf";
      tailf:display-when "not(../../ncs:module) or ../../ncs:module[ncs:name='Cisco-IOS-XR-ipv4-bgp-act']";
      tailf:action clear-bgp-update-outq-neighbor-ip-addr-refresh-update-parent {
        tailf:actionpoint ncsproxy {
          tailf:internal;
        }
        csc:xr-task "bgp";
        csc:cli-command "clear bgp update outq neighbor <ip-addr> refresh update-parent";
        description
          "Clear Update information (Do NOT execute without cisco support)(cisco-support).
           Clear Update generation OutQ counters (Do NOT execute without cisco support)(cisco-support).
           Neighbor.
           Refresh OutQ.
           Update parents' OutQ counters too.
          ";
        input {
          leaf ip-addr {
            mandatory true;
            type inet:ip-address;
            description
              "Neighbor address";
          }
        }
      }
    }
  }
  augment "/ncs:devices/ncs:device-group/ncs:ned-id/ncs:rpc" {
    container rpc-clear-bgp-update-outq-neighbor-ip-addr-refresh-update-parent {
      tailf:ncs-device-type "netconf";
      tailf:display-when "/ncs:devices/ncs:device[ncs:name=current()/../../../ncs:member]/ncs:module[ncs:name='Cisco-IOS-XR-ipv4-bgp-act']";
      tailf:action clear-bgp-update-outq-neighbor-ip-addr-refresh-update-parent {
        tailf:actionpoint ncsproxy {
          tailf:internal;
        }
        csc:xr-task "bgp";
        csc:cli-command "clear bgp update outq neighbor <ip-addr> refresh update-parent";
        description
          "Clear Update information (Do NOT execute without cisco support)(cisco-support).
           Clear Update generation OutQ counters (Do NOT execute without cisco support)(cisco-support).
           Neighbor.
           Refresh OutQ.
           Update parents' OutQ counters too.
          ";
        input {
          leaf ip-addr {
            mandatory true;
            type inet:ip-address;
            description
              "Neighbor address";
          }
        }
      }
    }
  }
  augment "/ncs:devices/ncs:device/ncs:rpc" {
    container rpc-clear-bgp-update-outq-address-family {
      tailf:ncs-device-type "netconf";
      tailf:display-when "not(../../ncs:module) or ../../ncs:module[ncs:name='Cisco-IOS-XR-ipv4-bgp-act']";
      tailf:action clear-bgp-update-outq-address-family {
        tailf:actionpoint ncsproxy {
          tailf:internal;
        }
        csc:xr-task "bgp";
        csc:cli-command "clear bgp update outq address-family";
        description
          "Clear Update information (Do NOT execute without cisco support)(cisco-support).
           Clear Update generation OutQ counters (Do NOT execute without cisco support)(cisco-support).
           Address-family.
          ";
      }
    }
  }
  augment "/ncs:devices/ncs:device-group/ncs:ned-id/ncs:rpc" {
    container rpc-clear-bgp-update-outq-address-family {
      tailf:ncs-device-type "netconf";
      tailf:display-when "/ncs:devices/ncs:device[ncs:name=current()/../../../ncs:member]/ncs:module[ncs:name='Cisco-IOS-XR-ipv4-bgp-act']";
      tailf:action clear-bgp-update-outq-address-family {
        tailf:actionpoint ncsproxy {
          tailf:internal;
        }
        csc:xr-task "bgp";
        csc:cli-command "clear bgp update outq address-family";
        description
          "Clear Update information (Do NOT execute without cisco support)(cisco-support).
           Clear Update generation OutQ counters (Do NOT execute without cisco support)(cisco-support).
           Address-family.
          ";
      }
    }
  }
  augment "/ncs:devices/ncs:device/ncs:rpc" {
    container rpc-clear-bgp-update-outq-address-family-update-parent {
      tailf:ncs-device-type "netconf";
      tailf:display-when "not(../../ncs:module) or ../../ncs:module[ncs:name='Cisco-IOS-XR-ipv4-bgp-act']";
      tailf:action clear-bgp-update-outq-address-family-update-parent {
        tailf:actionpoint ncsproxy {
          tailf:internal;
        }
        csc:xr-task "bgp";
        csc:cli-command "clear bgp update outq address-family update-parent";
        description
          "Clear Update information (Do NOT execute without cisco support)(cisco-support).
           Clear Update generation OutQ counters (Do NOT execute without cisco support)(cisco-support).
           Address-family.
           Update parents' OutQ counters too.
          ";
      }
    }
  }
  augment "/ncs:devices/ncs:device-group/ncs:ned-id/ncs:rpc" {
    container rpc-clear-bgp-update-outq-address-family-update-parent {
      tailf:ncs-device-type "netconf";
      tailf:display-when "/ncs:devices/ncs:device[ncs:name=current()/../../../ncs:member]/ncs:module[ncs:name='Cisco-IOS-XR-ipv4-bgp-act']";
      tailf:action clear-bgp-update-outq-address-family-update-parent {
        tailf:actionpoint ncsproxy {
          tailf:internal;
        }
        csc:xr-task "bgp";
        csc:cli-command "clear bgp update outq address-family update-parent";
        description
          "Clear Update information (Do NOT execute without cisco support)(cisco-support).
           Clear Update generation OutQ counters (Do NOT execute without cisco support)(cisco-support).
           Address-family.
           Update parents' OutQ counters too.
          ";
      }
    }
  }
  augment "/ncs:devices/ncs:device/ncs:rpc" {
    container rpc-clear-bgp-shutdown {
      tailf:ncs-device-type "netconf";
      tailf:display-when "not(../../ncs:module) or ../../ncs:module[ncs:name='Cisco-IOS-XR-ipv4-bgp-act']";
      tailf:action clear-bgp-shutdown {
        tailf:actionpoint ncsproxy {
          tailf:internal;
        }
        csc:xr-task "bgp";
        csc:cli-command "clear bgp shutdown";
        description
          "Clear all peers which were shut down due to low memory.
          ";
      }
    }
  }
  augment "/ncs:devices/ncs:device-group/ncs:ned-id/ncs:rpc" {
    container rpc-clear-bgp-shutdown {
      tailf:ncs-device-type "netconf";
      tailf:display-when "/ncs:devices/ncs:device[ncs:name=current()/../../../ncs:member]/ncs:module[ncs:name='Cisco-IOS-XR-ipv4-bgp-act']";
      tailf:action clear-bgp-shutdown {
        tailf:actionpoint ncsproxy {
          tailf:internal;
        }
        csc:xr-task "bgp";
        csc:cli-command "clear bgp shutdown";
        description
          "Clear all peers which were shut down due to low memory.
          ";
      }
    }
  }
  augment "/ncs:devices/ncs:device/ncs:rpc" {
    container rpc-clear-bgp-rpki-validation {
      tailf:ncs-device-type "netconf";
      tailf:display-when "not(../../ncs:module) or ../../ncs:module[ncs:name='Cisco-IOS-XR-ipv4-bgp-act']";
      tailf:action clear-bgp-rpki-validation {
        tailf:actionpoint ncsproxy {
          tailf:internal;
        }
        csc:xr-task "bgp";
        csc:cli-command "clear bgp rpki validation";
        description
          "RPKI clear command.
           clear RPKI origin-validation (trigger origin validation).
          ";
      }
    }
  }
  augment "/ncs:devices/ncs:device-group/ncs:ned-id/ncs:rpc" {
    container rpc-clear-bgp-rpki-validation {
      tailf:ncs-device-type "netconf";
      tailf:display-when "/ncs:devices/ncs:device[ncs:name=current()/../../../ncs:member]/ncs:module[ncs:name='Cisco-IOS-XR-ipv4-bgp-act']";
      tailf:action clear-bgp-rpki-validation {
        tailf:actionpoint ncsproxy {
          tailf:internal;
        }
        csc:xr-task "bgp";
        csc:cli-command "clear bgp rpki validation";
        description
          "RPKI clear command.
           clear RPKI origin-validation (trigger origin validation).
          ";
      }
    }
  }
  augment "/ncs:devices/ncs:device/ncs:rpc" {
    container rpc-clear-bgp-rpki-validation-ipv6 {
      tailf:ncs-device-type "netconf";
      tailf:display-when "not(../../ncs:module) or ../../ncs:module[ncs:name='Cisco-IOS-XR-ipv4-bgp-act']";
      tailf:action clear-bgp-rpki-validation-ipv6 {
        tailf:actionpoint ncsproxy {
          tailf:internal;
        }
        csc:xr-task "bgp";
        csc:cli-command "clear bgp rpki validation ipv6";
        description
          "RPKI clear command.
           clear RPKI origin-validation (trigger origin validation).
           trigger origin validation walk for the IPv6 table.
          ";
      }
    }
  }
  augment "/ncs:devices/ncs:device-group/ncs:ned-id/ncs:rpc" {
    container rpc-clear-bgp-rpki-validation-ipv6 {
      tailf:ncs-device-type "netconf";
      tailf:display-when "/ncs:devices/ncs:device[ncs:name=current()/../../../ncs:member]/ncs:module[ncs:name='Cisco-IOS-XR-ipv4-bgp-act']";
      tailf:action clear-bgp-rpki-validation-ipv6 {
        tailf:actionpoint ncsproxy {
          tailf:internal;
        }
        csc:xr-task "bgp";
        csc:cli-command "clear bgp rpki validation ipv6";
        description
          "RPKI clear command.
           clear RPKI origin-validation (trigger origin validation).
           trigger origin validation walk for the IPv6 table.
          ";
      }
    }
  }
  augment "/ncs:devices/ncs:device/ncs:rpc" {
    container rpc-clear-bgp-rpki-validation-ipv4 {
      tailf:ncs-device-type "netconf";
      tailf:display-when "not(../../ncs:module) or ../../ncs:module[ncs:name='Cisco-IOS-XR-ipv4-bgp-act']";
      tailf:action clear-bgp-rpki-validation-ipv4 {
        tailf:actionpoint ncsproxy {
          tailf:internal;
        }
        csc:xr-task "bgp";
        csc:cli-command "clear bgp rpki validation ipv4";
        description
          "RPKI clear command.
           clear RPKI origin-validation (trigger origin validation).
           trigger origin validation walk for the IPv4 table.
          ";
      }
    }
  }
  augment "/ncs:devices/ncs:device-group/ncs:ned-id/ncs:rpc" {
    container rpc-clear-bgp-rpki-validation-ipv4 {
      tailf:ncs-device-type "netconf";
      tailf:display-when "/ncs:devices/ncs:device[ncs:name=current()/../../../ncs:member]/ncs:module[ncs:name='Cisco-IOS-XR-ipv4-bgp-act']";
      tailf:action clear-bgp-rpki-validation-ipv4 {
        tailf:actionpoint ncsproxy {
          tailf:internal;
        }
        csc:xr-task "bgp";
        csc:cli-command "clear bgp rpki validation ipv4";
        description
          "RPKI clear command.
           clear RPKI origin-validation (trigger origin validation).
           trigger origin validation walk for the IPv4 table.
          ";
      }
    }
  }
  augment "/ncs:devices/ncs:device/ncs:rpc" {
    container rpc-clear-bgp-rpki-server-rpki-server {
      tailf:ncs-device-type "netconf";
      tailf:display-when "not(../../ncs:module) or ../../ncs:module[ncs:name='Cisco-IOS-XR-ipv4-bgp-act']";
      tailf:action clear-bgp-rpki-server-rpki-server {
        tailf:actionpoint ncsproxy {
          tailf:internal;
        }
        csc:xr-task "bgp";
        csc:cli-command "clear bgp rpki server <rpki-server>";
        description
          "RPKI clear command.
           clear RPKI cache-server.
          ";
        input {
          leaf rpki-server {
            mandatory true;
            type string;
            description
              "clear a specific RPKI cache-server (hostname or IP address)";
          }
        }
      }
    }
  }
  augment "/ncs:devices/ncs:device-group/ncs:ned-id/ncs:rpc" {
    container rpc-clear-bgp-rpki-server-rpki-server {
      tailf:ncs-device-type "netconf";
      tailf:display-when "/ncs:devices/ncs:device[ncs:name=current()/../../../ncs:member]/ncs:module[ncs:name='Cisco-IOS-XR-ipv4-bgp-act']";
      tailf:action clear-bgp-rpki-server-rpki-server {
        tailf:actionpoint ncsproxy {
          tailf:internal;
        }
        csc:xr-task "bgp";
        csc:cli-command "clear bgp rpki server <rpki-server>";
        description
          "RPKI clear command.
           clear RPKI cache-server.
          ";
        input {
          leaf rpki-server {
            mandatory true;
            type string;
            description
              "clear a specific RPKI cache-server (hostname or IP address)";
          }
        }
      }
    }
  }
  augment "/ncs:devices/ncs:device/ncs:rpc" {
    container rpc-clear-bgp-rpki-server-all {
      tailf:ncs-device-type "netconf";
      tailf:display-when "not(../../ncs:module) or ../../ncs:module[ncs:name='Cisco-IOS-XR-ipv4-bgp-act']";
      tailf:action clear-bgp-rpki-server-all {
        tailf:actionpoint ncsproxy {
          tailf:internal;
        }
        csc:xr-task "bgp";
        csc:cli-command "clear bgp rpki server *";
        description
          "RPKI clear command.
           clear RPKI cache-server.
           clear all RPKI cache-servers.
          ";
      }
    }
  }
  augment "/ncs:devices/ncs:device-group/ncs:ned-id/ncs:rpc" {
    container rpc-clear-bgp-rpki-server-all {
      tailf:ncs-device-type "netconf";
      tailf:display-when "/ncs:devices/ncs:device[ncs:name=current()/../../../ncs:member]/ncs:module[ncs:name='Cisco-IOS-XR-ipv4-bgp-act']";
      tailf:action clear-bgp-rpki-server-all {
        tailf:actionpoint ncsproxy {
          tailf:internal;
        }
        csc:xr-task "bgp";
        csc:cli-command "clear bgp rpki server *";
        description
          "RPKI clear command.
           clear RPKI cache-server.
           clear all RPKI cache-servers.
          ";
      }
    }
  }
  augment "/ncs:devices/ncs:device/ncs:rpc" {
    container rpc-clear-bgp-rpki-server-all-serial-query {
      tailf:ncs-device-type "netconf";
      tailf:display-when "not(../../ncs:module) or ../../ncs:module[ncs:name='Cisco-IOS-XR-ipv4-bgp-act']";
      tailf:action clear-bgp-rpki-server-all-serial-query {
        tailf:actionpoint ncsproxy {
          tailf:internal;
        }
        csc:xr-task "bgp";
        csc:cli-command "clear bgp rpki server * serial-query";
        description
          "RPKI clear command.
           clear RPKI cache-server.
           clear all RPKI cache-servers.
           send serial-queries to all cache-servers (with latest serial numbers).
          ";
      }
    }
  }
  augment "/ncs:devices/ncs:device-group/ncs:ned-id/ncs:rpc" {
    container rpc-clear-bgp-rpki-server-all-serial-query {
      tailf:ncs-device-type "netconf";
      tailf:display-when "/ncs:devices/ncs:device[ncs:name=current()/../../../ncs:member]/ncs:module[ncs:name='Cisco-IOS-XR-ipv4-bgp-act']";
      tailf:action clear-bgp-rpki-server-all-serial-query {
        tailf:actionpoint ncsproxy {
          tailf:internal;
        }
        csc:xr-task "bgp";
        csc:cli-command "clear bgp rpki server * serial-query";
        description
          "RPKI clear command.
           clear RPKI cache-server.
           clear all RPKI cache-servers.
           send serial-queries to all cache-servers (with latest serial numbers).
          ";
      }
    }
  }
  augment "/ncs:devices/ncs:device/ncs:rpc" {
    container rpc-clear-bgp-performance-statistics {
      tailf:ncs-device-type "netconf";
      tailf:display-when "not(../../ncs:module) or ../../ncs:module[ncs:name='Cisco-IOS-XR-ipv4-bgp-act']";
      tailf:action clear-bgp-performance-statistics {
        tailf:actionpoint ncsproxy {
          tailf:internal;
        }
        csc:xr-task "bgp";
        csc:cli-command "clear bgp performance-statistics";
        description
          "Clear performance statistics.
          ";
      }
    }
  }
  augment "/ncs:devices/ncs:device-group/ncs:ned-id/ncs:rpc" {
    container rpc-clear-bgp-performance-statistics {
      tailf:ncs-device-type "netconf";
      tailf:display-when "/ncs:devices/ncs:device[ncs:name=current()/../../../ncs:member]/ncs:module[ncs:name='Cisco-IOS-XR-ipv4-bgp-act']";
      tailf:action clear-bgp-performance-statistics {
        tailf:actionpoint ncsproxy {
          tailf:internal;
        }
        csc:xr-task "bgp";
        csc:cli-command "clear bgp performance-statistics";
        description
          "Clear performance statistics.
          ";
      }
    }
  }
  augment "/ncs:devices/ncs:device/ncs:rpc" {
    container rpc-clear-bgp-peer-drops-ip-addr {
      tailf:ncs-device-type "netconf";
      tailf:display-when "not(../../ncs:module) or ../../ncs:module[ncs:name='Cisco-IOS-XR-ipv4-bgp-act']";
      tailf:action clear-bgp-peer-drops-ip-addr {
        tailf:actionpoint ncsproxy {
          tailf:internal;
        }
        csc:xr-task "bgp";
        csc:cli-command "clear bgp peer-drops <ip-addr>";
        description
          "Clear established/dropped counters for a peer.
          ";
        input {
          leaf ip-addr {
            mandatory true;
            type inet:ip-address;
            description
              "BGP neighbor IP address";
          }
        }
      }
    }
  }
  augment "/ncs:devices/ncs:device-group/ncs:ned-id/ncs:rpc" {
    container rpc-clear-bgp-peer-drops-ip-addr {
      tailf:ncs-device-type "netconf";
      tailf:display-when "/ncs:devices/ncs:device[ncs:name=current()/../../../ncs:member]/ncs:module[ncs:name='Cisco-IOS-XR-ipv4-bgp-act']";
      tailf:action clear-bgp-peer-drops-ip-addr {
        tailf:actionpoint ncsproxy {
          tailf:internal;
        }
        csc:xr-task "bgp";
        csc:cli-command "clear bgp peer-drops <ip-addr>";
        description
          "Clear established/dropped counters for a peer.
          ";
        input {
          leaf ip-addr {
            mandatory true;
            type inet:ip-address;
            description
              "BGP neighbor IP address";
          }
        }
      }
    }
  }
  augment "/ncs:devices/ncs:device/ncs:rpc" {
    container rpc-clear-bgp-peer-drops-all {
      tailf:ncs-device-type "netconf";
      tailf:display-when "not(../../ncs:module) or ../../ncs:module[ncs:name='Cisco-IOS-XR-ipv4-bgp-act']";
      tailf:action clear-bgp-peer-drops-all {
        tailf:actionpoint ncsproxy {
          tailf:internal;
        }
        csc:xr-task "bgp";
        csc:cli-command "clear bgp peer-drops *";
        description
          "Clear established/dropped counters for a peer.
           All Neighbors.
          ";
      }
    }
  }
  augment "/ncs:devices/ncs:device-group/ncs:ned-id/ncs:rpc" {
    container rpc-clear-bgp-peer-drops-all {
      tailf:ncs-device-type "netconf";
      tailf:display-when "/ncs:devices/ncs:device[ncs:name=current()/../../../ncs:member]/ncs:module[ncs:name='Cisco-IOS-XR-ipv4-bgp-act']";
      tailf:action clear-bgp-peer-drops-all {
        tailf:actionpoint ncsproxy {
          tailf:internal;
        }
        csc:xr-task "bgp";
        csc:cli-command "clear bgp peer-drops *";
        description
          "Clear established/dropped counters for a peer.
           All Neighbors.
          ";
      }
    }
  }
  augment "/ncs:devices/ncs:device/ncs:rpc" {
    container rpc-clear-bgp-nexthop-registration-ip-addr {
      tailf:ncs-device-type "netconf";
      tailf:display-when "not(../../ncs:module) or ../../ncs:module[ncs:name='Cisco-IOS-XR-ipv4-bgp-act']";
      tailf:action clear-bgp-nexthop-registration-ip-addr {
        tailf:actionpoint ncsproxy {
          tailf:internal;
        }
        csc:xr-task "bgp";
        csc:cli-command "clear bgp nexthop registration <ip-addr>";
        description
          "Clear nexthop.
           Registration with RIB and reregister.
          ";
        input {
          leaf ip-addr {
            mandatory true;
            type inet:ip-address;
            description
              "Nexthop address";
          }
        }
      }
    }
  }
  augment "/ncs:devices/ncs:device-group/ncs:ned-id/ncs:rpc" {
    container rpc-clear-bgp-nexthop-registration-ip-addr {
      tailf:ncs-device-type "netconf";
      tailf:display-when "/ncs:devices/ncs:device[ncs:name=current()/../../../ncs:member]/ncs:module[ncs:name='Cisco-IOS-XR-ipv4-bgp-act']";
      tailf:action clear-bgp-nexthop-registration-ip-addr {
        tailf:actionpoint ncsproxy {
          tailf:internal;
        }
        csc:xr-task "bgp";
        csc:cli-command "clear bgp nexthop registration <ip-addr>";
        description
          "Clear nexthop.
           Registration with RIB and reregister.
          ";
        input {
          leaf ip-addr {
            mandatory true;
            type inet:ip-address;
            description
              "Nexthop address";
          }
        }
      }
    }
  }
  augment "/ncs:devices/ncs:device/ncs:rpc" {
    container rpc-clear-bgp-nexthop-performance-statistics {
      tailf:ncs-device-type "netconf";
      tailf:display-when "not(../../ncs:module) or ../../ncs:module[ncs:name='Cisco-IOS-XR-ipv4-bgp-act']";
      tailf:action clear-bgp-nexthop-performance-statistics {
        tailf:actionpoint ncsproxy {
          tailf:internal;
        }
        csc:xr-task "bgp";
        csc:cli-command "clear bgp nexthop performance-statistics";
        description
          "Clear nexthop.
           Performance statistics information related to processing.
          ";
      }
    }
  }
  augment "/ncs:devices/ncs:device-group/ncs:ned-id/ncs:rpc" {
    container rpc-clear-bgp-nexthop-performance-statistics {
      tailf:ncs-device-type "netconf";
      tailf:display-when "/ncs:devices/ncs:device[ncs:name=current()/../../../ncs:member]/ncs:module[ncs:name='Cisco-IOS-XR-ipv4-bgp-act']";
      tailf:action clear-bgp-nexthop-performance-statistics {
        tailf:actionpoint ncsproxy {
          tailf:internal;
        }
        csc:xr-task "bgp";
        csc:cli-command "clear bgp nexthop performance-statistics";
        description
          "Clear nexthop.
           Performance statistics information related to processing.
          ";
      }
    }
  }
  augment "/ncs:devices/ncs:device/ncs:rpc" {
    container rpc-clear-bgp-afi-safi-flap-statistics-ipv6-prefix {
      tailf:ncs-device-type "netconf";
      tailf:display-when "not(../../ncs:module) or ../../ncs:module[ncs:name='Cisco-IOS-XR-ipv4-bgp-act']";
      tailf:action clear-bgp-afi-safi-flap-statistics-ipv6-prefix {
        tailf:actionpoint ncsproxy {
          tailf:internal;
        }
        csc:xr-task "bgp";
        csc:cli-command "clear bgp <afi-safi-name> flap-statistics <ipv6-prefix>";
        description
          "Clear flap statistics.
          ";
        input {
          leaf afi-safi-name {
            mandatory true;
            type afi-safi-type;
            description
              "AFI and SAFI";
          }
          leaf ipv6-prefix {
            mandatory true;
            type inet:ipv6-prefix;
            description
              "IPv6 Network and mask or masklength to clear flap statistics";
          }
        }
      }
    }
  }
  augment "/ncs:devices/ncs:device-group/ncs:ned-id/ncs:rpc" {
    container rpc-clear-bgp-afi-safi-flap-statistics-ipv6-prefix {
      tailf:ncs-device-type "netconf";
      tailf:display-when "/ncs:devices/ncs:device[ncs:name=current()/../../../ncs:member]/ncs:module[ncs:name='Cisco-IOS-XR-ipv4-bgp-act']";
      tailf:action clear-bgp-afi-safi-flap-statistics-ipv6-prefix {
        tailf:actionpoint ncsproxy {
          tailf:internal;
        }
        csc:xr-task "bgp";
        csc:cli-command "clear bgp <afi-safi-name> flap-statistics <ipv6-prefix>";
        description
          "Clear flap statistics.
          ";
        input {
          leaf afi-safi-name {
            mandatory true;
            type afi-safi-type;
            description
              "AFI and SAFI";
          }
          leaf ipv6-prefix {
            mandatory true;
            type inet:ipv6-prefix;
            description
              "IPv6 Network and mask or masklength to clear flap statistics";
          }
        }
      }
    }
  }
  augment "/ncs:devices/ncs:device/ncs:rpc" {
    container rpc-clear-bgp-afi-safi-dampening-ipv6-prefix {
      tailf:ncs-device-type "netconf";
      tailf:display-when "not(../../ncs:module) or ../../ncs:module[ncs:name='Cisco-IOS-XR-ipv4-bgp-act']";
      tailf:action clear-bgp-afi-safi-dampening-ipv6-prefix {
        tailf:actionpoint ncsproxy {
          tailf:internal;
        }
        csc:xr-task "bgp";
        csc:cli-command "clear bgp <afi-safi-name> dampening <ipv6-prefix>";
        description
          "Clear route flap dampening information.
          ";
        input {
          leaf afi-safi-name {
            mandatory true;
            type afi-safi-type;
            description
              "AFI and SAFI";
          }
          leaf ipv6-prefix {
            mandatory true;
            type inet:ipv6-prefix;
            description
              "IPv6 Network and mask or masklength to clear dampening information";
          }
        }
      }
    }
  }
  augment "/ncs:devices/ncs:device-group/ncs:ned-id/ncs:rpc" {
    container rpc-clear-bgp-afi-safi-dampening-ipv6-prefix {
      tailf:ncs-device-type "netconf";
      tailf:display-when "/ncs:devices/ncs:device[ncs:name=current()/../../../ncs:member]/ncs:module[ncs:name='Cisco-IOS-XR-ipv4-bgp-act']";
      tailf:action clear-bgp-afi-safi-dampening-ipv6-prefix {
        tailf:actionpoint ncsproxy {
          tailf:internal;
        }
        csc:xr-task "bgp";
        csc:cli-command "clear bgp <afi-safi-name> dampening <ipv6-prefix>";
        description
          "Clear route flap dampening information.
          ";
        input {
          leaf afi-safi-name {
            mandatory true;
            type afi-safi-type;
            description
              "AFI and SAFI";
          }
          leaf ipv6-prefix {
            mandatory true;
            type inet:ipv6-prefix;
            description
              "IPv6 Network and mask or masklength to clear dampening information";
          }
        }
      }
    }
  }
  augment "/ncs:devices/ncs:device/ncs:rpc" {
    container rpc-clear-bgp-afi-safi-flap-statistics-ipv4-prefix {
      tailf:ncs-device-type "netconf";
      tailf:display-when "not(../../ncs:module) or ../../ncs:module[ncs:name='Cisco-IOS-XR-ipv4-bgp-act']";
      tailf:action clear-bgp-afi-safi-flap-statistics-ipv4-prefix {
        tailf:actionpoint ncsproxy {
          tailf:internal;
        }
        csc:xr-task "bgp";
        csc:cli-command "clear bgp <afi-safi-name> flap-statistics <ipv4-prefix>";
        description
          "Clear flap statistics.
          ";
        input {
          leaf afi-safi-name {
            mandatory true;
            type afi-safi-type;
            description
              "AFI and SAFI";
          }
          leaf ipv4-prefix {
            mandatory true;
            type inet:ipv4-prefix;
            description
              "IPv4 Network and mask or masklength to clear flap statistics";
          }
        }
      }
    }
  }
  augment "/ncs:devices/ncs:device-group/ncs:ned-id/ncs:rpc" {
    container rpc-clear-bgp-afi-safi-flap-statistics-ipv4-prefix {
      tailf:ncs-device-type "netconf";
      tailf:display-when "/ncs:devices/ncs:device[ncs:name=current()/../../../ncs:member]/ncs:module[ncs:name='Cisco-IOS-XR-ipv4-bgp-act']";
      tailf:action clear-bgp-afi-safi-flap-statistics-ipv4-prefix {
        tailf:actionpoint ncsproxy {
          tailf:internal;
        }
        csc:xr-task "bgp";
        csc:cli-command "clear bgp <afi-safi-name> flap-statistics <ipv4-prefix>";
        description
          "Clear flap statistics.
          ";
        input {
          leaf afi-safi-name {
            mandatory true;
            type afi-safi-type;
            description
              "AFI and SAFI";
          }
          leaf ipv4-prefix {
            mandatory true;
            type inet:ipv4-prefix;
            description
              "IPv4 Network and mask or masklength to clear flap statistics";
          }
        }
      }
    }
  }
  augment "/ncs:devices/ncs:device/ncs:rpc" {
    container rpc-clear-bgp-afi-safi-dampening-ipv4-prefix {
      tailf:ncs-device-type "netconf";
      tailf:display-when "not(../../ncs:module) or ../../ncs:module[ncs:name='Cisco-IOS-XR-ipv4-bgp-act']";
      tailf:action clear-bgp-afi-safi-dampening-ipv4-prefix {
        tailf:actionpoint ncsproxy {
          tailf:internal;
        }
        csc:xr-task "bgp";
        csc:cli-command "clear bgp <afi-safi-name> dampening <ipv4-prefix>";
        description
          "Clear route flap dampening information.
          ";
        input {
          leaf afi-safi-name {
            mandatory true;
            type afi-safi-type;
            description
              "AFI and SAFI";
          }
          leaf ipv4-prefix {
            mandatory true;
            type inet:ipv4-prefix;
            description
              "IPv4 Network and mask or masklength to clear dampening information";
          }
        }
      }
    }
  }
  augment "/ncs:devices/ncs:device-group/ncs:ned-id/ncs:rpc" {
    container rpc-clear-bgp-afi-safi-dampening-ipv4-prefix {
      tailf:ncs-device-type "netconf";
      tailf:display-when "/ncs:devices/ncs:device[ncs:name=current()/../../../ncs:member]/ncs:module[ncs:name='Cisco-IOS-XR-ipv4-bgp-act']";
      tailf:action clear-bgp-afi-safi-dampening-ipv4-prefix {
        tailf:actionpoint ncsproxy {
          tailf:internal;
        }
        csc:xr-task "bgp";
        csc:cli-command "clear bgp <afi-safi-name> dampening <ipv4-prefix>";
        description
          "Clear route flap dampening information.
          ";
        input {
          leaf afi-safi-name {
            mandatory true;
            type afi-safi-type;
            description
              "AFI and SAFI";
          }
          leaf ipv4-prefix {
            mandatory true;
            type inet:ipv4-prefix;
            description
              "IPv4 Network and mask or masklength to clear dampening information";
          }
        }
      }
    }
  }
  augment "/ncs:devices/ncs:device/ncs:rpc" {
    container rpc-clear-bgp-instance-vrf-update-outq-update-group {
      tailf:ncs-device-type "netconf";
      tailf:display-when "not(../../ncs:module) or ../../ncs:module[ncs:name='Cisco-IOS-XR-ipv4-bgp-act']";
      tailf:action clear-bgp-instance-vrf-update-outq-update-group {
        tailf:actionpoint ncsproxy {
          tailf:internal;
        }
        csc:xr-task "bgp";
        csc:cli-command "clear bgp instance <instance-name> vrf <vrf-all> update outq update-group <update-group>";
        description
          "Choose a particular BGP instance.
           Specify a VRF.
           Clear Update information (Do NOT execute without cisco support)(cisco-support).
           Clear Update generation OutQ counters (Do NOT execute without cisco support)(cisco-support).
           Update-group.
          ";
        input {
          leaf instance-name {
            mandatory true;
            type instance-name;
            description
              "instance name or all";
          }
          leaf vrf-all {
            mandatory true;
            type vrf-name;
            description
              "VRF name or all";
          }
          leaf update-group {
            mandatory true;
            type update-group-id;
            description
              "Update-group process ID <x.y>";
          }
        }
      }
    }
  }
  augment "/ncs:devices/ncs:device-group/ncs:ned-id/ncs:rpc" {
    container rpc-clear-bgp-instance-vrf-update-outq-update-group {
      tailf:ncs-device-type "netconf";
      tailf:display-when "/ncs:devices/ncs:device[ncs:name=current()/../../../ncs:member]/ncs:module[ncs:name='Cisco-IOS-XR-ipv4-bgp-act']";
      tailf:action clear-bgp-instance-vrf-update-outq-update-group {
        tailf:actionpoint ncsproxy {
          tailf:internal;
        }
        csc:xr-task "bgp";
        csc:cli-command "clear bgp instance <instance-name> vrf <vrf-all> update outq update-group <update-group>";
        description
          "Choose a particular BGP instance.
           Specify a VRF.
           Clear Update information (Do NOT execute without cisco support)(cisco-support).
           Clear Update generation OutQ counters (Do NOT execute without cisco support)(cisco-support).
           Update-group.
          ";
        input {
          leaf instance-name {
            mandatory true;
            type instance-name;
            description
              "instance name or all";
          }
          leaf vrf-all {
            mandatory true;
            type vrf-name;
            description
              "VRF name or all";
          }
          leaf update-group {
            mandatory true;
            type update-group-id;
            description
              "Update-group process ID <x.y>";
          }
        }
      }
    }
  }
  augment "/ncs:devices/ncs:device/ncs:rpc" {
    container rpc-clear-bgp-instance-vrf-update-outq-update-group-update-parent {
      tailf:ncs-device-type "netconf";
      tailf:display-when "not(../../ncs:module) or ../../ncs:module[ncs:name='Cisco-IOS-XR-ipv4-bgp-act']";
      tailf:action clear-bgp-instance-vrf-update-outq-update-group-update-parent {
        tailf:actionpoint ncsproxy {
          tailf:internal;
        }
        csc:xr-task "bgp";
        csc:cli-command "clear bgp instance <instance-name> vrf <vrf-all> update outq update-group <update-group> update-parent";
        description
          "Choose a particular BGP instance.
           Specify a VRF.
           Clear Update information (Do NOT execute without cisco support)(cisco-support).
           Clear Update generation OutQ counters (Do NOT execute without cisco support)(cisco-support).
           Update-group.
           Update parents' OutQ counters too.
          ";
        input {
          leaf instance-name {
            mandatory true;
            type instance-name;
            description
              "instance name or all";
          }
          leaf vrf-all {
            mandatory true;
            type vrf-name;
            description
              "VRF name or all";
          }
          leaf update-group {
            mandatory true;
            type update-group-id;
            description
              "Update-group process ID <x.y>";
          }
        }
      }
    }
  }
  augment "/ncs:devices/ncs:device-group/ncs:ned-id/ncs:rpc" {
    container rpc-clear-bgp-instance-vrf-update-outq-update-group-update-parent {
      tailf:ncs-device-type "netconf";
      tailf:display-when "/ncs:devices/ncs:device[ncs:name=current()/../../../ncs:member]/ncs:module[ncs:name='Cisco-IOS-XR-ipv4-bgp-act']";
      tailf:action clear-bgp-instance-vrf-update-outq-update-group-update-parent {
        tailf:actionpoint ncsproxy {
          tailf:internal;
        }
        csc:xr-task "bgp";
        csc:cli-command "clear bgp instance <instance-name> vrf <vrf-all> update outq update-group <update-group> update-parent";
        description
          "Choose a particular BGP instance.
           Specify a VRF.
           Clear Update information (Do NOT execute without cisco support)(cisco-support).
           Clear Update generation OutQ counters (Do NOT execute without cisco support)(cisco-support).
           Update-group.
           Update parents' OutQ counters too.
          ";
        input {
          leaf instance-name {
            mandatory true;
            type instance-name;
            description
              "instance name or all";
          }
          leaf vrf-all {
            mandatory true;
            type vrf-name;
            description
              "VRF name or all";
          }
          leaf update-group {
            mandatory true;
            type update-group-id;
            description
              "Update-group process ID <x.y>";
          }
        }
      }
    }
  }
  augment "/ncs:devices/ncs:device/ncs:rpc" {
    container rpc-clear-bgp-instance-vrf-update-outq-update-group-sub-group-refresh-sub-group {
      tailf:ncs-device-type "netconf";
      tailf:display-when "not(../../ncs:module) or ../../ncs:module[ncs:name='Cisco-IOS-XR-ipv4-bgp-act']";
      tailf:action clear-bgp-instance-vrf-update-outq-update-group-sub-group-refresh-sub-group {
        tailf:actionpoint ncsproxy {
          tailf:internal;
        }
        csc:xr-task "bgp";
        csc:cli-command "clear bgp instance <instance-name> vrf <vrf-all> update outq update-group <update-group> sub-group <refresh-sub-group>";
        description
          "Choose a particular BGP instance.
           Specify a VRF.
           Clear Update information (Do NOT execute without cisco support)(cisco-support).
           Clear Update generation OutQ counters (Do NOT execute without cisco support)(cisco-support).
           Update-group.
           Sub-group.
          ";
        input {
          leaf instance-name {
            mandatory true;
            type instance-name;
            description
              "instance name or all";
          }
          leaf vrf-all {
            mandatory true;
            type vrf-name;
            description
              "VRF name or all";
          }
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device-group/ncs:ned-id/ncs:rpc" {
    container rpc-clear-bgp-instance-vrf-update-outq-update-group-sub-group-refresh-sub-group {
      tailf:ncs-device-type "netconf";
      tailf:display-when "/ncs:devices/ncs:device[ncs:name=current()/../../../ncs:member]/ncs:module[ncs:name='Cisco-IOS-XR-ipv4-bgp-act']";
      tailf:action clear-bgp-instance-vrf-update-outq-update-group-sub-group-refresh-sub-group {
        tailf:actionpoint ncsproxy {
          tailf:internal;
        }
        csc:xr-task "bgp";
        csc:cli-command "clear bgp instance <instance-name> vrf <vrf-all> update outq update-group <update-group> sub-group <refresh-sub-group>";
        description
          "Choose a particular BGP instance.
           Specify a VRF.
           Clear Update information (Do NOT execute without cisco support)(cisco-support).
           Clear Update generation OutQ counters (Do NOT execute without cisco support)(cisco-support).
           Update-group.
           Sub-group.
          ";
        input {
          leaf instance-name {
            mandatory true;
            type instance-name;
            description
              "instance name or all";
          }
          leaf vrf-all {
            mandatory true;
            type vrf-name;
            description
              "VRF name or all";
          }
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device/ncs:rpc" {
    container rpc-clear-bgp-instance-vrf-update-outq-update-group-sub-group-refresh-sub-group-update-parent {
      tailf:ncs-device-type "netconf";
      tailf:display-when "not(../../ncs:module) or ../../ncs:module[ncs:name='Cisco-IOS-XR-ipv4-bgp-act']";
      tailf:action clear-bgp-instance-vrf-update-outq-update-group-sub-group-refresh-sub-group-update-parent {
        tailf:actionpoint ncsproxy {
          tailf:internal;
        }
        csc:xr-task "bgp";
        csc:cli-command "clear bgp instance <instance-name> vrf <vrf-all> update outq update-group <update-group> sub-group <refresh-sub-group> update-parent";
        description
          "Choose a particular BGP instance.
           Specify a VRF.
           Clear Update information (Do NOT execute without cisco support)(cisco-support).
           Clear Update generation OutQ counters (Do NOT execute without cisco support)(cisco-support).
           Update-group.
           Sub-group.
           Update parents' OutQ counters too.
          ";
        input {
          leaf instance-name {
            mandatory true;
            type instance-name;
            description
              "instance name or all";
          }
          leaf vrf-all {
            mandatory true;
            type vrf-name;
            description
              "VRF name or all";
          }
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device-group/ncs:ned-id/ncs:rpc" {
    container rpc-clear-bgp-instance-vrf-update-outq-update-group-sub-group-refresh-sub-group-update-parent {
      tailf:ncs-device-type "netconf";
      tailf:display-when "/ncs:devices/ncs:device[ncs:name=current()/../../../ncs:member]/ncs:module[ncs:name='Cisco-IOS-XR-ipv4-bgp-act']";
      tailf:action clear-bgp-instance-vrf-update-outq-update-group-sub-group-refresh-sub-group-update-parent {
        tailf:actionpoint ncsproxy {
          tailf:internal;
        }
        csc:xr-task "bgp";
        csc:cli-command "clear bgp instance <instance-name> vrf <vrf-all> update outq update-group <update-group> sub-group <refresh-sub-group> update-parent";
        description
          "Choose a particular BGP instance.
           Specify a VRF.
           Clear Update information (Do NOT execute without cisco support)(cisco-support).
           Clear Update generation OutQ counters (Do NOT execute without cisco support)(cisco-support).
           Update-group.
           Sub-group.
           Update parents' OutQ counters too.
          ";
        input {
          leaf instance-name {
            mandatory true;
            type instance-name;
            description
              "instance name or all";
          }
          leaf vrf-all {
            mandatory true;
            type vrf-name;
            description
              "VRF name or all";
          }
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device/ncs:rpc" {
    container rpc-clear-bgp-instance-vrf-update-outq-update-group-sub-group {
      tailf:ncs-device-type "netconf";
      tailf:display-when "not(../../ncs:module) or ../../ncs:module[ncs:name='Cisco-IOS-XR-ipv4-bgp-act']";
      tailf:action clear-bgp-instance-vrf-update-outq-update-group-sub-group {
        tailf:actionpoint ncsproxy {
          tailf:internal;
        }
        csc:xr-task "bgp";
        csc:cli-command "clear bgp instance <instance-name> vrf <vrf-all> update outq update-group <update-group> sub-group <sub-group>";
        description
          "Choose a particular BGP instance.
           Specify a VRF.
           Clear Update information (Do NOT execute without cisco support)(cisco-support).
           Clear Update generation OutQ counters (Do NOT execute without cisco support)(cisco-support).
           Update-group.
           Sub-group.
          ";
        input {
          leaf instance-name {
            mandatory true;
            type instance-name;
            description
              "instance name or all";
          }
          leaf vrf-all {
            mandatory true;
            type vrf-name;
            description
              "VRF name or all";
          }
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device-group/ncs:ned-id/ncs:rpc" {
    container rpc-clear-bgp-instance-vrf-update-outq-update-group-sub-group {
      tailf:ncs-device-type "netconf";
      tailf:display-when "/ncs:devices/ncs:device[ncs:name=current()/../../../ncs:member]/ncs:module[ncs:name='Cisco-IOS-XR-ipv4-bgp-act']";
      tailf:action clear-bgp-instance-vrf-update-outq-update-group-sub-group {
        tailf:actionpoint ncsproxy {
          tailf:internal;
        }
        csc:xr-task "bgp";
        csc:cli-command "clear bgp instance <instance-name> vrf <vrf-all> update outq update-group <update-group> sub-group <sub-group>";
        description
          "Choose a particular BGP instance.
           Specify a VRF.
           Clear Update information (Do NOT execute without cisco support)(cisco-support).
           Clear Update generation OutQ counters (Do NOT execute without cisco support)(cisco-support).
           Update-group.
           Sub-group.
          ";
        input {
          leaf instance-name {
            mandatory true;
            type instance-name;
            description
              "instance name or all";
          }
          leaf vrf-all {
            mandatory true;
            type vrf-name;
            description
              "VRF name or all";
          }
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device/ncs:rpc" {
    container rpc-clear-bgp-instance-vrf-update-outq-update-group-sub-group-update-parent {
      tailf:ncs-device-type "netconf";
      tailf:display-when "not(../../ncs:module) or ../../ncs:module[ncs:name='Cisco-IOS-XR-ipv4-bgp-act']";
      tailf:action clear-bgp-instance-vrf-update-outq-update-group-sub-group-update-parent {
        tailf:actionpoint ncsproxy {
          tailf:internal;
        }
        csc:xr-task "bgp";
        csc:cli-command "clear bgp instance <instance-name> vrf <vrf-all> update outq update-group <update-group> sub-group <sub-group> update-parent";
        description
          "Choose a particular BGP instance.
           Specify a VRF.
           Clear Update information (Do NOT execute without cisco support)(cisco-support).
           Clear Update generation OutQ counters (Do NOT execute without cisco support)(cisco-support).
           Update-group.
           Sub-group.
           Update parents' OutQ counters too.
          ";
        input {
          leaf instance-name {
            mandatory true;
            type instance-name;
            description
              "instance name or all";
          }
          leaf vrf-all {
            mandatory true;
            type vrf-name;
            description
              "VRF name or all";
          }
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device-group/ncs:ned-id/ncs:rpc" {
    container rpc-clear-bgp-instance-vrf-update-outq-update-group-sub-group-update-parent {
      tailf:ncs-device-type "netconf";
      tailf:display-when "/ncs:devices/ncs:device[ncs:name=current()/../../../ncs:member]/ncs:module[ncs:name='Cisco-IOS-XR-ipv4-bgp-act']";
      tailf:action clear-bgp-instance-vrf-update-outq-update-group-sub-group-update-parent {
        tailf:actionpoint ncsproxy {
          tailf:internal;
        }
        csc:xr-task "bgp";
        csc:cli-command "clear bgp instance <instance-name> vrf <vrf-all> update outq update-group <update-group> sub-group <sub-group> update-parent";
        description
          "Choose a particular BGP instance.
           Specify a VRF.
           Clear Update information (Do NOT execute without cisco support)(cisco-support).
           Clear Update generation OutQ counters (Do NOT execute without cisco support)(cisco-support).
           Update-group.
           Sub-group.
           Update parents' OutQ counters too.
          ";
        input {
          leaf instance-name {
            mandatory true;
            type instance-name;
            description
              "instance name or all";
          }
          leaf vrf-all {
            mandatory true;
            type vrf-name;
            description
              "VRF name or all";
          }
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device/ncs:rpc" {
    container rpc-clear-bgp-instance-vrf-update-outq-neighbor-ip-addr {
      tailf:ncs-device-type "netconf";
      tailf:display-when "not(../../ncs:module) or ../../ncs:module[ncs:name='Cisco-IOS-XR-ipv4-bgp-act']";
      tailf:action clear-bgp-instance-vrf-update-outq-neighbor-ip-addr {
        tailf:actionpoint ncsproxy {
          tailf:internal;
        }
        csc:xr-task "bgp";
        csc:cli-command "clear bgp instance <instance-name> vrf <vrf-all> update outq neighbor <ip-addr>";
        description
          "Choose a particular BGP instance.
           Specify a VRF.
           Clear Update information (Do NOT execute without cisco support)(cisco-support).
           Clear Update generation OutQ counters (Do NOT execute without cisco support)(cisco-support).
           Neighbor.
          ";
        input {
          leaf instance-name {
            mandatory true;
            type instance-name;
            description
              "instance name or all";
          }
          leaf vrf-all {
            mandatory true;
            type vrf-name;
            description
              "VRF name or all";
          }
          leaf ip-addr {
            mandatory true;
            type inet:ip-address;
            description
              "Neighbor address";
          }
        }
      }
    }
  }
  augment "/ncs:devices/ncs:device-group/ncs:ned-id/ncs:rpc" {
    container rpc-clear-bgp-instance-vrf-update-outq-neighbor-ip-addr {
      tailf:ncs-device-type "netconf";
      tailf:display-when "/ncs:devices/ncs:device[ncs:name=current()/../../../ncs:member]/ncs:module[ncs:name='Cisco-IOS-XR-ipv4-bgp-act']";
      tailf:action clear-bgp-instance-vrf-update-outq-neighbor-ip-addr {
        tailf:actionpoint ncsproxy {
          tailf:internal;
        }
        csc:xr-task "bgp";
        csc:cli-command "clear bgp instance <instance-name> vrf <vrf-all> update outq neighbor <ip-addr>";
        description
          "Choose a particular BGP instance.
           Specify a VRF.
           Clear Update information (Do NOT execute without cisco support)(cisco-support).
           Clear Update generation OutQ counters (Do NOT execute without cisco support)(cisco-support).
           Neighbor.
          ";
        input {
          leaf instance-name {
            mandatory true;
            type instance-name;
            description
              "instance name or all";
          }
          leaf vrf-all {
            mandatory true;
            type vrf-name;
            description
              "VRF name or all";
          }
          leaf ip-addr {
            mandatory true;
            type inet:ip-address;
            description
              "Neighbor address";
          }
        }
      }
    }
  }
  augment "/ncs:devices/ncs:device/ncs:rpc" {
    container rpc-clear-bgp-instance-vrf-update-outq-neighbor-ip-addr-update-parent {
      tailf:ncs-device-type "netconf";
      tailf:display-when "not(../../ncs:module) or ../../ncs:module[ncs:name='Cisco-IOS-XR-ipv4-bgp-act']";
      tailf:action clear-bgp-instance-vrf-update-outq-neighbor-ip-addr-update-parent {
        tailf:actionpoint ncsproxy {
          tailf:internal;
        }
        csc:xr-task "bgp";
        csc:cli-command "clear bgp instance <instance-name> vrf <vrf-all> update outq neighbor <ip-addr> update-parent";
        description
          "Choose a particular BGP instance.
           Specify a VRF.
           Clear Update information (Do NOT execute without cisco support)(cisco-support).
           Clear Update generation OutQ counters (Do NOT execute without cisco support)(cisco-support).
           Neighbor.
           Update parents' OutQ counters too.
          ";
        input {
          leaf instance-name {
            mandatory true;
            type instance-name;
            description
              "instance name or all";
          }
          leaf vrf-all {
            mandatory true;
            type vrf-name;
            description
              "VRF name or all";
          }
          leaf ip-addr {
            mandatory true;
            type inet:ip-address;
            description
              "Neighbor address";
          }
        }
      }
    }
  }
  augment "/ncs:devices/ncs:device-group/ncs:ned-id/ncs:rpc" {
    container rpc-clear-bgp-instance-vrf-update-outq-neighbor-ip-addr-update-parent {
      tailf:ncs-device-type "netconf";
      tailf:display-when "/ncs:devices/ncs:device[ncs:name=current()/../../../ncs:member]/ncs:module[ncs:name='Cisco-IOS-XR-ipv4-bgp-act']";
      tailf:action clear-bgp-instance-vrf-update-outq-neighbor-ip-addr-update-parent {
        tailf:actionpoint ncsproxy {
          tailf:internal;
        }
        csc:xr-task "bgp";
        csc:cli-command "clear bgp instance <instance-name> vrf <vrf-all> update outq neighbor <ip-addr> update-parent";
        description
          "Choose a particular BGP instance.
           Specify a VRF.
           Clear Update information (Do NOT execute without cisco support)(cisco-support).
           Clear Update generation OutQ counters (Do NOT execute without cisco support)(cisco-support).
           Neighbor.
           Update parents' OutQ counters too.
          ";
        input {
          leaf instance-name {
            mandatory true;
            type instance-name;
            description
              "instance name or all";
          }
          leaf vrf-all {
            mandatory true;
            type vrf-name;
            description
              "VRF name or all";
          }
          leaf ip-addr {
            mandatory true;
            type inet:ip-address;
            description
              "Neighbor address";
          }
        }
      }
    }
  }
  augment "/ncs:devices/ncs:device/ncs:rpc" {
    container rpc-clear-bgp-instance-vrf-update-outq-neighbor-ip-addr-refresh {
      tailf:ncs-device-type "netconf";
      tailf:display-when "not(../../ncs:module) or ../../ncs:module[ncs:name='Cisco-IOS-XR-ipv4-bgp-act']";
      tailf:action clear-bgp-instance-vrf-update-outq-neighbor-ip-addr-refresh {
        tailf:actionpoint ncsproxy {
          tailf:internal;
        }
        csc:xr-task "bgp";
        csc:cli-command "clear bgp instance <instance-name> vrf <vrf-all> update outq neighbor <ip-addr> refresh";
        description
          "Choose a particular BGP instance.
           Specify a VRF.
           Clear Update information (Do NOT execute without cisco support)(cisco-support).
           Clear Update generation OutQ counters (Do NOT execute without cisco support)(cisco-support).
           Neighbor.
           Refresh OutQ.
          ";
        input {
          leaf instance-name {
            mandatory true;
            type instance-name;
            description
              "instance name or all";
          }
          leaf vrf-all {
            mandatory true;
            type vrf-name;
            description
              "VRF name or all";
          }
          leaf ip-addr {
            mandatory true;
            type inet:ip-address;
            description
              "Neighbor address";
          }
        }
      }
    }
  }
  augment "/ncs:devices/ncs:device-group/ncs:ned-id/ncs:rpc" {
    container rpc-clear-bgp-instance-vrf-update-outq-neighbor-ip-addr-refresh {
      tailf:ncs-device-type "netconf";
      tailf:display-when "/ncs:devices/ncs:device[ncs:name=current()/../../../ncs:member]/ncs:module[ncs:name='Cisco-IOS-XR-ipv4-bgp-act']";
      tailf:action clear-bgp-instance-vrf-update-outq-neighbor-ip-addr-refresh {
        tailf:actionpoint ncsproxy {
          tailf:internal;
        }
        csc:xr-task "bgp";
        csc:cli-command "clear bgp instance <instance-name> vrf <vrf-all> update outq neighbor <ip-addr> refresh";
        description
          "Choose a particular BGP instance.
           Specify a VRF.
           Clear Update information (Do NOT execute without cisco support)(cisco-support).
           Clear Update generation OutQ counters (Do NOT execute without cisco support)(cisco-support).
           Neighbor.
           Refresh OutQ.
          ";
        input {
          leaf instance-name {
            mandatory true;
            type instance-name;
            description
              "instance name or all";
          }
          leaf vrf-all {
            mandatory true;
            type vrf-name;
            description
              "VRF name or all";
          }
          leaf ip-addr {
            mandatory true;
            type inet:ip-address;
            description
              "Neighbor address";
          }
        }
      }
    }
  }
  augment "/ncs:devices/ncs:device/ncs:rpc" {
    container rpc-clear-bgp-instance-vrf-update-outq-neighbor-ip-addr-refresh-update-parent {
      tailf:ncs-device-type "netconf";
      tailf:display-when "not(../../ncs:module) or ../../ncs:module[ncs:name='Cisco-IOS-XR-ipv4-bgp-act']";
      tailf:action clear-bgp-instance-vrf-update-outq-neighbor-ip-addr-refresh-update-parent {
        tailf:actionpoint ncsproxy {
          tailf:internal;
        }
        csc:xr-task "bgp";
        csc:cli-command "clear bgp instance <instance-name> vrf <vrf-all> update outq neighbor <ip-addr> refresh update-parent";
        description
          "Choose a particular BGP instance.
           Specify a VRF.
           Clear Update information (Do NOT execute without cisco support)(cisco-support).
           Clear Update generation OutQ counters (Do NOT execute without cisco support)(cisco-support).
           Neighbor.
           Refresh OutQ.
           Update parents' OutQ counters too.
          ";
        input {
          leaf instance-name {
            mandatory true;
            type instance-name;
            description
              "instance name or all";
          }
          leaf vrf-all {
            mandatory true;
            type vrf-name;
            description
              "VRF name or all";
          }
          leaf ip-addr {
            mandatory true;
            type inet:ip-address;
            description
              "Neighbor address";
          }
        }
      }
    }
  }
  augment "/ncs:devices/ncs:device-group/ncs:ned-id/ncs:rpc" {
    container rpc-clear-bgp-instance-vrf-update-outq-neighbor-ip-addr-refresh-update-parent {
      tailf:ncs-device-type "netconf";
      tailf:display-when "/ncs:devices/ncs:device[ncs:name=current()/../../../ncs:member]/ncs:module[ncs:name='Cisco-IOS-XR-ipv4-bgp-act']";
      tailf:action clear-bgp-instance-vrf-update-outq-neighbor-ip-addr-refresh-update-parent {
        tailf:actionpoint ncsproxy {
          tailf:internal;
        }
        csc:xr-task "bgp";
        csc:cli-command "clear bgp instance <instance-name> vrf <vrf-all> update outq neighbor <ip-addr> refresh update-parent";
        description
          "Choose a particular BGP instance.
           Specify a VRF.
           Clear Update information (Do NOT execute without cisco support)(cisco-support).
           Clear Update generation OutQ counters (Do NOT execute without cisco support)(cisco-support).
           Neighbor.
           Refresh OutQ.
           Update parents' OutQ counters too.
          ";
        input {
          leaf instance-name {
            mandatory true;
            type instance-name;
            description
              "instance name or all";
          }
          leaf vrf-all {
            mandatory true;
            type vrf-name;
            description
              "VRF name or all";
          }
          leaf ip-addr {
            mandatory true;
            type inet:ip-address;
            description
              "Neighbor address";
          }
        }
      }
    }
  }
  augment "/ncs:devices/ncs:device/ncs:rpc" {
    container rpc-clear-bgp-instance-vrf-update-outq-address-family {
      tailf:ncs-device-type "netconf";
      tailf:display-when "not(../../ncs:module) or ../../ncs:module[ncs:name='Cisco-IOS-XR-ipv4-bgp-act']";
      tailf:action clear-bgp-instance-vrf-update-outq-address-family {
        tailf:actionpoint ncsproxy {
          tailf:internal;
        }
        csc:xr-task "bgp";
        csc:cli-command "clear bgp instance <instance-name> vrf <vrf-all> update outq address-family";
        description
          "Choose a particular BGP instance.
           Specify a VRF.
           Clear Update information (Do NOT execute without cisco support)(cisco-support).
           Clear Update generation OutQ counters (Do NOT execute without cisco support)(cisco-support).
           Address-family.
          ";
        input {
          leaf instance-name {
            mandatory true;
            type instance-name;
            description
              "instance name or all";
          }
          leaf vrf-all {
            mandatory true;
            type vrf-name;
            description
              "VRF name or all";
          }
        }
      }
    }
  }
  augment "/ncs:devices/ncs:device-group/ncs:ned-id/ncs:rpc" {
    container rpc-clear-bgp-instance-vrf-update-outq-address-family {
      tailf:ncs-device-type "netconf";
      tailf:display-when "/ncs:devices/ncs:device[ncs:name=current()/../../../ncs:member]/ncs:module[ncs:name='Cisco-IOS-XR-ipv4-bgp-act']";
      tailf:action clear-bgp-instance-vrf-update-outq-address-family {
        tailf:actionpoint ncsproxy {
          tailf:internal;
        }
        csc:xr-task "bgp";
        csc:cli-command "clear bgp instance <instance-name> vrf <vrf-all> update outq address-family";
        description
          "Choose a particular BGP instance.
           Specify a VRF.
           Clear Update information (Do NOT execute without cisco support)(cisco-support).
           Clear Update generation OutQ counters (Do NOT execute without cisco support)(cisco-support).
           Address-family.
          ";
        input {
          leaf instance-name {
            mandatory true;
            type instance-name;
            description
              "instance name or all";
          }
          leaf vrf-all {
            mandatory true;
            type vrf-name;
            description
              "VRF name or all";
          }
        }
      }
    }
  }
  augment "/ncs:devices/ncs:device/ncs:rpc" {
    container rpc-clear-bgp-instance-vrf-update-outq-address-family-update-parent {
      tailf:ncs-device-type "netconf";
      tailf:display-when "not(../../ncs:module) or ../../ncs:module[ncs:name='Cisco-IOS-XR-ipv4-bgp-act']";
      tailf:action clear-bgp-instance-vrf-update-outq-address-family-update-parent {
        tailf:actionpoint ncsproxy {
          tailf:internal;
        }
        csc:xr-task "bgp";
        csc:cli-command "clear bgp instance <instance-name> vrf <vrf-all> update outq address-family update-parent";
        description
          "Choose a particular BGP instance.
           Specify a VRF.
           Clear Update information (Do NOT execute without cisco support)(cisco-support).
           Clear Update generation OutQ counters (Do NOT execute without cisco support)(cisco-support).
           Address-family.
           Update parents' OutQ counters too.
          ";
        input {
          leaf instance-name {
            mandatory true;
            type instance-name;
            description
              "instance name or all";
          }
          leaf vrf-all {
            mandatory true;
            type vrf-name;
            description
              "VRF name or all";
          }
        }
      }
    }
  }
  augment "/ncs:devices/ncs:device-group/ncs:ned-id/ncs:rpc" {
    container rpc-clear-bgp-instance-vrf-update-outq-address-family-update-parent {
      tailf:ncs-device-type "netconf";
      tailf:display-when "/ncs:devices/ncs:device[ncs:name=current()/../../../ncs:member]/ncs:module[ncs:name='Cisco-IOS-XR-ipv4-bgp-act']";
      tailf:action clear-bgp-instance-vrf-update-outq-address-family-update-parent {
        tailf:actionpoint ncsproxy {
          tailf:internal;
        }
        csc:xr-task "bgp";
        csc:cli-command "clear bgp instance <instance-name> vrf <vrf-all> update outq address-family update-parent";
        description
          "Choose a particular BGP instance.
           Specify a VRF.
           Clear Update information (Do NOT execute without cisco support)(cisco-support).
           Clear Update generation OutQ counters (Do NOT execute without cisco support)(cisco-support).
           Address-family.
           Update parents' OutQ counters too.
          ";
        input {
          leaf instance-name {
            mandatory true;
            type instance-name;
            description
              "instance name or all";
          }
          leaf vrf-all {
            mandatory true;
            type vrf-name;
            description
              "VRF name or all";
          }
        }
      }
    }
  }
  augment "/ncs:devices/ncs:device/ncs:rpc" {
    container rpc-clear-bgp-instance-vrf-shutdown {
      tailf:ncs-device-type "netconf";
      tailf:display-when "not(../../ncs:module) or ../../ncs:module[ncs:name='Cisco-IOS-XR-ipv4-bgp-act']";
      tailf:action clear-bgp-instance-vrf-shutdown {
        tailf:actionpoint ncsproxy {
          tailf:internal;
        }
        csc:xr-task "bgp";
        csc:cli-command "clear bgp instance <instance-name> vrf <vrf-all> shutdown";
        description
          "Choose a particular BGP instance.
           Specify a VRF.
           Clear all peers which were shut down due to low memory.
          ";
        input {
          leaf instance-name {
            mandatory true;
            type instance-name;
            description
              "instance name or all";
          }
          leaf vrf-all {
            mandatory true;
            type vrf-name;
            description
              "VRF name or all";
          }
        }
      }
    }
  }
  augment "/ncs:devices/ncs:device-group/ncs:ned-id/ncs:rpc" {
    container rpc-clear-bgp-instance-vrf-shutdown {
      tailf:ncs-device-type "netconf";
      tailf:display-when "/ncs:devices/ncs:device[ncs:name=current()/../../../ncs:member]/ncs:module[ncs:name='Cisco-IOS-XR-ipv4-bgp-act']";
      tailf:action clear-bgp-instance-vrf-shutdown {
        tailf:actionpoint ncsproxy {
          tailf:internal;
        }
        csc:xr-task "bgp";
        csc:cli-command "clear bgp instance <instance-name> vrf <vrf-all> shutdown";
        description
          "Choose a particular BGP instance.
           Specify a VRF.
           Clear all peers which were shut down due to low memory.
          ";
        input {
          leaf instance-name {
            mandatory true;
            type instance-name;
            description
              "instance name or all";
          }
          leaf vrf-all {
            mandatory true;
            type vrf-name;
            description
              "VRF name or all";
          }
        }
      }
    }
  }
  augment "/ncs:devices/ncs:device/ncs:rpc" {
    container rpc-clear-bgp-instance-vrf-performance-statistics {
      tailf:ncs-device-type "netconf";
      tailf:display-when "not(../../ncs:module) or ../../ncs:module[ncs:name='Cisco-IOS-XR-ipv4-bgp-act']";
      tailf:action clear-bgp-instance-vrf-performance-statistics {
        tailf:actionpoint ncsproxy {
          tailf:internal;
        }
        csc:xr-task "bgp";
        csc:cli-command "clear bgp instance <instance-name> vrf <vrf-all> performance-statistics";
        description
          "Choose a particular BGP instance.
           Specify a VRF.
           Clear performance statistics.
          ";
        input {
          leaf instance-name {
            mandatory true;
            type instance-name;
            description
              "instance name or all";
          }
          leaf vrf-all {
            mandatory true;
            type vrf-name;
            description
              "VRF name or all";
          }
        }
      }
    }
  }
  augment "/ncs:devices/ncs:device-group/ncs:ned-id/ncs:rpc" {
    container rpc-clear-bgp-instance-vrf-performance-statistics {
      tailf:ncs-device-type "netconf";
      tailf:display-when "/ncs:devices/ncs:device[ncs:name=current()/../../../ncs:member]/ncs:module[ncs:name='Cisco-IOS-XR-ipv4-bgp-act']";
      tailf:action clear-bgp-instance-vrf-performance-statistics {
        tailf:actionpoint ncsproxy {
          tailf:internal;
        }
        csc:xr-task "bgp";
        csc:cli-command "clear bgp instance <instance-name> vrf <vrf-all> performance-statistics";
        description
          "Choose a particular BGP instance.
           Specify a VRF.
           Clear performance statistics.
          ";
        input {
          leaf instance-name {
            mandatory true;
            type instance-name;
            description
              "instance name or all";
          }
          leaf vrf-all {
            mandatory true;
            type vrf-name;
            description
              "VRF name or all";
          }
        }
      }
    }
  }
  augment "/ncs:devices/ncs:device/ncs:rpc" {
    container rpc-clear-bgp-instance-vrf-peer-drops-ip-addr {
      tailf:ncs-device-type "netconf";
      tailf:display-when "not(../../ncs:module) or ../../ncs:module[ncs:name='Cisco-IOS-XR-ipv4-bgp-act']";
      tailf:action clear-bgp-instance-vrf-peer-drops-ip-addr {
        tailf:actionpoint ncsproxy {
          tailf:internal;
        }
        csc:xr-task "bgp";
        csc:cli-command "clear bgp instance <instance-name> vrf <vrf-all> peer-drops <ip-addr>";
        description
          "Choose a particular BGP instance.
           Specify a VRF.
           Clear established/dropped counters for a peer.
          ";
        input {
          leaf instance-name {
            mandatory true;
            type instance-name;
            description
              "instance name or all";
          }
          leaf vrf-all {
            mandatory true;
            type vrf-name;
            description
              "VRF name or all";
          }
          leaf ip-addr {
            mandatory true;
            type inet:ip-address;
            description
              "BGP neighbor IP address";
          }
        }
      }
    }
  }
  augment "/ncs:devices/ncs:device-group/ncs:ned-id/ncs:rpc" {
    container rpc-clear-bgp-instance-vrf-peer-drops-ip-addr {
      tailf:ncs-device-type "netconf";
      tailf:display-when "/ncs:devices/ncs:device[ncs:name=current()/../../../ncs:member]/ncs:module[ncs:name='Cisco-IOS-XR-ipv4-bgp-act']";
      tailf:action clear-bgp-instance-vrf-peer-drops-ip-addr {
        tailf:actionpoint ncsproxy {
          tailf:internal;
        }
        csc:xr-task "bgp";
        csc:cli-command "clear bgp instance <instance-name> vrf <vrf-all> peer-drops <ip-addr>";
        description
          "Choose a particular BGP instance.
           Specify a VRF.
           Clear established/dropped counters for a peer.
          ";
        input {
          leaf instance-name {
            mandatory true;
            type instance-name;
            description
              "instance name or all";
          }
          leaf vrf-all {
            mandatory true;
            type vrf-name;
            description
              "VRF name or all";
          }
          leaf ip-addr {
            mandatory true;
            type inet:ip-address;
            description
              "BGP neighbor IP address";
          }
        }
      }
    }
  }
  augment "/ncs:devices/ncs:device/ncs:rpc" {
    container rpc-clear-bgp-instance-vrf-peer-drops-all {
      tailf:ncs-device-type "netconf";
      tailf:display-when "not(../../ncs:module) or ../../ncs:module[ncs:name='Cisco-IOS-XR-ipv4-bgp-act']";
      tailf:action clear-bgp-instance-vrf-peer-drops-all {
        tailf:actionpoint ncsproxy {
          tailf:internal;
        }
        csc:xr-task "bgp";
        csc:cli-command "clear bgp instance <instance-name> vrf <vrf-all> peer-drops *";
        description
          "Choose a particular BGP instance.
           Specify a VRF.
           Clear established/dropped counters for a peer.
           All Neighbors.
          ";
        input {
          leaf instance-name {
            mandatory true;
            type instance-name;
            description
              "instance name or all";
          }
          leaf vrf-all {
            mandatory true;
            type vrf-name;
            description
              "VRF name or all";
          }
        }
      }
    }
  }
  augment "/ncs:devices/ncs:device-group/ncs:ned-id/ncs:rpc" {
    container rpc-clear-bgp-instance-vrf-peer-drops-all {
      tailf:ncs-device-type "netconf";
      tailf:display-when "/ncs:devices/ncs:device[ncs:name=current()/../../../ncs:member]/ncs:module[ncs:name='Cisco-IOS-XR-ipv4-bgp-act']";
      tailf:action clear-bgp-instance-vrf-peer-drops-all {
        tailf:actionpoint ncsproxy {
          tailf:internal;
        }
        csc:xr-task "bgp";
        csc:cli-command "clear bgp instance <instance-name> vrf <vrf-all> peer-drops *";
        description
          "Choose a particular BGP instance.
           Specify a VRF.
           Clear established/dropped counters for a peer.
           All Neighbors.
          ";
        input {
          leaf instance-name {
            mandatory true;
            type instance-name;
            description
              "instance name or all";
          }
          leaf vrf-all {
            mandatory true;
            type vrf-name;
            description
              "VRF name or all";
          }
        }
      }
    }
  }
  augment "/ncs:devices/ncs:device/ncs:rpc" {
    container rpc-clear-bgp-instance-vrf-nexthop-registration-ip-addr {
      tailf:ncs-device-type "netconf";
      tailf:display-when "not(../../ncs:module) or ../../ncs:module[ncs:name='Cisco-IOS-XR-ipv4-bgp-act']";
      tailf:action clear-bgp-instance-vrf-nexthop-registration-ip-addr {
        tailf:actionpoint ncsproxy {
          tailf:internal;
        }
        csc:xr-task "bgp";
        csc:cli-command "clear bgp instance <instance-name> vrf <vrf-all> nexthop registration <ip-addr>";
        description
          "Choose a particular BGP instance.
           Specify a VRF.
           Clear nexthop.
           Registration with RIB and reregister.
          ";
        input {
          leaf instance-name {
            mandatory true;
            type instance-name;
            description
              "instance name or all";
          }
          leaf vrf-all {
            mandatory true;
            type vrf-name;
            description
              "VRF name or all";
          }
          leaf ip-addr {
            mandatory true;
            type inet:ip-address;
            description
              "Nexthop address";
          }
        }
      }
    }
  }
  augment "/ncs:devices/ncs:device-group/ncs:ned-id/ncs:rpc" {
    container rpc-clear-bgp-instance-vrf-nexthop-registration-ip-addr {
      tailf:ncs-device-type "netconf";
      tailf:display-when "/ncs:devices/ncs:device[ncs:name=current()/../../../ncs:member]/ncs:module[ncs:name='Cisco-IOS-XR-ipv4-bgp-act']";
      tailf:action clear-bgp-instance-vrf-nexthop-registration-ip-addr {
        tailf:actionpoint ncsproxy {
          tailf:internal;
        }
        csc:xr-task "bgp";
        csc:cli-command "clear bgp instance <instance-name> vrf <vrf-all> nexthop registration <ip-addr>";
        description
          "Choose a particular BGP instance.
           Specify a VRF.
           Clear nexthop.
           Registration with RIB and reregister.
          ";
        input {
          leaf instance-name {
            mandatory true;
            type instance-name;
            description
              "instance name or all";
          }
          leaf vrf-all {
            mandatory true;
            type vrf-name;
            description
              "VRF name or all";
          }
          leaf ip-addr {
            mandatory true;
            type inet:ip-address;
            description
              "Nexthop address";
          }
        }
      }
    }
  }
  augment "/ncs:devices/ncs:device/ncs:rpc" {
    container rpc-clear-bgp-instance-vrf-nexthop-performance-statistics {
      tailf:ncs-device-type "netconf";
      tailf:display-when "not(../../ncs:module) or ../../ncs:module[ncs:name='Cisco-IOS-XR-ipv4-bgp-act']";
      tailf:action clear-bgp-instance-vrf-nexthop-performance-statistics {
        tailf:actionpoint ncsproxy {
          tailf:internal;
        }
        csc:xr-task "bgp";
        csc:cli-command "clear bgp instance <instance-name> vrf <vrf-all> nexthop performance-statistics";
        description
          "Choose a particular BGP instance.
           Specify a VRF.
           Clear nexthop.
           Performance statistics information related to processing.
          ";
        input {
          leaf instance-name {
            mandatory true;
            type instance-name;
            description
              "instance name or all";
          }
          leaf vrf-all {
            mandatory true;
            type vrf-name;
            description
              "VRF name or all";
          }
        }
      }
    }
  }
  augment "/ncs:devices/ncs:device-group/ncs:ned-id/ncs:rpc" {
    container rpc-clear-bgp-instance-vrf-nexthop-performance-statistics {
      tailf:ncs-device-type "netconf";
      tailf:display-when "/ncs:devices/ncs:device[ncs:name=current()/../../../ncs:member]/ncs:module[ncs:name='Cisco-IOS-XR-ipv4-bgp-act']";
      tailf:action clear-bgp-instance-vrf-nexthop-performance-statistics {
        tailf:actionpoint ncsproxy {
          tailf:internal;
        }
        csc:xr-task "bgp";
        csc:cli-command "clear bgp instance <instance-name> vrf <vrf-all> nexthop performance-statistics";
        description
          "Choose a particular BGP instance.
           Specify a VRF.
           Clear nexthop.
           Performance statistics information related to processing.
          ";
        input {
          leaf instance-name {
            mandatory true;
            type instance-name;
            description
              "instance name or all";
          }
          leaf vrf-all {
            mandatory true;
            type vrf-name;
            description
              "VRF name or all";
          }
        }
      }
    }
  }
  augment "/ncs:devices/ncs:device/ncs:rpc" {
    container rpc-clear-bgp-instance-vrf-afi-safi-flap-statistics-ipv6-prefix {
      tailf:ncs-device-type "netconf";
      tailf:display-when "not(../../ncs:module) or ../../ncs:module[ncs:name='Cisco-IOS-XR-ipv4-bgp-act']";
      tailf:action clear-bgp-instance-vrf-afi-safi-flap-statistics-ipv6-prefix {
        tailf:actionpoint ncsproxy {
          tailf:internal;
        }
        csc:xr-task "bgp";
        csc:cli-command "clear bgp instance <instance-name> vrf <vrf-all> <afi-safi-name> flap-statistics <ipv6-prefix>";
        description
          "Choose a particular BGP instance.
           Specify a VRF.
           Clear flap statistics.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv6-prefix {
            mandatory true;
            type inet:ipv6-prefix;
            description
              "IPv6 Network and mask or masklength to clear flap statistics";
          }
        }
      }
    }
  }
  augment "/ncs:devices/ncs:device-group/ncs:ned-id/ncs:rpc" {
    container rpc-clear-bgp-instance-vrf-afi-safi-flap-statistics-ipv6-prefix {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-flap-statistics-ipv6-prefix {
        tailf:actionpoint ncsproxy {
          tailf:internal;
        }
        csc:xr-task "bgp";
        csc:cli-command "clear bgp instance <instance-name> vrf <vrf-all> <afi-safi-name> flap-statistics <ipv6-prefix>";
        description
          "Choose a particular BGP instance.
           Specify a VRF.
           Clear flap statistics.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv6-prefix {
            mandatory true;
            type inet:ipv6-prefix;
            description
              "IPv6 Network and mask or masklength to clear flap statistics";
          }
        }
      }
    }
  }
  augment "/ncs:devices/ncs:device/ncs:rpc" {
    container rpc-clear-bgp-instance-vrf-afi-safi-dampening-ipv6-prefix {
      tailf:ncs-device-type "netconf";
      tailf:display-when "not(../../ncs:module) or ../../ncs:module[ncs:name='Cisco-IOS-XR-ipv4-bgp-act']";
      tailf:action clear-bgp-instance-vrf-afi-safi-dampening-ipv6-prefix {
        tailf:actionpoint ncsproxy {
          tailf:internal;
        }
        csc:xr-task "bgp";
        csc:cli-command "clear bgp instance <instance-name> vrf <vrf-all> <afi-safi-name> dampening <ipv6-prefix>";
        description
          "Choose a particular BGP instance.
           Specify a VRF.
           Clear route flap dampening information.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv6-prefix {
            mandatory true;
            type inet:ipv6-prefix;
            description
              "IPv6 Network and mask or masklength to clear dampening information";
          }
        }
      }
    }
  }
  augment "/ncs:devices/ncs:device-group/ncs:ned-id/ncs:rpc" {
    container rpc-clear-bgp-instance-vrf-afi-safi-dampening-ipv6-prefix {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-dampening-ipv6-prefix {
        tailf:actionpoint ncsproxy {
          tailf:internal;
        }
        csc:xr-task "bgp";
        csc:cli-command "clear bgp instance <instance-name> vrf <vrf-all> <afi-safi-name> dampening <ipv6-prefix>";
        description
          "Choose a particular BGP instance.
           Specify a VRF.
           Clear route flap dampening information.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv6-prefix {
            mandatory true;
            type inet:ipv6-prefix;
            description
              "IPv6 Network and mask or masklength to clear dampening information";
          }
        }
      }
    }
  }
  augment "/ncs:devices/ncs:device/ncs:rpc" {
    container rpc-clear-bgp-instance-vrf-afi-safi-update-outq-update-group {
      tailf:ncs-device-type "netconf";
      tailf:display-when "not(../../ncs:module) or ../../ncs:module[ncs:name='Cisco-IOS-XR-ipv4-bgp-act']";
      tailf:action clear-bgp-instance-vrf-afi-safi-update-outq-update-group {
        tailf:actionpoint ncsproxy {
          tailf:internal;
        }
        csc:xr-task "bgp";
        csc:cli-command "clear bgp instance <instance-name> vrf <vrf-all> <afi-safi-name> update outq update-group <update-group>";
        description
          "Choose a particular BGP instance.
           Specify a VRF.
           Clear Update information (Do NOT execute without cisco support)(cisco-support).
           Clear Update generation OutQ counters (Do NOT execute without cisco support)(cisco-support).
           Update-group.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf update-group {
            mandatory true;
            type update-group-id;
            description
              "Update-group process ID <x.y>";
          }
        }
      }
    }
  }
  augment "/ncs:devices/ncs:device-group/ncs:ned-id/ncs:rpc" {
    container rpc-clear-bgp-instance-vrf-afi-safi-update-outq-update-group {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-update-outq-update-group {
        tailf:actionpoint ncsproxy {
          tailf:internal;
        }
        csc:xr-task "bgp";
        csc:cli-command "clear bgp instance <instance-name> vrf <vrf-all> <afi-safi-name> update outq update-group <update-group>";
        description
          "Choose a particular BGP instance.
           Specify a VRF.
           Clear Update information (Do NOT execute without cisco support)(cisco-support).
           Clear Update generation OutQ counters (Do NOT execute without cisco support)(cisco-support).
           Update-group.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf update-group {
            mandatory true;
            type update-group-id;
            description
              "Update-group process ID <x.y>";
          }
        }
      }
    }
  }
  augment "/ncs:devices/ncs:device/ncs:rpc" {
    container rpc-clear-bgp-instance-vrf-afi-safi-update-outq-update-group-update-parent {
      tailf:ncs-device-type "netconf";
      tailf:display-when "not(../../ncs:module) or ../../ncs:module[ncs:name='Cisco-IOS-XR-ipv4-bgp-act']";
      tailf:action clear-bgp-instance-vrf-afi-safi-update-outq-update-group-update-parent {
        tailf:actionpoint ncsproxy {
          tailf:internal;
        }
        csc:xr-task "bgp";
        csc:cli-command "clear bgp instance <instance-name> vrf <vrf-all> <afi-safi-name> update outq update-group <update-group> update-parent";
        description
          "Choose a particular BGP instance.
           Specify a VRF.
           Clear Update information (Do NOT execute without cisco support)(cisco-support).
           Clear Update generation OutQ counters (Do NOT execute without cisco support)(cisco-support).
           Update-group.
           Update parents' OutQ counters too.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf update-group {
            mandatory true;
            type update-group-id;
            description
              "Update-group process ID <x.y>";
          }
        }
      }
    }
  }
  augment "/ncs:devices/ncs:device-group/ncs:ned-id/ncs:rpc" {
    container rpc-clear-bgp-instance-vrf-afi-safi-update-outq-update-group-update-parent {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-update-outq-update-group-update-parent {
        tailf:actionpoint ncsproxy {
          tailf:internal;
        }
        csc:xr-task "bgp";
        csc:cli-command "clear bgp instance <instance-name> vrf <vrf-all> <afi-safi-name> update outq update-group <update-group> update-parent";
        description
          "Choose a particular BGP instance.
           Specify a VRF.
           Clear Update information (Do NOT execute without cisco support)(cisco-support).
           Clear Update generation OutQ counters (Do NOT execute without cisco support)(cisco-support).
           Update-group.
           Update parents' OutQ counters too.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf update-group {
            mandatory true;
            type update-group-id;
            description
              "Update-group process ID <x.y>";
          }
        }
      }
    }
  }
  augment "/ncs:devices/ncs:device/ncs:rpc" {
    container rpc-clear-bgp-instance-vrf-afi-safi-update-outq-update-group-sub-group-refresh-sub-group {
      tailf:ncs-device-type "netconf";
      tailf:display-when "not(../../ncs:module) or ../../ncs:module[ncs:name='Cisco-IOS-XR-ipv4-bgp-act']";
      tailf:action clear-bgp-instance-vrf-afi-safi-update-outq-update-group-sub-group-refresh-sub-group {
        tailf:actionpoint ncsproxy {
          tailf:internal;
        }
        csc:xr-task "bgp";
        csc:cli-command "clear bgp instance <instance-name> vrf <vrf-all> <afi-safi-name> update outq update-group <update-group> sub-group <refresh-sub-group>";
        description
          "Choose a particular BGP instance.
           Specify a VRF.
           Clear Update information (Do NOT execute without cisco support)(cisco-support).
           Clear Update generation OutQ counters (Do NOT execute without cisco support)(cisco-support).
           Update-group.
           Sub-group.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device-group/ncs:ned-id/ncs:rpc" {
    container rpc-clear-bgp-instance-vrf-afi-safi-update-outq-update-group-sub-group-refresh-sub-group {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-update-outq-update-group-sub-group-refresh-sub-group {
        tailf:actionpoint ncsproxy {
          tailf:internal;
        }
        csc:xr-task "bgp";
        csc:cli-command "clear bgp instance <instance-name> vrf <vrf-all> <afi-safi-name> update outq update-group <update-group> sub-group <refresh-sub-group>";
        description
          "Choose a particular BGP instance.
           Specify a VRF.
           Clear Update information (Do NOT execute without cisco support)(cisco-support).
           Clear Update generation OutQ counters (Do NOT execute without cisco support)(cisco-support).
           Update-group.
           Sub-group.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device/ncs:rpc" {
    container rpc-clear-bgp-instance-vrf-afi-safi-update-outq-update-group-sub-group-refresh-sub-group-update-parent {
      tailf:ncs-device-type "netconf";
      tailf:display-when "not(../../ncs:module) or ../../ncs:module[ncs:name='Cisco-IOS-XR-ipv4-bgp-act']";
      tailf:action clear-bgp-instance-vrf-afi-safi-update-outq-update-group-sub-group-refresh-sub-group-update-parent {
        tailf:actionpoint ncsproxy {
          tailf:internal;
        }
        csc:xr-task "bgp";
        csc:cli-command "clear bgp instance <instance-name> vrf <vrf-all> <afi-safi-name> update outq update-group <update-group> sub-group <refresh-sub-group> update-parent";
        description
          "Choose a particular BGP instance.
           Specify a VRF.
           Clear Update information (Do NOT execute without cisco support)(cisco-support).
           Clear Update generation OutQ counters (Do NOT execute without cisco support)(cisco-support).
           Update-group.
           Sub-group.
           Update parents' OutQ counters too.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device-group/ncs:ned-id/ncs:rpc" {
    container rpc-clear-bgp-instance-vrf-afi-safi-update-outq-update-group-sub-group-refresh-sub-group-update-parent {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-update-outq-update-group-sub-group-refresh-sub-group-update-parent {
        tailf:actionpoint ncsproxy {
          tailf:internal;
        }
        csc:xr-task "bgp";
        csc:cli-command "clear bgp instance <instance-name> vrf <vrf-all> <afi-safi-name> update outq update-group <update-group> sub-group <refresh-sub-group> update-parent";
        description
          "Choose a particular BGP instance.
           Specify a VRF.
           Clear Update information (Do NOT execute without cisco support)(cisco-support).
           Clear Update generation OutQ counters (Do NOT execute without cisco support)(cisco-support).
           Update-group.
           Sub-group.
           Update parents' OutQ counters too.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device/ncs:rpc" {
    container rpc-clear-bgp-instance-vrf-afi-safi-update-outq-update-group-sub-group {
      tailf:ncs-device-type "netconf";
      tailf:display-when "not(../../ncs:module) or ../../ncs:module[ncs:name='Cisco-IOS-XR-ipv4-bgp-act']";
      tailf:action clear-bgp-instance-vrf-afi-safi-update-outq-update-group-sub-group {
        tailf:actionpoint ncsproxy {
          tailf:internal;
        }
        csc:xr-task "bgp";
        csc:cli-command "clear bgp instance <instance-name> vrf <vrf-all> <afi-safi-name> update outq update-group <update-group> sub-group <sub-group>";
        description
          "Choose a particular BGP instance.
           Specify a VRF.
           Clear Update information (Do NOT execute without cisco support)(cisco-support).
           Clear Update generation OutQ counters (Do NOT execute without cisco support)(cisco-support).
           Update-group.
           Sub-group.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device-group/ncs:ned-id/ncs:rpc" {
    container rpc-clear-bgp-instance-vrf-afi-safi-update-outq-update-group-sub-group {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-update-outq-update-group-sub-group {
        tailf:actionpoint ncsproxy {
          tailf:internal;
        }
        csc:xr-task "bgp";
        csc:cli-command "clear bgp instance <instance-name> vrf <vrf-all> <afi-safi-name> update outq update-group <update-group> sub-group <sub-group>";
        description
          "Choose a particular BGP instance.
           Specify a VRF.
           Clear Update information (Do NOT execute without cisco support)(cisco-support).
           Clear Update generation OutQ counters (Do NOT execute without cisco support)(cisco-support).
           Update-group.
           Sub-group.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device/ncs:rpc" {
    container rpc-clear-bgp-instance-vrf-afi-safi-update-outq-update-group-sub-group-update-parent {
      tailf:ncs-device-type "netconf";
      tailf:display-when "not(../../ncs:module) or ../../ncs:module[ncs:name='Cisco-IOS-XR-ipv4-bgp-act']";
      tailf:action clear-bgp-instance-vrf-afi-safi-update-outq-update-group-sub-group-update-parent {
        tailf:actionpoint ncsproxy {
          tailf:internal;
        }
        csc:xr-task "bgp";
        csc:cli-command "clear bgp instance <instance-name> vrf <vrf-all> <afi-safi-name> update outq update-group <update-group> sub-group <sub-group> update-parent";
        description
          "Choose a particular BGP instance.
           Specify a VRF.
           Clear Update information (Do NOT execute without cisco support)(cisco-support).
           Clear Update generation OutQ counters (Do NOT execute without cisco support)(cisco-support).
           Update-group.
           Sub-group.
           Update parents' OutQ counters too.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device-group/ncs:ned-id/ncs:rpc" {
    container rpc-clear-bgp-instance-vrf-afi-safi-update-outq-update-group-sub-group-update-parent {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-update-outq-update-group-sub-group-update-parent {
        tailf:actionpoint ncsproxy {
          tailf:internal;
        }
        csc:xr-task "bgp";
        csc:cli-command "clear bgp instance <instance-name> vrf <vrf-all> <afi-safi-name> update outq update-group <update-group> sub-group <sub-group> update-parent";
        description
          "Choose a particular BGP instance.
           Specify a VRF.
           Clear Update information (Do NOT execute without cisco support)(cisco-support).
           Clear Update generation OutQ counters (Do NOT execute without cisco support)(cisco-support).
           Update-group.
           Sub-group.
           Update parents' OutQ counters too.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device/ncs:rpc" {
    container rpc-clear-bgp-instance-vrf-afi-safi-update-outq-neighbor-ip-addr {
      tailf:ncs-device-type "netconf";
      tailf:display-when "not(../../ncs:module) or ../../ncs:module[ncs:name='Cisco-IOS-XR-ipv4-bgp-act']";
      tailf:action clear-bgp-instance-vrf-afi-safi-update-outq-neighbor-ip-addr {
        tailf:actionpoint ncsproxy {
          tailf:internal;
        }
        csc:xr-task "bgp";
        csc:cli-command "clear bgp instance <instance-name> vrf <vrf-all> <afi-safi-name> update outq neighbor <ip-addr>";
        description
          "Choose a particular BGP instance.
           Specify a VRF.
           Clear Update information (Do NOT execute without cisco support)(cisco-support).
           Clear Update generation OutQ counters (Do NOT execute without cisco support)(cisco-support).
           Neighbor.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device-group/ncs:ned-id/ncs:rpc" {
    container rpc-clear-bgp-instance-vrf-afi-safi-update-outq-neighbor-ip-addr {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-update-outq-neighbor-ip-addr {
        tailf:actionpoint ncsproxy {
          tailf:internal;
        }
        csc:xr-task "bgp";
        csc:cli-command "clear bgp instance <instance-name> vrf <vrf-all> <afi-safi-name> update outq neighbor <ip-addr>";
        description
          "Choose a particular BGP instance.
           Specify a VRF.
           Clear Update information (Do NOT execute without cisco support)(cisco-support).
           Clear Update generation OutQ counters (Do NOT execute without cisco support)(cisco-support).
           Neighbor.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device/ncs:rpc" {
    container rpc-clear-bgp-instance-vrf-afi-safi-update-outq-neighbor-ip-addr-update-parent {
      tailf:ncs-device-type "netconf";
      tailf:display-when "not(../../ncs:module) or ../../ncs:module[ncs:name='Cisco-IOS-XR-ipv4-bgp-act']";
      tailf:action clear-bgp-instance-vrf-afi-safi-update-outq-neighbor-ip-addr-update-parent {
        tailf:actionpoint ncsproxy {
          tailf:internal;
        }
        csc:xr-task "bgp";
        csc:cli-command "clear bgp instance <instance-name> vrf <vrf-all> <afi-safi-name> update outq neighbor <ip-addr> update-parent";
        description
          "Choose a particular BGP instance.
           Specify a VRF.
           Clear Update information (Do NOT execute without cisco support)(cisco-support).
           Clear Update generation OutQ counters (Do NOT execute without cisco support)(cisco-support).
           Neighbor.
           Update parents' OutQ counters too.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device-group/ncs:ned-id/ncs:rpc" {
    container rpc-clear-bgp-instance-vrf-afi-safi-update-outq-neighbor-ip-addr-update-parent {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-update-outq-neighbor-ip-addr-update-parent {
        tailf:actionpoint ncsproxy {
          tailf:internal;
        }
        csc:xr-task "bgp";
        csc:cli-command "clear bgp instance <instance-name> vrf <vrf-all> <afi-safi-name> update outq neighbor <ip-addr> update-parent";
        description
          "Choose a particular BGP instance.
           Specify a VRF.
           Clear Update information (Do NOT execute without cisco support)(cisco-support).
           Clear Update generation OutQ counters (Do NOT execute without cisco support)(cisco-support).
           Neighbor.
           Update parents' OutQ counters too.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device/ncs:rpc" {
    container rpc-clear-bgp-instance-vrf-afi-safi-update-outq-neighbor-ip-addr-refresh {
      tailf:ncs-device-type "netconf";
      tailf:display-when "not(../../ncs:module) or ../../ncs:module[ncs:name='Cisco-IOS-XR-ipv4-bgp-act']";
      tailf:action clear-bgp-instance-vrf-afi-safi-update-outq-neighbor-ip-addr-refresh {
        tailf:actionpoint ncsproxy {
          tailf:internal;
        }
        csc:xr-task "bgp";
        csc:cli-command "clear bgp instance <instance-name> vrf <vrf-all> <afi-safi-name> update outq neighbor <ip-addr> refresh";
        description
          "Choose a particular BGP instance.
           Specify a VRF.
           Clear Update information (Do NOT execute without cisco support)(cisco-support).
           Clear Update generation OutQ counters (Do NOT execute without cisco support)(cisco-support).
           Neighbor.
           Refresh OutQ.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device-group/ncs:ned-id/ncs:rpc" {
    container rpc-clear-bgp-instance-vrf-afi-safi-update-outq-neighbor-ip-addr-refresh {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-update-outq-neighbor-ip-addr-refresh {
        tailf:actionpoint ncsproxy {
          tailf:internal;
        }
        csc:xr-task "bgp";
        csc:cli-command "clear bgp instance <instance-name> vrf <vrf-all> <afi-safi-name> update outq neighbor <ip-addr> refresh";
        description
          "Choose a particular BGP instance.
           Specify a VRF.
           Clear Update information (Do NOT execute without cisco support)(cisco-support).
           Clear Update generation OutQ counters (Do NOT execute without cisco support)(cisco-support).
           Neighbor.
           Refresh OutQ.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device/ncs:rpc" {
    container rpc-clear-bgp-instance-vrf-afi-safi-update-outq-neighbor-ip-addr-refresh-update-parent {
      tailf:ncs-device-type "netconf";
      tailf:display-when "not(../../ncs:module) or ../../ncs:module[ncs:name='Cisco-IOS-XR-ipv4-bgp-act']";
      tailf:action clear-bgp-instance-vrf-afi-safi-update-outq-neighbor-ip-addr-refresh-update-parent {
        tailf:actionpoint ncsproxy {
          tailf:internal;
        }
        csc:xr-task "bgp";
        csc:cli-command "clear bgp instance <instance-name> vrf <vrf-all> <afi-safi-name> update outq neighbor <ip-addr> refresh update-parent";
        description
          "Choose a particular BGP instance.
           Specify a VRF.
           Clear Update information (Do NOT execute without cisco support)(cisco-support).
           Clear Update generation OutQ counters (Do NOT execute without cisco support)(cisco-support).
           Neighbor.
           Refresh OutQ.
           Update parents' OutQ counters too.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device-group/ncs:ned-id/ncs:rpc" {
    container rpc-clear-bgp-instance-vrf-afi-safi-update-outq-neighbor-ip-addr-refresh-update-parent {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-update-outq-neighbor-ip-addr-refresh-update-parent {
        tailf:actionpoint ncsproxy {
          tailf:internal;
        }
        csc:xr-task "bgp";
        csc:cli-command "clear bgp instance <instance-name> vrf <vrf-all> <afi-safi-name> update outq neighbor <ip-addr> refresh update-parent";
        description
          "Choose a particular BGP instance.
           Specify a VRF.
           Clear Update information (Do NOT execute without cisco support)(cisco-support).
           Clear Update generation OutQ counters (Do NOT execute without cisco support)(cisco-support).
           Neighbor.
           Refresh OutQ.
           Update parents' OutQ counters too.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device/ncs:rpc" {
    container rpc-clear-bgp-instance-vrf-afi-safi-update-outq-address-family {
      tailf:ncs-device-type "netconf";
      tailf:display-when "not(../../ncs:module) or ../../ncs:module[ncs:name='Cisco-IOS-XR-ipv4-bgp-act']";
      tailf:action clear-bgp-instance-vrf-afi-safi-update-outq-address-family {
        tailf:actionpoint ncsproxy {
          tailf:internal;
        }
        csc:xr-task "bgp";
        csc:cli-command "clear bgp instance <instance-name> vrf <vrf-all> <afi-safi-name> update outq address-family";
        description
          "Choose a particular BGP instance.
           Specify a VRF.
           Clear Update information (Do NOT execute without cisco support)(cisco-support).
           Clear Update generation OutQ counters (Do NOT execute without cisco support)(cisco-support).
           Address-family.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-vrf-afi-safi-update-outq-address-family {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-update-outq-address-family {
        tailf:actionpoint ncsproxy {
          tailf:internal;
        }
        csc:xr-task "bgp";
        csc:cli-command "clear bgp instance <instance-name> vrf <vrf-all> <afi-safi-name> update outq address-family";
        description
          "Choose a particular BGP instance.
           Specify a VRF.
           Clear Update information (Do NOT execute without cisco support)(cisco-support).
           Clear Update generation OutQ counters (Do NOT execute without cisco support)(cisco-support).
           Address-family.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-instance-vrf-afi-safi-update-outq-address-family-update-parent {
      tailf:ncs-device-type "netconf";
      tailf:display-when "not(../../ncs:module) or ../../ncs:module[ncs:name='Cisco-IOS-XR-ipv4-bgp-act']";
      tailf:action clear-bgp-instance-vrf-afi-safi-update-outq-address-family-update-parent {
        tailf:actionpoint ncsproxy {
          tailf:internal;
        }
        csc:xr-task "bgp";
        csc:cli-command "clear bgp instance <instance-name> vrf <vrf-all> <afi-safi-name> update outq address-family update-parent";
        description
          "Choose a particular BGP instance.
           Specify a VRF.
           Clear Update information (Do NOT execute without cisco support)(cisco-support).
           Clear Update generation OutQ counters (Do NOT execute without cisco support)(cisco-support).
           Address-family.
           Update parents' OutQ counters too.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-vrf-afi-safi-update-outq-address-family-update-parent {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-update-outq-address-family-update-parent {
        tailf:actionpoint ncsproxy {
          tailf:internal;
        }
        csc:xr-task "bgp";
        csc:cli-command "clear bgp instance <instance-name> vrf <vrf-all> <afi-safi-name> update outq address-family update-parent";
        description
          "Choose a particular BGP instance.
           Specify a VRF.
           Clear Update information (Do NOT execute without cisco support)(cisco-support).
           Clear Update generation OutQ counters (Do NOT execute without cisco support)(cisco-support).
           Address-family.
           Update parents' OutQ counters too.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-instance-vrf-afi-safi-shutdown {
      tailf:ncs-device-type "netconf";
      tailf:display-when "not(../../ncs:module) or ../../ncs:module[ncs:name='Cisco-IOS-XR-ipv4-bgp-act']";
      tailf:action clear-bgp-instance-vrf-afi-safi-shutdown {
        tailf:actionpoint ncsproxy {
          tailf:internal;
        }
        csc:xr-task "bgp";
        csc:cli-command "clear bgp instance <instance-name> vrf <vrf-all> <afi-safi-name> shutdown";
        description
          "Choose a particular BGP instance.
           Specify a VRF.
           Clear all peers which were shut down due to low memory.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-vrf-afi-safi-shutdown {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-shutdown {
        tailf:actionpoint ncsproxy {
          tailf:internal;
        }
        csc:xr-task "bgp";
        csc:cli-command "clear bgp instance <instance-name> vrf <vrf-all> <afi-safi-name> shutdown";
        description
          "Choose a particular BGP instance.
           Specify a VRF.
           Clear all peers which were shut down due to low memory.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-instance-vrf-afi-safi-self-originated {
      tailf:ncs-device-type "netconf";
      tailf:display-when "not(../../ncs:module) or ../../ncs:module[ncs:name='Cisco-IOS-XR-ipv4-bgp-act']";
      tailf:action clear-bgp-instance-vrf-afi-safi-self-originated {
        tailf:actionpoint ncsproxy {
          tailf:internal;
        }
        csc:xr-task "bgp";
        csc:cli-command "clear bgp instance <instance-name> vrf <vrf-all> <afi-safi-name> self-originated";
        description
          "Choose a particular BGP instance.
           Specify a VRF.
           Clear redistributed, network and aggregate routes originated here.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-vrf-afi-safi-self-originated {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-self-originated {
        tailf:actionpoint ncsproxy {
          tailf:internal;
        }
        csc:xr-task "bgp";
        csc:cli-command "clear bgp instance <instance-name> vrf <vrf-all> <afi-safi-name> self-originated";
        description
          "Choose a particular BGP instance.
           Specify a VRF.
           Clear redistributed, network and aggregate routes originated here.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-instance-vrf-afi-safi-nexthop-registration-ip-addr {
      tailf:ncs-device-type "netconf";
      tailf:display-when "not(../../ncs:module) or ../../ncs:module[ncs:name='Cisco-IOS-XR-ipv4-bgp-act']";
      tailf:action clear-bgp-instance-vrf-afi-safi-nexthop-registration-ip-addr {
        tailf:actionpoint ncsproxy {
          tailf:internal;
        }
        csc:xr-task "bgp";
        csc:cli-command "clear bgp instance <instance-name> vrf <vrf-all> <afi-safi-name> nexthop registration <ip-addr>";
        description
          "Choose a particular BGP instance.
           Specify a VRF.
           Clear nexthop.
           Registration with RIB and reregister.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "Nexthop address";
          }
        }
      }
    }
  }
  augment "/ncs:devices/ncs:device-group/ncs:ned-id/ncs:rpc" {
    container rpc-clear-bgp-instance-vrf-afi-safi-nexthop-registration-ip-addr {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-nexthop-registration-ip-addr {
        tailf:actionpoint ncsproxy {
          tailf:internal;
        }
        csc:xr-task "bgp";
        csc:cli-command "clear bgp instance <instance-name> vrf <vrf-all> <afi-safi-name> nexthop registration <ip-addr>";
        description
          "Choose a particular BGP instance.
           Specify a VRF.
           Clear nexthop.
           Registration with RIB and reregister.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "Nexthop address";
          }
        }
      }
    }
  }
  augment "/ncs:devices/ncs:device/ncs:rpc" {
    container rpc-clear-bgp-instance-vrf-afi-safi-nexthop-performance-statistics {
      tailf:ncs-device-type "netconf";
      tailf:display-when "not(../../ncs:module) or ../../ncs:module[ncs:name='Cisco-IOS-XR-ipv4-bgp-act']";
      tailf:action clear-bgp-instance-vrf-afi-safi-nexthop-performance-statistics {
        tailf:actionpoint ncsproxy {
          tailf:internal;
        }
        csc:xr-task "bgp";
        csc:cli-command "clear bgp instance <instance-name> vrf <vrf-all> <afi-safi-name> nexthop performance-statistics";
        description
          "Choose a particular BGP instance.
           Specify a VRF.
           Clear nexthop.
           Performance statistics information related to processing.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-vrf-afi-safi-nexthop-performance-statistics {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-nexthop-performance-statistics {
        tailf:actionpoint ncsproxy {
          tailf:internal;
        }
        csc:xr-task "bgp";
        csc:cli-command "clear bgp instance <instance-name> vrf <vrf-all> <afi-safi-name> nexthop performance-statistics";
        description
          "Choose a particular BGP instance.
           Specify a VRF.
           Clear nexthop.
           Performance statistics information related to processing.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-instance-vrf-afi-safi-flap-statistics {
      tailf:ncs-device-type "netconf";
      tailf:display-when "not(../../ncs:module) or ../../ncs:module[ncs:name='Cisco-IOS-XR-ipv4-bgp-act']";
      tailf:action clear-bgp-instance-vrf-afi-safi-flap-statistics {
        tailf:actionpoint ncsproxy {
          tailf:internal;
        }
        csc:xr-task "bgp";
        csc:cli-command "clear bgp instance <instance-name> vrf <vrf-all> <afi-safi-name> flap-statistics";
        description
          "Choose a particular BGP instance.
           Specify a VRF.
           Clear flap statistics.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-vrf-afi-safi-flap-statistics {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-flap-statistics {
        tailf:actionpoint ncsproxy {
          tailf:internal;
        }
        csc:xr-task "bgp";
        csc:cli-command "clear bgp instance <instance-name> vrf <vrf-all> <afi-safi-name> flap-statistics";
        description
          "Choose a particular BGP instance.
           Specify a VRF.
           Clear flap statistics.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-instance-vrf-afi-safi-flap-statistics-route-policy {
      tailf:ncs-device-type "netconf";
      tailf:display-when "not(../../ncs:module) or ../../ncs:module[ncs:name='Cisco-IOS-XR-ipv4-bgp-act']";
      tailf:action clear-bgp-instance-vrf-afi-safi-flap-statistics-route-policy {
        tailf:actionpoint ncsproxy {
          tailf:internal;
        }
        csc:xr-task "bgp";
        csc:cli-command "clear bgp instance <instance-name> vrf <vrf-all> <afi-safi-name> flap-statistics route-policy <route-policy-name>";
        description
          "Choose a particular BGP instance.
           Specify a VRF.
           Clear flap statistics.
           Clear flap statistics for routes matching the route policy.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf route-policy-name {
            mandatory true;
            type string;
            description
              "Route Policy name";
          }
        }
      }
    }
  }
  augment "/ncs:devices/ncs:device-group/ncs:ned-id/ncs:rpc" {
    container rpc-clear-bgp-instance-vrf-afi-safi-flap-statistics-route-policy {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-flap-statistics-route-policy {
        tailf:actionpoint ncsproxy {
          tailf:internal;
        }
        csc:xr-task "bgp";
        csc:cli-command "clear bgp instance <instance-name> vrf <vrf-all> <afi-safi-name> flap-statistics route-policy <route-policy-name>";
        description
          "Choose a particular BGP instance.
           Specify a VRF.
           Clear flap statistics.
           Clear flap statistics for routes matching the route policy.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf route-policy-name {
            mandatory true;
            type string;
            description
              "Route Policy name";
          }
        }
      }
    }
  }
  augment "/ncs:devices/ncs:device/ncs:rpc" {
    container rpc-clear-bgp-instance-vrf-afi-safi-flap-statistics-regexp {
      tailf:ncs-device-type "netconf";
      tailf:display-when "not(../../ncs:module) or ../../ncs:module[ncs:name='Cisco-IOS-XR-ipv4-bgp-act']";
      tailf:action clear-bgp-instance-vrf-afi-safi-flap-statistics-regexp {
        tailf:actionpoint ncsproxy {
          tailf:internal;
        }
        csc:xr-task "bgp";
        csc:cli-command "clear bgp instance <instance-name> vrf <vrf-all> <afi-safi-name> flap-statistics regexp <regexp-pattern>";
        description
          "Choose a particular BGP instance.
           Specify a VRF.
           Clear flap statistics.
           Clear flap statistics for routes matching the regular expression.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf regexp-pattern {
            mandatory true;
            type string;
            description
              "A regular expression to match the BGP AS paths.  Use 'ctrl-v ?' to enter '?'";
          }
        }
      }
    }
  }
  augment "/ncs:devices/ncs:device-group/ncs:ned-id/ncs:rpc" {
    container rpc-clear-bgp-instance-vrf-afi-safi-flap-statistics-regexp {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-flap-statistics-regexp {
        tailf:actionpoint ncsproxy {
          tailf:internal;
        }
        csc:xr-task "bgp";
        csc:cli-command "clear bgp instance <instance-name> vrf <vrf-all> <afi-safi-name> flap-statistics regexp <regexp-pattern>";
        description
          "Choose a particular BGP instance.
           Specify a VRF.
           Clear flap statistics.
           Clear flap statistics for routes matching the regular expression.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf regexp-pattern {
            mandatory true;
            type string;
            description
              "A regular expression to match the BGP AS paths.  Use 'ctrl-v ?' to enter '?'";
          }
        }
      }
    }
  }
  augment "/ncs:devices/ncs:device/ncs:rpc" {
    container rpc-clear-bgp-instance-vrf-afi-safi-flap-statistics-ipv4-prefix {
      tailf:ncs-device-type "netconf";
      tailf:display-when "not(../../ncs:module) or ../../ncs:module[ncs:name='Cisco-IOS-XR-ipv4-bgp-act']";
      tailf:action clear-bgp-instance-vrf-afi-safi-flap-statistics-ipv4-prefix {
        tailf:actionpoint ncsproxy {
          tailf:internal;
        }
        csc:xr-task "bgp";
        csc:cli-command "clear bgp instance <instance-name> vrf <vrf-all> <afi-safi-name> flap-statistics <ipv4-prefix>";
        description
          "Choose a particular BGP instance.
           Specify a VRF.
           Clear flap statistics.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv4-prefix {
            mandatory true;
            type inet:ipv4-prefix;
            description
              "IPv4 Network and mask or masklength to clear flap statistics";
          }
        }
      }
    }
  }
  augment "/ncs:devices/ncs:device-group/ncs:ned-id/ncs:rpc" {
    container rpc-clear-bgp-instance-vrf-afi-safi-flap-statistics-ipv4-prefix {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-flap-statistics-ipv4-prefix {
        tailf:actionpoint ncsproxy {
          tailf:internal;
        }
        csc:xr-task "bgp";
        csc:cli-command "clear bgp instance <instance-name> vrf <vrf-all> <afi-safi-name> flap-statistics <ipv4-prefix>";
        description
          "Choose a particular BGP instance.
           Specify a VRF.
           Clear flap statistics.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv4-prefix {
            mandatory true;
            type inet:ipv4-prefix;
            description
              "IPv4 Network and mask or masklength to clear flap statistics";
          }
        }
      }
    }
  }
  augment "/ncs:devices/ncs:device/ncs:rpc" {
    container rpc-clear-bgp-instance-vrf-afi-safi-flap-statistics-ip-addr {
      tailf:ncs-device-type "netconf";
      tailf:display-when "not(../../ncs:module) or ../../ncs:module[ncs:name='Cisco-IOS-XR-ipv4-bgp-act']";
      tailf:action clear-bgp-instance-vrf-afi-safi-flap-statistics-ip-addr {
        tailf:actionpoint ncsproxy {
          tailf:internal;
        }
        csc:xr-task "bgp";
        csc:cli-command "clear bgp instance <instance-name> vrf <vrf-all> <afi-safi-name> flap-statistics <ip-addr>";
        description
          "Choose a particular BGP instance.
           Specify a VRF.
           Clear flap statistics.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device-group/ncs:ned-id/ncs:rpc" {
    container rpc-clear-bgp-instance-vrf-afi-safi-flap-statistics-ip-addr {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-flap-statistics-ip-addr {
        tailf:actionpoint ncsproxy {
          tailf:internal;
        }
        csc:xr-task "bgp";
        csc:cli-command "clear bgp instance <instance-name> vrf <vrf-all> <afi-safi-name> flap-statistics <ip-addr>";
        description
          "Choose a particular BGP instance.
           Specify a VRF.
           Clear flap statistics.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device/ncs:rpc" {
    container rpc-clear-bgp-instance-vrf-afi-safi-flap-statistics-ip-addr-ipv4-mask {
      tailf:ncs-device-type "netconf";
      tailf:display-when "not(../../ncs:module) or ../../ncs:module[ncs:name='Cisco-IOS-XR-ipv4-bgp-act']";
      tailf:action clear-bgp-instance-vrf-afi-safi-flap-statistics-ip-addr-ipv4-mask {
        tailf:actionpoint ncsproxy {
          tailf:internal;
        }
        csc:xr-task "bgp";
        csc:cli-command "clear bgp instance <instance-name> vrf <vrf-all> <afi-safi-name> flap-statistics <ip-addr> <ipv4-mask>";
        description
          "Choose a particular BGP instance.
           Specify a VRF.
           Clear flap statistics.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "BGP neighbor address to clear";
          }
          leaf ipv4-mask {
            mandatory true;
            type ipv4-netmask;
            description
              "IPv4 Network and mask or masklength to clear flap statistics";
          }
        }
      }
    }
  }
  augment "/ncs:devices/ncs:device-group/ncs:ned-id/ncs:rpc" {
    container rpc-clear-bgp-instance-vrf-afi-safi-flap-statistics-ip-addr-ipv4-mask {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-flap-statistics-ip-addr-ipv4-mask {
        tailf:actionpoint ncsproxy {
          tailf:internal;
        }
        csc:xr-task "bgp";
        csc:cli-command "clear bgp instance <instance-name> vrf <vrf-all> <afi-safi-name> flap-statistics <ip-addr> <ipv4-mask>";
        description
          "Choose a particular BGP instance.
           Specify a VRF.
           Clear flap statistics.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "BGP neighbor address to clear";
          }
          leaf ipv4-mask {
            mandatory true;
            type ipv4-netmask;
            description
              "IPv4 Network and mask or masklength to clear flap statistics";
          }
        }
      }
    }
  }
  augment "/ncs:devices/ncs:device/ncs:rpc" {
    container rpc-clear-bgp-instance-vrf-afi-safi-external-soft {
      tailf:ncs-device-type "netconf";
      tailf:display-when "not(../../ncs:module) or ../../ncs:module[ncs:name='Cisco-IOS-XR-ipv4-bgp-act']";
      tailf:action clear-bgp-instance-vrf-afi-safi-external-soft {
        tailf:actionpoint ncsproxy {
          tailf:internal;
        }
        csc:xr-task "bgp";
        csc:cli-command "clear bgp instance <instance-name> vrf <vrf-all> <afi-safi-name> external soft";
        description
          "Choose a particular BGP instance.
           Specify a VRF.
           Clear all external peers.
           Soft reconfig.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-vrf-afi-safi-external-soft {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-external-soft {
        tailf:actionpoint ncsproxy {
          tailf:internal;
        }
        csc:xr-task "bgp";
        csc:cli-command "clear bgp instance <instance-name> vrf <vrf-all> <afi-safi-name> external soft";
        description
          "Choose a particular BGP instance.
           Specify a VRF.
           Clear all external peers.
           Soft reconfig.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-instance-vrf-afi-safi-external-soft-out {
      tailf:ncs-device-type "netconf";
      tailf:display-when "not(../../ncs:module) or ../../ncs:module[ncs:name='Cisco-IOS-XR-ipv4-bgp-act']";
      tailf:action clear-bgp-instance-vrf-afi-safi-external-soft-out {
        tailf:actionpoint ncsproxy {
          tailf:internal;
        }
        csc:xr-task "bgp";
        csc:cli-command "clear bgp instance <instance-name> vrf <vrf-all> <afi-safi-name> external soft out";
        description
          "Choose a particular BGP instance.
           Specify a VRF.
           Clear all external peers.
           Soft reconfig.
           Soft reconfig outbound update.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-vrf-afi-safi-external-soft-out {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-external-soft-out {
        tailf:actionpoint ncsproxy {
          tailf:internal;
        }
        csc:xr-task "bgp";
        csc:cli-command "clear bgp instance <instance-name> vrf <vrf-all> <afi-safi-name> external soft out";
        description
          "Choose a particular BGP instance.
           Specify a VRF.
           Clear all external peers.
           Soft reconfig.
           Soft reconfig outbound update.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-instance-vrf-afi-safi-external-soft-in {
      tailf:ncs-device-type "netconf";
      tailf:display-when "not(../../ncs:module) or ../../ncs:module[ncs:name='Cisco-IOS-XR-ipv4-bgp-act']";
      tailf:action clear-bgp-instance-vrf-afi-safi-external-soft-in {
        tailf:actionpoint ncsproxy {
          tailf:internal;
        }
        csc:xr-task "bgp";
        csc:cli-command "clear bgp instance <instance-name> vrf <vrf-all> <afi-safi-name> external soft in";
        description
          "Choose a particular BGP instance.
           Specify a VRF.
           Clear all external peers.
           Soft reconfig.
           Soft reconfig inbound update.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-vrf-afi-safi-external-soft-in {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-external-soft-in {
        tailf:actionpoint ncsproxy {
          tailf:internal;
        }
        csc:xr-task "bgp";
        csc:cli-command "clear bgp instance <instance-name> vrf <vrf-all> <afi-safi-name> external soft in";
        description
          "Choose a particular BGP instance.
           Specify a VRF.
           Clear all external peers.
           Soft reconfig.
           Soft reconfig inbound update.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-instance-vrf-afi-safi-external-soft-in-prefix-filter {
      tailf:ncs-device-type "netconf";
      tailf:display-when "not(../../ncs:module) or ../../ncs:module[ncs:name='Cisco-IOS-XR-ipv4-bgp-act']";
      tailf:action clear-bgp-instance-vrf-afi-safi-external-soft-in-prefix-filter {
        tailf:actionpoint ncsproxy {
          tailf:internal;
        }
        csc:xr-task "bgp";
        csc:cli-command "clear bgp instance <instance-name> vrf <vrf-all> <afi-safi-name> external soft in prefix-filter";
        description
          "Choose a particular BGP instance.
           Specify a VRF.
           Clear all external peers.
           Soft reconfig.
           Soft reconfig inbound update.
           Push out prefix ORF and do inbound soft reconfig.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-vrf-afi-safi-external-soft-in-prefix-filter {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-external-soft-in-prefix-filter {
        tailf:actionpoint ncsproxy {
          tailf:internal;
        }
        csc:xr-task "bgp";
        csc:cli-command "clear bgp instance <instance-name> vrf <vrf-all> <afi-safi-name> external soft in prefix-filter";
        description
          "Choose a particular BGP instance.
           Specify a VRF.
           Clear all external peers.
           Soft reconfig.
           Soft reconfig inbound update.
           Push out prefix ORF and do inbound soft reconfig.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-instance-vrf-afi-safi-dampening {
      tailf:ncs-device-type "netconf";
      tailf:display-when "not(../../ncs:module) or ../../ncs:module[ncs:name='Cisco-IOS-XR-ipv4-bgp-act']";
      tailf:action clear-bgp-instance-vrf-afi-safi-dampening {
        tailf:actionpoint ncsproxy {
          tailf:internal;
        }
        csc:xr-task "bgp";
        csc:cli-command "clear bgp instance <instance-name> vrf <vrf-all> <afi-safi-name> dampening";
        description
          "Choose a particular BGP instance.
           Specify a VRF.
           Clear route flap dampening information.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-vrf-afi-safi-dampening {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-dampening {
        tailf:actionpoint ncsproxy {
          tailf:internal;
        }
        csc:xr-task "bgp";
        csc:cli-command "clear bgp instance <instance-name> vrf <vrf-all> <afi-safi-name> dampening";
        description
          "Choose a particular BGP instance.
           Specify a VRF.
           Clear route flap dampening information.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-instance-vrf-afi-safi-dampening-ipv4-prefix {
      tailf:ncs-device-type "netconf";
      tailf:display-when "not(../../ncs:module) or ../../ncs:module[ncs:name='Cisco-IOS-XR-ipv4-bgp-act']";
      tailf:action clear-bgp-instance-vrf-afi-safi-dampening-ipv4-prefix {
        tailf:actionpoint ncsproxy {
          tailf:internal;
        }
        csc:xr-task "bgp";
        csc:cli-command "clear bgp instance <instance-name> vrf <vrf-all> <afi-safi-name> dampening <ipv4-prefix>";
        description
          "Choose a particular BGP instance.
           Specify a VRF.
           Clear route flap dampening information.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv4-prefix {
            mandatory true;
            type inet:ipv4-prefix;
            description
              "IPv4 Network and mask or masklength to clear dampening information";
          }
        }
      }
    }
  }
  augment "/ncs:devices/ncs:device-group/ncs:ned-id/ncs:rpc" {
    container rpc-clear-bgp-instance-vrf-afi-safi-dampening-ipv4-prefix {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-dampening-ipv4-prefix {
        tailf:actionpoint ncsproxy {
          tailf:internal;
        }
        csc:xr-task "bgp";
        csc:cli-command "clear bgp instance <instance-name> vrf <vrf-all> <afi-safi-name> dampening <ipv4-prefix>";
        description
          "Choose a particular BGP instance.
           Specify a VRF.
           Clear route flap dampening information.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv4-prefix {
            mandatory true;
            type inet:ipv4-prefix;
            description
              "IPv4 Network and mask or masklength to clear dampening information";
          }
        }
      }
    }
  }
  augment "/ncs:devices/ncs:device/ncs:rpc" {
    container rpc-clear-bgp-instance-vrf-afi-safi-as-soft {
      tailf:ncs-device-type "netconf";
      tailf:display-when "not(../../ncs:module) or ../../ncs:module[ncs:name='Cisco-IOS-XR-ipv4-bgp-act']";
      tailf:action clear-bgp-instance-vrf-afi-safi-as-soft {
        tailf:actionpoint ncsproxy {
          tailf:internal;
        }
        csc:xr-task "bgp";
        csc:cli-command "clear bgp instance <instance-name> vrf <vrf-all> <afi-safi-name> as <as-number> soft";
        description
          "Choose a particular BGP instance.
           Specify a VRF.
           Clear peers in a specific AS.
           Soft reconfig.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf as-number {
            mandatory true;
            type as-number;
            description
              "AS number";
          }
        }
      }
    }
  }
  augment "/ncs:devices/ncs:device-group/ncs:ned-id/ncs:rpc" {
    container rpc-clear-bgp-instance-vrf-afi-safi-as-soft {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-as-soft {
        tailf:actionpoint ncsproxy {
          tailf:internal;
        }
        csc:xr-task "bgp";
        csc:cli-command "clear bgp instance <instance-name> vrf <vrf-all> <afi-safi-name> as <as-number> soft";
        description
          "Choose a particular BGP instance.
           Specify a VRF.
           Clear peers in a specific AS.
           Soft reconfig.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf as-number {
            mandatory true;
            type as-number;
            description
              "AS number";
          }
        }
      }
    }
  }
  augment "/ncs:devices/ncs:device/ncs:rpc" {
    container rpc-clear-bgp-instance-vrf-afi-safi-as-soft-out {
      tailf:ncs-device-type "netconf";
      tailf:display-when "not(../../ncs:module) or ../../ncs:module[ncs:name='Cisco-IOS-XR-ipv4-bgp-act']";
      tailf:action clear-bgp-instance-vrf-afi-safi-as-soft-out {
        tailf:actionpoint ncsproxy {
          tailf:internal;
        }
        csc:xr-task "bgp";
        csc:cli-command "clear bgp instance <instance-name> vrf <vrf-all> <afi-safi-name> as <as-number> soft out";
        description
          "Choose a particular BGP instance.
           Specify a VRF.
           Clear peers in a specific AS.
           Soft reconfig.
           Soft reconfig outbound update.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf as-number {
            mandatory true;
            type as-number;
            description
              "AS number";
          }
        }
      }
    }
  }
  augment "/ncs:devices/ncs:device-group/ncs:ned-id/ncs:rpc" {
    container rpc-clear-bgp-instance-vrf-afi-safi-as-soft-out {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-as-soft-out {
        tailf:actionpoint ncsproxy {
          tailf:internal;
        }
        csc:xr-task "bgp";
        csc:cli-command "clear bgp instance <instance-name> vrf <vrf-all> <afi-safi-name> as <as-number> soft out";
        description
          "Choose a particular BGP instance.
           Specify a VRF.
           Clear peers in a specific AS.
           Soft reconfig.
           Soft reconfig outbound update.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf as-number {
            mandatory true;
            type as-number;
            description
              "AS number";
          }
        }
      }
    }
  }
  augment "/ncs:devices/ncs:device/ncs:rpc" {
    container rpc-clear-bgp-instance-vrf-afi-safi-as-soft-in {
      tailf:ncs-device-type "netconf";
      tailf:display-when "not(../../ncs:module) or ../../ncs:module[ncs:name='Cisco-IOS-XR-ipv4-bgp-act']";
      tailf:action clear-bgp-instance-vrf-afi-safi-as-soft-in {
        tailf:actionpoint ncsproxy {
          tailf:internal;
        }
        csc:xr-task "bgp";
        csc:cli-command "clear bgp instance <instance-name> vrf <vrf-all> <afi-safi-name> as <as-number> soft in";
        description
          "Choose a particular BGP instance.
           Specify a VRF.
           Clear peers in a specific AS.
           Soft reconfig.
           Soft reconfig inbound update.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf as-number {
            mandatory true;
            type as-number;
            description
              "AS number";
          }
        }
      }
    }
  }
  augment "/ncs:devices/ncs:device-group/ncs:ned-id/ncs:rpc" {
    container rpc-clear-bgp-instance-vrf-afi-safi-as-soft-in {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-as-soft-in {
        tailf:actionpoint ncsproxy {
          tailf:internal;
        }
        csc:xr-task "bgp";
        csc:cli-command "clear bgp instance <instance-name> vrf <vrf-all> <afi-safi-name> as <as-number> soft in";
        description
          "Choose a particular BGP instance.
           Specify a VRF.
           Clear peers in a specific AS.
           Soft reconfig.
           Soft reconfig inbound update.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf as-number {
            mandatory true;
            type as-number;
            description
              "AS number";
          }
        }
      }
    }
  }
  augment "/ncs:devices/ncs:device/ncs:rpc" {
    container rpc-clear-bgp-instance-vrf-afi-safi-as-soft-in-prefix-filter {
      tailf:ncs-device-type "netconf";
      tailf:display-when "not(../../ncs:module) or ../../ncs:module[ncs:name='Cisco-IOS-XR-ipv4-bgp-act']";
      tailf:action clear-bgp-instance-vrf-afi-safi-as-soft-in-prefix-filter {
        tailf:actionpoint ncsproxy {
          tailf:internal;
        }
        csc:xr-task "bgp";
        csc:cli-command "clear bgp instance <instance-name> vrf <vrf-all> <afi-safi-name> as <as-number> soft in prefix-filter";
        description
          "Choose a particular BGP instance.
           Specify a VRF.
           Clear peers in a specific AS.
           Soft reconfig.
           Soft reconfig inbound update.
           Push out prefix ORF and do inbound soft reconfig.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf as-number {
            mandatory true;
            type as-number;
            description
              "AS number";
          }
        }
      }
    }
  }
  augment "/ncs:devices/ncs:device-group/ncs:ned-id/ncs:rpc" {
    container rpc-clear-bgp-instance-vrf-afi-safi-as-soft-in-prefix-filter {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-as-soft-in-prefix-filter {
        tailf:actionpoint ncsproxy {
          tailf:internal;
        }
        csc:xr-task "bgp";
        csc:cli-command "clear bgp instance <instance-name> vrf <vrf-all> <afi-safi-name> as <as-number> soft in prefix-filter";
        description
          "Choose a particular BGP instance.
           Specify a VRF.
           Clear peers in a specific AS.
           Soft reconfig.
           Soft reconfig inbound update.
           Push out prefix ORF and do inbound soft reconfig.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf as-number {
            mandatory true;
            type as-number;
            description
              "AS number";
          }
        }
      }
    }
  }
  augment "/ncs:devices/ncs:device/ncs:rpc" {
    container rpc-clear-bgp-instance-vrf-afi-safi-ip-addr-soft {
      tailf:ncs-device-type "netconf";
      tailf:display-when "not(../../ncs:module) or ../../ncs:module[ncs:name='Cisco-IOS-XR-ipv4-bgp-act']";
      tailf:action clear-bgp-instance-vrf-afi-safi-ip-addr-soft {
        tailf:actionpoint ncsproxy {
          tailf:internal;
        }
        csc:xr-task "bgp";
        csc:cli-command "clear bgp instance <instance-name> vrf <vrf-all> <afi-safi-name> <ip-addr> soft";
        description
          "Choose a particular BGP instance.
           Specify a VRF.
           Soft reconfig.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device-group/ncs:ned-id/ncs:rpc" {
    container rpc-clear-bgp-instance-vrf-afi-safi-ip-addr-soft {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-ip-addr-soft {
        tailf:actionpoint ncsproxy {
          tailf:internal;
        }
        csc:xr-task "bgp";
        csc:cli-command "clear bgp instance <instance-name> vrf <vrf-all> <afi-safi-name> <ip-addr> soft";
        description
          "Choose a particular BGP instance.
           Specify a VRF.
           Soft reconfig.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device/ncs:rpc" {
    container rpc-clear-bgp-instance-vrf-afi-safi-ip-addr-soft-out {
      tailf:ncs-device-type "netconf";
      tailf:display-when "not(../../ncs:module) or ../../ncs:module[ncs:name='Cisco-IOS-XR-ipv4-bgp-act']";
      tailf:action clear-bgp-instance-vrf-afi-safi-ip-addr-soft-out {
        tailf:actionpoint ncsproxy {
          tailf:internal;
        }
        csc:xr-task "bgp";
        csc:cli-command "clear bgp instance <instance-name> vrf <vrf-all> <afi-safi-name> <ip-addr> soft out";
        description
          "Choose a particular BGP instance.
           Specify a VRF.
           Soft reconfig.
           Soft reconfig outbound update.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device-group/ncs:ned-id/ncs:rpc" {
    container rpc-clear-bgp-instance-vrf-afi-safi-ip-addr-soft-out {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-ip-addr-soft-out {
        tailf:actionpoint ncsproxy {
          tailf:internal;
        }
        csc:xr-task "bgp";
        csc:cli-command "clear bgp instance <instance-name> vrf <vrf-all> <afi-safi-name> <ip-addr> soft out";
        description
          "Choose a particular BGP instance.
           Specify a VRF.
           Soft reconfig.
           Soft reconfig outbound update.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device/ncs:rpc" {
    container rpc-clear-bgp-instance-vrf-afi-safi-ip-addr-soft-in {
      tailf:ncs-device-type "netconf";
      tailf:display-when "not(../../ncs:module) or ../../ncs:module[ncs:name='Cisco-IOS-XR-ipv4-bgp-act']";
      tailf:action clear-bgp-instance-vrf-afi-safi-ip-addr-soft-in {
        tailf:actionpoint ncsproxy {
          tailf:internal;
        }
        csc:xr-task "bgp";
        csc:cli-command "clear bgp instance <instance-name> vrf <vrf-all> <afi-safi-name> <ip-addr> soft in";
        description
          "Choose a particular BGP instance.
           Specify a VRF.
           Soft reconfig.
           Soft reconfig inbound update.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device-group/ncs:ned-id/ncs:rpc" {
    container rpc-clear-bgp-instance-vrf-afi-safi-ip-addr-soft-in {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-ip-addr-soft-in {
        tailf:actionpoint ncsproxy {
          tailf:internal;
        }
        csc:xr-task "bgp";
        csc:cli-command "clear bgp instance <instance-name> vrf <vrf-all> <afi-safi-name> <ip-addr> soft in";
        description
          "Choose a particular BGP instance.
           Specify a VRF.
           Soft reconfig.
           Soft reconfig inbound update.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device/ncs:rpc" {
    container rpc-clear-bgp-instance-vrf-afi-safi-ip-addr-soft-in-prefix-filter {
      tailf:ncs-device-type "netconf";
      tailf:display-when "not(../../ncs:module) or ../../ncs:module[ncs:name='Cisco-IOS-XR-ipv4-bgp-act']";
      tailf:action clear-bgp-instance-vrf-afi-safi-ip-addr-soft-in-prefix-filter {
        tailf:actionpoint ncsproxy {
          tailf:internal;
        }
        csc:xr-task "bgp";
        csc:cli-command "clear bgp instance <instance-name> vrf <vrf-all> <afi-safi-name> <ip-addr> soft in prefix-filter";
        description
          "Choose a particular BGP instance.
           Specify a VRF.
           Soft reconfig.
           Soft reconfig inbound update.
           Push out prefix ORF and do inbound soft reconfig.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device-group/ncs:ned-id/ncs:rpc" {
    container rpc-clear-bgp-instance-vrf-afi-safi-ip-addr-soft-in-prefix-filter {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-ip-addr-soft-in-prefix-filter {
        tailf:actionpoint ncsproxy {
          tailf:internal;
        }
        csc:xr-task "bgp";
        csc:cli-command "clear bgp instance <instance-name> vrf <vrf-all> <afi-safi-name> <ip-addr> soft in prefix-filter";
        description
          "Choose a particular BGP instance.
           Specify a VRF.
           Soft reconfig.
           Soft reconfig inbound update.
           Push out prefix ORF and do inbound soft reconfig.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device/ncs:rpc" {
    container rpc-clear-bgp-instance-vrf-afi-safi-ip-addr-long-lived-stale {
      tailf:ncs-device-type "netconf";
      tailf:display-when "not(../../ncs:module) or ../../ncs:module[ncs:name='Cisco-IOS-XR-ipv4-bgp-act']";
      tailf:action clear-bgp-instance-vrf-afi-safi-ip-addr-long-lived-stale {
        tailf:actionpoint ncsproxy {
          tailf:internal;
        }
        csc:xr-task "bgp";
        csc:cli-command "clear bgp instance <instance-name> vrf <vrf-all> <afi-safi-name> <ip-addr> long-lived-stale";
        description
          "Choose a particular BGP instance.
           Specify a VRF.
           Clear long-lived-stale routes.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device-group/ncs:ned-id/ncs:rpc" {
    container rpc-clear-bgp-instance-vrf-afi-safi-ip-addr-long-lived-stale {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-ip-addr-long-lived-stale {
        tailf:actionpoint ncsproxy {
          tailf:internal;
        }
        csc:xr-task "bgp";
        csc:cli-command "clear bgp instance <instance-name> vrf <vrf-all> <afi-safi-name> <ip-addr> long-lived-stale";
        description
          "Choose a particular BGP instance.
           Specify a VRF.
           Clear long-lived-stale routes.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device/ncs:rpc" {
    container rpc-clear-bgp-instance-vrf-afi-safi-all-soft {
      tailf:ncs-device-type "netconf";
      tailf:display-when "not(../../ncs:module) or ../../ncs:module[ncs:name='Cisco-IOS-XR-ipv4-bgp-act']";
      tailf:action clear-bgp-instance-vrf-afi-safi-all-soft {
        tailf:actionpoint ncsproxy {
          tailf:internal;
        }
        csc:xr-task "bgp";
        csc:cli-command "clear bgp instance <instance-name> vrf <vrf-all> <afi-safi-name> * soft";
        description
          "Choose a particular BGP instance.
           Specify a VRF.
           Clear all peers and all routes from the BGP table.
           Soft reconfig.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-vrf-afi-safi-all-soft {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-all-soft {
        tailf:actionpoint ncsproxy {
          tailf:internal;
        }
        csc:xr-task "bgp";
        csc:cli-command "clear bgp instance <instance-name> vrf <vrf-all> <afi-safi-name> * soft";
        description
          "Choose a particular BGP instance.
           Specify a VRF.
           Clear all peers and all routes from the BGP table.
           Soft reconfig.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-instance-vrf-afi-safi-all-soft-out {
      tailf:ncs-device-type "netconf";
      tailf:display-when "not(../../ncs:module) or ../../ncs:module[ncs:name='Cisco-IOS-XR-ipv4-bgp-act']";
      tailf:action clear-bgp-instance-vrf-afi-safi-all-soft-out {
        tailf:actionpoint ncsproxy {
          tailf:internal;
        }
        csc:xr-task "bgp";
        csc:cli-command "clear bgp instance <instance-name> vrf <vrf-all> <afi-safi-name> * soft out";
        description
          "Choose a particular BGP instance.
           Specify a VRF.
           Clear all peers and all routes from the BGP table.
           Soft reconfig.
           Soft reconfig outbound update.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-vrf-afi-safi-all-soft-out {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-all-soft-out {
        tailf:actionpoint ncsproxy {
          tailf:internal;
        }
        csc:xr-task "bgp";
        csc:cli-command "clear bgp instance <instance-name> vrf <vrf-all> <afi-safi-name> * soft out";
        description
          "Choose a particular BGP instance.
           Specify a VRF.
           Clear all peers and all routes from the BGP table.
           Soft reconfig.
           Soft reconfig outbound update.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-instance-vrf-afi-safi-all-soft-in {
      tailf:ncs-device-type "netconf";
      tailf:display-when "not(../../ncs:module) or ../../ncs:module[ncs:name='Cisco-IOS-XR-ipv4-bgp-act']";
      tailf:action clear-bgp-instance-vrf-afi-safi-all-soft-in {
        tailf:actionpoint ncsproxy {
          tailf:internal;
        }
        csc:xr-task "bgp";
        csc:cli-command "clear bgp instance <instance-name> vrf <vrf-all> <afi-safi-name> * soft in";
        description
          "Choose a particular BGP instance.
           Specify a VRF.
           Clear all peers and all routes from the BGP table.
           Soft reconfig.
           Soft reconfig inbound update.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-vrf-afi-safi-all-soft-in {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-all-soft-in {
        tailf:actionpoint ncsproxy {
          tailf:internal;
        }
        csc:xr-task "bgp";
        csc:cli-command "clear bgp instance <instance-name> vrf <vrf-all> <afi-safi-name> * soft in";
        description
          "Choose a particular BGP instance.
           Specify a VRF.
           Clear all peers and all routes from the BGP table.
           Soft reconfig.
           Soft reconfig inbound update.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-instance-vrf-afi-safi-all-soft-in-prefix-filter {
      tailf:ncs-device-type "netconf";
      tailf:display-when "not(../../ncs:module) or ../../ncs:module[ncs:name='Cisco-IOS-XR-ipv4-bgp-act']";
      tailf:action clear-bgp-instance-vrf-afi-safi-all-soft-in-prefix-filter {
        tailf:actionpoint ncsproxy {
          tailf:internal;
        }
        csc:xr-task "bgp";
        csc:cli-command "clear bgp instance <instance-name> vrf <vrf-all> <afi-safi-name> * soft in prefix-filter";
        description
          "Choose a particular BGP instance.
           Specify a VRF.
           Clear all peers and all routes from the BGP table.
           Soft reconfig.
           Soft reconfig inbound update.
           Push out prefix ORF and do inbound soft reconfig.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-vrf-afi-safi-all-soft-in-prefix-filter {
      tailf:ncs-device-type "netconf";
      tailf:display-when "/ncs:devices/ncs:device[ncs:name=current()/../../../ncs:member]/ncs:module[ncs:name='Cisco-IOS-XR-ipv4-bgp-act']";
      tailf:action clear-bgp-instance-vrf-afi-safi-all-soft-in-prefix-filter {
        tailf:actionpoint ncsproxy {
          tailf:internal;
        }
        csc:xr-task "bgp";
        csc:cli-command "clear bgp instance <instance-name> vrf <vrf-all> <afi-safi-name> * soft in prefix-filter";
        description
          "Choose a particular BGP instance.
           Specify a VRF.
           Clear all peers and all routes from the BGP table.
           Soft reconfig.
           Soft reconfig inbound update.
           Push out prefix ORF and do inbound soft reconfig.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-instance-vrf-external {
      tailf:ncs-device-type "netconf";
      tailf:display-when "not(../../ncs:module) or ../../ncs:module[ncs:name='Cisco-IOS-XR-ipv4-bgp-act']";
      tailf:action clear-bgp-instance-vrf-external {
        tailf:actionpoint ncsproxy {
          tailf:internal;
        }
        csc:xr-task "bgp";
        csc:cli-command "clear bgp instance <instance-name> vrf <vrf-all> external";
        description
          "Choose a particular BGP instance.
           Specify a VRF.
           Clear all external peers.
          ";
        input {
          leaf instance-name {
            mandatory true;
            type instance-name;
            description
              "instance name or all";
          }
          leaf vrf-all {
            mandatory true;
            type vrf-name;
            description
              "VRF name or all";
          }
        }
      }
    }
  }
  augment "/ncs:devices/ncs:device-group/ncs:ned-id/ncs:rpc" {
    container rpc-clear-bgp-instance-vrf-external {
      tailf:ncs-device-type "netconf";
      tailf:display-when "/ncs:devices/ncs:device[ncs:name=current()/../../../ncs:member]/ncs:module[ncs:name='Cisco-IOS-XR-ipv4-bgp-act']";
      tailf:action clear-bgp-instance-vrf-external {
        tailf:actionpoint ncsproxy {
          tailf:internal;
        }
        csc:xr-task "bgp";
        csc:cli-command "clear bgp instance <instance-name> vrf <vrf-all> external";
        description
          "Choose a particular BGP instance.
           Specify a VRF.
           Clear all external peers.
          ";
        input {
          leaf instance-name {
            mandatory true;
            type instance-name;
            description
              "instance name or all";
          }
          leaf vrf-all {
            mandatory true;
            type vrf-name;
            description
              "VRF name or all";
          }
        }
      }
    }
  }
  augment "/ncs:devices/ncs:device/ncs:rpc" {
    container rpc-clear-bgp-instance-vrf-external-graceful {
      tailf:ncs-device-type "netconf";
      tailf:display-when "not(../../ncs:module) or ../../ncs:module[ncs:name='Cisco-IOS-XR-ipv4-bgp-act']";
      tailf:action clear-bgp-instance-vrf-external-graceful {
        tailf:actionpoint ncsproxy {
          tailf:internal;
        }
        csc:xr-task "bgp";
        csc:cli-command "clear bgp instance <instance-name> vrf <vrf-all> external graceful";
        description
          "Choose a particular BGP instance.
           Specify a VRF.
           Clear all external peers.
           Clear with a hard reset and a graceful restart.
          ";
        input {
          leaf instance-name {
            mandatory true;
            type instance-name;
            description
              "instance name or all";
          }
          leaf vrf-all {
            mandatory true;
            type vrf-name;
            description
              "VRF name or all";
          }
        }
      }
    }
  }
  augment "/ncs:devices/ncs:device-group/ncs:ned-id/ncs:rpc" {
    container rpc-clear-bgp-instance-vrf-external-graceful {
      tailf:ncs-device-type "netconf";
      tailf:display-when "/ncs:devices/ncs:device[ncs:name=current()/../../../ncs:member]/ncs:module[ncs:name='Cisco-IOS-XR-ipv4-bgp-act']";
      tailf:action clear-bgp-instance-vrf-external-graceful {
        tailf:actionpoint ncsproxy {
          tailf:internal;
        }
        csc:xr-task "bgp";
        csc:cli-command "clear bgp instance <instance-name> vrf <vrf-all> external graceful";
        description
          "Choose a particular BGP instance.
           Specify a VRF.
           Clear all external peers.
           Clear with a hard reset and a graceful restart.
          ";
        input {
          leaf instance-name {
            mandatory true;
            type instance-name;
            description
              "instance name or all";
          }
          leaf vrf-all {
            mandatory true;
            type vrf-name;
            description
              "VRF name or all";
          }
        }
      }
    }
  }
  augment "/ncs:devices/ncs:device/ncs:rpc" {
    container rpc-clear-bgp-instance-vrf-as {
      tailf:ncs-device-type "netconf";
      tailf:display-when "not(../../ncs:module) or ../../ncs:module[ncs:name='Cisco-IOS-XR-ipv4-bgp-act']";
      tailf:action clear-bgp-instance-vrf-as {
        tailf:actionpoint ncsproxy {
          tailf:internal;
        }
        csc:xr-task "bgp";
        csc:cli-command "clear bgp instance <instance-name> vrf <vrf-all> as <as-number>";
        description
          "Choose a particular BGP instance.
           Specify a VRF.
           Clear peers in a specific AS.
          ";
        input {
          leaf instance-name {
            mandatory true;
            type instance-name;
            description
              "instance name or all";
          }
          leaf vrf-all {
            mandatory true;
            type vrf-name;
            description
              "VRF name or all";
          }
          leaf as-number {
            mandatory true;
            type as-number;
            description
              "AS number";
          }
        }
      }
    }
  }
  augment "/ncs:devices/ncs:device-group/ncs:ned-id/ncs:rpc" {
    container rpc-clear-bgp-instance-vrf-as {
      tailf:ncs-device-type "netconf";
      tailf:display-when "/ncs:devices/ncs:device[ncs:name=current()/../../../ncs:member]/ncs:module[ncs:name='Cisco-IOS-XR-ipv4-bgp-act']";
      tailf:action clear-bgp-instance-vrf-as {
        tailf:actionpoint ncsproxy {
          tailf:internal;
        }
        csc:xr-task "bgp";
        csc:cli-command "clear bgp instance <instance-name> vrf <vrf-all> as <as-number>";
        description
          "Choose a particular BGP instance.
           Specify a VRF.
           Clear peers in a specific AS.
          ";
        input {
          leaf instance-name {
            mandatory true;
            type instance-name;
            description
              "instance name or all";
          }
          leaf vrf-all {
            mandatory true;
            type vrf-name;
            description
              "VRF name or all";
          }
          leaf as-number {
            mandatory true;
            type as-number;
            description
              "AS number";
          }
        }
      }
    }
  }
  augment "/ncs:devices/ncs:device/ncs:rpc" {
    container rpc-clear-bgp-instance-vrf-as-graceful {
      tailf:ncs-device-type "netconf";
      tailf:display-when "not(../../ncs:module) or ../../ncs:module[ncs:name='Cisco-IOS-XR-ipv4-bgp-act']";
      tailf:action clear-bgp-instance-vrf-as-graceful {
        tailf:actionpoint ncsproxy {
          tailf:internal;
        }
        csc:xr-task "bgp";
        csc:cli-command "clear bgp instance <instance-name> vrf <vrf-all> as <as-number> graceful";
        description
          "Choose a particular BGP instance.
           Specify a VRF.
           Clear peers in a specific AS.
           Clear with a hard reset and a graceful restart.
          ";
        input {
          leaf instance-name {
            mandatory true;
            type instance-name;
            description
              "instance name or all";
          }
          leaf vrf-all {
            mandatory true;
            type vrf-name;
            description
              "VRF name or all";
          }
          leaf as-number {
            mandatory true;
            type as-number;
            description
              "AS number";
          }
        }
      }
    }
  }
  augment "/ncs:devices/ncs:device-group/ncs:ned-id/ncs:rpc" {
    container rpc-clear-bgp-instance-vrf-as-graceful {
      tailf:ncs-device-type "netconf";
      tailf:display-when "/ncs:devices/ncs:device[ncs:name=current()/../../../ncs:member]/ncs:module[ncs:name='Cisco-IOS-XR-ipv4-bgp-act']";
      tailf:action clear-bgp-instance-vrf-as-graceful {
        tailf:actionpoint ncsproxy {
          tailf:internal;
        }
        csc:xr-task "bgp";
        csc:cli-command "clear bgp instance <instance-name> vrf <vrf-all> as <as-number> graceful";
        description
          "Choose a particular BGP instance.
           Specify a VRF.
           Clear peers in a specific AS.
           Clear with a hard reset and a graceful restart.
          ";
        input {
          leaf instance-name {
            mandatory true;
            type instance-name;
            description
              "instance name or all";
          }
          leaf vrf-all {
            mandatory true;
            type vrf-name;
            description
              "VRF name or all";
          }
          leaf as-number {
            mandatory true;
            type as-number;
            description
              "AS number";
          }
        }
      }
    }
  }
  augment "/ncs:devices/ncs:device/ncs:rpc" {
    container rpc-clear-bgp-instance-vrf-ip-addr {
      tailf:ncs-device-type "netconf";
      tailf:display-when "not(../../ncs:module) or ../../ncs:module[ncs:name='Cisco-IOS-XR-ipv4-bgp-act']";
      tailf:action clear-bgp-instance-vrf-ip-addr {
        tailf:actionpoint ncsproxy {
          tailf:internal;
        }
        csc:xr-task "bgp";
        csc:cli-command "clear bgp instance <instance-name> vrf <vrf-all> <ip-addr>";
        description
          "Choose a particular BGP instance.
           Specify a VRF.
          ";
        input {
          leaf instance-name {
            mandatory true;
            type instance-name;
            description
              "instance name or all";
          }
          leaf vrf-all {
            mandatory true;
            type vrf-name;
            description
              "VRF name or all";
          }
          leaf ip-addr {
            mandatory true;
            type inet:ip-address;
            description
              "BGP neighbor address to clear";
          }
        }
      }
    }
  }
  augment "/ncs:devices/ncs:device-group/ncs:ned-id/ncs:rpc" {
    container rpc-clear-bgp-instance-vrf-ip-addr {
      tailf:ncs-device-type "netconf";
      tailf:display-when "/ncs:devices/ncs:device[ncs:name=current()/../../../ncs:member]/ncs:module[ncs:name='Cisco-IOS-XR-ipv4-bgp-act']";
      tailf:action clear-bgp-instance-vrf-ip-addr {
        tailf:actionpoint ncsproxy {
          tailf:internal;
        }
        csc:xr-task "bgp";
        csc:cli-command "clear bgp instance <instance-name> vrf <vrf-all> <ip-addr>";
        description
          "Choose a particular BGP instance.
           Specify a VRF.
          ";
        input {
          leaf instance-name {
            mandatory true;
            type instance-name;
            description
              "instance name or all";
          }
          leaf vrf-all {
            mandatory true;
            type vrf-name;
            description
              "VRF name or all";
          }
          leaf ip-addr {
            mandatory true;
            type inet:ip-address;
            description
              "BGP neighbor address to clear";
          }
        }
      }
    }
  }
  augment "/ncs:devices/ncs:device/ncs:rpc" {
    container rpc-clear-bgp-instance-vrf-ip-addr-long-lived-stale {
      tailf:ncs-device-type "netconf";
      tailf:display-when "not(../../ncs:module) or ../../ncs:module[ncs:name='Cisco-IOS-XR-ipv4-bgp-act']";
      tailf:action clear-bgp-instance-vrf-ip-addr-long-lived-stale {
        tailf:actionpoint ncsproxy {
          tailf:internal;
        }
        csc:xr-task "bgp";
        csc:cli-command "clear bgp instance <instance-name> vrf <vrf-all> <ip-addr> long-lived-stale";
        description
          "Choose a particular BGP instance.
           Specify a VRF.
           Clear long-lived-stale routes.
          ";
        input {
          leaf instance-name {
            mandatory true;
            type instance-name;
            description
              "instance name or all";
          }
          leaf vrf-all {
            mandatory true;
            type vrf-name;
            description
              "VRF name or all";
          }
          leaf ip-addr {
            mandatory true;
            type inet:ip-address;
            description
              "BGP neighbor address to clear";
          }
        }
      }
    }
  }
  augment "/ncs:devices/ncs:device-group/ncs:ned-id/ncs:rpc" {
    container rpc-clear-bgp-instance-vrf-ip-addr-long-lived-stale {
      tailf:ncs-device-type "netconf";
      tailf:display-when "/ncs:devices/ncs:device[ncs:name=current()/../../../ncs:member]/ncs:module[ncs:name='Cisco-IOS-XR-ipv4-bgp-act']";
      tailf:action clear-bgp-instance-vrf-ip-addr-long-lived-stale {
        tailf:actionpoint ncsproxy {
          tailf:internal;
        }
        csc:xr-task "bgp";
        csc:cli-command "clear bgp instance <instance-name> vrf <vrf-all> <ip-addr> long-lived-stale";
        description
          "Choose a particular BGP instance.
           Specify a VRF.
           Clear long-lived-stale routes.
          ";
        input {
          leaf instance-name {
            mandatory true;
            type instance-name;
            description
              "instance name or all";
          }
          leaf vrf-all {
            mandatory true;
            type vrf-name;
            description
              "VRF name or all";
          }
          leaf ip-addr {
            mandatory true;
            type inet:ip-address;
            description
              "BGP neighbor address to clear";
          }
        }
      }
    }
  }
  augment "/ncs:devices/ncs:device/ncs:rpc" {
    container rpc-clear-bgp-instance-vrf-ip-addr-graceful {
      tailf:ncs-device-type "netconf";
      tailf:display-when "not(../../ncs:module) or ../../ncs:module[ncs:name='Cisco-IOS-XR-ipv4-bgp-act']";
      tailf:action clear-bgp-instance-vrf-ip-addr-graceful {
        tailf:actionpoint ncsproxy {
          tailf:internal;
        }
        csc:xr-task "bgp";
        csc:cli-command "clear bgp instance <instance-name> vrf <vrf-all> <ip-addr> graceful";
        description
          "Choose a particular BGP instance.
           Specify a VRF.
           Clear with a hard reset and a graceful restart.
          ";
        input {
          leaf instance-name {
            mandatory true;
            type instance-name;
            description
              "instance name or all";
          }
          leaf vrf-all {
            mandatory true;
            type vrf-name;
            description
              "VRF name or all";
          }
          leaf ip-addr {
            mandatory true;
            type inet:ip-address;
            description
              "BGP neighbor address to clear";
          }
        }
      }
    }
  }
  augment "/ncs:devices/ncs:device-group/ncs:ned-id/ncs:rpc" {
    container rpc-clear-bgp-instance-vrf-ip-addr-graceful {
      tailf:ncs-device-type "netconf";
      tailf:display-when "/ncs:devices/ncs:device[ncs:name=current()/../../../ncs:member]/ncs:module[ncs:name='Cisco-IOS-XR-ipv4-bgp-act']";
      tailf:action clear-bgp-instance-vrf-ip-addr-graceful {
        tailf:actionpoint ncsproxy {
          tailf:internal;
        }
        csc:xr-task "bgp";
        csc:cli-command "clear bgp instance <instance-name> vrf <vrf-all> <ip-addr> graceful";
        description
          "Choose a particular BGP instance.
           Specify a VRF.
           Clear with a hard reset and a graceful restart.
          ";
        input {
          leaf instance-name {
            mandatory true;
            type instance-name;
            description
              "instance name or all";
          }
          leaf vrf-all {
            mandatory true;
            type vrf-name;
            description
              "VRF name or all";
          }
          leaf ip-addr {
            mandatory true;
            type inet:ip-address;
            description
              "BGP neighbor address to clear";
          }
        }
      }
    }
  }
  augment "/ncs:devices/ncs:device/ncs:rpc" {
    container rpc-clear-bgp-instance-vrf-all {
      tailf:ncs-device-type "netconf";
      tailf:display-when "not(../../ncs:module) or ../../ncs:module[ncs:name='Cisco-IOS-XR-ipv4-bgp-act']";
      tailf:action clear-bgp-instance-vrf-all {
        tailf:actionpoint ncsproxy {
          tailf:internal;
        }
        csc:xr-task "bgp";
        csc:cli-command "clear bgp instance <instance-name> vrf <vrf-all> *";
        description
          "Choose a particular BGP instance.
           Specify a VRF.
           Clear all peers and all routes from the BGP table.
          ";
        input {
          leaf instance-name {
            mandatory true;
            type instance-name;
            description
              "instance name or all";
          }
          leaf vrf-all {
            mandatory true;
            type vrf-name;
            description
              "VRF name or all";
          }
        }
      }
    }
  }
  augment "/ncs:devices/ncs:device-group/ncs:ned-id/ncs:rpc" {
    container rpc-clear-bgp-instance-vrf-all {
      tailf:ncs-device-type "netconf";
      tailf:display-when "/ncs:devices/ncs:device[ncs:name=current()/../../../ncs:member]/ncs:module[ncs:name='Cisco-IOS-XR-ipv4-bgp-act']";
      tailf:action clear-bgp-instance-vrf-all {
        tailf:actionpoint ncsproxy {
          tailf:internal;
        }
        csc:xr-task "bgp";
        csc:cli-command "clear bgp instance <instance-name> vrf <vrf-all> *";
        description
          "Choose a particular BGP instance.
           Specify a VRF.
           Clear all peers and all routes from the BGP table.
          ";
        input {
          leaf instance-name {
            mandatory true;
            type instance-name;
            description
              "instance name or all";
          }
          leaf vrf-all {
            mandatory true;
            type vrf-name;
            description
              "VRF name or all";
          }
        }
      }
    }
  }
  augment "/ncs:devices/ncs:device/ncs:rpc" {
    container rpc-clear-bgp-instance-vrf-all-graceful {
      tailf:ncs-device-type "netconf";
      tailf:display-when "not(../../ncs:module) or ../../ncs:module[ncs:name='Cisco-IOS-XR-ipv4-bgp-act']";
      tailf:action clear-bgp-instance-vrf-all-graceful {
        tailf:actionpoint ncsproxy {
          tailf:internal;
        }
        csc:xr-task "bgp";
        csc:cli-command "clear bgp instance <instance-name> vrf <vrf-all> * graceful";
        description
          "Choose a particular BGP instance.
           Specify a VRF.
           Clear all peers and all routes from the BGP table.
           Clear with a hard reset and a graceful restart.
          ";
        input {
          leaf instance-name {
            mandatory true;
            type instance-name;
            description
              "instance name or all";
          }
          leaf vrf-all {
            mandatory true;
            type vrf-name;
            description
              "VRF name or all";
          }
        }
      }
    }
  }
  augment "/ncs:devices/ncs:device-group/ncs:ned-id/ncs:rpc" {
    container rpc-clear-bgp-instance-vrf-all-graceful {
      tailf:ncs-device-type "netconf";
      tailf:display-when "/ncs:devices/ncs:device[ncs:name=current()/../../../ncs:member]/ncs:module[ncs:name='Cisco-IOS-XR-ipv4-bgp-act']";
      tailf:action clear-bgp-instance-vrf-all-graceful {
        tailf:actionpoint ncsproxy {
          tailf:internal;
        }
        csc:xr-task "bgp";
        csc:cli-command "clear bgp instance <instance-name> vrf <vrf-all> * graceful";
        description
          "Choose a particular BGP instance.
           Specify a VRF.
           Clear all peers and all routes from the BGP table.
           Clear with a hard reset and a graceful restart.
          ";
        input {
          leaf instance-name {
            mandatory true;
            type instance-name;
            description
              "instance name or all";
          }
          leaf vrf-all {
            mandatory true;
            type vrf-name;
            description
              "VRF name or all";
          }
        }
      }
    }
  }
  augment "/ncs:devices/ncs:device/ncs:rpc" {
    container rpc-clear-bgp-instance-version-vrf-afi-safi {
      tailf:ncs-device-type "netconf";
      tailf:display-when "not(../../ncs:module) or ../../ncs:module[ncs:name='Cisco-IOS-XR-ipv4-bgp-act']";
      tailf:action clear-bgp-instance-version-vrf-afi-safi {
        tailf:actionpoint ncsproxy {
          tailf:internal;
        }
        csc:xr-task "bgp";
        csc:cli-command "clear bgp instance <instance-name> version vrf <vrf-all> <afi-safi-name>";
        description
          "Choose a particular BGP instance.
           clear BGP prefix version.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-version-vrf-afi-safi {
      tailf:ncs-device-type "netconf";
      tailf:display-when "/ncs:devices/ncs:device[ncs:name=current()/../../../ncs:member]/ncs:module[ncs:name='Cisco-IOS-XR-ipv4-bgp-act']";
      tailf:action clear-bgp-instance-version-vrf-afi-safi {
        tailf:actionpoint ncsproxy {
          tailf:internal;
        }
        csc:xr-task "bgp";
        csc:cli-command "clear bgp instance <instance-name> version vrf <vrf-all> <afi-safi-name>";
        description
          "Choose a particular BGP instance.
           clear BGP prefix version.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-instance-version-vrf-afi-safi-vrf {
      tailf:ncs-device-type "netconf";
      tailf:display-when "not(../../ncs:module) or ../../ncs:module[ncs:name='Cisco-IOS-XR-ipv4-bgp-act']";
      tailf:action clear-bgp-instance-version-vrf-afi-safi-vrf {
        tailf:actionpoint ncsproxy {
          tailf:internal;
        }
        csc:xr-task "bgp";
        csc:cli-command "clear bgp instance <instance-name> version vrf <vrf-all> <afi-safi-name> vrf <vrf-name>";
        description
          "Choose a particular BGP instance.
           clear BGP prefix version.
           Specify a VRF.
           Display routes for a specified VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf vrf-name {
            mandatory true;
            type string;
            description
              "VRF name";
          }
        }
      }
    }
  }
  augment "/ncs:devices/ncs:device-group/ncs:ned-id/ncs:rpc" {
    container rpc-clear-bgp-instance-version-vrf-afi-safi-vrf {
      tailf:ncs-device-type "netconf";
      tailf:display-when "/ncs:devices/ncs:device[ncs:name=current()/../../../ncs:member]/ncs:module[ncs:name='Cisco-IOS-XR-ipv4-bgp-act']";
      tailf:action clear-bgp-instance-version-vrf-afi-safi-vrf {
        tailf:actionpoint ncsproxy {
          tailf:internal;
        }
        csc:xr-task "bgp";
        csc:cli-command "clear bgp instance <instance-name> version vrf <vrf-all> <afi-safi-name> vrf <vrf-name>";
        description
          "Choose a particular BGP instance.
           clear BGP prefix version.
           Specify a VRF.
           Display routes for a specified VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf vrf-name {
            mandatory true;
            type string;
            description
              "VRF name";
          }
        }
      }
    }
  }
  augment "/ncs:devices/ncs:device/ncs:rpc" {
    container rpc-clear-bgp-instance-version-vrf-afi-safi-rd {
      tailf:ncs-device-type "netconf";
      tailf:display-when "not(../../ncs:module) or ../../ncs:module[ncs:name='Cisco-IOS-XR-ipv4-bgp-act']";
      tailf:action clear-bgp-instance-version-vrf-afi-safi-rd {
        tailf:actionpoint ncsproxy {
          tailf:internal;
        }
        csc:xr-task "bgp";
        csc:cli-command "clear bgp instance <instance-name> version vrf <vrf-all> <afi-safi-name> rd <rd>";
        description
          "Choose a particular BGP instance.
           clear BGP prefix version.
           Specify a VRF.
           Display routes with a specific route distinguisher.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf rd {
            mandatory true;
            type rd;
            description
              "Route distinguisher";
          }
        }
      }
    }
  }
  augment "/ncs:devices/ncs:device-group/ncs:ned-id/ncs:rpc" {
    container rpc-clear-bgp-instance-version-vrf-afi-safi-rd {
      tailf:ncs-device-type "netconf";
      tailf:display-when "/ncs:devices/ncs:device[ncs:name=current()/../../../ncs:member]/ncs:module[ncs:name='Cisco-IOS-XR-ipv4-bgp-act']";
      tailf:action clear-bgp-instance-version-vrf-afi-safi-rd {
        tailf:actionpoint ncsproxy {
          tailf:internal;
        }
        csc:xr-task "bgp";
        csc:cli-command "clear bgp instance <instance-name> version vrf <vrf-all> <afi-safi-name> rd <rd>";
        description
          "Choose a particular BGP instance.
           clear BGP prefix version.
           Specify a VRF.
           Display routes with a specific route distinguisher.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf rd {
            mandatory true;
            type rd;
            description
              "Route distinguisher";
          }
        }
      }
    }
  }
  augment "/ncs:devices/ncs:device/ncs:rpc" {
    container rpc-clear-bgp-instance-version-vrf-afi-safi-ipv6-prefix {
      tailf:ncs-device-type "netconf";
      tailf:display-when "not(../../ncs:module) or ../../ncs:module[ncs:name='Cisco-IOS-XR-ipv4-bgp-act']";
      tailf:action clear-bgp-instance-version-vrf-afi-safi-ipv6-prefix {
        tailf:actionpoint ncsproxy {
          tailf:internal;
        }
        csc:xr-task "bgp";
        csc:cli-command "clear bgp instance <instance-name> version vrf <vrf-all> <afi-safi-name> <ipv6-prefix>";
        description
          "Choose a particular BGP instance.
           clear BGP prefix version.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv6-prefix {
            mandatory true;
            type inet:ipv6-prefix;
            description
              "IPv6 network and masklength";
          }
        }
      }
    }
  }
  augment "/ncs:devices/ncs:device-group/ncs:ned-id/ncs:rpc" {
    container rpc-clear-bgp-instance-version-vrf-afi-safi-ipv6-prefix {
      tailf:ncs-device-type "netconf";
      tailf:display-when "/ncs:devices/ncs:device[ncs:name=current()/../../../ncs:member]/ncs:module[ncs:name='Cisco-IOS-XR-ipv4-bgp-act']";
      tailf:action clear-bgp-instance-version-vrf-afi-safi-ipv6-prefix {
        tailf:actionpoint ncsproxy {
          tailf:internal;
        }
        csc:xr-task "bgp";
        csc:cli-command "clear bgp instance <instance-name> version vrf <vrf-all> <afi-safi-name> <ipv6-prefix>";
        description
          "Choose a particular BGP instance.
           clear BGP prefix version.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv6-prefix {
            mandatory true;
            type inet:ipv6-prefix;
            description
              "IPv6 network and masklength";
          }
        }
      }
    }
  }
  augment "/ncs:devices/ncs:device/ncs:rpc" {
    container rpc-clear-bgp-instance-version-vrf-afi-safi-ipv6-addr {
      tailf:ncs-device-type "netconf";
      tailf:display-when "not(../../ncs:module) or ../../ncs:module[ncs:name='Cisco-IOS-XR-ipv4-bgp-act']";
      tailf:action clear-bgp-instance-version-vrf-afi-safi-ipv6-addr {
        tailf:actionpoint ncsproxy {
          tailf:internal;
        }
        csc:xr-task "bgp";
        csc:cli-command "clear bgp instance <instance-name> version vrf <vrf-all> <afi-safi-name> <ipv6-addr>";
        description
          "Choose a particular BGP instance.
           clear BGP prefix version.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv6-addr {
            mandatory true;
            type inet:ipv6-address;
            description
              "IPv6 network";
          }
        }
      }
    }
  }
  augment "/ncs:devices/ncs:device-group/ncs:ned-id/ncs:rpc" {
    container rpc-clear-bgp-instance-version-vrf-afi-safi-ipv6-addr {
      tailf:ncs-device-type "netconf";
      tailf:display-when "/ncs:devices/ncs:device[ncs:name=current()/../../../ncs:member]/ncs:module[ncs:name='Cisco-IOS-XR-ipv4-bgp-act']";
      tailf:action clear-bgp-instance-version-vrf-afi-safi-ipv6-addr {
        tailf:actionpoint ncsproxy {
          tailf:internal;
        }
        csc:xr-task "bgp";
        csc:cli-command "clear bgp instance <instance-name> version vrf <vrf-all> <afi-safi-name> <ipv6-addr>";
        description
          "Choose a particular BGP instance.
           clear BGP prefix version.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv6-addr {
            mandatory true;
            type inet:ipv6-address;
            description
              "IPv6 network";
          }
        }
      }
    }
  }
  augment "/ncs:devices/ncs:device/ncs:rpc" {
    container rpc-clear-bgp-instance-version-vrf-afi-safi-ipv6-addr-ipv6-netmask {
      tailf:ncs-device-type "netconf";
      tailf:display-when "not(../../ncs:module) or ../../ncs:module[ncs:name='Cisco-IOS-XR-ipv4-bgp-act']";
      tailf:action clear-bgp-instance-version-vrf-afi-safi-ipv6-addr-ipv6-netmask {
        tailf:actionpoint ncsproxy {
          tailf:internal;
        }
        csc:xr-task "bgp";
        csc:cli-command "clear bgp instance <instance-name> version vrf <vrf-all> <afi-safi-name> <ipv6-addr> <ipv6-netmask>";
        description
          "Choose a particular BGP instance.
           clear BGP prefix version.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device-group/ncs:ned-id/ncs:rpc" {
    container rpc-clear-bgp-instance-version-vrf-afi-safi-ipv6-addr-ipv6-netmask {
      tailf:ncs-device-type "netconf";
      tailf:display-when "/ncs:devices/ncs:device[ncs:name=current()/../../../ncs:member]/ncs:module[ncs:name='Cisco-IOS-XR-ipv4-bgp-act']";
      tailf:action clear-bgp-instance-version-vrf-afi-safi-ipv6-addr-ipv6-netmask {
        tailf:actionpoint ncsproxy {
          tailf:internal;
        }
        csc:xr-task "bgp";
        csc:cli-command "clear bgp instance <instance-name> version vrf <vrf-all> <afi-safi-name> <ipv6-addr> <ipv6-netmask>";
        description
          "Choose a particular BGP instance.
           clear BGP prefix version.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device/ncs:rpc" {
    container rpc-clear-bgp-instance-version-vrf-afi-safi-vrf-network {
      tailf:ncs-device-type "netconf";
      tailf:display-when "not(../../ncs:module) or ../../ncs:module[ncs:name='Cisco-IOS-XR-ipv4-bgp-act']";
      tailf:action clear-bgp-instance-version-vrf-afi-safi-vrf-network {
        tailf:actionpoint ncsproxy {
          tailf:internal;
        }
        csc:xr-task "bgp";
        csc:cli-command "clear bgp instance <instance-name> version vrf <vrf-all> <afi-safi-name> vrf <vrf-name> <network>";
        description
          "Choose a particular BGP instance.
           clear BGP prefix version.
           Specify a VRF.
           Display routes for a specified VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf vrf-name {
            mandatory true;
            type string;
            description
              "VRF name";
          }
          leaf network {
            mandatory true;
            type string;
            description
              "Address family modifier specific network";
          }
        }
      }
    }
  }
  augment "/ncs:devices/ncs:device-group/ncs:ned-id/ncs:rpc" {
    container rpc-clear-bgp-instance-version-vrf-afi-safi-vrf-network {
      tailf:ncs-device-type "netconf";
      tailf:display-when "/ncs:devices/ncs:device[ncs:name=current()/../../../ncs:member]/ncs:module[ncs:name='Cisco-IOS-XR-ipv4-bgp-act']";
      tailf:action clear-bgp-instance-version-vrf-afi-safi-vrf-network {
        tailf:actionpoint ncsproxy {
          tailf:internal;
        }
        csc:xr-task "bgp";
        csc:cli-command "clear bgp instance <instance-name> version vrf <vrf-all> <afi-safi-name> vrf <vrf-name> <network>";
        description
          "Choose a particular BGP instance.
           clear BGP prefix version.
           Specify a VRF.
           Display routes for a specified VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf vrf-name {
            mandatory true;
            type string;
            description
              "VRF name";
          }
          leaf network {
            mandatory true;
            type string;
            description
              "Address family modifier specific network";
          }
        }
      }
    }
  }
  augment "/ncs:devices/ncs:device/ncs:rpc" {
    container rpc-clear-bgp-instance-version-vrf-afi-safi-rd-network {
      tailf:ncs-device-type "netconf";
      tailf:display-when "not(../../ncs:module) or ../../ncs:module[ncs:name='Cisco-IOS-XR-ipv4-bgp-act']";
      tailf:action clear-bgp-instance-version-vrf-afi-safi-rd-network {
        tailf:actionpoint ncsproxy {
          tailf:internal;
        }
        csc:xr-task "bgp";
        csc:cli-command "clear bgp instance <instance-name> version vrf <vrf-all> <afi-safi-name> rd <rd> <network>";
        description
          "Choose a particular BGP instance.
           clear BGP prefix version.
           Specify a VRF.
           Display routes with a specific route distinguisher.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf rd {
            mandatory true;
            type rd;
            description
              "Route distinguisher";
          }
          leaf network {
            mandatory true;
            type string;
            description
              "Address family modifier specific network";
          }
        }
      }
    }
  }
  augment "/ncs:devices/ncs:device-group/ncs:ned-id/ncs:rpc" {
    container rpc-clear-bgp-instance-version-vrf-afi-safi-rd-network {
      tailf:ncs-device-type "netconf";
      tailf:display-when "/ncs:devices/ncs:device[ncs:name=current()/../../../ncs:member]/ncs:module[ncs:name='Cisco-IOS-XR-ipv4-bgp-act']";
      tailf:action clear-bgp-instance-version-vrf-afi-safi-rd-network {
        tailf:actionpoint ncsproxy {
          tailf:internal;
        }
        csc:xr-task "bgp";
        csc:cli-command "clear bgp instance <instance-name> version vrf <vrf-all> <afi-safi-name> rd <rd> <network>";
        description
          "Choose a particular BGP instance.
           clear BGP prefix version.
           Specify a VRF.
           Display routes with a specific route distinguisher.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf rd {
            mandatory true;
            type rd;
            description
              "Route distinguisher";
          }
          leaf network {
            mandatory true;
            type string;
            description
              "Address family modifier specific network";
          }
        }
      }
    }
  }
  augment "/ncs:devices/ncs:device/ncs:rpc" {
    container rpc-clear-bgp-instance-version-vrf-afi-safi-network {
      tailf:ncs-device-type "netconf";
      tailf:display-when "not(../../ncs:module) or ../../ncs:module[ncs:name='Cisco-IOS-XR-ipv4-bgp-act']";
      tailf:action clear-bgp-instance-version-vrf-afi-safi-network {
        tailf:actionpoint ncsproxy {
          tailf:internal;
        }
        csc:xr-task "bgp";
        csc:cli-command "clear bgp instance <instance-name> version vrf <vrf-all> <afi-safi-name> <network>";
        description
          "Choose a particular BGP instance.
           clear BGP prefix version.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf network {
            mandatory true;
            type string;
            description
              "Address family modifier specific network";
          }
        }
      }
    }
  }
  augment "/ncs:devices/ncs:device-group/ncs:ned-id/ncs:rpc" {
    container rpc-clear-bgp-instance-version-vrf-afi-safi-network {
      tailf:ncs-device-type "netconf";
      tailf:display-when "/ncs:devices/ncs:device[ncs:name=current()/../../../ncs:member]/ncs:module[ncs:name='Cisco-IOS-XR-ipv4-bgp-act']";
      tailf:action clear-bgp-instance-version-vrf-afi-safi-network {
        tailf:actionpoint ncsproxy {
          tailf:internal;
        }
        csc:xr-task "bgp";
        csc:cli-command "clear bgp instance <instance-name> version vrf <vrf-all> <afi-safi-name> <network>";
        description
          "Choose a particular BGP instance.
           clear BGP prefix version.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf network {
            mandatory true;
            type string;
            description
              "Address family modifier specific network";
          }
        }
      }
    }
  }
  augment "/ncs:devices/ncs:device/ncs:rpc" {
    container rpc-clear-bgp-instance-version-vrf-afi-safi-ipv4-addr {
      tailf:ncs-device-type "netconf";
      tailf:display-when "not(../../ncs:module) or ../../ncs:module[ncs:name='Cisco-IOS-XR-ipv4-bgp-act']";
      tailf:action clear-bgp-instance-version-vrf-afi-safi-ipv4-addr {
        tailf:actionpoint ncsproxy {
          tailf:internal;
        }
        csc:xr-task "bgp";
        csc:cli-command "clear bgp instance <instance-name> version vrf <vrf-all> <afi-safi-name> <ipv4-addr>";
        description
          "Choose a particular BGP instance.
           clear BGP prefix version.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv4-addr {
            mandatory true;
            type inet:ipv4-address;
            description
              "IPv4 network";
          }
        }
      }
    }
  }
  augment "/ncs:devices/ncs:device-group/ncs:ned-id/ncs:rpc" {
    container rpc-clear-bgp-instance-version-vrf-afi-safi-ipv4-addr {
      tailf:ncs-device-type "netconf";
      tailf:display-when "/ncs:devices/ncs:device[ncs:name=current()/../../../ncs:member]/ncs:module[ncs:name='Cisco-IOS-XR-ipv4-bgp-act']";
      tailf:action clear-bgp-instance-version-vrf-afi-safi-ipv4-addr {
        tailf:actionpoint ncsproxy {
          tailf:internal;
        }
        csc:xr-task "bgp";
        csc:cli-command "clear bgp instance <instance-name> version vrf <vrf-all> <afi-safi-name> <ipv4-addr>";
        description
          "Choose a particular BGP instance.
           clear BGP prefix version.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv4-addr {
            mandatory true;
            type inet:ipv4-address;
            description
              "IPv4 network";
          }
        }
      }
    }
  }
  augment "/ncs:devices/ncs:device/ncs:rpc" {
    container rpc-clear-bgp-instance-version-vrf-afi-safi-ipv4-addr-ipv4-mask {
      tailf:ncs-device-type "netconf";
      tailf:display-when "not(../../ncs:module) or ../../ncs:module[ncs:name='Cisco-IOS-XR-ipv4-bgp-act']";
      tailf:action clear-bgp-instance-version-vrf-afi-safi-ipv4-addr-ipv4-mask {
        tailf:actionpoint ncsproxy {
          tailf:internal;
        }
        csc:xr-task "bgp";
        csc:cli-command "clear bgp instance <instance-name> version vrf <vrf-all> <afi-safi-name> <ipv4-addr> <ipv4-mask>";
        description
          "Choose a particular BGP instance.
           clear BGP prefix version.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device-group/ncs:ned-id/ncs:rpc" {
    container rpc-clear-bgp-instance-version-vrf-afi-safi-ipv4-addr-ipv4-mask {
      tailf:ncs-device-type "netconf";
      tailf:display-when "/ncs:devices/ncs:device[ncs:name=current()/../../../ncs:member]/ncs:module[ncs:name='Cisco-IOS-XR-ipv4-bgp-act']";
      tailf:action clear-bgp-instance-version-vrf-afi-safi-ipv4-addr-ipv4-mask {
        tailf:actionpoint ncsproxy {
          tailf:internal;
        }
        csc:xr-task "bgp";
        csc:cli-command "clear bgp instance <instance-name> version vrf <vrf-all> <afi-safi-name> <ipv4-addr> <ipv4-mask>";
        description
          "Choose a particular BGP instance.
           clear BGP prefix version.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device/ncs:rpc" {
    container rpc-clear-bgp-instance-version-vrf-afi-safi-ipv4-prefix {
      tailf:ncs-device-type "netconf";
      tailf:display-when "not(../../ncs:module) or ../../ncs:module[ncs:name='Cisco-IOS-XR-ipv4-bgp-act']";
      tailf:action clear-bgp-instance-version-vrf-afi-safi-ipv4-prefix {
        tailf:actionpoint ncsproxy {
          tailf:internal;
        }
        csc:xr-task "bgp";
        csc:cli-command "clear bgp instance <instance-name> version vrf <vrf-all> <afi-safi-name> <ipv4-prefix>";
        description
          "Choose a particular BGP instance.
           clear BGP prefix version.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv4-prefix {
            mandatory true;
            type inet:ipv4-prefix;
            description
              "Fspec IPv4 Prefix";
          }
        }
      }
    }
  }
  augment "/ncs:devices/ncs:device-group/ncs:ned-id/ncs:rpc" {
    container rpc-clear-bgp-instance-version-vrf-afi-safi-ipv4-prefix {
      tailf:ncs-device-type "netconf";
      tailf:display-when "/ncs:devices/ncs:device[ncs:name=current()/../../../ncs:member]/ncs:module[ncs:name='Cisco-IOS-XR-ipv4-bgp-act']";
      tailf:action clear-bgp-instance-version-vrf-afi-safi-ipv4-prefix {
        tailf:actionpoint ncsproxy {
          tailf:internal;
        }
        csc:xr-task "bgp";
        csc:cli-command "clear bgp instance <instance-name> version vrf <vrf-all> <afi-safi-name> <ipv4-prefix>";
        description
          "Choose a particular BGP instance.
           clear BGP prefix version.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv4-prefix {
            mandatory true;
            type inet:ipv4-prefix;
            description
              "Fspec IPv4 Prefix";
          }
        }
      }
    }
  }
  augment "/ncs:devices/ncs:device/ncs:rpc" {
    container rpc-clear-bgp-instance-version-vrf-ip-prefix {
      tailf:ncs-device-type "netconf";
      tailf:display-when "not(../../ncs:module) or ../../ncs:module[ncs:name='Cisco-IOS-XR-ipv4-bgp-act']";
      tailf:action clear-bgp-instance-version-vrf-ip-prefix {
        tailf:actionpoint ncsproxy {
          tailf:internal;
        }
        csc:xr-task "bgp";
        csc:cli-command "clear bgp instance <instance-name> version vrf <vrf-all> <ip-prefix>";
        description
          "Choose a particular BGP instance.
           clear BGP prefix version.
           Specify a VRF.
          ";
        input {
          leaf instance-name {
            mandatory true;
            type instance-name;
            description
              "instance name or all";
          }
          leaf vrf-all {
            mandatory true;
            type vrf-name;
            description
              "VRF name or all";
          }
          leaf ip-prefix {
            mandatory true;
            type inet:ip-prefix;
            description
              "Network and masklength";
          }
        }
      }
    }
  }
  augment "/ncs:devices/ncs:device-group/ncs:ned-id/ncs:rpc" {
    container rpc-clear-bgp-instance-version-vrf-ip-prefix {
      tailf:ncs-device-type "netconf";
      tailf:display-when "/ncs:devices/ncs:device[ncs:name=current()/../../../ncs:member]/ncs:module[ncs:name='Cisco-IOS-XR-ipv4-bgp-act']";
      tailf:action clear-bgp-instance-version-vrf-ip-prefix {
        tailf:actionpoint ncsproxy {
          tailf:internal;
        }
        csc:xr-task "bgp";
        csc:cli-command "clear bgp instance <instance-name> version vrf <vrf-all> <ip-prefix>";
        description
          "Choose a particular BGP instance.
           clear BGP prefix version.
           Specify a VRF.
          ";
        input {
          leaf instance-name {
            mandatory true;
            type instance-name;
            description
              "instance name or all";
          }
          leaf vrf-all {
            mandatory true;
            type vrf-name;
            description
              "VRF name or all";
          }
          leaf ip-prefix {
            mandatory true;
            type inet:ip-prefix;
            description
              "Network and masklength";
          }
        }
      }
    }
  }
  augment "/ncs:devices/ncs:device/ncs:rpc" {
    container rpc-clear-bgp-instance-version-vrf-ip-addr {
      tailf:ncs-device-type "netconf";
      tailf:display-when "not(../../ncs:module) or ../../ncs:module[ncs:name='Cisco-IOS-XR-ipv4-bgp-act']";
      tailf:action clear-bgp-instance-version-vrf-ip-addr {
        tailf:actionpoint ncsproxy {
          tailf:internal;
        }
        csc:xr-task "bgp";
        csc:cli-command "clear bgp instance <instance-name> version vrf <vrf-all> <ip-addr>";
        description
          "Choose a particular BGP instance.
           clear BGP prefix version.
           Specify a VRF.
          ";
        input {
          leaf instance-name {
            mandatory true;
            type instance-name;
            description
              "instance name or all";
          }
          leaf vrf-all {
            mandatory true;
            type vrf-name;
            description
              "VRF name or all";
          }
          leaf ip-addr {
            mandatory true;
            type inet:ip-address;
            description
              "Network";
          }
        }
      }
    }
  }
  augment "/ncs:devices/ncs:device-group/ncs:ned-id/ncs:rpc" {
    container rpc-clear-bgp-instance-version-vrf-ip-addr {
      tailf:ncs-device-type "netconf";
      tailf:display-when "/ncs:devices/ncs:device[ncs:name=current()/../../../ncs:member]/ncs:module[ncs:name='Cisco-IOS-XR-ipv4-bgp-act']";
      tailf:action clear-bgp-instance-version-vrf-ip-addr {
        tailf:actionpoint ncsproxy {
          tailf:internal;
        }
        csc:xr-task "bgp";
        csc:cli-command "clear bgp instance <instance-name> version vrf <vrf-all> <ip-addr>";
        description
          "Choose a particular BGP instance.
           clear BGP prefix version.
           Specify a VRF.
          ";
        input {
          leaf instance-name {
            mandatory true;
            type instance-name;
            description
              "instance name or all";
          }
          leaf vrf-all {
            mandatory true;
            type vrf-name;
            description
              "VRF name or all";
          }
          leaf ip-addr {
            mandatory true;
            type inet:ip-address;
            description
              "Network";
          }
        }
      }
    }
  }
  augment "/ncs:devices/ncs:device/ncs:rpc" {
    container rpc-clear-bgp-instance-version-vrf-ip-addr-ip-netmask {
      tailf:ncs-device-type "netconf";
      tailf:display-when "not(../../ncs:module) or ../../ncs:module[ncs:name='Cisco-IOS-XR-ipv4-bgp-act']";
      tailf:action clear-bgp-instance-version-vrf-ip-addr-ip-netmask {
        tailf:actionpoint ncsproxy {
          tailf:internal;
        }
        csc:xr-task "bgp";
        csc:cli-command "clear bgp instance <instance-name> version vrf <vrf-all> <ip-addr> <ip-netmask>";
        description
          "Choose a particular BGP instance.
           clear BGP prefix version.
           Specify a VRF.
          ";
        input {
          leaf instance-name {
            mandatory true;
            type instance-name;
            description
              "instance name or all";
          }
          leaf vrf-all {
            mandatory true;
            type vrf-name;
            description
              "VRF name or all";
          }
          leaf ip-addr {
            mandatory true;
            type inet:ip-address;
            description
              "Network";
          }
          leaf ip-netmask {
            mandatory true;
            type ip-netmask;
            description
              "Mask";
          }
        }
      }
    }
  }
  augment "/ncs:devices/ncs:device-group/ncs:ned-id/ncs:rpc" {
    container rpc-clear-bgp-instance-version-vrf-ip-addr-ip-netmask {
      tailf:ncs-device-type "netconf";
      tailf:display-when "/ncs:devices/ncs:device[ncs:name=current()/../../../ncs:member]/ncs:module[ncs:name='Cisco-IOS-XR-ipv4-bgp-act']";
      tailf:action clear-bgp-instance-version-vrf-ip-addr-ip-netmask {
        tailf:actionpoint ncsproxy {
          tailf:internal;
        }
        csc:xr-task "bgp";
        csc:cli-command "clear bgp instance <instance-name> version vrf <vrf-all> <ip-addr> <ip-netmask>";
        description
          "Choose a particular BGP instance.
           clear BGP prefix version.
           Specify a VRF.
          ";
        input {
          leaf instance-name {
            mandatory true;
            type instance-name;
            description
              "instance name or all";
          }
          leaf vrf-all {
            mandatory true;
            type vrf-name;
            description
              "VRF name or all";
          }
          leaf ip-addr {
            mandatory true;
            type inet:ip-address;
            description
              "Network";
          }
          leaf ip-netmask {
            mandatory true;
            type ip-netmask;
            description
              "Mask";
          }
        }
      }
    }
  }
  augment "/ncs:devices/ncs:device/ncs:rpc" {
    container rpc-clear-bgp-instance-version-afi-safi-vrf-ipv6-prefix {
      tailf:ncs-device-type "netconf";
      tailf:display-when "not(../../ncs:module) or ../../ncs:module[ncs:name='Cisco-IOS-XR-ipv4-bgp-act']";
      tailf:action clear-bgp-instance-version-afi-safi-vrf-ipv6-prefix {
        tailf:actionpoint ncsproxy {
          tailf:internal;
        }
        csc:xr-task "bgp";
        csc:cli-command "clear bgp instance <instance-name> version <afi-safi-name> vrf <vrf-name> <ipv6-prefix>";
        description
          "Choose a particular BGP instance.
           clear BGP prefix version.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
          leaf ipv6-prefix {
            mandatory true;
            type inet:ipv6-prefix;
            description
              "IPv6 network and masklength";
          }
        }
      }
    }
  }
  augment "/ncs:devices/ncs:device-group/ncs:ned-id/ncs:rpc" {
    container rpc-clear-bgp-instance-version-afi-safi-vrf-ipv6-prefix {
      tailf:ncs-device-type "netconf";
      tailf:display-when "/ncs:devices/ncs:device[ncs:name=current()/../../../ncs:member]/ncs:module[ncs:name='Cisco-IOS-XR-ipv4-bgp-act']";
      tailf:action clear-bgp-instance-version-afi-safi-vrf-ipv6-prefix {
        tailf:actionpoint ncsproxy {
          tailf:internal;
        }
        csc:xr-task "bgp";
        csc:cli-command "clear bgp instance <instance-name> version <afi-safi-name> vrf <vrf-name> <ipv6-prefix>";
        description
          "Choose a particular BGP instance.
           clear BGP prefix version.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
          leaf ipv6-prefix {
            mandatory true;
            type inet:ipv6-prefix;
            description
              "IPv6 network and masklength";
          }
        }
      }
    }
  }
  augment "/ncs:devices/ncs:device/ncs:rpc" {
    container rpc-clear-bgp-instance-version-afi-safi-vrf-ipv6-addr {
      tailf:ncs-device-type "netconf";
      tailf:display-when "not(../../ncs:module) or ../../ncs:module[ncs:name='Cisco-IOS-XR-ipv4-bgp-act']";
      tailf:action clear-bgp-instance-version-afi-safi-vrf-ipv6-addr {
        tailf:actionpoint ncsproxy {
          tailf:internal;
        }
        csc:xr-task "bgp";
        csc:cli-command "clear bgp instance <instance-name> version <afi-safi-name> vrf <vrf-name> <ipv6-addr>";
        description
          "Choose a particular BGP instance.
           clear BGP prefix version.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
          leaf ipv6-addr {
            mandatory true;
            type inet:ipv6-address;
            description
              "IPv6 network";
          }
        }
      }
    }
  }
  augment "/ncs:devices/ncs:device-group/ncs:ned-id/ncs:rpc" {
    container rpc-clear-bgp-instance-version-afi-safi-vrf-ipv6-addr {
      tailf:ncs-device-type "netconf";
      tailf:display-when "/ncs:devices/ncs:device[ncs:name=current()/../../../ncs:member]/ncs:module[ncs:name='Cisco-IOS-XR-ipv4-bgp-act']";
      tailf:action clear-bgp-instance-version-afi-safi-vrf-ipv6-addr {
        tailf:actionpoint ncsproxy {
          tailf:internal;
        }
        csc:xr-task "bgp";
        csc:cli-command "clear bgp instance <instance-name> version <afi-safi-name> vrf <vrf-name> <ipv6-addr>";
        description
          "Choose a particular BGP instance.
           clear BGP prefix version.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
          leaf ipv6-addr {
            mandatory true;
            type inet:ipv6-address;
            description
              "IPv6 network";
          }
        }
      }
    }
  }
  augment "/ncs:devices/ncs:device/ncs:rpc" {
    container rpc-clear-bgp-instance-version-afi-safi-vrf-ipv6-addr-ipv6-netmask {
      tailf:ncs-device-type "netconf";
      tailf:display-when "not(../../ncs:module) or ../../ncs:module[ncs:name='Cisco-IOS-XR-ipv4-bgp-act']";
      tailf:action clear-bgp-instance-version-afi-safi-vrf-ipv6-addr-ipv6-netmask {
        tailf:actionpoint ncsproxy {
          tailf:internal;
        }
        csc:xr-task "bgp";
        csc:cli-command "clear bgp instance <instance-name> version <afi-safi-name> vrf <vrf-name> <ipv6-addr> <ipv6-netmask>";
        description
          "Choose a particular BGP instance.
           clear BGP prefix version.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device-group/ncs:ned-id/ncs:rpc" {
    container rpc-clear-bgp-instance-version-afi-safi-vrf-ipv6-addr-ipv6-netmask {
      tailf:ncs-device-type "netconf";
      tailf:display-when "/ncs:devices/ncs:device[ncs:name=current()/../../../ncs:member]/ncs:module[ncs:name='Cisco-IOS-XR-ipv4-bgp-act']";
      tailf:action clear-bgp-instance-version-afi-safi-vrf-ipv6-addr-ipv6-netmask {
        tailf:actionpoint ncsproxy {
          tailf:internal;
        }
        csc:xr-task "bgp";
        csc:cli-command "clear bgp instance <instance-name> version <afi-safi-name> vrf <vrf-name> <ipv6-addr> <ipv6-netmask>";
        description
          "Choose a particular BGP instance.
           clear BGP prefix version.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device/ncs:rpc" {
    container rpc-clear-bgp-instance-version-afi-safi-rd-ipv6-prefix {
      tailf:ncs-device-type "netconf";
      tailf:display-when "not(../../ncs:module) or ../../ncs:module[ncs:name='Cisco-IOS-XR-ipv4-bgp-act']";
      tailf:action clear-bgp-instance-version-afi-safi-rd-ipv6-prefix {
        tailf:actionpoint ncsproxy {
          tailf:internal;
        }
        csc:xr-task "bgp";
        csc:cli-command "clear bgp instance <instance-name> version <afi-safi-name> rd <rd> <ipv6-prefix>";
        description
          "Choose a particular BGP instance.
           clear BGP prefix version.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ipv6-prefix {
            mandatory true;
            type inet:ipv6-prefix;
            description
              "IPv6 network and masklength";
          }
        }
      }
    }
  }
  augment "/ncs:devices/ncs:device-group/ncs:ned-id/ncs:rpc" {
    container rpc-clear-bgp-instance-version-afi-safi-rd-ipv6-prefix {
      tailf:ncs-device-type "netconf";
      tailf:display-when "/ncs:devices/ncs:device[ncs:name=current()/../../../ncs:member]/ncs:module[ncs:name='Cisco-IOS-XR-ipv4-bgp-act']";
      tailf:action clear-bgp-instance-version-afi-safi-rd-ipv6-prefix {
        tailf:actionpoint ncsproxy {
          tailf:internal;
        }
        csc:xr-task "bgp";
        csc:cli-command "clear bgp instance <instance-name> version <afi-safi-name> rd <rd> <ipv6-prefix>";
        description
          "Choose a particular BGP instance.
           clear BGP prefix version.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ipv6-prefix {
            mandatory true;
            type inet:ipv6-prefix;
            description
              "IPv6 network and masklength";
          }
        }
      }
    }
  }
  augment "/ncs:devices/ncs:device/ncs:rpc" {
    container rpc-clear-bgp-instance-version-afi-safi-rd-ipv6-addr {
      tailf:ncs-device-type "netconf";
      tailf:display-when "not(../../ncs:module) or ../../ncs:module[ncs:name='Cisco-IOS-XR-ipv4-bgp-act']";
      tailf:action clear-bgp-instance-version-afi-safi-rd-ipv6-addr {
        tailf:actionpoint ncsproxy {
          tailf:internal;
        }
        csc:xr-task "bgp";
        csc:cli-command "clear bgp instance <instance-name> version <afi-safi-name> rd <rd> <ipv6-addr>";
        description
          "Choose a particular BGP instance.
           clear BGP prefix version.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ipv6-addr {
            mandatory true;
            type inet:ipv6-address;
            description
              "IPv6 network";
          }
        }
      }
    }
  }
  augment "/ncs:devices/ncs:device-group/ncs:ned-id/ncs:rpc" {
    container rpc-clear-bgp-instance-version-afi-safi-rd-ipv6-addr {
      tailf:ncs-device-type "netconf";
      tailf:display-when "/ncs:devices/ncs:device[ncs:name=current()/../../../ncs:member]/ncs:module[ncs:name='Cisco-IOS-XR-ipv4-bgp-act']";
      tailf:action clear-bgp-instance-version-afi-safi-rd-ipv6-addr {
        tailf:actionpoint ncsproxy {
          tailf:internal;
        }
        csc:xr-task "bgp";
        csc:cli-command "clear bgp instance <instance-name> version <afi-safi-name> rd <rd> <ipv6-addr>";
        description
          "Choose a particular BGP instance.
           clear BGP prefix version.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ipv6-addr {
            mandatory true;
            type inet:ipv6-address;
            description
              "IPv6 network";
          }
        }
      }
    }
  }
  augment "/ncs:devices/ncs:device/ncs:rpc" {
    container rpc-clear-bgp-instance-version-afi-safi-rd-ipv6-addr-ipv6-netmask {
      tailf:ncs-device-type "netconf";
      tailf:display-when "not(../../ncs:module) or ../../ncs:module[ncs:name='Cisco-IOS-XR-ipv4-bgp-act']";
      tailf:action clear-bgp-instance-version-afi-safi-rd-ipv6-addr-ipv6-netmask {
        tailf:actionpoint ncsproxy {
          tailf:internal;
        }
        csc:xr-task "bgp";
        csc:cli-command "clear bgp instance <instance-name> version <afi-safi-name> rd <rd> <ipv6-addr> <ipv6-netmask>";
        description
          "Choose a particular BGP instance.
           clear BGP prefix version.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device-group/ncs:ned-id/ncs:rpc" {
    container rpc-clear-bgp-instance-version-afi-safi-rd-ipv6-addr-ipv6-netmask {
      tailf:ncs-device-type "netconf";
      tailf:display-when "/ncs:devices/ncs:device[ncs:name=current()/../../../ncs:member]/ncs:module[ncs:name='Cisco-IOS-XR-ipv4-bgp-act']";
      tailf:action clear-bgp-instance-version-afi-safi-rd-ipv6-addr-ipv6-netmask {
        tailf:actionpoint ncsproxy {
          tailf:internal;
        }
        csc:xr-task "bgp";
        csc:cli-command "clear bgp instance <instance-name> version <afi-safi-name> rd <rd> <ipv6-addr> <ipv6-netmask>";
        description
          "Choose a particular BGP instance.
           clear BGP prefix version.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device/ncs:rpc" {
    container rpc-clear-bgp-instance-version-afi-safi-vrf-ipv4-addr-ipv4-mask {
      tailf:ncs-device-type "netconf";
      tailf:display-when "not(../../ncs:module) or ../../ncs:module[ncs:name='Cisco-IOS-XR-ipv4-bgp-act']";
      tailf:action clear-bgp-instance-version-afi-safi-vrf-ipv4-addr-ipv4-mask {
        tailf:actionpoint ncsproxy {
          tailf:internal;
        }
        csc:xr-task "bgp";
        csc:cli-command "clear bgp instance <instance-name> version <afi-safi-name> vrf <vrf-name> <ipv4-addr> <ipv4-mask>";
        description
          "Choose a particular BGP instance.
           clear BGP prefix version.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device-group/ncs:ned-id/ncs:rpc" {
    container rpc-clear-bgp-instance-version-afi-safi-vrf-ipv4-addr-ipv4-mask {
      tailf:ncs-device-type "netconf";
      tailf:display-when "/ncs:devices/ncs:device[ncs:name=current()/../../../ncs:member]/ncs:module[ncs:name='Cisco-IOS-XR-ipv4-bgp-act']";
      tailf:action clear-bgp-instance-version-afi-safi-vrf-ipv4-addr-ipv4-mask {
        tailf:actionpoint ncsproxy {
          tailf:internal;
        }
        csc:xr-task "bgp";
        csc:cli-command "clear bgp instance <instance-name> version <afi-safi-name> vrf <vrf-name> <ipv4-addr> <ipv4-mask>";
        description
          "Choose a particular BGP instance.
           clear BGP prefix version.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device/ncs:rpc" {
    container rpc-clear-bgp-instance-version-afi-safi-rd-ipv4-addr-ipv4-mask {
      tailf:ncs-device-type "netconf";
      tailf:display-when "not(../../ncs:module) or ../../ncs:module[ncs:name='Cisco-IOS-XR-ipv4-bgp-act']";
      tailf:action clear-bgp-instance-version-afi-safi-rd-ipv4-addr-ipv4-mask {
        tailf:actionpoint ncsproxy {
          tailf:internal;
        }
        csc:xr-task "bgp";
        csc:cli-command "clear bgp instance <instance-name> version <afi-safi-name> rd <rd> <ipv4-addr> <ipv4-mask>";
        description
          "Choose a particular BGP instance.
           clear BGP prefix version.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device-group/ncs:ned-id/ncs:rpc" {
    container rpc-clear-bgp-instance-version-afi-safi-rd-ipv4-addr-ipv4-mask {
      tailf:ncs-device-type "netconf";
      tailf:display-when "/ncs:devices/ncs:device[ncs:name=current()/../../../ncs:member]/ncs:module[ncs:name='Cisco-IOS-XR-ipv4-bgp-act']";
      tailf:action clear-bgp-instance-version-afi-safi-rd-ipv4-addr-ipv4-mask {
        tailf:actionpoint ncsproxy {
          tailf:internal;
        }
        csc:xr-task "bgp";
        csc:cli-command "clear bgp instance <instance-name> version <afi-safi-name> rd <rd> <ipv4-addr> <ipv4-mask>";
        description
          "Choose a particular BGP instance.
           clear BGP prefix version.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device/ncs:rpc" {
    container rpc-clear-bgp-instance-version-afi-safi-vrf-ipv4-prefix {
      tailf:ncs-device-type "netconf";
      tailf:display-when "not(../../ncs:module) or ../../ncs:module[ncs:name='Cisco-IOS-XR-ipv4-bgp-act']";
      tailf:action clear-bgp-instance-version-afi-safi-vrf-ipv4-prefix {
        tailf:actionpoint ncsproxy {
          tailf:internal;
        }
        csc:xr-task "bgp";
        csc:cli-command "clear bgp instance <instance-name> version <afi-safi-name> vrf <vrf-name> <ipv4-prefix>";
        description
          "Choose a particular BGP instance.
           clear BGP prefix version.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
          leaf ipv4-prefix {
            mandatory true;
            type inet:ipv4-prefix;
            description
              "VPN Fspec Prefix";
          }
        }
      }
    }
  }
  augment "/ncs:devices/ncs:device-group/ncs:ned-id/ncs:rpc" {
    container rpc-clear-bgp-instance-version-afi-safi-vrf-ipv4-prefix {
      tailf:ncs-device-type "netconf";
      tailf:display-when "/ncs:devices/ncs:device[ncs:name=current()/../../../ncs:member]/ncs:module[ncs:name='Cisco-IOS-XR-ipv4-bgp-act']";
      tailf:action clear-bgp-instance-version-afi-safi-vrf-ipv4-prefix {
        tailf:actionpoint ncsproxy {
          tailf:internal;
        }
        csc:xr-task "bgp";
        csc:cli-command "clear bgp instance <instance-name> version <afi-safi-name> vrf <vrf-name> <ipv4-prefix>";
        description
          "Choose a particular BGP instance.
           clear BGP prefix version.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
          leaf ipv4-prefix {
            mandatory true;
            type inet:ipv4-prefix;
            description
              "VPN Fspec Prefix";
          }
        }
      }
    }
  }
  augment "/ncs:devices/ncs:device/ncs:rpc" {
    container rpc-clear-bgp-instance-version-afi-safi-mp2mp-ipv4-prefix {
      tailf:ncs-device-type "netconf";
      tailf:display-when "not(../../ncs:module) or ../../ncs:module[ncs:name='Cisco-IOS-XR-ipv4-bgp-act']";
      tailf:action clear-bgp-instance-version-afi-safi-mp2mp-ipv4-prefix {
        tailf:actionpoint ncsproxy {
          tailf:internal;
        }
        csc:xr-task "bgp";
        csc:cli-command "clear bgp instance <instance-name> version <afi-safi-name> mp2mp <mp2mp> <ipv4-prefix>";
        description
          "Choose a particular BGP instance.
           clear BGP prefix version.
           Display routes for a specified Xconnect group:MP2MP.
          ";
        input {
          leaf instance-name {
            mandatory true;
            type instance-name;
            description
              "instance name or all";
          }
          leaf afi-safi-name {
            mandatory true;
            type afi-safi-type;
            description
              "AFI and SAFI";
          }
          leaf mp2mp {
            mandatory true;
            type string;
            description
              "Xconnect Group:mp2mp";
          }
          leaf ipv4-prefix {
            mandatory true;
            type inet:ipv4-prefix;
            description
              "L2VPN VPWS Prefix";
          }
        }
      }
    }
  }
  augment "/ncs:devices/ncs:device-group/ncs:ned-id/ncs:rpc" {
    container rpc-clear-bgp-instance-version-afi-safi-mp2mp-ipv4-prefix {
      tailf:ncs-device-type "netconf";
      tailf:display-when "/ncs:devices/ncs:device[ncs:name=current()/../../../ncs:member]/ncs:module[ncs:name='Cisco-IOS-XR-ipv4-bgp-act']";
      tailf:action clear-bgp-instance-version-afi-safi-mp2mp-ipv4-prefix {
        tailf:actionpoint ncsproxy {
          tailf:internal;
        }
        csc:xr-task "bgp";
        csc:cli-command "clear bgp instance <instance-name> version <afi-safi-name> mp2mp <mp2mp> <ipv4-prefix>";
        description
          "Choose a particular BGP instance.
           clear BGP prefix version.
           Display routes for a specified Xconnect group:MP2MP.
          ";
        input {
          leaf instance-name {
            mandatory true;
            type instance-name;
            description
              "instance name or all";
          }
          leaf afi-safi-name {
            mandatory true;
            type afi-safi-type;
            description
              "AFI and SAFI";
          }
          leaf mp2mp {
            mandatory true;
            type string;
            description
              "Xconnect Group:mp2mp";
          }
          leaf ipv4-prefix {
            mandatory true;
            type inet:ipv4-prefix;
            description
              "L2VPN VPWS Prefix";
          }
        }
      }
    }
  }
  augment "/ncs:devices/ncs:device/ncs:rpc" {
    container rpc-clear-bgp-instance-version-afi-safi-rd-ipv4-prefix {
      tailf:ncs-device-type "netconf";
      tailf:display-when "not(../../ncs:module) or ../../ncs:module[ncs:name='Cisco-IOS-XR-ipv4-bgp-act']";
      tailf:action clear-bgp-instance-version-afi-safi-rd-ipv4-prefix {
        tailf:actionpoint ncsproxy {
          tailf:internal;
        }
        csc:xr-task "bgp";
        csc:cli-command "clear bgp instance <instance-name> version <afi-safi-name> rd <rd> <ipv4-prefix>";
        description
          "Choose a particular BGP instance.
           clear BGP prefix version.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ipv4-prefix {
            mandatory true;
            type inet:ipv4-prefix;
            description
              "L2VPN EVPN Prefix";
          }
        }
      }
    }
  }
  augment "/ncs:devices/ncs:device-group/ncs:ned-id/ncs:rpc" {
    container rpc-clear-bgp-instance-version-afi-safi-rd-ipv4-prefix {
      tailf:ncs-device-type "netconf";
      tailf:display-when "/ncs:devices/ncs:device[ncs:name=current()/../../../ncs:member]/ncs:module[ncs:name='Cisco-IOS-XR-ipv4-bgp-act']";
      tailf:action clear-bgp-instance-version-afi-safi-rd-ipv4-prefix {
        tailf:actionpoint ncsproxy {
          tailf:internal;
        }
        csc:xr-task "bgp";
        csc:cli-command "clear bgp instance <instance-name> version <afi-safi-name> rd <rd> <ipv4-prefix>";
        description
          "Choose a particular BGP instance.
           clear BGP prefix version.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ipv4-prefix {
            mandatory true;
            type inet:ipv4-prefix;
            description
              "L2VPN EVPN Prefix";
          }
        }
      }
    }
  }
  augment "/ncs:devices/ncs:device/ncs:rpc" {
    container rpc-clear-bgp-instance-version-afi-safi-bridge-domain-ipv4-prefix {
      tailf:ncs-device-type "netconf";
      tailf:display-when "not(../../ncs:module) or ../../ncs:module[ncs:name='Cisco-IOS-XR-ipv4-bgp-act']";
      tailf:action clear-bgp-instance-version-afi-safi-bridge-domain-ipv4-prefix {
        tailf:actionpoint ncsproxy {
          tailf:internal;
        }
        csc:xr-task "bgp";
        csc:cli-command "clear bgp instance <instance-name> version <afi-safi-name> bridge-domain <bridge-domain-name> <ipv4-prefix>";
        description
          "Choose a particular BGP instance.
           clear BGP prefix version.
           Display routes for a specified Bridge Domain.
          ";
        input {
          leaf instance-name {
            mandatory true;
            type instance-name;
            description
              "instance name or all";
          }
          leaf afi-safi-name {
            mandatory true;
            type afi-safi-type;
            description
              "AFI and SAFI";
          }
          leaf bridge-domain-name {
            mandatory true;
            type string;
            description
              "Bridge Domain";
          }
          leaf ipv4-prefix {
            mandatory true;
            type inet:ipv4-prefix;
            description
              "L2VPN EVPN Prefix";
          }
        }
      }
    }
  }
  augment "/ncs:devices/ncs:device-group/ncs:ned-id/ncs:rpc" {
    container rpc-clear-bgp-instance-version-afi-safi-bridge-domain-ipv4-prefix {
      tailf:ncs-device-type "netconf";
      tailf:display-when "/ncs:devices/ncs:device[ncs:name=current()/../../../ncs:member]/ncs:module[ncs:name='Cisco-IOS-XR-ipv4-bgp-act']";
      tailf:action clear-bgp-instance-version-afi-safi-bridge-domain-ipv4-prefix {
        tailf:actionpoint ncsproxy {
          tailf:internal;
        }
        csc:xr-task "bgp";
        csc:cli-command "clear bgp instance <instance-name> version <afi-safi-name> bridge-domain <bridge-domain-name> <ipv4-prefix>";
        description
          "Choose a particular BGP instance.
           clear BGP prefix version.
           Display routes for a specified Bridge Domain.
          ";
        input {
          leaf instance-name {
            mandatory true;
            type instance-name;
            description
              "instance name or all";
          }
          leaf afi-safi-name {
            mandatory true;
            type afi-safi-type;
            description
              "AFI and SAFI";
          }
          leaf bridge-domain-name {
            mandatory true;
            type string;
            description
              "Bridge Domain";
          }
          leaf ipv4-prefix {
            mandatory true;
            type inet:ipv4-prefix;
            description
              "L2VPN EVPN Prefix";
          }
        }
      }
    }
  }
  augment "/ncs:devices/ncs:device/ncs:rpc" {
    container rpc-clear-bgp-instance-version-afi-safi-sr-policy-prefix {
      tailf:ncs-device-type "netconf";
      tailf:display-when "not(../../ncs:module) or ../../ncs:module[ncs:name='Cisco-IOS-XR-ipv4-bgp-act']";
      tailf:action clear-bgp-instance-version-afi-safi-sr-policy-prefix {
        tailf:actionpoint ncsproxy {
          tailf:internal;
        }
        csc:xr-task "bgp";
        csc:cli-command "clear bgp instance <instance-name> version <afi-safi-name> <sr-policy-prefix>";
        description
          "Choose a particular BGP instance.
           clear BGP prefix version.
          ";
        input {
          leaf instance-name {
            mandatory true;
            type instance-name;
            description
              "instance name or all";
          }
          leaf afi-safi-name {
            mandatory true;
            type afi-safi-type;
            description
              "AFI and SAFI";
          }
          leaf sr-policy-prefix {
            mandatory true;
            type string;
            description
              "SR Policy prefix";
          }
        }
      }
    }
  }
  augment "/ncs:devices/ncs:device-group/ncs:ned-id/ncs:rpc" {
    container rpc-clear-bgp-instance-version-afi-safi-sr-policy-prefix {
      tailf:ncs-device-type "netconf";
      tailf:display-when "/ncs:devices/ncs:device[ncs:name=current()/../../../ncs:member]/ncs:module[ncs:name='Cisco-IOS-XR-ipv4-bgp-act']";
      tailf:action clear-bgp-instance-version-afi-safi-sr-policy-prefix {
        tailf:actionpoint ncsproxy {
          tailf:internal;
        }
        csc:xr-task "bgp";
        csc:cli-command "clear bgp instance <instance-name> version <afi-safi-name> <sr-policy-prefix>";
        description
          "Choose a particular BGP instance.
           clear BGP prefix version.
          ";
        input {
          leaf instance-name {
            mandatory true;
            type instance-name;
            description
              "instance name or all";
          }
          leaf afi-safi-name {
            mandatory true;
            type afi-safi-type;
            description
              "AFI and SAFI";
          }
          leaf sr-policy-prefix {
            mandatory true;
            type string;
            description
              "SR Policy prefix";
          }
        }
      }
    }
  }
  augment "/ncs:devices/ncs:device/ncs:rpc" {
    container rpc-clear-bgp-instance-version-afi-safi {
      tailf:ncs-device-type "netconf";
      tailf:display-when "not(../../ncs:module) or ../../ncs:module[ncs:name='Cisco-IOS-XR-ipv4-bgp-act']";
      tailf:action clear-bgp-instance-version-afi-safi {
        tailf:actionpoint ncsproxy {
          tailf:internal;
        }
        csc:xr-task "bgp";
        csc:cli-command "clear bgp instance <instance-name> version <afi-safi-name>";
        description
          "Choose a particular BGP instance.
           clear BGP prefix version.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-version-afi-safi {
      tailf:ncs-device-type "netconf";
      tailf:display-when "/ncs:devices/ncs:device[ncs:name=current()/../../../ncs:member]/ncs:module[ncs:name='Cisco-IOS-XR-ipv4-bgp-act']";
      tailf:action clear-bgp-instance-version-afi-safi {
        tailf:actionpoint ncsproxy {
          tailf:internal;
        }
        csc:xr-task "bgp";
        csc:cli-command "clear bgp instance <instance-name> version <afi-safi-name>";
        description
          "Choose a particular BGP instance.
           clear BGP prefix version.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device/ncs:rpc" {
    container rpc-clear-bgp-instance-version-afi-safi-vrf {
      tailf:ncs-device-type "netconf";
      tailf:display-when "not(../../ncs:module) or ../../ncs:module[ncs:name='Cisco-IOS-XR-ipv4-bgp-act']";
      tailf:action clear-bgp-instance-version-afi-safi-vrf {
        tailf:actionpoint ncsproxy {
          tailf:internal;
        }
        csc:xr-task "bgp";
        csc:cli-command "clear bgp instance <instance-name> version <afi-safi-name> vrf <vrf-name>";
        description
          "Choose a particular BGP instance.
           clear BGP prefix version.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
        }
      }
    }
  }
  augment "/ncs:devices/ncs:device-group/ncs:ned-id/ncs:rpc" {
    container rpc-clear-bgp-instance-version-afi-safi-vrf {
      tailf:ncs-device-type "netconf";
      tailf:display-when "/ncs:devices/ncs:device[ncs:name=current()/../../../ncs:member]/ncs:module[ncs:name='Cisco-IOS-XR-ipv4-bgp-act']";
      tailf:action clear-bgp-instance-version-afi-safi-vrf {
        tailf:actionpoint ncsproxy {
          tailf:internal;
        }
        csc:xr-task "bgp";
        csc:cli-command "clear bgp instance <instance-name> version <afi-safi-name> vrf <vrf-name>";
        description
          "Choose a particular BGP instance.
           clear BGP prefix version.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
        }
      }
    }
  }
  augment "/ncs:devices/ncs:device/ncs:rpc" {
    container rpc-clear-bgp-instance-version-afi-safi-rd {
      tailf:ncs-device-type "netconf";
      tailf:display-when "not(../../ncs:module) or ../../ncs:module[ncs:name='Cisco-IOS-XR-ipv4-bgp-act']";
      tailf:action clear-bgp-instance-version-afi-safi-rd {
        tailf:actionpoint ncsproxy {
          tailf:internal;
        }
        csc:xr-task "bgp";
        csc:cli-command "clear bgp instance <instance-name> version <afi-safi-name> rd <rd>";
        description
          "Choose a particular BGP instance.
           clear BGP prefix version.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
        }
      }
    }
  }
  augment "/ncs:devices/ncs:device-group/ncs:ned-id/ncs:rpc" {
    container rpc-clear-bgp-instance-version-afi-safi-rd {
      tailf:ncs-device-type "netconf";
      tailf:display-when "/ncs:devices/ncs:device[ncs:name=current()/../../../ncs:member]/ncs:module[ncs:name='Cisco-IOS-XR-ipv4-bgp-act']";
      tailf:action clear-bgp-instance-version-afi-safi-rd {
        tailf:actionpoint ncsproxy {
          tailf:internal;
        }
        csc:xr-task "bgp";
        csc:cli-command "clear bgp instance <instance-name> version <afi-safi-name> rd <rd>";
        description
          "Choose a particular BGP instance.
           clear BGP prefix version.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
        }
      }
    }
  }
  augment "/ncs:devices/ncs:device/ncs:rpc" {
    container rpc-clear-bgp-instance-version-afi-safi-ipv6-prefix {
      tailf:ncs-device-type "netconf";
      tailf:display-when "not(../../ncs:module) or ../../ncs:module[ncs:name='Cisco-IOS-XR-ipv4-bgp-act']";
      tailf:action clear-bgp-instance-version-afi-safi-ipv6-prefix {
        tailf:actionpoint ncsproxy {
          tailf:internal;
        }
        csc:xr-task "bgp";
        csc:cli-command "clear bgp instance <instance-name> version <afi-safi-name> <ipv6-prefix>";
        description
          "Choose a particular BGP instance.
           clear BGP prefix version.
          ";
        input {
          leaf instance-name {
            mandatory true;
            type instance-name;
            description
              "instance name or all";
          }
          leaf afi-safi-name {
            mandatory true;
            type afi-safi-type;
            description
              "AFI and SAFI";
          }
          leaf ipv6-prefix {
            mandatory true;
            type inet:ipv6-prefix;
            description
              "IPv6 network and masklength";
          }
        }
      }
    }
  }
  augment "/ncs:devices/ncs:device-group/ncs:ned-id/ncs:rpc" {
    container rpc-clear-bgp-instance-version-afi-safi-ipv6-prefix {
      tailf:ncs-device-type "netconf";
      tailf:display-when "/ncs:devices/ncs:device[ncs:name=current()/../../../ncs:member]/ncs:module[ncs:name='Cisco-IOS-XR-ipv4-bgp-act']";
      tailf:action clear-bgp-instance-version-afi-safi-ipv6-prefix {
        tailf:actionpoint ncsproxy {
          tailf:internal;
        }
        csc:xr-task "bgp";
        csc:cli-command "clear bgp instance <instance-name> version <afi-safi-name> <ipv6-prefix>";
        description
          "Choose a particular BGP instance.
           clear BGP prefix version.
          ";
        input {
          leaf instance-name {
            mandatory true;
            type instance-name;
            description
              "instance name or all";
          }
          leaf afi-safi-name {
            mandatory true;
            type afi-safi-type;
            description
              "AFI and SAFI";
          }
          leaf ipv6-prefix {
            mandatory true;
            type inet:ipv6-prefix;
            description
              "IPv6 network and masklength";
          }
        }
      }
    }
  }
  augment "/ncs:devices/ncs:device/ncs:rpc" {
    container rpc-clear-bgp-instance-version-afi-safi-ipv6-addr {
      tailf:ncs-device-type "netconf";
      tailf:display-when "not(../../ncs:module) or ../../ncs:module[ncs:name='Cisco-IOS-XR-ipv4-bgp-act']";
      tailf:action clear-bgp-instance-version-afi-safi-ipv6-addr {
        tailf:actionpoint ncsproxy {
          tailf:internal;
        }
        csc:xr-task "bgp";
        csc:cli-command "clear bgp instance <instance-name> version <afi-safi-name> <ipv6-addr>";
        description
          "Choose a particular BGP instance.
           clear BGP prefix version.
          ";
        input {
          leaf instance-name {
            mandatory true;
            type instance-name;
            description
              "instance name or all";
          }
          leaf afi-safi-name {
            mandatory true;
            type afi-safi-type;
            description
              "AFI and SAFI";
          }
          leaf ipv6-addr {
            mandatory true;
            type inet:ipv6-address;
            description
              "IPv6 network";
          }
        }
      }
    }
  }
  augment "/ncs:devices/ncs:device-group/ncs:ned-id/ncs:rpc" {
    container rpc-clear-bgp-instance-version-afi-safi-ipv6-addr {
      tailf:ncs-device-type "netconf";
      tailf:display-when "/ncs:devices/ncs:device[ncs:name=current()/../../../ncs:member]/ncs:module[ncs:name='Cisco-IOS-XR-ipv4-bgp-act']";
      tailf:action clear-bgp-instance-version-afi-safi-ipv6-addr {
        tailf:actionpoint ncsproxy {
          tailf:internal;
        }
        csc:xr-task "bgp";
        csc:cli-command "clear bgp instance <instance-name> version <afi-safi-name> <ipv6-addr>";
        description
          "Choose a particular BGP instance.
           clear BGP prefix version.
          ";
        input {
          leaf instance-name {
            mandatory true;
            type instance-name;
            description
              "instance name or all";
          }
          leaf afi-safi-name {
            mandatory true;
            type afi-safi-type;
            description
              "AFI and SAFI";
          }
          leaf ipv6-addr {
            mandatory true;
            type inet:ipv6-address;
            description
              "IPv6 network";
          }
        }
      }
    }
  }
  augment "/ncs:devices/ncs:device/ncs:rpc" {
    container rpc-clear-bgp-instance-version-afi-safi-ipv6-addr-ipv6-netmask {
      tailf:ncs-device-type "netconf";
      tailf:display-when "not(../../ncs:module) or ../../ncs:module[ncs:name='Cisco-IOS-XR-ipv4-bgp-act']";
      tailf:action clear-bgp-instance-version-afi-safi-ipv6-addr-ipv6-netmask {
        tailf:actionpoint ncsproxy {
          tailf:internal;
        }
        csc:xr-task "bgp";
        csc:cli-command "clear bgp instance <instance-name> version <afi-safi-name> <ipv6-addr> <ipv6-netmask>";
        description
          "Choose a particular BGP instance.
           clear BGP prefix version.
          ";
        input {
          leaf instance-name {
            mandatory true;
            type instance-name;
            description
              "instance name or all";
          }
          leaf afi-safi-name {
            mandatory true;
            type afi-safi-type;
            description
              "AFI and SAFI";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device-group/ncs:ned-id/ncs:rpc" {
    container rpc-clear-bgp-instance-version-afi-safi-ipv6-addr-ipv6-netmask {
      tailf:ncs-device-type "netconf";
      tailf:display-when "/ncs:devices/ncs:device[ncs:name=current()/../../../ncs:member]/ncs:module[ncs:name='Cisco-IOS-XR-ipv4-bgp-act']";
      tailf:action clear-bgp-instance-version-afi-safi-ipv6-addr-ipv6-netmask {
        tailf:actionpoint ncsproxy {
          tailf:internal;
        }
        csc:xr-task "bgp";
        csc:cli-command "clear bgp instance <instance-name> version <afi-safi-name> <ipv6-addr> <ipv6-netmask>";
        description
          "Choose a particular BGP instance.
           clear BGP prefix version.
          ";
        input {
          leaf instance-name {
            mandatory true;
            type instance-name;
            description
              "instance name or all";
          }
          leaf afi-safi-name {
            mandatory true;
            type afi-safi-type;
            description
              "AFI and SAFI";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device/ncs:rpc" {
    container rpc-clear-bgp-instance-version-afi-safi-ipv4-tunnel-network {
      tailf:ncs-device-type "netconf";
      tailf:display-when "not(../../ncs:module) or ../../ncs:module[ncs:name='Cisco-IOS-XR-ipv4-bgp-act']";
      tailf:action clear-bgp-instance-version-afi-safi-ipv4-tunnel-network {
        tailf:actionpoint ncsproxy {
          tailf:internal;
        }
        csc:xr-task "bgp";
        csc:cli-command "clear bgp instance <instance-name> version <afi-safi-name> <ipv4-tunnel-network>";
        description
          "Choose a particular BGP instance.
           clear BGP prefix version.
          ";
        input {
          leaf instance-name {
            mandatory true;
            type instance-name;
            description
              "instance name or all";
          }
          leaf afi-safi-name {
            mandatory true;
            type afi-safi-type;
            description
              "AFI and SAFI";
          }
          leaf ipv4-tunnel-network {
            mandatory true;
            type string;
            description
              "IPv4 Tunnel network <Tunnel-ID>:<IPv4 Address>";
          }
        }
      }
    }
  }
  augment "/ncs:devices/ncs:device-group/ncs:ned-id/ncs:rpc" {
    container rpc-clear-bgp-instance-version-afi-safi-ipv4-tunnel-network {
      tailf:ncs-device-type "netconf";
      tailf:display-when "/ncs:devices/ncs:device[ncs:name=current()/../../../ncs:member]/ncs:module[ncs:name='Cisco-IOS-XR-ipv4-bgp-act']";
      tailf:action clear-bgp-instance-version-afi-safi-ipv4-tunnel-network {
        tailf:actionpoint ncsproxy {
          tailf:internal;
        }
        csc:xr-task "bgp";
        csc:cli-command "clear bgp instance <instance-name> version <afi-safi-name> <ipv4-tunnel-network>";
        description
          "Choose a particular BGP instance.
           clear BGP prefix version.
          ";
        input {
          leaf instance-name {
            mandatory true;
            type instance-name;
            description
              "instance name or all";
          }
          leaf afi-safi-name {
            mandatory true;
            type afi-safi-type;
            description
              "AFI and SAFI";
          }
          leaf ipv4-tunnel-network {
            mandatory true;
            type string;
            description
              "IPv4 Tunnel network <Tunnel-ID>:<IPv4 Address>";
          }
        }
      }
    }
  }
  augment "/ncs:devices/ncs:device/ncs:rpc" {
    container rpc-clear-bgp-instance-version-afi-safi-rt-constraint-network {
      tailf:ncs-device-type "netconf";
      tailf:display-when "not(../../ncs:module) or ../../ncs:module[ncs:name='Cisco-IOS-XR-ipv4-bgp-act']";
      tailf:action clear-bgp-instance-version-afi-safi-rt-constraint-network {
        tailf:actionpoint ncsproxy {
          tailf:internal;
        }
        csc:xr-task "bgp";
        csc:cli-command "clear bgp instance <instance-name> version <afi-safi-name> <rt-constraint-network>";
        description
          "Choose a particular BGP instance.
           clear BGP prefix version.
          ";
        input {
          leaf instance-name {
            mandatory true;
            type instance-name;
            description
              "instance name or all";
          }
          leaf afi-safi-name {
            mandatory true;
            type afi-safi-type;
            description
              "AFI and SAFI";
          }
          leaf rt-constraint-network {
            mandatory true;
            type string;
            description
              "RT-Constraint network";
          }
        }
      }
    }
  }
  augment "/ncs:devices/ncs:device-group/ncs:ned-id/ncs:rpc" {
    container rpc-clear-bgp-instance-version-afi-safi-rt-constraint-network {
      tailf:ncs-device-type "netconf";
      tailf:display-when "/ncs:devices/ncs:device[ncs:name=current()/../../../ncs:member]/ncs:module[ncs:name='Cisco-IOS-XR-ipv4-bgp-act']";
      tailf:action clear-bgp-instance-version-afi-safi-rt-constraint-network {
        tailf:actionpoint ncsproxy {
          tailf:internal;
        }
        csc:xr-task "bgp";
        csc:cli-command "clear bgp instance <instance-name> version <afi-safi-name> <rt-constraint-network>";
        description
          "Choose a particular BGP instance.
           clear BGP prefix version.
          ";
        input {
          leaf instance-name {
            mandatory true;
            type instance-name;
            description
              "instance name or all";
          }
          leaf afi-safi-name {
            mandatory true;
            type afi-safi-type;
            description
              "AFI and SAFI";
          }
          leaf rt-constraint-network {
            mandatory true;
            type string;
            description
              "RT-Constraint network";
          }
        }
      }
    }
  }
  augment "/ncs:devices/ncs:device/ncs:rpc" {
    container rpc-clear-bgp-instance-version-afi-safi-vrf-network {
      tailf:ncs-device-type "netconf";
      tailf:display-when "not(../../ncs:module) or ../../ncs:module[ncs:name='Cisco-IOS-XR-ipv4-bgp-act']";
      tailf:action clear-bgp-instance-version-afi-safi-vrf-network {
        tailf:actionpoint ncsproxy {
          tailf:internal;
        }
        csc:xr-task "bgp";
        csc:cli-command "clear bgp instance <instance-name> version <afi-safi-name> vrf <vrf-name> <network>";
        description
          "Choose a particular BGP instance.
           clear BGP prefix version.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
          leaf network {
            mandatory true;
            type string;
            description
              "Address family modifier specific network";
          }
        }
      }
    }
  }
  augment "/ncs:devices/ncs:device-group/ncs:ned-id/ncs:rpc" {
    container rpc-clear-bgp-instance-version-afi-safi-vrf-network {
      tailf:ncs-device-type "netconf";
      tailf:display-when "/ncs:devices/ncs:device[ncs:name=current()/../../../ncs:member]/ncs:module[ncs:name='Cisco-IOS-XR-ipv4-bgp-act']";
      tailf:action clear-bgp-instance-version-afi-safi-vrf-network {
        tailf:actionpoint ncsproxy {
          tailf:internal;
        }
        csc:xr-task "bgp";
        csc:cli-command "clear bgp instance <instance-name> version <afi-safi-name> vrf <vrf-name> <network>";
        description
          "Choose a particular BGP instance.
           clear BGP prefix version.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
          leaf network {
            mandatory true;
            type string;
            description
              "Address family modifier specific network";
          }
        }
      }
    }
  }
  augment "/ncs:devices/ncs:device/ncs:rpc" {
    container rpc-clear-bgp-instance-version-afi-safi-rd-network {
      tailf:ncs-device-type "netconf";
      tailf:display-when "not(../../ncs:module) or ../../ncs:module[ncs:name='Cisco-IOS-XR-ipv4-bgp-act']";
      tailf:action clear-bgp-instance-version-afi-safi-rd-network {
        tailf:actionpoint ncsproxy {
          tailf:internal;
        }
        csc:xr-task "bgp";
        csc:cli-command "clear bgp instance <instance-name> version <afi-safi-name> rd <rd> <network>";
        description
          "Choose a particular BGP instance.
           clear BGP prefix version.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf network {
            mandatory true;
            type string;
            description
              "Address family modifier specific network";
          }
        }
      }
    }
  }
  augment "/ncs:devices/ncs:device-group/ncs:ned-id/ncs:rpc" {
    container rpc-clear-bgp-instance-version-afi-safi-rd-network {
      tailf:ncs-device-type "netconf";
      tailf:display-when "/ncs:devices/ncs:device[ncs:name=current()/../../../ncs:member]/ncs:module[ncs:name='Cisco-IOS-XR-ipv4-bgp-act']";
      tailf:action clear-bgp-instance-version-afi-safi-rd-network {
        tailf:actionpoint ncsproxy {
          tailf:internal;
        }
        csc:xr-task "bgp";
        csc:cli-command "clear bgp instance <instance-name> version <afi-safi-name> rd <rd> <network>";
        description
          "Choose a particular BGP instance.
           clear BGP prefix version.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf network {
            mandatory true;
            type string;
            description
              "Address family modifier specific network";
          }
        }
      }
    }
  }
  augment "/ncs:devices/ncs:device/ncs:rpc" {
    container rpc-clear-bgp-instance-version-afi-safi-network {
      tailf:ncs-device-type "netconf";
      tailf:display-when "not(../../ncs:module) or ../../ncs:module[ncs:name='Cisco-IOS-XR-ipv4-bgp-act']";
      tailf:action clear-bgp-instance-version-afi-safi-network {
        tailf:actionpoint ncsproxy {
          tailf:internal;
        }
        csc:xr-task "bgp";
        csc:cli-command "clear bgp instance <instance-name> version <afi-safi-name> <network>";
        description
          "Choose a particular BGP instance.
           clear BGP prefix version.
          ";
        input {
          leaf instance-name {
            mandatory true;
            type instance-name;
            description
              "instance name or all";
          }
          leaf afi-safi-name {
            mandatory true;
            type afi-safi-type;
            description
              "AFI and SAFI";
          }
          leaf network {
            mandatory true;
            type string;
            description
              "Address family modifier specific network";
          }
        }
      }
    }
  }
  augment "/ncs:devices/ncs:device-group/ncs:ned-id/ncs:rpc" {
    container rpc-clear-bgp-instance-version-afi-safi-network {
      tailf:ncs-device-type "netconf";
      tailf:display-when "/ncs:devices/ncs:device[ncs:name=current()/../../../ncs:member]/ncs:module[ncs:name='Cisco-IOS-XR-ipv4-bgp-act']";
      tailf:action clear-bgp-instance-version-afi-safi-network {
        tailf:actionpoint ncsproxy {
          tailf:internal;
        }
        csc:xr-task "bgp";
        csc:cli-command "clear bgp instance <instance-name> version <afi-safi-name> <network>";
        description
          "Choose a particular BGP instance.
           clear BGP prefix version.
          ";
        input {
          leaf instance-name {
            mandatory true;
            type instance-name;
            description
              "instance name or all";
          }
          leaf afi-safi-name {
            mandatory true;
            type afi-safi-type;
            description
              "AFI and SAFI";
          }
          leaf network {
            mandatory true;
            type string;
            description
              "Address family modifier specific network";
          }
        }
      }
    }
  }
  augment "/ncs:devices/ncs:device/ncs:rpc" {
    container rpc-clear-bgp-instance-version-afi-safi-vrf-ipv4-addr {
      tailf:ncs-device-type "netconf";
      tailf:display-when "not(../../ncs:module) or ../../ncs:module[ncs:name='Cisco-IOS-XR-ipv4-bgp-act']";
      tailf:action clear-bgp-instance-version-afi-safi-vrf-ipv4-addr {
        tailf:actionpoint ncsproxy {
          tailf:internal;
        }
        csc:xr-task "bgp";
        csc:cli-command "clear bgp instance <instance-name> version <afi-safi-name> vrf <vrf-name> <ipv4-addr>";
        description
          "Choose a particular BGP instance.
           clear BGP prefix version.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
          leaf ipv4-addr {
            mandatory true;
            type inet:ipv4-address;
            description
              "IPv4 MDT network";
          }
        }
      }
    }
  }
  augment "/ncs:devices/ncs:device-group/ncs:ned-id/ncs:rpc" {
    container rpc-clear-bgp-instance-version-afi-safi-vrf-ipv4-addr {
      tailf:ncs-device-type "netconf";
      tailf:display-when "/ncs:devices/ncs:device[ncs:name=current()/../../../ncs:member]/ncs:module[ncs:name='Cisco-IOS-XR-ipv4-bgp-act']";
      tailf:action clear-bgp-instance-version-afi-safi-vrf-ipv4-addr {
        tailf:actionpoint ncsproxy {
          tailf:internal;
        }
        csc:xr-task "bgp";
        csc:cli-command "clear bgp instance <instance-name> version <afi-safi-name> vrf <vrf-name> <ipv4-addr>";
        description
          "Choose a particular BGP instance.
           clear BGP prefix version.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
          leaf ipv4-addr {
            mandatory true;
            type inet:ipv4-address;
            description
              "IPv4 MDT network";
          }
        }
      }
    }
  }
  augment "/ncs:devices/ncs:device/ncs:rpc" {
    container rpc-clear-bgp-instance-version-afi-safi-rd-ipv4-addr {
      tailf:ncs-device-type "netconf";
      tailf:display-when "not(../../ncs:module) or ../../ncs:module[ncs:name='Cisco-IOS-XR-ipv4-bgp-act']";
      tailf:action clear-bgp-instance-version-afi-safi-rd-ipv4-addr {
        tailf:actionpoint ncsproxy {
          tailf:internal;
        }
        csc:xr-task "bgp";
        csc:cli-command "clear bgp instance <instance-name> version <afi-safi-name> rd <rd> <ipv4-addr>";
        description
          "Choose a particular BGP instance.
           clear BGP prefix version.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ipv4-addr {
            mandatory true;
            type inet:ipv4-address;
            description
              "IPv4 MDT network";
          }
        }
      }
    }
  }
  augment "/ncs:devices/ncs:device-group/ncs:ned-id/ncs:rpc" {
    container rpc-clear-bgp-instance-version-afi-safi-rd-ipv4-addr {
      tailf:ncs-device-type "netconf";
      tailf:display-when "/ncs:devices/ncs:device[ncs:name=current()/../../../ncs:member]/ncs:module[ncs:name='Cisco-IOS-XR-ipv4-bgp-act']";
      tailf:action clear-bgp-instance-version-afi-safi-rd-ipv4-addr {
        tailf:actionpoint ncsproxy {
          tailf:internal;
        }
        csc:xr-task "bgp";
        csc:cli-command "clear bgp instance <instance-name> version <afi-safi-name> rd <rd> <ipv4-addr>";
        description
          "Choose a particular BGP instance.
           clear BGP prefix version.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ipv4-addr {
            mandatory true;
            type inet:ipv4-address;
            description
              "IPv4 MDT network";
          }
        }
      }
    }
  }
  augment "/ncs:devices/ncs:device/ncs:rpc" {
    container rpc-clear-bgp-instance-version-afi-safi-ipv4-prefix {
      tailf:ncs-device-type "netconf";
      tailf:display-when "not(../../ncs:module) or ../../ncs:module[ncs:name='Cisco-IOS-XR-ipv4-bgp-act']";
      tailf:action clear-bgp-instance-version-afi-safi-ipv4-prefix {
        tailf:actionpoint ncsproxy {
          tailf:internal;
        }
        csc:xr-task "bgp";
        csc:cli-command "clear bgp instance <instance-name> version <afi-safi-name> <ipv4-prefix>";
        description
          "Choose a particular BGP instance.
           clear BGP prefix version.
          ";
        input {
          leaf instance-name {
            mandatory true;
            type instance-name;
            description
              "instance name or all";
          }
          leaf afi-safi-name {
            mandatory true;
            type afi-safi-type;
            description
              "AFI and SAFI";
          }
          leaf ipv4-prefix {
            mandatory true;
            type inet:ipv4-prefix;
            description
              "IPv4 network and masklength";
          }
        }
      }
    }
  }
  augment "/ncs:devices/ncs:device-group/ncs:ned-id/ncs:rpc" {
    container rpc-clear-bgp-instance-version-afi-safi-ipv4-prefix {
      tailf:ncs-device-type "netconf";
      tailf:display-when "/ncs:devices/ncs:device[ncs:name=current()/../../../ncs:member]/ncs:module[ncs:name='Cisco-IOS-XR-ipv4-bgp-act']";
      tailf:action clear-bgp-instance-version-afi-safi-ipv4-prefix {
        tailf:actionpoint ncsproxy {
          tailf:internal;
        }
        csc:xr-task "bgp";
        csc:cli-command "clear bgp instance <instance-name> version <afi-safi-name> <ipv4-prefix>";
        description
          "Choose a particular BGP instance.
           clear BGP prefix version.
          ";
        input {
          leaf instance-name {
            mandatory true;
            type instance-name;
            description
              "instance name or all";
          }
          leaf afi-safi-name {
            mandatory true;
            type afi-safi-type;
            description
              "AFI and SAFI";
          }
          leaf ipv4-prefix {
            mandatory true;
            type inet:ipv4-prefix;
            description
              "IPv4 network and masklength";
          }
        }
      }
    }
  }
  augment "/ncs:devices/ncs:device/ncs:rpc" {
    container rpc-clear-bgp-instance-version-afi-safi-ipv4-addr {
      tailf:ncs-device-type "netconf";
      tailf:display-when "not(../../ncs:module) or ../../ncs:module[ncs:name='Cisco-IOS-XR-ipv4-bgp-act']";
      tailf:action clear-bgp-instance-version-afi-safi-ipv4-addr {
        tailf:actionpoint ncsproxy {
          tailf:internal;
        }
        csc:xr-task "bgp";
        csc:cli-command "clear bgp instance <instance-name> version <afi-safi-name> <ipv4-addr>";
        description
          "Choose a particular BGP instance.
           clear BGP prefix version.
          ";
        input {
          leaf instance-name {
            mandatory true;
            type instance-name;
            description
              "instance name or all";
          }
          leaf afi-safi-name {
            mandatory true;
            type afi-safi-type;
            description
              "AFI and SAFI";
          }
          leaf ipv4-addr {
            mandatory true;
            type inet:ipv4-address;
            description
              "IPv4 network";
          }
        }
      }
    }
  }
  augment "/ncs:devices/ncs:device-group/ncs:ned-id/ncs:rpc" {
    container rpc-clear-bgp-instance-version-afi-safi-ipv4-addr {
      tailf:ncs-device-type "netconf";
      tailf:display-when "/ncs:devices/ncs:device[ncs:name=current()/../../../ncs:member]/ncs:module[ncs:name='Cisco-IOS-XR-ipv4-bgp-act']";
      tailf:action clear-bgp-instance-version-afi-safi-ipv4-addr {
        tailf:actionpoint ncsproxy {
          tailf:internal;
        }
        csc:xr-task "bgp";
        csc:cli-command "clear bgp instance <instance-name> version <afi-safi-name> <ipv4-addr>";
        description
          "Choose a particular BGP instance.
           clear BGP prefix version.
          ";
        input {
          leaf instance-name {
            mandatory true;
            type instance-name;
            description
              "instance name or all";
          }
          leaf afi-safi-name {
            mandatory true;
            type afi-safi-type;
            description
              "AFI and SAFI";
          }
          leaf ipv4-addr {
            mandatory true;
            type inet:ipv4-address;
            description
              "IPv4 network";
          }
        }
      }
    }
  }
  augment "/ncs:devices/ncs:device/ncs:rpc" {
    container rpc-clear-bgp-instance-version-afi-safi-ipv4-addr-ipv4-mask {
      tailf:ncs-device-type "netconf";
      tailf:display-when "not(../../ncs:module) or ../../ncs:module[ncs:name='Cisco-IOS-XR-ipv4-bgp-act']";
      tailf:action clear-bgp-instance-version-afi-safi-ipv4-addr-ipv4-mask {
        tailf:actionpoint ncsproxy {
          tailf:internal;
        }
        csc:xr-task "bgp";
        csc:cli-command "clear bgp instance <instance-name> version <afi-safi-name> <ipv4-addr> <ipv4-mask>";
        description
          "Choose a particular BGP instance.
           clear BGP prefix version.
          ";
        input {
          leaf instance-name {
            mandatory true;
            type instance-name;
            description
              "instance name or all";
          }
          leaf afi-safi-name {
            mandatory true;
            type afi-safi-type;
            description
              "AFI and SAFI";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device-group/ncs:ned-id/ncs:rpc" {
    container rpc-clear-bgp-instance-version-afi-safi-ipv4-addr-ipv4-mask {
      tailf:ncs-device-type "netconf";
      tailf:display-when "/ncs:devices/ncs:device[ncs:name=current()/../../../ncs:member]/ncs:module[ncs:name='Cisco-IOS-XR-ipv4-bgp-act']";
      tailf:action clear-bgp-instance-version-afi-safi-ipv4-addr-ipv4-mask {
        tailf:actionpoint ncsproxy {
          tailf:internal;
        }
        csc:xr-task "bgp";
        csc:cli-command "clear bgp instance <instance-name> version <afi-safi-name> <ipv4-addr> <ipv4-mask>";
        description
          "Choose a particular BGP instance.
           clear BGP prefix version.
          ";
        input {
          leaf instance-name {
            mandatory true;
            type instance-name;
            description
              "instance name or all";
          }
          leaf afi-safi-name {
            mandatory true;
            type afi-safi-type;
            description
              "AFI and SAFI";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device/ncs:rpc" {
    container rpc-clear-bgp-instance-version-afi-safi-rd-ip-prefix {
      tailf:ncs-device-type "netconf";
      tailf:display-when "not(../../ncs:module) or ../../ncs:module[ncs:name='Cisco-IOS-XR-ipv4-bgp-act']";
      tailf:action clear-bgp-instance-version-afi-safi-rd-ip-prefix {
        tailf:actionpoint ncsproxy {
          tailf:internal;
        }
        csc:xr-task "bgp";
        csc:cli-command "clear bgp instance <instance-name> version <afi-safi-name> rd <rd> <ip-prefix>";
        description
          "Choose a particular BGP instance.
           clear BGP prefix version.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ip-prefix {
            mandatory true;
            type inet:ip-prefix;
            description
              "Network and masklength";
          }
        }
      }
    }
  }
  augment "/ncs:devices/ncs:device-group/ncs:ned-id/ncs:rpc" {
    container rpc-clear-bgp-instance-version-afi-safi-rd-ip-prefix {
      tailf:ncs-device-type "netconf";
      tailf:display-when "/ncs:devices/ncs:device[ncs:name=current()/../../../ncs:member]/ncs:module[ncs:name='Cisco-IOS-XR-ipv4-bgp-act']";
      tailf:action clear-bgp-instance-version-afi-safi-rd-ip-prefix {
        tailf:actionpoint ncsproxy {
          tailf:internal;
        }
        csc:xr-task "bgp";
        csc:cli-command "clear bgp instance <instance-name> version <afi-safi-name> rd <rd> <ip-prefix>";
        description
          "Choose a particular BGP instance.
           clear BGP prefix version.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ip-prefix {
            mandatory true;
            type inet:ip-prefix;
            description
              "Network and masklength";
          }
        }
      }
    }
  }
  augment "/ncs:devices/ncs:device/ncs:rpc" {
    container rpc-clear-bgp-instance-version-afi-safi-rd-ip-addr {
      tailf:ncs-device-type "netconf";
      tailf:display-when "not(../../ncs:module) or ../../ncs:module[ncs:name='Cisco-IOS-XR-ipv4-bgp-act']";
      tailf:action clear-bgp-instance-version-afi-safi-rd-ip-addr {
        tailf:actionpoint ncsproxy {
          tailf:internal;
        }
        csc:xr-task "bgp";
        csc:cli-command "clear bgp instance <instance-name> version <afi-safi-name> rd <rd> <ip-addr>";
        description
          "Choose a particular BGP instance.
           clear BGP prefix version.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ip-addr {
            mandatory true;
            type inet:ip-address;
            description
              "Network";
          }
        }
      }
    }
  }
  augment "/ncs:devices/ncs:device-group/ncs:ned-id/ncs:rpc" {
    container rpc-clear-bgp-instance-version-afi-safi-rd-ip-addr {
      tailf:ncs-device-type "netconf";
      tailf:display-when "/ncs:devices/ncs:device[ncs:name=current()/../../../ncs:member]/ncs:module[ncs:name='Cisco-IOS-XR-ipv4-bgp-act']";
      tailf:action clear-bgp-instance-version-afi-safi-rd-ip-addr {
        tailf:actionpoint ncsproxy {
          tailf:internal;
        }
        csc:xr-task "bgp";
        csc:cli-command "clear bgp instance <instance-name> version <afi-safi-name> rd <rd> <ip-addr>";
        description
          "Choose a particular BGP instance.
           clear BGP prefix version.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ip-addr {
            mandatory true;
            type inet:ip-address;
            description
              "Network";
          }
        }
      }
    }
  }
  augment "/ncs:devices/ncs:device/ncs:rpc" {
    container rpc-clear-bgp-instance-version-afi-safi-rd-ip-addr-ip-netmask {
      tailf:ncs-device-type "netconf";
      tailf:display-when "not(../../ncs:module) or ../../ncs:module[ncs:name='Cisco-IOS-XR-ipv4-bgp-act']";
      tailf:action clear-bgp-instance-version-afi-safi-rd-ip-addr-ip-netmask {
        tailf:actionpoint ncsproxy {
          tailf:internal;
        }
        csc:xr-task "bgp";
        csc:cli-command "clear bgp instance <instance-name> version <afi-safi-name> rd <rd> <ip-addr> <ip-netmask>";
        description
          "Choose a particular BGP instance.
           clear BGP prefix version.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ip-addr {
            mandatory true;
            type inet:ip-address;
            description
              "Network";
          }
          leaf ip-netmask {
            mandatory true;
            type ip-netmask;
            description
              "Mask";
          }
        }
      }
    }
  }
  augment "/ncs:devices/ncs:device-group/ncs:ned-id/ncs:rpc" {
    container rpc-clear-bgp-instance-version-afi-safi-rd-ip-addr-ip-netmask {
      tailf:ncs-device-type "netconf";
      tailf:display-when "/ncs:devices/ncs:device[ncs:name=current()/../../../ncs:member]/ncs:module[ncs:name='Cisco-IOS-XR-ipv4-bgp-act']";
      tailf:action clear-bgp-instance-version-afi-safi-rd-ip-addr-ip-netmask {
        tailf:actionpoint ncsproxy {
          tailf:internal;
        }
        csc:xr-task "bgp";
        csc:cli-command "clear bgp instance <instance-name> version <afi-safi-name> rd <rd> <ip-addr> <ip-netmask>";
        description
          "Choose a particular BGP instance.
           clear BGP prefix version.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ip-addr {
            mandatory true;
            type inet:ip-address;
            description
              "Network";
          }
          leaf ip-netmask {
            mandatory true;
            type ip-netmask;
            description
              "Mask";
          }
        }
      }
    }
  }
  augment "/ncs:devices/ncs:device/ncs:rpc" {
    container rpc-clear-bgp-instance-version-afi-safi-bridge-domain-ip-prefix {
      tailf:ncs-device-type "netconf";
      tailf:display-when "not(../../ncs:module) or ../../ncs:module[ncs:name='Cisco-IOS-XR-ipv4-bgp-act']";
      tailf:action clear-bgp-instance-version-afi-safi-bridge-domain-ip-prefix {
        tailf:actionpoint ncsproxy {
          tailf:internal;
        }
        csc:xr-task "bgp";
        csc:cli-command "clear bgp instance <instance-name> version <afi-safi-name> bridge-domain <bridge-domain-name> <ip-prefix>";
        description
          "Choose a particular BGP instance.
           clear BGP prefix version.
           Display routes for a specified Bridge Domain.
          ";
        input {
          leaf instance-name {
            mandatory true;
            type instance-name;
            description
              "instance name or all";
          }
          leaf afi-safi-name {
            mandatory true;
            type afi-safi-type;
            description
              "AFI and SAFI";
          }
          leaf bridge-domain-name {
            mandatory true;
            type string;
            description
              "Bridge Domain";
          }
          leaf ip-prefix {
            mandatory true;
            type inet:ip-prefix;
            description
              "Network and masklength";
          }
        }
      }
    }
  }
  augment "/ncs:devices/ncs:device-group/ncs:ned-id/ncs:rpc" {
    container rpc-clear-bgp-instance-version-afi-safi-bridge-domain-ip-prefix {
      tailf:ncs-device-type "netconf";
      tailf:display-when "/ncs:devices/ncs:device[ncs:name=current()/../../../ncs:member]/ncs:module[ncs:name='Cisco-IOS-XR-ipv4-bgp-act']";
      tailf:action clear-bgp-instance-version-afi-safi-bridge-domain-ip-prefix {
        tailf:actionpoint ncsproxy {
          tailf:internal;
        }
        csc:xr-task "bgp";
        csc:cli-command "clear bgp instance <instance-name> version <afi-safi-name> bridge-domain <bridge-domain-name> <ip-prefix>";
        description
          "Choose a particular BGP instance.
           clear BGP prefix version.
           Display routes for a specified Bridge Domain.
          ";
        input {
          leaf instance-name {
            mandatory true;
            type instance-name;
            description
              "instance name or all";
          }
          leaf afi-safi-name {
            mandatory true;
            type afi-safi-type;
            description
              "AFI and SAFI";
          }
          leaf bridge-domain-name {
            mandatory true;
            type string;
            description
              "Bridge Domain";
          }
          leaf ip-prefix {
            mandatory true;
            type inet:ip-prefix;
            description
              "Network and masklength";
          }
        }
      }
    }
  }
  augment "/ncs:devices/ncs:device/ncs:rpc" {
    container rpc-clear-bgp-instance-version-afi-safi-bridge-domain-ip-addr {
      tailf:ncs-device-type "netconf";
      tailf:display-when "not(../../ncs:module) or ../../ncs:module[ncs:name='Cisco-IOS-XR-ipv4-bgp-act']";
      tailf:action clear-bgp-instance-version-afi-safi-bridge-domain-ip-addr {
        tailf:actionpoint ncsproxy {
          tailf:internal;
        }
        csc:xr-task "bgp";
        csc:cli-command "clear bgp instance <instance-name> version <afi-safi-name> bridge-domain <bridge-domain-name> <ip-addr>";
        description
          "Choose a particular BGP instance.
           clear BGP prefix version.
           Display routes for a specified Bridge Domain.
          ";
        input {
          leaf instance-name {
            mandatory true;
            type instance-name;
            description
              "instance name or all";
          }
          leaf afi-safi-name {
            mandatory true;
            type afi-safi-type;
            description
              "AFI and SAFI";
          }
          leaf bridge-domain-name {
            mandatory true;
            type string;
            description
              "Bridge Domain";
          }
          leaf ip-addr {
            mandatory true;
            type inet:ip-address;
            description
              "Network";
          }
        }
      }
    }
  }
  augment "/ncs:devices/ncs:device-group/ncs:ned-id/ncs:rpc" {
    container rpc-clear-bgp-instance-version-afi-safi-bridge-domain-ip-addr {
      tailf:ncs-device-type "netconf";
      tailf:display-when "/ncs:devices/ncs:device[ncs:name=current()/../../../ncs:member]/ncs:module[ncs:name='Cisco-IOS-XR-ipv4-bgp-act']";
      tailf:action clear-bgp-instance-version-afi-safi-bridge-domain-ip-addr {
        tailf:actionpoint ncsproxy {
          tailf:internal;
        }
        csc:xr-task "bgp";
        csc:cli-command "clear bgp instance <instance-name> version <afi-safi-name> bridge-domain <bridge-domain-name> <ip-addr>";
        description
          "Choose a particular BGP instance.
           clear BGP prefix version.
           Display routes for a specified Bridge Domain.
          ";
        input {
          leaf instance-name {
            mandatory true;
            type instance-name;
            description
              "instance name or all";
          }
          leaf afi-safi-name {
            mandatory true;
            type afi-safi-type;
            description
              "AFI and SAFI";
          }
          leaf bridge-domain-name {
            mandatory true;
            type string;
            description
              "Bridge Domain";
          }
          leaf ip-addr {
            mandatory true;
            type inet:ip-address;
            description
              "Network";
          }
        }
      }
    }
  }
  augment "/ncs:devices/ncs:device/ncs:rpc" {
    container rpc-clear-bgp-instance-version-afi-safi-bridge-domain-ip-addr-ip-netmask {
      tailf:ncs-device-type "netconf";
      tailf:display-when "not(../../ncs:module) or ../../ncs:module[ncs:name='Cisco-IOS-XR-ipv4-bgp-act']";
      tailf:action clear-bgp-instance-version-afi-safi-bridge-domain-ip-addr-ip-netmask {
        tailf:actionpoint ncsproxy {
          tailf:internal;
        }
        csc:xr-task "bgp";
        csc:cli-command "clear bgp instance <instance-name> version <afi-safi-name> bridge-domain <bridge-domain-name> <ip-addr> <ip-netmask>";
        description
          "Choose a particular BGP instance.
           clear BGP prefix version.
           Display routes for a specified Bridge Domain.
          ";
        input {
          leaf instance-name {
            mandatory true;
            type instance-name;
            description
              "instance name or all";
          }
          leaf afi-safi-name {
            mandatory true;
            type afi-safi-type;
            description
              "AFI and SAFI";
          }
          leaf bridge-domain-name {
            mandatory true;
            type string;
            description
              "Bridge Domain";
          }
          leaf ip-addr {
            mandatory true;
            type inet:ip-address;
            description
              "Network";
          }
          leaf ip-netmask {
            mandatory true;
            type ip-netmask;
            description
              "Mask";
          }
        }
      }
    }
  }
  augment "/ncs:devices/ncs:device-group/ncs:ned-id/ncs:rpc" {
    container rpc-clear-bgp-instance-version-afi-safi-bridge-domain-ip-addr-ip-netmask {
      tailf:ncs-device-type "netconf";
      tailf:display-when "/ncs:devices/ncs:device[ncs:name=current()/../../../ncs:member]/ncs:module[ncs:name='Cisco-IOS-XR-ipv4-bgp-act']";
      tailf:action clear-bgp-instance-version-afi-safi-bridge-domain-ip-addr-ip-netmask {
        tailf:actionpoint ncsproxy {
          tailf:internal;
        }
        csc:xr-task "bgp";
        csc:cli-command "clear bgp instance <instance-name> version <afi-safi-name> bridge-domain <bridge-domain-name> <ip-addr> <ip-netmask>";
        description
          "Choose a particular BGP instance.
           clear BGP prefix version.
           Display routes for a specified Bridge Domain.
          ";
        input {
          leaf instance-name {
            mandatory true;
            type instance-name;
            description
              "instance name or all";
          }
          leaf afi-safi-name {
            mandatory true;
            type afi-safi-type;
            description
              "AFI and SAFI";
          }
          leaf bridge-domain-name {
            mandatory true;
            type string;
            description
              "Bridge Domain";
          }
          leaf ip-addr {
            mandatory true;
            type inet:ip-address;
            description
              "Network";
          }
          leaf ip-netmask {
            mandatory true;
            type ip-netmask;
            description
              "Mask";
          }
        }
      }
    }
  }
  augment "/ncs:devices/ncs:device/ncs:rpc" {
    container rpc-clear-bgp-instance-version-afi-safi-ip-prefix {
      tailf:ncs-device-type "netconf";
      tailf:display-when "not(../../ncs:module) or ../../ncs:module[ncs:name='Cisco-IOS-XR-ipv4-bgp-act']";
      tailf:action clear-bgp-instance-version-afi-safi-ip-prefix {
        tailf:actionpoint ncsproxy {
          tailf:internal;
        }
        csc:xr-task "bgp";
        csc:cli-command "clear bgp instance <instance-name> version <afi-safi-name> <ip-prefix>";
        description
          "Choose a particular BGP instance.
           clear BGP prefix version.
          ";
        input {
          leaf instance-name {
            mandatory true;
            type instance-name;
            description
              "instance name or all";
          }
          leaf afi-safi-name {
            mandatory true;
            type afi-safi-type;
            description
              "AFI and SAFI";
          }
          leaf ip-prefix {
            mandatory true;
            type inet:ip-prefix;
            description
              "Network and masklength";
          }
        }
      }
    }
  }
  augment "/ncs:devices/ncs:device-group/ncs:ned-id/ncs:rpc" {
    container rpc-clear-bgp-instance-version-afi-safi-ip-prefix {
      tailf:ncs-device-type "netconf";
      tailf:display-when "/ncs:devices/ncs:device[ncs:name=current()/../../../ncs:member]/ncs:module[ncs:name='Cisco-IOS-XR-ipv4-bgp-act']";
      tailf:action clear-bgp-instance-version-afi-safi-ip-prefix {
        tailf:actionpoint ncsproxy {
          tailf:internal;
        }
        csc:xr-task "bgp";
        csc:cli-command "clear bgp instance <instance-name> version <afi-safi-name> <ip-prefix>";
        description
          "Choose a particular BGP instance.
           clear BGP prefix version.
          ";
        input {
          leaf instance-name {
            mandatory true;
            type instance-name;
            description
              "instance name or all";
          }
          leaf afi-safi-name {
            mandatory true;
            type afi-safi-type;
            description
              "AFI and SAFI";
          }
          leaf ip-prefix {
            mandatory true;
            type inet:ip-prefix;
            description
              "Network and masklength";
          }
        }
      }
    }
  }
  augment "/ncs:devices/ncs:device/ncs:rpc" {
    container rpc-clear-bgp-instance-version-afi-safi-ip-addr {
      tailf:ncs-device-type "netconf";
      tailf:display-when "not(../../ncs:module) or ../../ncs:module[ncs:name='Cisco-IOS-XR-ipv4-bgp-act']";
      tailf:action clear-bgp-instance-version-afi-safi-ip-addr {
        tailf:actionpoint ncsproxy {
          tailf:internal;
        }
        csc:xr-task "bgp";
        csc:cli-command "clear bgp instance <instance-name> version <afi-safi-name> <ip-addr>";
        description
          "Choose a particular BGP instance.
           clear BGP prefix version.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "Network";
          }
        }
      }
    }
  }
  augment "/ncs:devices/ncs:device-group/ncs:ned-id/ncs:rpc" {
    container rpc-clear-bgp-instance-version-afi-safi-ip-addr {
      tailf:ncs-device-type "netconf";
      tailf:display-when "/ncs:devices/ncs:device[ncs:name=current()/../../../ncs:member]/ncs:module[ncs:name='Cisco-IOS-XR-ipv4-bgp-act']";
      tailf:action clear-bgp-instance-version-afi-safi-ip-addr {
        tailf:actionpoint ncsproxy {
          tailf:internal;
        }
        csc:xr-task "bgp";
        csc:cli-command "clear bgp instance <instance-name> version <afi-safi-name> <ip-addr>";
        description
          "Choose a particular BGP instance.
           clear BGP prefix version.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "Network";
          }
        }
      }
    }
  }
  augment "/ncs:devices/ncs:device/ncs:rpc" {
    container rpc-clear-bgp-instance-version-afi-safi-ip-addr-ip-netmask {
      tailf:ncs-device-type "netconf";
      tailf:display-when "not(../../ncs:module) or ../../ncs:module[ncs:name='Cisco-IOS-XR-ipv4-bgp-act']";
      tailf:action clear-bgp-instance-version-afi-safi-ip-addr-ip-netmask {
        tailf:actionpoint ncsproxy {
          tailf:internal;
        }
        csc:xr-task "bgp";
        csc:cli-command "clear bgp instance <instance-name> version <afi-safi-name> <ip-addr> <ip-netmask>";
        description
          "Choose a particular BGP instance.
           clear BGP prefix version.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "Network";
          }
          leaf ip-netmask {
            mandatory true;
            type ip-netmask;
            description
              "Mask";
          }
        }
      }
    }
  }
  augment "/ncs:devices/ncs:device-group/ncs:ned-id/ncs:rpc" {
    container rpc-clear-bgp-instance-version-afi-safi-ip-addr-ip-netmask {
      tailf:ncs-device-type "netconf";
      tailf:display-when "/ncs:devices/ncs:device[ncs:name=current()/../../../ncs:member]/ncs:module[ncs:name='Cisco-IOS-XR-ipv4-bgp-act']";
      tailf:action clear-bgp-instance-version-afi-safi-ip-addr-ip-netmask {
        tailf:actionpoint ncsproxy {
          tailf:internal;
        }
        csc:xr-task "bgp";
        csc:cli-command "clear bgp instance <instance-name> version <afi-safi-name> <ip-addr> <ip-netmask>";
        description
          "Choose a particular BGP instance.
           clear BGP prefix version.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "Network";
          }
          leaf ip-netmask {
            mandatory true;
            type ip-netmask;
            description
              "Mask";
          }
        }
      }
    }
  }
  augment "/ncs:devices/ncs:device/ncs:rpc" {
    container rpc-clear-bgp-instance-version-ip-prefix {
      tailf:ncs-device-type "netconf";
      tailf:display-when "not(../../ncs:module) or ../../ncs:module[ncs:name='Cisco-IOS-XR-ipv4-bgp-act']";
      tailf:action clear-bgp-instance-version-ip-prefix {
        tailf:actionpoint ncsproxy {
          tailf:internal;
        }
        csc:xr-task "bgp";
        csc:cli-command "clear bgp instance <instance-name> version <ip-prefix>";
        description
          "Choose a particular BGP instance.
           clear BGP prefix version.
          ";
        input {
          leaf instance-name {
            mandatory true;
            type instance-name;
            description
              "instance name or all";
          }
          leaf ip-prefix {
            mandatory true;
            type inet:ip-prefix;
            description
              "Network and masklength";
          }
        }
      }
    }
  }
  augment "/ncs:devices/ncs:device-group/ncs:ned-id/ncs:rpc" {
    container rpc-clear-bgp-instance-version-ip-prefix {
      tailf:ncs-device-type "netconf";
      tailf:display-when "/ncs:devices/ncs:device[ncs:name=current()/../../../ncs:member]/ncs:module[ncs:name='Cisco-IOS-XR-ipv4-bgp-act']";
      tailf:action clear-bgp-instance-version-ip-prefix {
        tailf:actionpoint ncsproxy {
          tailf:internal;
        }
        csc:xr-task "bgp";
        csc:cli-command "clear bgp instance <instance-name> version <ip-prefix>";
        description
          "Choose a particular BGP instance.
           clear BGP prefix version.
          ";
        input {
          leaf instance-name {
            mandatory true;
            type instance-name;
            description
              "instance name or all";
          }
          leaf ip-prefix {
            mandatory true;
            type inet:ip-prefix;
            description
              "Network and masklength";
          }
        }
      }
    }
  }
  augment "/ncs:devices/ncs:device/ncs:rpc" {
    container rpc-clear-bgp-instance-version-ip-addr {
      tailf:ncs-device-type "netconf";
      tailf:display-when "not(../../ncs:module) or ../../ncs:module[ncs:name='Cisco-IOS-XR-ipv4-bgp-act']";
      tailf:action clear-bgp-instance-version-ip-addr {
        tailf:actionpoint ncsproxy {
          tailf:internal;
        }
        csc:xr-task "bgp";
        csc:cli-command "clear bgp instance <instance-name> version <ip-addr>";
        description
          "Choose a particular BGP instance.
           clear BGP prefix version.
          ";
        input {
          leaf instance-name {
            mandatory true;
            type instance-name;
            description
              "instance name or all";
          }
          leaf ip-addr {
            mandatory true;
            type inet:ip-address;
            description
              "Network";
          }
        }
      }
    }
  }
  augment "/ncs:devices/ncs:device-group/ncs:ned-id/ncs:rpc" {
    container rpc-clear-bgp-instance-version-ip-addr {
      tailf:ncs-device-type "netconf";
      tailf:display-when "/ncs:devices/ncs:device[ncs:name=current()/../../../ncs:member]/ncs:module[ncs:name='Cisco-IOS-XR-ipv4-bgp-act']";
      tailf:action clear-bgp-instance-version-ip-addr {
        tailf:actionpoint ncsproxy {
          tailf:internal;
        }
        csc:xr-task "bgp";
        csc:cli-command "clear bgp instance <instance-name> version <ip-addr>";
        description
          "Choose a particular BGP instance.
           clear BGP prefix version.
          ";
        input {
          leaf instance-name {
            mandatory true;
            type instance-name;
            description
              "instance name or all";
          }
          leaf ip-addr {
            mandatory true;
            type inet:ip-address;
            description
              "Network";
          }
        }
      }
    }
  }
  augment "/ncs:devices/ncs:device/ncs:rpc" {
    container rpc-clear-bgp-instance-version-ip-addr-ip-netmask {
      tailf:ncs-device-type "netconf";
      tailf:display-when "not(../../ncs:module) or ../../ncs:module[ncs:name='Cisco-IOS-XR-ipv4-bgp-act']";
      tailf:action clear-bgp-instance-version-ip-addr-ip-netmask {
        tailf:actionpoint ncsproxy {
          tailf:internal;
        }
        csc:xr-task "bgp";
        csc:cli-command "clear bgp instance <instance-name> version <ip-addr> <ip-netmask>";
        description
          "Choose a particular BGP instance.
           clear BGP prefix version.
          ";
        input {
          leaf instance-name {
            mandatory true;
            type instance-name;
            description
              "instance name or all";
          }
          leaf ip-addr {
            mandatory true;
            type inet:ip-address;
            description
              "Network";
          }
          leaf ip-netmask {
            mandatory true;
            type ip-netmask;
            description
              "Mask";
          }
        }
      }
    }
  }
  augment "/ncs:devices/ncs:device-group/ncs:ned-id/ncs:rpc" {
    container rpc-clear-bgp-instance-version-ip-addr-ip-netmask {
      tailf:ncs-device-type "netconf";
      tailf:display-when "/ncs:devices/ncs:device[ncs:name=current()/../../../ncs:member]/ncs:module[ncs:name='Cisco-IOS-XR-ipv4-bgp-act']";
      tailf:action clear-bgp-instance-version-ip-addr-ip-netmask {
        tailf:actionpoint ncsproxy {
          tailf:internal;
        }
        csc:xr-task "bgp";
        csc:cli-command "clear bgp instance <instance-name> version <ip-addr> <ip-netmask>";
        description
          "Choose a particular BGP instance.
           clear BGP prefix version.
          ";
        input {
          leaf instance-name {
            mandatory true;
            type instance-name;
            description
              "instance name or all";
          }
          leaf ip-addr {
            mandatory true;
            type inet:ip-address;
            description
              "Network";
          }
          leaf ip-netmask {
            mandatory true;
            type ip-netmask;
            description
              "Mask";
          }
        }
      }
    }
  }
  augment "/ncs:devices/ncs:device/ncs:rpc" {
    container rpc-clear-bgp-instance-update-outq-update-group {
      tailf:ncs-device-type "netconf";
      tailf:display-when "not(../../ncs:module) or ../../ncs:module[ncs:name='Cisco-IOS-XR-ipv4-bgp-act']";
      tailf:action clear-bgp-instance-update-outq-update-group {
        tailf:actionpoint ncsproxy {
          tailf:internal;
        }
        csc:xr-task "bgp";
        csc:cli-command "clear bgp instance <instance-name> update outq update-group <update-group>";
        description
          "Choose a particular BGP instance.
           Clear Update information (Do NOT execute without cisco support)(cisco-support).
           Clear Update generation OutQ counters (Do NOT execute without cisco support)(cisco-support).
           Update-group.
          ";
        input {
          leaf instance-name {
            mandatory true;
            type instance-name;
            description
              "instance name or all";
          }
          leaf update-group {
            mandatory true;
            type update-group-id;
            description
              "Update-group process ID <x.y>";
          }
        }
      }
    }
  }
  augment "/ncs:devices/ncs:device-group/ncs:ned-id/ncs:rpc" {
    container rpc-clear-bgp-instance-update-outq-update-group {
      tailf:ncs-device-type "netconf";
      tailf:display-when "/ncs:devices/ncs:device[ncs:name=current()/../../../ncs:member]/ncs:module[ncs:name='Cisco-IOS-XR-ipv4-bgp-act']";
      tailf:action clear-bgp-instance-update-outq-update-group {
        tailf:actionpoint ncsproxy {
          tailf:internal;
        }
        csc:xr-task "bgp";
        csc:cli-command "clear bgp instance <instance-name> update outq update-group <update-group>";
        description
          "Choose a particular BGP instance.
           Clear Update information (Do NOT execute without cisco support)(cisco-support).
           Clear Update generation OutQ counters (Do NOT execute without cisco support)(cisco-support).
           Update-group.
          ";
        input {
          leaf instance-name {
            mandatory true;
            type instance-name;
            description
              "instance name or all";
          }
          leaf update-group {
            mandatory true;
            type update-group-id;
            description
              "Update-group process ID <x.y>";
          }
        }
      }
    }
  }
  augment "/ncs:devices/ncs:device/ncs:rpc" {
    container rpc-clear-bgp-instance-update-outq-update-group-update-parent {
      tailf:ncs-device-type "netconf";
      tailf:display-when "not(../../ncs:module) or ../../ncs:module[ncs:name='Cisco-IOS-XR-ipv4-bgp-act']";
      tailf:action clear-bgp-instance-update-outq-update-group-update-parent {
        tailf:actionpoint ncsproxy {
          tailf:internal;
        }
        csc:xr-task "bgp";
        csc:cli-command "clear bgp instance <instance-name> update outq update-group <update-group> update-parent";
        description
          "Choose a particular BGP instance.
           Clear Update information (Do NOT execute without cisco support)(cisco-support).
           Clear Update generation OutQ counters (Do NOT execute without cisco support)(cisco-support).
           Update-group.
           Update parents' OutQ counters too.
          ";
        input {
          leaf instance-name {
            mandatory true;
            type instance-name;
            description
              "instance name or all";
          }
          leaf update-group {
            mandatory true;
            type update-group-id;
            description
              "Update-group process ID <x.y>";
          }
        }
      }
    }
  }
  augment "/ncs:devices/ncs:device-group/ncs:ned-id/ncs:rpc" {
    container rpc-clear-bgp-instance-update-outq-update-group-update-parent {
      tailf:ncs-device-type "netconf";
      tailf:display-when "/ncs:devices/ncs:device[ncs:name=current()/../../../ncs:member]/ncs:module[ncs:name='Cisco-IOS-XR-ipv4-bgp-act']";
      tailf:action clear-bgp-instance-update-outq-update-group-update-parent {
        tailf:actionpoint ncsproxy {
          tailf:internal;
        }
        csc:xr-task "bgp";
        csc:cli-command "clear bgp instance <instance-name> update outq update-group <update-group> update-parent";
        description
          "Choose a particular BGP instance.
           Clear Update information (Do NOT execute without cisco support)(cisco-support).
           Clear Update generation OutQ counters (Do NOT execute without cisco support)(cisco-support).
           Update-group.
           Update parents' OutQ counters too.
          ";
        input {
          leaf instance-name {
            mandatory true;
            type instance-name;
            description
              "instance name or all";
          }
          leaf update-group {
            mandatory true;
            type update-group-id;
            description
              "Update-group process ID <x.y>";
          }
        }
      }
    }
  }
  augment "/ncs:devices/ncs:device/ncs:rpc" {
    container rpc-clear-bgp-instance-update-outq-update-group-sub-group-refresh-sub-group {
      tailf:ncs-device-type "netconf";
      tailf:display-when "not(../../ncs:module) or ../../ncs:module[ncs:name='Cisco-IOS-XR-ipv4-bgp-act']";
      tailf:action clear-bgp-instance-update-outq-update-group-sub-group-refresh-sub-group {
        tailf:actionpoint ncsproxy {
          tailf:internal;
        }
        csc:xr-task "bgp";
        csc:cli-command "clear bgp instance <instance-name> update outq update-group <update-group> sub-group <refresh-sub-group>";
        description
          "Choose a particular BGP instance.
           Clear Update information (Do NOT execute without cisco support)(cisco-support).
           Clear Update generation OutQ counters (Do NOT execute without cisco support)(cisco-support).
           Update-group.
           Sub-group.
          ";
        input {
          leaf instance-name {
            mandatory true;
            type instance-name;
            description
              "instance name or all";
          }
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device-group/ncs:ned-id/ncs:rpc" {
    container rpc-clear-bgp-instance-update-outq-update-group-sub-group-refresh-sub-group {
      tailf:ncs-device-type "netconf";
      tailf:display-when "/ncs:devices/ncs:device[ncs:name=current()/../../../ncs:member]/ncs:module[ncs:name='Cisco-IOS-XR-ipv4-bgp-act']";
      tailf:action clear-bgp-instance-update-outq-update-group-sub-group-refresh-sub-group {
        tailf:actionpoint ncsproxy {
          tailf:internal;
        }
        csc:xr-task "bgp";
        csc:cli-command "clear bgp instance <instance-name> update outq update-group <update-group> sub-group <refresh-sub-group>";
        description
          "Choose a particular BGP instance.
           Clear Update information (Do NOT execute without cisco support)(cisco-support).
           Clear Update generation OutQ counters (Do NOT execute without cisco support)(cisco-support).
           Update-group.
           Sub-group.
          ";
        input {
          leaf instance-name {
            mandatory true;
            type instance-name;
            description
              "instance name or all";
          }
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device/ncs:rpc" {
    container rpc-clear-bgp-instance-update-outq-update-group-sub-group-refresh-sub-group-update-parent {
      tailf:ncs-device-type "netconf";
      tailf:display-when "not(../../ncs:module) or ../../ncs:module[ncs:name='Cisco-IOS-XR-ipv4-bgp-act']";
      tailf:action clear-bgp-instance-update-outq-update-group-sub-group-refresh-sub-group-update-parent {
        tailf:actionpoint ncsproxy {
          tailf:internal;
        }
        csc:xr-task "bgp";
        csc:cli-command "clear bgp instance <instance-name> update outq update-group <update-group> sub-group <refresh-sub-group> update-parent";
        description
          "Choose a particular BGP instance.
           Clear Update information (Do NOT execute without cisco support)(cisco-support).
           Clear Update generation OutQ counters (Do NOT execute without cisco support)(cisco-support).
           Update-group.
           Sub-group.
           Update parents' OutQ counters too.
          ";
        input {
          leaf instance-name {
            mandatory true;
            type instance-name;
            description
              "instance name or all";
          }
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device-group/ncs:ned-id/ncs:rpc" {
    container rpc-clear-bgp-instance-update-outq-update-group-sub-group-refresh-sub-group-update-parent {
      tailf:ncs-device-type "netconf";
      tailf:display-when "/ncs:devices/ncs:device[ncs:name=current()/../../../ncs:member]/ncs:module[ncs:name='Cisco-IOS-XR-ipv4-bgp-act']";
      tailf:action clear-bgp-instance-update-outq-update-group-sub-group-refresh-sub-group-update-parent {
        tailf:actionpoint ncsproxy {
          tailf:internal;
        }
        csc:xr-task "bgp";
        csc:cli-command "clear bgp instance <instance-name> update outq update-group <update-group> sub-group <refresh-sub-group> update-parent";
        description
          "Choose a particular BGP instance.
           Clear Update information (Do NOT execute without cisco support)(cisco-support).
           Clear Update generation OutQ counters (Do NOT execute without cisco support)(cisco-support).
           Update-group.
           Sub-group.
           Update parents' OutQ counters too.
          ";
        input {
          leaf instance-name {
            mandatory true;
            type instance-name;
            description
              "instance name or all";
          }
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device/ncs:rpc" {
    container rpc-clear-bgp-instance-update-outq-update-group-sub-group {
      tailf:ncs-device-type "netconf";
      tailf:display-when "not(../../ncs:module) or ../../ncs:module[ncs:name='Cisco-IOS-XR-ipv4-bgp-act']";
      tailf:action clear-bgp-instance-update-outq-update-group-sub-group {
        tailf:actionpoint ncsproxy {
          tailf:internal;
        }
        csc:xr-task "bgp";
        csc:cli-command "clear bgp instance <instance-name> update outq update-group <update-group> sub-group <sub-group>";
        description
          "Choose a particular BGP instance.
           Clear Update information (Do NOT execute without cisco support)(cisco-support).
           Clear Update generation OutQ counters (Do NOT execute without cisco support)(cisco-support).
           Update-group.
           Sub-group.
          ";
        input {
          leaf instance-name {
            mandatory true;
            type instance-name;
            description
              "instance name or all";
          }
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device-group/ncs:ned-id/ncs:rpc" {
    container rpc-clear-bgp-instance-update-outq-update-group-sub-group {
      tailf:ncs-device-type "netconf";
      tailf:display-when "/ncs:devices/ncs:device[ncs:name=current()/../../../ncs:member]/ncs:module[ncs:name='Cisco-IOS-XR-ipv4-bgp-act']";
      tailf:action clear-bgp-instance-update-outq-update-group-sub-group {
        tailf:actionpoint ncsproxy {
          tailf:internal;
        }
        csc:xr-task "bgp";
        csc:cli-command "clear bgp instance <instance-name> update outq update-group <update-group> sub-group <sub-group>";
        description
          "Choose a particular BGP instance.
           Clear Update information (Do NOT execute without cisco support)(cisco-support).
           Clear Update generation OutQ counters (Do NOT execute without cisco support)(cisco-support).
           Update-group.
           Sub-group.
          ";
        input {
          leaf instance-name {
            mandatory true;
            type instance-name;
            description
              "instance name or all";
          }
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device/ncs:rpc" {
    container rpc-clear-bgp-instance-update-outq-update-group-sub-group-update-parent {
      tailf:ncs-device-type "netconf";
      tailf:display-when "not(../../ncs:module) or ../../ncs:module[ncs:name='Cisco-IOS-XR-ipv4-bgp-act']";
      tailf:action clear-bgp-instance-update-outq-update-group-sub-group-update-parent {
        tailf:actionpoint ncsproxy {
          tailf:internal;
        }
        csc:xr-task "bgp";
        csc:cli-command "clear bgp instance <instance-name> update outq update-group <update-group> sub-group <sub-group> update-parent";
        description
          "Choose a particular BGP instance.
           Clear Update information (Do NOT execute without cisco support)(cisco-support).
           Clear Update generation OutQ counters (Do NOT execute without cisco support)(cisco-support).
           Update-group.
           Sub-group.
           Update parents' OutQ counters too.
          ";
        input {
          leaf instance-name {
            mandatory true;
            type instance-name;
            description
              "instance name or all";
          }
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device-group/ncs:ned-id/ncs:rpc" {
    container rpc-clear-bgp-instance-update-outq-update-group-sub-group-update-parent {
      tailf:ncs-device-type "netconf";
      tailf:display-when "/ncs:devices/ncs:device[ncs:name=current()/../../../ncs:member]/ncs:module[ncs:name='Cisco-IOS-XR-ipv4-bgp-act']";
      tailf:action clear-bgp-instance-update-outq-update-group-sub-group-update-parent {
        tailf:actionpoint ncsproxy {
          tailf:internal;
        }
        csc:xr-task "bgp";
        csc:cli-command "clear bgp instance <instance-name> update outq update-group <update-group> sub-group <sub-group> update-parent";
        description
          "Choose a particular BGP instance.
           Clear Update information (Do NOT execute without cisco support)(cisco-support).
           Clear Update generation OutQ counters (Do NOT execute without cisco support)(cisco-support).
           Update-group.
           Sub-group.
           Update parents' OutQ counters too.
          ";
        input {
          leaf instance-name {
            mandatory true;
            type instance-name;
            description
              "instance name or all";
          }
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device/ncs:rpc" {
    container rpc-clear-bgp-instance-update-outq-process {
      tailf:ncs-device-type "netconf";
      tailf:display-when "not(../../ncs:module) or ../../ncs:module[ncs:name='Cisco-IOS-XR-ipv4-bgp-act']";
      tailf:action clear-bgp-instance-update-outq-process {
        tailf:actionpoint ncsproxy {
          tailf:internal;
        }
        csc:xr-task "bgp";
        csc:cli-command "clear bgp instance <instance-name> update outq process";
        description
          "Choose a particular BGP instance.
           Clear Update information (Do NOT execute without cisco support)(cisco-support).
           Clear Update generation OutQ counters (Do NOT execute without cisco support)(cisco-support).
           Process.
          ";
        input {
          leaf instance-name {
            mandatory true;
            type instance-name;
            description
              "instance name or all";
          }
        }
      }
    }
  }
  augment "/ncs:devices/ncs:device-group/ncs:ned-id/ncs:rpc" {
    container rpc-clear-bgp-instance-update-outq-process {
      tailf:ncs-device-type "netconf";
      tailf:display-when "/ncs:devices/ncs:device[ncs:name=current()/../../../ncs:member]/ncs:module[ncs:name='Cisco-IOS-XR-ipv4-bgp-act']";
      tailf:action clear-bgp-instance-update-outq-process {
        tailf:actionpoint ncsproxy {
          tailf:internal;
        }
        csc:xr-task "bgp";
        csc:cli-command "clear bgp instance <instance-name> update outq process";
        description
          "Choose a particular BGP instance.
           Clear Update information (Do NOT execute without cisco support)(cisco-support).
           Clear Update generation OutQ counters (Do NOT execute without cisco support)(cisco-support).
           Process.
          ";
        input {
          leaf instance-name {
            mandatory true;
            type instance-name;
            description
              "instance name or all";
          }
        }
      }
    }
  }
  augment "/ncs:devices/ncs:device/ncs:rpc" {
    container rpc-clear-bgp-instance-update-outq-neighbor-ip-addr {
      tailf:ncs-device-type "netconf";
      tailf:display-when "not(../../ncs:module) or ../../ncs:module[ncs:name='Cisco-IOS-XR-ipv4-bgp-act']";
      tailf:action clear-bgp-instance-update-outq-neighbor-ip-addr {
        tailf:actionpoint ncsproxy {
          tailf:internal;
        }
        csc:xr-task "bgp";
        csc:cli-command "clear bgp instance <instance-name> update outq neighbor <ip-addr>";
        description
          "Choose a particular BGP instance.
           Clear Update information (Do NOT execute without cisco support)(cisco-support).
           Clear Update generation OutQ counters (Do NOT execute without cisco support)(cisco-support).
           Neighbor.
          ";
        input {
          leaf instance-name {
            mandatory true;
            type instance-name;
            description
              "instance name or all";
          }
          leaf ip-addr {
            mandatory true;
            type inet:ip-address;
            description
              "Neighbor address";
          }
        }
      }
    }
  }
  augment "/ncs:devices/ncs:device-group/ncs:ned-id/ncs:rpc" {
    container rpc-clear-bgp-instance-update-outq-neighbor-ip-addr {
      tailf:ncs-device-type "netconf";
      tailf:display-when "/ncs:devices/ncs:device[ncs:name=current()/../../../ncs:member]/ncs:module[ncs:name='Cisco-IOS-XR-ipv4-bgp-act']";
      tailf:action clear-bgp-instance-update-outq-neighbor-ip-addr {
        tailf:actionpoint ncsproxy {
          tailf:internal;
        }
        csc:xr-task "bgp";
        csc:cli-command "clear bgp instance <instance-name> update outq neighbor <ip-addr>";
        description
          "Choose a particular BGP instance.
           Clear Update information (Do NOT execute without cisco support)(cisco-support).
           Clear Update generation OutQ counters (Do NOT execute without cisco support)(cisco-support).
           Neighbor.
          ";
        input {
          leaf instance-name {
            mandatory true;
            type instance-name;
            description
              "instance name or all";
          }
          leaf ip-addr {
            mandatory true;
            type inet:ip-address;
            description
              "Neighbor address";
          }
        }
      }
    }
  }
  augment "/ncs:devices/ncs:device/ncs:rpc" {
    container rpc-clear-bgp-instance-update-outq-neighbor-ip-addr-update-parent {
      tailf:ncs-device-type "netconf";
      tailf:display-when "not(../../ncs:module) or ../../ncs:module[ncs:name='Cisco-IOS-XR-ipv4-bgp-act']";
      tailf:action clear-bgp-instance-update-outq-neighbor-ip-addr-update-parent {
        tailf:actionpoint ncsproxy {
          tailf:internal;
        }
        csc:xr-task "bgp";
        csc:cli-command "clear bgp instance <instance-name> update outq neighbor <ip-addr> update-parent";
        description
          "Choose a particular BGP instance.
           Clear Update information (Do NOT execute without cisco support)(cisco-support).
           Clear Update generation OutQ counters (Do NOT execute without cisco support)(cisco-support).
           Neighbor.
           Update parents' OutQ counters too.
          ";
        input {
          leaf instance-name {
            mandatory true;
            type instance-name;
            description
              "instance name or all";
          }
          leaf ip-addr {
            mandatory true;
            type inet:ip-address;
            description
              "Neighbor address";
          }
        }
      }
    }
  }
  augment "/ncs:devices/ncs:device-group/ncs:ned-id/ncs:rpc" {
    container rpc-clear-bgp-instance-update-outq-neighbor-ip-addr-update-parent {
      tailf:ncs-device-type "netconf";
      tailf:display-when "/ncs:devices/ncs:device[ncs:name=current()/../../../ncs:member]/ncs:module[ncs:name='Cisco-IOS-XR-ipv4-bgp-act']";
      tailf:action clear-bgp-instance-update-outq-neighbor-ip-addr-update-parent {
        tailf:actionpoint ncsproxy {
          tailf:internal;
        }
        csc:xr-task "bgp";
        csc:cli-command "clear bgp instance <instance-name> update outq neighbor <ip-addr> update-parent";
        description
          "Choose a particular BGP instance.
           Clear Update information (Do NOT execute without cisco support)(cisco-support).
           Clear Update generation OutQ counters (Do NOT execute without cisco support)(cisco-support).
           Neighbor.
           Update parents' OutQ counters too.
          ";
        input {
          leaf instance-name {
            mandatory true;
            type instance-name;
            description
              "instance name or all";
          }
          leaf ip-addr {
            mandatory true;
            type inet:ip-address;
            description
              "Neighbor address";
          }
        }
      }
    }
  }
  augment "/ncs:devices/ncs:device/ncs:rpc" {
    container rpc-clear-bgp-instance-update-outq-neighbor-ip-addr-refresh {
      tailf:ncs-device-type "netconf";
      tailf:display-when "not(../../ncs:module) or ../../ncs:module[ncs:name='Cisco-IOS-XR-ipv4-bgp-act']";
      tailf:action clear-bgp-instance-update-outq-neighbor-ip-addr-refresh {
        tailf:actionpoint ncsproxy {
          tailf:internal;
        }
        csc:xr-task "bgp";
        csc:cli-command "clear bgp instance <instance-name> update outq neighbor <ip-addr> refresh";
        description
          "Choose a particular BGP instance.
           Clear Update information (Do NOT execute without cisco support)(cisco-support).
           Clear Update generation OutQ counters (Do NOT execute without cisco support)(cisco-support).
           Neighbor.
           Refresh OutQ.
          ";
        input {
          leaf instance-name {
            mandatory true;
            type instance-name;
            description
              "instance name or all";
          }
          leaf ip-addr {
            mandatory true;
            type inet:ip-address;
            description
              "Neighbor address";
          }
        }
      }
    }
  }
  augment "/ncs:devices/ncs:device-group/ncs:ned-id/ncs:rpc" {
    container rpc-clear-bgp-instance-update-outq-neighbor-ip-addr-refresh {
      tailf:ncs-device-type "netconf";
      tailf:display-when "/ncs:devices/ncs:device[ncs:name=current()/../../../ncs:member]/ncs:module[ncs:name='Cisco-IOS-XR-ipv4-bgp-act']";
      tailf:action clear-bgp-instance-update-outq-neighbor-ip-addr-refresh {
        tailf:actionpoint ncsproxy {
          tailf:internal;
        }
        csc:xr-task "bgp";
        csc:cli-command "clear bgp instance <instance-name> update outq neighbor <ip-addr> refresh";
        description
          "Choose a particular BGP instance.
           Clear Update information (Do NOT execute without cisco support)(cisco-support).
           Clear Update generation OutQ counters (Do NOT execute without cisco support)(cisco-support).
           Neighbor.
           Refresh OutQ.
          ";
        input {
          leaf instance-name {
            mandatory true;
            type instance-name;
            description
              "instance name or all";
          }
          leaf ip-addr {
            mandatory true;
            type inet:ip-address;
            description
              "Neighbor address";
          }
        }
      }
    }
  }
  augment "/ncs:devices/ncs:device/ncs:rpc" {
    container rpc-clear-bgp-instance-update-outq-neighbor-ip-addr-refresh-update-parent {
      tailf:ncs-device-type "netconf";
      tailf:display-when "not(../../ncs:module) or ../../ncs:module[ncs:name='Cisco-IOS-XR-ipv4-bgp-act']";
      tailf:action clear-bgp-instance-update-outq-neighbor-ip-addr-refresh-update-parent {
        tailf:actionpoint ncsproxy {
          tailf:internal;
        }
        csc:xr-task "bgp";
        csc:cli-command "clear bgp instance <instance-name> update outq neighbor <ip-addr> refresh update-parent";
        description
          "Choose a particular BGP instance.
           Clear Update information (Do NOT execute without cisco support)(cisco-support).
           Clear Update generation OutQ counters (Do NOT execute without cisco support)(cisco-support).
           Neighbor.
           Refresh OutQ.
           Update parents' OutQ counters too.
          ";
        input {
          leaf instance-name {
            mandatory true;
            type instance-name;
            description
              "instance name or all";
          }
          leaf ip-addr {
            mandatory true;
            type inet:ip-address;
            description
              "Neighbor address";
          }
        }
      }
    }
  }
  augment "/ncs:devices/ncs:device-group/ncs:ned-id/ncs:rpc" {
    container rpc-clear-bgp-instance-update-outq-neighbor-ip-addr-refresh-update-parent {
      tailf:ncs-device-type "netconf";
      tailf:display-when "/ncs:devices/ncs:device[ncs:name=current()/../../../ncs:member]/ncs:module[ncs:name='Cisco-IOS-XR-ipv4-bgp-act']";
      tailf:action clear-bgp-instance-update-outq-neighbor-ip-addr-refresh-update-parent {
        tailf:actionpoint ncsproxy {
          tailf:internal;
        }
        csc:xr-task "bgp";
        csc:cli-command "clear bgp instance <instance-name> update outq neighbor <ip-addr> refresh update-parent";
        description
          "Choose a particular BGP instance.
           Clear Update information (Do NOT execute without cisco support)(cisco-support).
           Clear Update generation OutQ counters (Do NOT execute without cisco support)(cisco-support).
           Neighbor.
           Refresh OutQ.
           Update parents' OutQ counters too.
          ";
        input {
          leaf instance-name {
            mandatory true;
            type instance-name;
            description
              "instance name or all";
          }
          leaf ip-addr {
            mandatory true;
            type inet:ip-address;
            description
              "Neighbor address";
          }
        }
      }
    }
  }
  augment "/ncs:devices/ncs:device/ncs:rpc" {
    container rpc-clear-bgp-instance-update-outq-address-family {
      tailf:ncs-device-type "netconf";
      tailf:display-when "not(../../ncs:module) or ../../ncs:module[ncs:name='Cisco-IOS-XR-ipv4-bgp-act']";
      tailf:action clear-bgp-instance-update-outq-address-family {
        tailf:actionpoint ncsproxy {
          tailf:internal;
        }
        csc:xr-task "bgp";
        csc:cli-command "clear bgp instance <instance-name> update outq address-family";
        description
          "Choose a particular BGP instance.
           Clear Update information (Do NOT execute without cisco support)(cisco-support).
           Clear Update generation OutQ counters (Do NOT execute without cisco support)(cisco-support).
           Address-family.
          ";
        input {
          leaf instance-name {
            mandatory true;
            type instance-name;
            description
              "instance name or all";
          }
        }
      }
    }
  }
  augment "/ncs:devices/ncs:device-group/ncs:ned-id/ncs:rpc" {
    container rpc-clear-bgp-instance-update-outq-address-family {
      tailf:ncs-device-type "netconf";
      tailf:display-when "/ncs:devices/ncs:device[ncs:name=current()/../../../ncs:member]/ncs:module[ncs:name='Cisco-IOS-XR-ipv4-bgp-act']";
      tailf:action clear-bgp-instance-update-outq-address-family {
        tailf:actionpoint ncsproxy {
          tailf:internal;
        }
        csc:xr-task "bgp";
        csc:cli-command "clear bgp instance <instance-name> update outq address-family";
        description
          "Choose a particular BGP instance.
           Clear Update information (Do NOT execute without cisco support)(cisco-support).
           Clear Update generation OutQ counters (Do NOT execute without cisco support)(cisco-support).
           Address-family.
          ";
        input {
          leaf instance-name {
            mandatory true;
            type instance-name;
            description
              "instance name or all";
          }
        }
      }
    }
  }
  augment "/ncs:devices/ncs:device/ncs:rpc" {
    container rpc-clear-bgp-instance-update-outq-address-family-update-parent {
      tailf:ncs-device-type "netconf";
      tailf:display-when "not(../../ncs:module) or ../../ncs:module[ncs:name='Cisco-IOS-XR-ipv4-bgp-act']";
      tailf:action clear-bgp-instance-update-outq-address-family-update-parent {
        tailf:actionpoint ncsproxy {
          tailf:internal;
        }
        csc:xr-task "bgp";
        csc:cli-command "clear bgp instance <instance-name> update outq address-family update-parent";
        description
          "Choose a particular BGP instance.
           Clear Update information (Do NOT execute without cisco support)(cisco-support).
           Clear Update generation OutQ counters (Do NOT execute without cisco support)(cisco-support).
           Address-family.
           Update parents' OutQ counters too.
          ";
        input {
          leaf instance-name {
            mandatory true;
            type instance-name;
            description
              "instance name or all";
          }
        }
      }
    }
  }
  augment "/ncs:devices/ncs:device-group/ncs:ned-id/ncs:rpc" {
    container rpc-clear-bgp-instance-update-outq-address-family-update-parent {
      tailf:ncs-device-type "netconf";
      tailf:display-when "/ncs:devices/ncs:device[ncs:name=current()/../../../ncs:member]/ncs:module[ncs:name='Cisco-IOS-XR-ipv4-bgp-act']";
      tailf:action clear-bgp-instance-update-outq-address-family-update-parent {
        tailf:actionpoint ncsproxy {
          tailf:internal;
        }
        csc:xr-task "bgp";
        csc:cli-command "clear bgp instance <instance-name> update outq address-family update-parent";
        description
          "Choose a particular BGP instance.
           Clear Update information (Do NOT execute without cisco support)(cisco-support).
           Clear Update generation OutQ counters (Do NOT execute without cisco support)(cisco-support).
           Address-family.
           Update parents' OutQ counters too.
          ";
        input {
          leaf instance-name {
            mandatory true;
            type instance-name;
            description
              "instance name or all";
          }
        }
      }
    }
  }
  augment "/ncs:devices/ncs:device/ncs:rpc" {
    container rpc-clear-bgp-instance-shutdown {
      tailf:ncs-device-type "netconf";
      tailf:display-when "not(../../ncs:module) or ../../ncs:module[ncs:name='Cisco-IOS-XR-ipv4-bgp-act']";
      tailf:action clear-bgp-instance-shutdown {
        tailf:actionpoint ncsproxy {
          tailf:internal;
        }
        csc:xr-task "bgp";
        csc:cli-command "clear bgp instance <instance-name> shutdown";
        description
          "Choose a particular BGP instance.
           Clear all peers which were shut down due to low memory.
          ";
        input {
          leaf instance-name {
            mandatory true;
            type instance-name;
            description
              "instance name or all";
          }
        }
      }
    }
  }
  augment "/ncs:devices/ncs:device-group/ncs:ned-id/ncs:rpc" {
    container rpc-clear-bgp-instance-shutdown {
      tailf:ncs-device-type "netconf";
      tailf:display-when "/ncs:devices/ncs:device[ncs:name=current()/../../../ncs:member]/ncs:module[ncs:name='Cisco-IOS-XR-ipv4-bgp-act']";
      tailf:action clear-bgp-instance-shutdown {
        tailf:actionpoint ncsproxy {
          tailf:internal;
        }
        csc:xr-task "bgp";
        csc:cli-command "clear bgp instance <instance-name> shutdown";
        description
          "Choose a particular BGP instance.
           Clear all peers which were shut down due to low memory.
          ";
        input {
          leaf instance-name {
            mandatory true;
            type instance-name;
            description
              "instance name or all";
          }
        }
      }
    }
  }
  augment "/ncs:devices/ncs:device/ncs:rpc" {
    container rpc-clear-bgp-instance-rpki-validation {
      tailf:ncs-device-type "netconf";
      tailf:display-when "not(../../ncs:module) or ../../ncs:module[ncs:name='Cisco-IOS-XR-ipv4-bgp-act']";
      tailf:action clear-bgp-instance-rpki-validation {
        tailf:actionpoint ncsproxy {
          tailf:internal;
        }
        csc:xr-task "bgp";
        csc:cli-command "clear bgp instance <instance-name> rpki validation";
        description
          "Choose a particular BGP instance.
           RPKI clear command.
           clear RPKI origin-validation (trigger origin validation).
          ";
        input {
          leaf instance-name {
            mandatory true;
            type instance-name;
            description
              "instance name or all";
          }
        }
      }
    }
  }
  augment "/ncs:devices/ncs:device-group/ncs:ned-id/ncs:rpc" {
    container rpc-clear-bgp-instance-rpki-validation {
      tailf:ncs-device-type "netconf";
      tailf:display-when "/ncs:devices/ncs:device[ncs:name=current()/../../../ncs:member]/ncs:module[ncs:name='Cisco-IOS-XR-ipv4-bgp-act']";
      tailf:action clear-bgp-instance-rpki-validation {
        tailf:actionpoint ncsproxy {
          tailf:internal;
        }
        csc:xr-task "bgp";
        csc:cli-command "clear bgp instance <instance-name> rpki validation";
        description
          "Choose a particular BGP instance.
           RPKI clear command.
           clear RPKI origin-validation (trigger origin validation).
          ";
        input {
          leaf instance-name {
            mandatory true;
            type instance-name;
            description
              "instance name or all";
          }
        }
      }
    }
  }
  augment "/ncs:devices/ncs:device/ncs:rpc" {
    container rpc-clear-bgp-instance-rpki-validation-ipv6 {
      tailf:ncs-device-type "netconf";
      tailf:display-when "not(../../ncs:module) or ../../ncs:module[ncs:name='Cisco-IOS-XR-ipv4-bgp-act']";
      tailf:action clear-bgp-instance-rpki-validation-ipv6 {
        tailf:actionpoint ncsproxy {
          tailf:internal;
        }
        csc:xr-task "bgp";
        csc:cli-command "clear bgp instance <instance-name> rpki validation ipv6";
        description
          "Choose a particular BGP instance.
           RPKI clear command.
           clear RPKI origin-validation (trigger origin validation).
           trigger origin validation walk for the IPv6 table.
          ";
        input {
          leaf instance-name {
            mandatory true;
            type instance-name;
            description
              "instance name or all";
          }
        }
      }
    }
  }
  augment "/ncs:devices/ncs:device-group/ncs:ned-id/ncs:rpc" {
    container rpc-clear-bgp-instance-rpki-validation-ipv6 {
      tailf:ncs-device-type "netconf";
      tailf:display-when "/ncs:devices/ncs:device[ncs:name=current()/../../../ncs:member]/ncs:module[ncs:name='Cisco-IOS-XR-ipv4-bgp-act']";
      tailf:action clear-bgp-instance-rpki-validation-ipv6 {
        tailf:actionpoint ncsproxy {
          tailf:internal;
        }
        csc:xr-task "bgp";
        csc:cli-command "clear bgp instance <instance-name> rpki validation ipv6";
        description
          "Choose a particular BGP instance.
           RPKI clear command.
           clear RPKI origin-validation (trigger origin validation).
           trigger origin validation walk for the IPv6 table.
          ";
        input {
          leaf instance-name {
            mandatory true;
            type instance-name;
            description
              "instance name or all";
          }
        }
      }
    }
  }
  augment "/ncs:devices/ncs:device/ncs:rpc" {
    container rpc-clear-bgp-instance-rpki-validation-ipv4 {
      tailf:ncs-device-type "netconf";
      tailf:display-when "not(../../ncs:module) or ../../ncs:module[ncs:name='Cisco-IOS-XR-ipv4-bgp-act']";
      tailf:action clear-bgp-instance-rpki-validation-ipv4 {
        tailf:actionpoint ncsproxy {
          tailf:internal;
        }
        csc:xr-task "bgp";
        csc:cli-command "clear bgp instance <instance-name> rpki validation ipv4";
        description
          "Choose a particular BGP instance.
           RPKI clear command.
           clear RPKI origin-validation (trigger origin validation).
           trigger origin validation walk for the IPv4 table.
          ";
        input {
          leaf instance-name {
            mandatory true;
            type instance-name;
            description
              "instance name or all";
          }
        }
      }
    }
  }
  augment "/ncs:devices/ncs:device-group/ncs:ned-id/ncs:rpc" {
    container rpc-clear-bgp-instance-rpki-validation-ipv4 {
      tailf:ncs-device-type "netconf";
      tailf:display-when "/ncs:devices/ncs:device[ncs:name=current()/../../../ncs:member]/ncs:module[ncs:name='Cisco-IOS-XR-ipv4-bgp-act']";
      tailf:action clear-bgp-instance-rpki-validation-ipv4 {
        tailf:actionpoint ncsproxy {
          tailf:internal;
        }
        csc:xr-task "bgp";
        csc:cli-command "clear bgp instance <instance-name> rpki validation ipv4";
        description
          "Choose a particular BGP instance.
           RPKI clear command.
           clear RPKI origin-validation (trigger origin validation).
           trigger origin validation walk for the IPv4 table.
          ";
        input {
          leaf instance-name {
            mandatory true;
            type instance-name;
            description
              "instance name or all";
          }
        }
      }
    }
  }
  augment "/ncs:devices/ncs:device/ncs:rpc" {
    container rpc-clear-bgp-instance-rpki-server-rpki-server {
      tailf:ncs-device-type "netconf";
      tailf:display-when "not(../../ncs:module) or ../../ncs:module[ncs:name='Cisco-IOS-XR-ipv4-bgp-act']";
      tailf:action clear-bgp-instance-rpki-server-rpki-server {
        tailf:actionpoint ncsproxy {
          tailf:internal;
        }
        csc:xr-task "bgp";
        csc:cli-command "clear bgp instance <instance-name> rpki server <rpki-server>";
        description
          "Choose a particular BGP instance.
           RPKI clear command.
           clear RPKI cache-server.
          ";
        input {
          leaf instance-name {
            mandatory true;
            type instance-name;
            description
              "instance name or all";
          }
          leaf rpki-server {
            mandatory true;
            type string;
            description
              "clear a specific RPKI cache-server (hostname or IP address)";
          }
        }
      }
    }
  }
  augment "/ncs:devices/ncs:device-group/ncs:ned-id/ncs:rpc" {
    container rpc-clear-bgp-instance-rpki-server-rpki-server {
      tailf:ncs-device-type "netconf";
      tailf:display-when "/ncs:devices/ncs:device[ncs:name=current()/../../../ncs:member]/ncs:module[ncs:name='Cisco-IOS-XR-ipv4-bgp-act']";
      tailf:action clear-bgp-instance-rpki-server-rpki-server {
        tailf:actionpoint ncsproxy {
          tailf:internal;
        }
        csc:xr-task "bgp";
        csc:cli-command "clear bgp instance <instance-name> rpki server <rpki-server>";
        description
          "Choose a particular BGP instance.
           RPKI clear command.
           clear RPKI cache-server.
          ";
        input {
          leaf instance-name {
            mandatory true;
            type instance-name;
            description
              "instance name or all";
          }
          leaf rpki-server {
            mandatory true;
            type string;
            description
              "clear a specific RPKI cache-server (hostname or IP address)";
          }
        }
      }
    }
  }
  augment "/ncs:devices/ncs:device/ncs:rpc" {
    container rpc-clear-bgp-instance-rpki-server-all {
      tailf:ncs-device-type "netconf";
      tailf:display-when "not(../../ncs:module) or ../../ncs:module[ncs:name='Cisco-IOS-XR-ipv4-bgp-act']";
      tailf:action clear-bgp-instance-rpki-server-all {
        tailf:actionpoint ncsproxy {
          tailf:internal;
        }
        csc:xr-task "bgp";
        csc:cli-command "clear bgp instance <instance-name> rpki server *";
        description
          "Choose a particular BGP instance.
           RPKI clear command.
           clear RPKI cache-server.
           clear all RPKI cache-servers.
          ";
        input {
          leaf instance-name {
            mandatory true;
            type instance-name;
            description
              "instance name or all";
          }
        }
      }
    }
  }
  augment "/ncs:devices/ncs:device-group/ncs:ned-id/ncs:rpc" {
    container rpc-clear-bgp-instance-rpki-server-all {
      tailf:ncs-device-type "netconf";
      tailf:display-when "/ncs:devices/ncs:device[ncs:name=current()/../../../ncs:member]/ncs:module[ncs:name='Cisco-IOS-XR-ipv4-bgp-act']";
      tailf:action clear-bgp-instance-rpki-server-all {
        tailf:actionpoint ncsproxy {
          tailf:internal;
        }
        csc:xr-task "bgp";
        csc:cli-command "clear bgp instance <instance-name> rpki server *";
        description
          "Choose a particular BGP instance.
           RPKI clear command.
           clear RPKI cache-server.
           clear all RPKI cache-servers.
          ";
        input {
          leaf instance-name {
            mandatory true;
            type instance-name;
            description
              "instance name or all";
          }
        }
      }
    }
  }
  augment "/ncs:devices/ncs:device/ncs:rpc" {
    container rpc-clear-bgp-instance-rpki-server-all-serial-query {
      tailf:ncs-device-type "netconf";
      tailf:display-when "not(../../ncs:module) or ../../ncs:module[ncs:name='Cisco-IOS-XR-ipv4-bgp-act']";
      tailf:action clear-bgp-instance-rpki-server-all-serial-query {
        tailf:actionpoint ncsproxy {
          tailf:internal;
        }
        csc:xr-task "bgp";
        csc:cli-command "clear bgp instance <instance-name> rpki server * serial-query";
        description
          "Choose a particular BGP instance.
           RPKI clear command.
           clear RPKI cache-server.
           clear all RPKI cache-servers.
           send serial-queries to all cache-servers (with latest serial numbers).
          ";
        input {
          leaf instance-name {
            mandatory true;
            type instance-name;
            description
              "instance name or all";
          }
        }
      }
    }
  }
  augment "/ncs:devices/ncs:device-group/ncs:ned-id/ncs:rpc" {
    container rpc-clear-bgp-instance-rpki-server-all-serial-query {
      tailf:ncs-device-type "netconf";
      tailf:display-when "/ncs:devices/ncs:device[ncs:name=current()/../../../ncs:member]/ncs:module[ncs:name='Cisco-IOS-XR-ipv4-bgp-act']";
      tailf:action clear-bgp-instance-rpki-server-all-serial-query {
        tailf:actionpoint ncsproxy {
          tailf:internal;
        }
        csc:xr-task "bgp";
        csc:cli-command "clear bgp instance <instance-name> rpki server * serial-query";
        description
          "Choose a particular BGP instance.
           RPKI clear command.
           clear RPKI cache-server.
           clear all RPKI cache-servers.
           send serial-queries to all cache-servers (with latest serial numbers).
          ";
        input {
          leaf instance-name {
            mandatory true;
            type instance-name;
            description
              "instance name or all";
          }
        }
      }
    }
  }
  augment "/ncs:devices/ncs:device/ncs:rpc" {
    container rpc-clear-bgp-instance-performance-statistics {
      tailf:ncs-device-type "netconf";
      tailf:display-when "not(../../ncs:module) or ../../ncs:module[ncs:name='Cisco-IOS-XR-ipv4-bgp-act']";
      tailf:action clear-bgp-instance-performance-statistics {
        tailf:actionpoint ncsproxy {
          tailf:internal;
        }
        csc:xr-task "bgp";
        csc:cli-command "clear bgp instance <instance-name> performance-statistics";
        description
          "Choose a particular BGP instance.
           Clear performance statistics.
          ";
        input {
          leaf instance-name {
            mandatory true;
            type instance-name;
            description
              "instance name or all";
          }
        }
      }
    }
  }
  augment "/ncs:devices/ncs:device-group/ncs:ned-id/ncs:rpc" {
    container rpc-clear-bgp-instance-performance-statistics {
      tailf:ncs-device-type "netconf";
      tailf:display-when "/ncs:devices/ncs:device[ncs:name=current()/../../../ncs:member]/ncs:module[ncs:name='Cisco-IOS-XR-ipv4-bgp-act']";
      tailf:action clear-bgp-instance-performance-statistics {
        tailf:actionpoint ncsproxy {
          tailf:internal;
        }
        csc:xr-task "bgp";
        csc:cli-command "clear bgp instance <instance-name> performance-statistics";
        description
          "Choose a particular BGP instance.
           Clear performance statistics.
          ";
        input {
          leaf instance-name {
            mandatory true;
            type instance-name;
            description
              "instance name or all";
          }
        }
      }
    }
  }
  augment "/ncs:devices/ncs:device/ncs:rpc" {
    container rpc-clear-bgp-instance-peer-drops-ip-addr {
      tailf:ncs-device-type "netconf";
      tailf:display-when "not(../../ncs:module) or ../../ncs:module[ncs:name='Cisco-IOS-XR-ipv4-bgp-act']";
      tailf:action clear-bgp-instance-peer-drops-ip-addr {
        tailf:actionpoint ncsproxy {
          tailf:internal;
        }
        csc:xr-task "bgp";
        csc:cli-command "clear bgp instance <instance-name> peer-drops <ip-addr>";
        description
          "Choose a particular BGP instance.
           Clear established/dropped counters for a peer.
          ";
        input {
          leaf instance-name {
            mandatory true;
            type instance-name;
            description
              "instance name or all";
          }
          leaf ip-addr {
            mandatory true;
            type inet:ip-address;
            description
              "BGP neighbor IP address";
          }
        }
      }
    }
  }
  augment "/ncs:devices/ncs:device-group/ncs:ned-id/ncs:rpc" {
    container rpc-clear-bgp-instance-peer-drops-ip-addr {
      tailf:ncs-device-type "netconf";
      tailf:display-when "/ncs:devices/ncs:device[ncs:name=current()/../../../ncs:member]/ncs:module[ncs:name='Cisco-IOS-XR-ipv4-bgp-act']";
      tailf:action clear-bgp-instance-peer-drops-ip-addr {
        tailf:actionpoint ncsproxy {
          tailf:internal;
        }
        csc:xr-task "bgp";
        csc:cli-command "clear bgp instance <instance-name> peer-drops <ip-addr>";
        description
          "Choose a particular BGP instance.
           Clear established/dropped counters for a peer.
          ";
        input {
          leaf instance-name {
            mandatory true;
            type instance-name;
            description
              "instance name or all";
          }
          leaf ip-addr {
            mandatory true;
            type inet:ip-address;
            description
              "BGP neighbor IP address";
          }
        }
      }
    }
  }
  augment "/ncs:devices/ncs:device/ncs:rpc" {
    container rpc-clear-bgp-instance-peer-drops-all {
      tailf:ncs-device-type "netconf";
      tailf:display-when "not(../../ncs:module) or ../../ncs:module[ncs:name='Cisco-IOS-XR-ipv4-bgp-act']";
      tailf:action clear-bgp-instance-peer-drops-all {
        tailf:actionpoint ncsproxy {
          tailf:internal;
        }
        csc:xr-task "bgp";
        csc:cli-command "clear bgp instance <instance-name> peer-drops *";
        description
          "Choose a particular BGP instance.
           Clear established/dropped counters for a peer.
           All Neighbors.
          ";
        input {
          leaf instance-name {
            mandatory true;
            type instance-name;
            description
              "instance name or all";
          }
        }
      }
    }
  }
  augment "/ncs:devices/ncs:device-group/ncs:ned-id/ncs:rpc" {
    container rpc-clear-bgp-instance-peer-drops-all {
      tailf:ncs-device-type "netconf";
      tailf:display-when "/ncs:devices/ncs:device[ncs:name=current()/../../../ncs:member]/ncs:module[ncs:name='Cisco-IOS-XR-ipv4-bgp-act']";
      tailf:action clear-bgp-instance-peer-drops-all {
        tailf:actionpoint ncsproxy {
          tailf:internal;
        }
        csc:xr-task "bgp";
        csc:cli-command "clear bgp instance <instance-name> peer-drops *";
        description
          "Choose a particular BGP instance.
           Clear established/dropped counters for a peer.
           All Neighbors.
          ";
        input {
          leaf instance-name {
            mandatory true;
            type instance-name;
            description
              "instance name or all";
          }
        }
      }
    }
  }
  augment "/ncs:devices/ncs:device/ncs:rpc" {
    container rpc-clear-bgp-instance-nexthop-registration-ip-addr {
      tailf:ncs-device-type "netconf";
      tailf:display-when "not(../../ncs:module) or ../../ncs:module[ncs:name='Cisco-IOS-XR-ipv4-bgp-act']";
      tailf:action clear-bgp-instance-nexthop-registration-ip-addr {
        tailf:actionpoint ncsproxy {
          tailf:internal;
        }
        csc:xr-task "bgp";
        csc:cli-command "clear bgp instance <instance-name> nexthop registration <ip-addr>";
        description
          "Choose a particular BGP instance.
           Clear nexthop.
           Registration with RIB and reregister.
          ";
        input {
          leaf instance-name {
            mandatory true;
            type instance-name;
            description
              "instance name or all";
          }
          leaf ip-addr {
            mandatory true;
            type inet:ip-address;
            description
              "Nexthop address";
          }
        }
      }
    }
  }
  augment "/ncs:devices/ncs:device-group/ncs:ned-id/ncs:rpc" {
    container rpc-clear-bgp-instance-nexthop-registration-ip-addr {
      tailf:ncs-device-type "netconf";
      tailf:display-when "/ncs:devices/ncs:device[ncs:name=current()/../../../ncs:member]/ncs:module[ncs:name='Cisco-IOS-XR-ipv4-bgp-act']";
      tailf:action clear-bgp-instance-nexthop-registration-ip-addr {
        tailf:actionpoint ncsproxy {
          tailf:internal;
        }
        csc:xr-task "bgp";
        csc:cli-command "clear bgp instance <instance-name> nexthop registration <ip-addr>";
        description
          "Choose a particular BGP instance.
           Clear nexthop.
           Registration with RIB and reregister.
          ";
        input {
          leaf instance-name {
            mandatory true;
            type instance-name;
            description
              "instance name or all";
          }
          leaf ip-addr {
            mandatory true;
            type inet:ip-address;
            description
              "Nexthop address";
          }
        }
      }
    }
  }
  augment "/ncs:devices/ncs:device/ncs:rpc" {
    container rpc-clear-bgp-instance-nexthop-performance-statistics {
      tailf:ncs-device-type "netconf";
      tailf:display-when "not(../../ncs:module) or ../../ncs:module[ncs:name='Cisco-IOS-XR-ipv4-bgp-act']";
      tailf:action clear-bgp-instance-nexthop-performance-statistics {
        tailf:actionpoint ncsproxy {
          tailf:internal;
        }
        csc:xr-task "bgp";
        csc:cli-command "clear bgp instance <instance-name> nexthop performance-statistics";
        description
          "Choose a particular BGP instance.
           Clear nexthop.
           Performance statistics information related to processing.
          ";
        input {
          leaf instance-name {
            mandatory true;
            type instance-name;
            description
              "instance name or all";
          }
        }
      }
    }
  }
  augment "/ncs:devices/ncs:device-group/ncs:ned-id/ncs:rpc" {
    container rpc-clear-bgp-instance-nexthop-performance-statistics {
      tailf:ncs-device-type "netconf";
      tailf:display-when "/ncs:devices/ncs:device[ncs:name=current()/../../../ncs:member]/ncs:module[ncs:name='Cisco-IOS-XR-ipv4-bgp-act']";
      tailf:action clear-bgp-instance-nexthop-performance-statistics {
        tailf:actionpoint ncsproxy {
          tailf:internal;
        }
        csc:xr-task "bgp";
        csc:cli-command "clear bgp instance <instance-name> nexthop performance-statistics";
        description
          "Choose a particular BGP instance.
           Clear nexthop.
           Performance statistics information related to processing.
          ";
        input {
          leaf instance-name {
            mandatory true;
            type instance-name;
            description
              "instance name or all";
          }
        }
      }
    }
  }
  augment "/ncs:devices/ncs:device/ncs:rpc" {
    container rpc-clear-bgp-instance-afi-safi-flap-statistics-ipv6-prefix {
      tailf:ncs-device-type "netconf";
      tailf:display-when "not(../../ncs:module) or ../../ncs:module[ncs:name='Cisco-IOS-XR-ipv4-bgp-act']";
      tailf:action clear-bgp-instance-afi-safi-flap-statistics-ipv6-prefix {
        tailf:actionpoint ncsproxy {
          tailf:internal;
        }
        csc:xr-task "bgp";
        csc:cli-command "clear bgp instance <instance-name> <afi-safi-name> flap-statistics <ipv6-prefix>";
        description
          "Choose a particular BGP instance.
           Clear flap statistics.
          ";
        input {
          leaf instance-name {
            mandatory true;
            type instance-name;
            description
              "instance name or all";
          }
          leaf afi-safi-name {
            mandatory true;
            type afi-safi-type;
            description
              "AFI and SAFI";
          }
          leaf ipv6-prefix {
            mandatory true;
            type inet:ipv6-prefix;
            description
              "IPv6 Network and mask or masklength to clear flap statistics";
          }
        }
      }
    }
  }
  augment "/ncs:devices/ncs:device-group/ncs:ned-id/ncs:rpc" {
    container rpc-clear-bgp-instance-afi-safi-flap-statistics-ipv6-prefix {
      tailf:ncs-device-type "netconf";
      tailf:display-when "/ncs:devices/ncs:device[ncs:name=current()/../../../ncs:member]/ncs:module[ncs:name='Cisco-IOS-XR-ipv4-bgp-act']";
      tailf:action clear-bgp-instance-afi-safi-flap-statistics-ipv6-prefix {
        tailf:actionpoint ncsproxy {
          tailf:internal;
        }
        csc:xr-task "bgp";
        csc:cli-command "clear bgp instance <instance-name> <afi-safi-name> flap-statistics <ipv6-prefix>";
        description
          "Choose a particular BGP instance.
           Clear flap statistics.
          ";
        input {
          leaf instance-name {
            mandatory true;
            type instance-name;
            description
              "instance name or all";
          }
          leaf afi-safi-name {
            mandatory true;
            type afi-safi-type;
            description
              "AFI and SAFI";
          }
          leaf ipv6-prefix {
            mandatory true;
            type inet:ipv6-prefix;
            description
              "IPv6 Network and mask or masklength to clear flap statistics";
          }
        }
      }
    }
  }
  augment "/ncs:devices/ncs:device/ncs:rpc" {
    container rpc-clear-bgp-instance-afi-safi-dampening-ipv6-prefix {
      tailf:ncs-device-type "netconf";
      tailf:display-when "not(../../ncs:module) or ../../ncs:module[ncs:name='Cisco-IOS-XR-ipv4-bgp-act']";
      tailf:action clear-bgp-instance-afi-safi-dampening-ipv6-prefix {
        tailf:actionpoint ncsproxy {
          tailf:internal;
        }
        csc:xr-task "bgp";
        csc:cli-command "clear bgp instance <instance-name> <afi-safi-name> dampening <ipv6-prefix>";
        description
          "Choose a particular BGP instance.
           Clear route flap dampening information.
          ";
        input {
          leaf instance-name {
            mandatory true;
            type instance-name;
            description
              "instance name or all";
          }
          leaf afi-safi-name {
            mandatory true;
            type afi-safi-type;
            description
              "AFI and SAFI";
          }
          leaf ipv6-prefix {
            mandatory true;
            type inet:ipv6-prefix;
            description
              "IPv6 Network and mask or masklength to clear dampening information";
          }
        }
      }
    }
  }
  augment "/ncs:devices/ncs:device-group/ncs:ned-id/ncs:rpc" {
    container rpc-clear-bgp-instance-afi-safi-dampening-ipv6-prefix {
      tailf:ncs-device-type "netconf";
      tailf:display-when "/ncs:devices/ncs:device[ncs:name=current()/../../../ncs:member]/ncs:module[ncs:name='Cisco-IOS-XR-ipv4-bgp-act']";
      tailf:action clear-bgp-instance-afi-safi-dampening-ipv6-prefix {
        tailf:actionpoint ncsproxy {
          tailf:internal;
        }
        csc:xr-task "bgp";
        csc:cli-command "clear bgp instance <instance-name> <afi-safi-name> dampening <ipv6-prefix>";
        description
          "Choose a particular BGP instance.
           Clear route flap dampening information.
          ";
        input {
          leaf instance-name {
            mandatory true;
            type instance-name;
            description
              "instance name or all";
          }
          leaf afi-safi-name {
            mandatory true;
            type afi-safi-type;
            description
              "AFI and SAFI";
          }
          leaf ipv6-prefix {
            mandatory true;
            type inet:ipv6-prefix;
            description
              "IPv6 Network and mask or masklength to clear dampening information";
          }
        }
      }
    }
  }
  augment "/ncs:devices/ncs:device/ncs:rpc" {
    container rpc-clear-bgp-instance-afi-safi-flap-statistics-ipv4-prefix {
      tailf:ncs-device-type "netconf";
      tailf:display-when "not(../../ncs:module) or ../../ncs:module[ncs:name='Cisco-IOS-XR-ipv4-bgp-act']";
      tailf:action clear-bgp-instance-afi-safi-flap-statistics-ipv4-prefix {
        tailf:actionpoint ncsproxy {
          tailf:internal;
        }
        csc:xr-task "bgp";
        csc:cli-command "clear bgp instance <instance-name> <afi-safi-name> flap-statistics <ipv4-prefix>";
        description
          "Choose a particular BGP instance.
           Clear flap statistics.
          ";
        input {
          leaf instance-name {
            mandatory true;
            type instance-name;
            description
              "instance name or all";
          }
          leaf afi-safi-name {
            mandatory true;
            type afi-safi-type;
            description
              "AFI and SAFI";
          }
          leaf ipv4-prefix {
            mandatory true;
            type inet:ipv4-prefix;
            description
              "IPv4 Network and mask or masklength to clear flap statistics";
          }
        }
      }
    }
  }
  augment "/ncs:devices/ncs:device-group/ncs:ned-id/ncs:rpc" {
    container rpc-clear-bgp-instance-afi-safi-flap-statistics-ipv4-prefix {
      tailf:ncs-device-type "netconf";
      tailf:display-when "/ncs:devices/ncs:device[ncs:name=current()/../../../ncs:member]/ncs:module[ncs:name='Cisco-IOS-XR-ipv4-bgp-act']";
      tailf:action clear-bgp-instance-afi-safi-flap-statistics-ipv4-prefix {
        tailf:actionpoint ncsproxy {
          tailf:internal;
        }
        csc:xr-task "bgp";
        csc:cli-command "clear bgp instance <instance-name> <afi-safi-name> flap-statistics <ipv4-prefix>";
        description
          "Choose a particular BGP instance.
           Clear flap statistics.
          ";
        input {
          leaf instance-name {
            mandatory true;
            type instance-name;
            description
              "instance name or all";
          }
          leaf afi-safi-name {
            mandatory true;
            type afi-safi-type;
            description
              "AFI and SAFI";
          }
          leaf ipv4-prefix {
            mandatory true;
            type inet:ipv4-prefix;
            description
              "IPv4 Network and mask or masklength to clear flap statistics";
          }
        }
      }
    }
  }
  augment "/ncs:devices/ncs:device/ncs:rpc" {
    container rpc-clear-bgp-instance-afi-safi-dampening-ipv4-prefix {
      tailf:ncs-device-type "netconf";
      tailf:display-when "not(../../ncs:module) or ../../ncs:module[ncs:name='Cisco-IOS-XR-ipv4-bgp-act']";
      tailf:action clear-bgp-instance-afi-safi-dampening-ipv4-prefix {
        tailf:actionpoint ncsproxy {
          tailf:internal;
        }
        csc:xr-task "bgp";
        csc:cli-command "clear bgp instance <instance-name> <afi-safi-name> dampening <ipv4-prefix>";
        description
          "Choose a particular BGP instance.
           Clear route flap dampening information.
          ";
        input {
          leaf instance-name {
            mandatory true;
            type instance-name;
            description
              "instance name or all";
          }
          leaf afi-safi-name {
            mandatory true;
            type afi-safi-type;
            description
              "AFI and SAFI";
          }
          leaf ipv4-prefix {
            mandatory true;
            type inet:ipv4-prefix;
            description
              "IPv4 Network and mask or masklength to clear dampening information";
          }
        }
      }
    }
  }
  augment "/ncs:devices/ncs:device-group/ncs:ned-id/ncs:rpc" {
    container rpc-clear-bgp-instance-afi-safi-dampening-ipv4-prefix {
      tailf:ncs-device-type "netconf";
      tailf:display-when "/ncs:devices/ncs:device[ncs:name=current()/../../../ncs:member]/ncs:module[ncs:name='Cisco-IOS-XR-ipv4-bgp-act']";
      tailf:action clear-bgp-instance-afi-safi-dampening-ipv4-prefix {
        tailf:actionpoint ncsproxy {
          tailf:internal;
        }
        csc:xr-task "bgp";
        csc:cli-command "clear bgp instance <instance-name> <afi-safi-name> dampening <ipv4-prefix>";
        description
          "Choose a particular BGP instance.
           Clear route flap dampening information.
          ";
        input {
          leaf instance-name {
            mandatory true;
            type instance-name;
            description
              "instance name or all";
          }
          leaf afi-safi-name {
            mandatory true;
            type afi-safi-type;
            description
              "AFI and SAFI";
          }
          leaf ipv4-prefix {
            mandatory true;
            type inet:ipv4-prefix;
            description
              "IPv4 Network and mask or masklength to clear dampening information";
          }
        }
      }
    }
  }
  augment "/ncs:devices/ncs:device/ncs:rpc" {
    container rpc-clear-bgp-instance-external {
      tailf:ncs-device-type "netconf";
      tailf:display-when "not(../../ncs:module) or ../../ncs:module[ncs:name='Cisco-IOS-XR-ipv4-bgp-act']";
      tailf:action clear-bgp-instance-external {
        tailf:actionpoint ncsproxy {
          tailf:internal;
        }
        csc:xr-task "bgp";
        csc:cli-command "clear bgp instance <instance-name> external";
        description
          "Choose a particular BGP instance.
           Clear all external peers.
          ";
        input {
          leaf instance-name {
            mandatory true;
            type instance-name;
            description
              "instance name or all";
          }
        }
      }
    }
  }
  augment "/ncs:devices/ncs:device-group/ncs:ned-id/ncs:rpc" {
    container rpc-clear-bgp-instance-external {
      tailf:ncs-device-type "netconf";
      tailf:display-when "/ncs:devices/ncs:device[ncs:name=current()/../../../ncs:member]/ncs:module[ncs:name='Cisco-IOS-XR-ipv4-bgp-act']";
      tailf:action clear-bgp-instance-external {
        tailf:actionpoint ncsproxy {
          tailf:internal;
        }
        csc:xr-task "bgp";
        csc:cli-command "clear bgp instance <instance-name> external";
        description
          "Choose a particular BGP instance.
           Clear all external peers.
          ";
        input {
          leaf instance-name {
            mandatory true;
            type instance-name;
            description
              "instance name or all";
          }
        }
      }
    }
  }
  augment "/ncs:devices/ncs:device/ncs:rpc" {
    container rpc-clear-bgp-instance-external-graceful {
      tailf:ncs-device-type "netconf";
      tailf:display-when "not(../../ncs:module) or ../../ncs:module[ncs:name='Cisco-IOS-XR-ipv4-bgp-act']";
      tailf:action clear-bgp-instance-external-graceful {
        tailf:actionpoint ncsproxy {
          tailf:internal;
        }
        csc:xr-task "bgp";
        csc:cli-command "clear bgp instance <instance-name> external graceful";
        description
          "Choose a particular BGP instance.
           Clear all external peers.
           Clear with a hard reset and a graceful restart.
          ";
        input {
          leaf instance-name {
            mandatory true;
            type instance-name;
            description
              "instance name or all";
          }
        }
      }
    }
  }
  augment "/ncs:devices/ncs:device-group/ncs:ned-id/ncs:rpc" {
    container rpc-clear-bgp-instance-external-graceful {
      tailf:ncs-device-type "netconf";
      tailf:display-when "/ncs:devices/ncs:device[ncs:name=current()/../../../ncs:member]/ncs:module[ncs:name='Cisco-IOS-XR-ipv4-bgp-act']";
      tailf:action clear-bgp-instance-external-graceful {
        tailf:actionpoint ncsproxy {
          tailf:internal;
        }
        csc:xr-task "bgp";
        csc:cli-command "clear bgp instance <instance-name> external graceful";
        description
          "Choose a particular BGP instance.
           Clear all external peers.
           Clear with a hard reset and a graceful restart.
          ";
        input {
          leaf instance-name {
            mandatory true;
            type instance-name;
            description
              "instance name or all";
          }
        }
      }
    }
  }
  augment "/ncs:devices/ncs:device/ncs:rpc" {
    container rpc-clear-bgp-instance-bestpath-vrf-afi-safi {
      tailf:ncs-device-type "netconf";
      tailf:display-when "not(../../ncs:module) or ../../ncs:module[ncs:name='Cisco-IOS-XR-ipv4-bgp-act']";
      tailf:action clear-bgp-instance-bestpath-vrf-afi-safi {
        tailf:actionpoint ncsproxy {
          tailf:internal;
        }
        csc:xr-task "bgp";
        csc:cli-command "clear bgp instance <instance-name> bestpath vrf <vrf-all> <afi-safi-name>";
        description
          "Choose a particular BGP instance.
           re-run BGP bestpath selection.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-bestpath-vrf-afi-safi {
      tailf:ncs-device-type "netconf";
      tailf:display-when "/ncs:devices/ncs:device[ncs:name=current()/../../../ncs:member]/ncs:module[ncs:name='Cisco-IOS-XR-ipv4-bgp-act']";
      tailf:action clear-bgp-instance-bestpath-vrf-afi-safi {
        tailf:actionpoint ncsproxy {
          tailf:internal;
        }
        csc:xr-task "bgp";
        csc:cli-command "clear bgp instance <instance-name> bestpath vrf <vrf-all> <afi-safi-name>";
        description
          "Choose a particular BGP instance.
           re-run BGP bestpath selection.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-instance-bestpath-vrf-afi-safi-vrf {
      tailf:ncs-device-type "netconf";
      tailf:display-when "not(../../ncs:module) or ../../ncs:module[ncs:name='Cisco-IOS-XR-ipv4-bgp-act']";
      tailf:action clear-bgp-instance-bestpath-vrf-afi-safi-vrf {
        tailf:actionpoint ncsproxy {
          tailf:internal;
        }
        csc:xr-task "bgp";
        csc:cli-command "clear bgp instance <instance-name> bestpath vrf <vrf-all> <afi-safi-name> vrf <vrf-name>";
        description
          "Choose a particular BGP instance.
           re-run BGP bestpath selection.
           Specify a VRF.
           Display routes for a specified VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf vrf-name {
            mandatory true;
            type string;
            description
              "VRF name";
          }
        }
      }
    }
  }
  augment "/ncs:devices/ncs:device-group/ncs:ned-id/ncs:rpc" {
    container rpc-clear-bgp-instance-bestpath-vrf-afi-safi-vrf {
      tailf:ncs-device-type "netconf";
      tailf:display-when "/ncs:devices/ncs:device[ncs:name=current()/../../../ncs:member]/ncs:module[ncs:name='Cisco-IOS-XR-ipv4-bgp-act']";
      tailf:action clear-bgp-instance-bestpath-vrf-afi-safi-vrf {
        tailf:actionpoint ncsproxy {
          tailf:internal;
        }
        csc:xr-task "bgp";
        csc:cli-command "clear bgp instance <instance-name> bestpath vrf <vrf-all> <afi-safi-name> vrf <vrf-name>";
        description
          "Choose a particular BGP instance.
           re-run BGP bestpath selection.
           Specify a VRF.
           Display routes for a specified VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf vrf-name {
            mandatory true;
            type string;
            description
              "VRF name";
          }
        }
      }
    }
  }
  augment "/ncs:devices/ncs:device/ncs:rpc" {
    container rpc-clear-bgp-instance-bestpath-vrf-afi-safi-rd {
      tailf:ncs-device-type "netconf";
      tailf:display-when "not(../../ncs:module) or ../../ncs:module[ncs:name='Cisco-IOS-XR-ipv4-bgp-act']";
      tailf:action clear-bgp-instance-bestpath-vrf-afi-safi-rd {
        tailf:actionpoint ncsproxy {
          tailf:internal;
        }
        csc:xr-task "bgp";
        csc:cli-command "clear bgp instance <instance-name> bestpath vrf <vrf-all> <afi-safi-name> rd <rd>";
        description
          "Choose a particular BGP instance.
           re-run BGP bestpath selection.
           Specify a VRF.
           Display routes with a specific route distinguisher.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf rd {
            mandatory true;
            type rd;
            description
              "Route distinguisher";
          }
        }
      }
    }
  }
  augment "/ncs:devices/ncs:device-group/ncs:ned-id/ncs:rpc" {
    container rpc-clear-bgp-instance-bestpath-vrf-afi-safi-rd {
      tailf:ncs-device-type "netconf";
      tailf:display-when "/ncs:devices/ncs:device[ncs:name=current()/../../../ncs:member]/ncs:module[ncs:name='Cisco-IOS-XR-ipv4-bgp-act']";
      tailf:action clear-bgp-instance-bestpath-vrf-afi-safi-rd {
        tailf:actionpoint ncsproxy {
          tailf:internal;
        }
        csc:xr-task "bgp";
        csc:cli-command "clear bgp instance <instance-name> bestpath vrf <vrf-all> <afi-safi-name> rd <rd>";
        description
          "Choose a particular BGP instance.
           re-run BGP bestpath selection.
           Specify a VRF.
           Display routes with a specific route distinguisher.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf rd {
            mandatory true;
            type rd;
            description
              "Route distinguisher";
          }
        }
      }
    }
  }
  augment "/ncs:devices/ncs:device/ncs:rpc" {
    container rpc-clear-bgp-instance-bestpath-vrf-afi-safi-ipv6-prefix {
      tailf:ncs-device-type "netconf";
      tailf:display-when "not(../../ncs:module) or ../../ncs:module[ncs:name='Cisco-IOS-XR-ipv4-bgp-act']";
      tailf:action clear-bgp-instance-bestpath-vrf-afi-safi-ipv6-prefix {
        tailf:actionpoint ncsproxy {
          tailf:internal;
        }
        csc:xr-task "bgp";
        csc:cli-command "clear bgp instance <instance-name> bestpath vrf <vrf-all> <afi-safi-name> <ipv6-prefix>";
        description
          "Choose a particular BGP instance.
           re-run BGP bestpath selection.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv6-prefix {
            mandatory true;
            type inet:ipv6-prefix;
            description
              "IPv6 network and masklength";
          }
        }
      }
    }
  }
  augment "/ncs:devices/ncs:device-group/ncs:ned-id/ncs:rpc" {
    container rpc-clear-bgp-instance-bestpath-vrf-afi-safi-ipv6-prefix {
      tailf:ncs-device-type "netconf";
      tailf:display-when "/ncs:devices/ncs:device[ncs:name=current()/../../../ncs:member]/ncs:module[ncs:name='Cisco-IOS-XR-ipv4-bgp-act']";
      tailf:action clear-bgp-instance-bestpath-vrf-afi-safi-ipv6-prefix {
        tailf:actionpoint ncsproxy {
          tailf:internal;
        }
        csc:xr-task "bgp";
        csc:cli-command "clear bgp instance <instance-name> bestpath vrf <vrf-all> <afi-safi-name> <ipv6-prefix>";
        description
          "Choose a particular BGP instance.
           re-run BGP bestpath selection.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv6-prefix {
            mandatory true;
            type inet:ipv6-prefix;
            description
              "IPv6 network and masklength";
          }
        }
      }
    }
  }
  augment "/ncs:devices/ncs:device/ncs:rpc" {
    container rpc-clear-bgp-instance-bestpath-vrf-afi-safi-ipv6-addr {
      tailf:ncs-device-type "netconf";
      tailf:display-when "not(../../ncs:module) or ../../ncs:module[ncs:name='Cisco-IOS-XR-ipv4-bgp-act']";
      tailf:action clear-bgp-instance-bestpath-vrf-afi-safi-ipv6-addr {
        tailf:actionpoint ncsproxy {
          tailf:internal;
        }
        csc:xr-task "bgp";
        csc:cli-command "clear bgp instance <instance-name> bestpath vrf <vrf-all> <afi-safi-name> <ipv6-addr>";
        description
          "Choose a particular BGP instance.
           re-run BGP bestpath selection.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv6-addr {
            mandatory true;
            type inet:ipv6-address;
            description
              "IPv6 network";
          }
        }
      }
    }
  }
  augment "/ncs:devices/ncs:device-group/ncs:ned-id/ncs:rpc" {
    container rpc-clear-bgp-instance-bestpath-vrf-afi-safi-ipv6-addr {
      tailf:ncs-device-type "netconf";
      tailf:display-when "/ncs:devices/ncs:device[ncs:name=current()/../../../ncs:member]/ncs:module[ncs:name='Cisco-IOS-XR-ipv4-bgp-act']";
      tailf:action clear-bgp-instance-bestpath-vrf-afi-safi-ipv6-addr {
        tailf:actionpoint ncsproxy {
          tailf:internal;
        }
        csc:xr-task "bgp";
        csc:cli-command "clear bgp instance <instance-name> bestpath vrf <vrf-all> <afi-safi-name> <ipv6-addr>";
        description
          "Choose a particular BGP instance.
           re-run BGP bestpath selection.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv6-addr {
            mandatory true;
            type inet:ipv6-address;
            description
              "IPv6 network";
          }
        }
      }
    }
  }
  augment "/ncs:devices/ncs:device/ncs:rpc" {
    container rpc-clear-bgp-instance-bestpath-vrf-afi-safi-ipv6-addr-ipv6-netmask {
      tailf:ncs-device-type "netconf";
      tailf:display-when "not(../../ncs:module) or ../../ncs:module[ncs:name='Cisco-IOS-XR-ipv4-bgp-act']";
      tailf:action clear-bgp-instance-bestpath-vrf-afi-safi-ipv6-addr-ipv6-netmask {
        tailf:actionpoint ncsproxy {
          tailf:internal;
        }
        csc:xr-task "bgp";
        csc:cli-command "clear bgp instance <instance-name> bestpath vrf <vrf-all> <afi-safi-name> <ipv6-addr> <ipv6-netmask>";
        description
          "Choose a particular BGP instance.
           re-run BGP bestpath selection.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device-group/ncs:ned-id/ncs:rpc" {
    container rpc-clear-bgp-instance-bestpath-vrf-afi-safi-ipv6-addr-ipv6-netmask {
      tailf:ncs-device-type "netconf";
      tailf:display-when "/ncs:devices/ncs:device[ncs:name=current()/../../../ncs:member]/ncs:module[ncs:name='Cisco-IOS-XR-ipv4-bgp-act']";
      tailf:action clear-bgp-instance-bestpath-vrf-afi-safi-ipv6-addr-ipv6-netmask {
        tailf:actionpoint ncsproxy {
          tailf:internal;
        }
        csc:xr-task "bgp";
        csc:cli-command "clear bgp instance <instance-name> bestpath vrf <vrf-all> <afi-safi-name> <ipv6-addr> <ipv6-netmask>";
        description
          "Choose a particular BGP instance.
           re-run BGP bestpath selection.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device/ncs:rpc" {
    container rpc-clear-bgp-instance-bestpath-vrf-afi-safi-vrf-network {
      tailf:ncs-device-type "netconf";
      tailf:display-when "not(../../ncs:module) or ../../ncs:module[ncs:name='Cisco-IOS-XR-ipv4-bgp-act']";
      tailf:action clear-bgp-instance-bestpath-vrf-afi-safi-vrf-network {
        tailf:actionpoint ncsproxy {
          tailf:internal;
        }
        csc:xr-task "bgp";
        csc:cli-command "clear bgp instance <instance-name> bestpath vrf <vrf-all> <afi-safi-name> vrf <vrf-name> <network>";
        description
          "Choose a particular BGP instance.
           re-run BGP bestpath selection.
           Specify a VRF.
           Display routes for a specified VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf vrf-name {
            mandatory true;
            type string;
            description
              "VRF name";
          }
          leaf network {
            mandatory true;
            type string;
            description
              "Address family modifier specific network";
          }
        }
      }
    }
  }
  augment "/ncs:devices/ncs:device-group/ncs:ned-id/ncs:rpc" {
    container rpc-clear-bgp-instance-bestpath-vrf-afi-safi-vrf-network {
      tailf:ncs-device-type "netconf";
      tailf:display-when "/ncs:devices/ncs:device[ncs:name=current()/../../../ncs:member]/ncs:module[ncs:name='Cisco-IOS-XR-ipv4-bgp-act']";
      tailf:action clear-bgp-instance-bestpath-vrf-afi-safi-vrf-network {
        tailf:actionpoint ncsproxy {
          tailf:internal;
        }
        csc:xr-task "bgp";
        csc:cli-command "clear bgp instance <instance-name> bestpath vrf <vrf-all> <afi-safi-name> vrf <vrf-name> <network>";
        description
          "Choose a particular BGP instance.
           re-run BGP bestpath selection.
           Specify a VRF.
           Display routes for a specified VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf vrf-name {
            mandatory true;
            type string;
            description
              "VRF name";
          }
          leaf network {
            mandatory true;
            type string;
            description
              "Address family modifier specific network";
          }
        }
      }
    }
  }
  augment "/ncs:devices/ncs:device/ncs:rpc" {
    container rpc-clear-bgp-instance-bestpath-vrf-afi-safi-rd-network {
      tailf:ncs-device-type "netconf";
      tailf:display-when "not(../../ncs:module) or ../../ncs:module[ncs:name='Cisco-IOS-XR-ipv4-bgp-act']";
      tailf:action clear-bgp-instance-bestpath-vrf-afi-safi-rd-network {
        tailf:actionpoint ncsproxy {
          tailf:internal;
        }
        csc:xr-task "bgp";
        csc:cli-command "clear bgp instance <instance-name> bestpath vrf <vrf-all> <afi-safi-name> rd <rd> <network>";
        description
          "Choose a particular BGP instance.
           re-run BGP bestpath selection.
           Specify a VRF.
           Display routes with a specific route distinguisher.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf rd {
            mandatory true;
            type rd;
            description
              "Route distinguisher";
          }
          leaf network {
            mandatory true;
            type string;
            description
              "Address family modifier specific network";
          }
        }
      }
    }
  }
  augment "/ncs:devices/ncs:device-group/ncs:ned-id/ncs:rpc" {
    container rpc-clear-bgp-instance-bestpath-vrf-afi-safi-rd-network {
      tailf:ncs-device-type "netconf";
      tailf:display-when "/ncs:devices/ncs:device[ncs:name=current()/../../../ncs:member]/ncs:module[ncs:name='Cisco-IOS-XR-ipv4-bgp-act']";
      tailf:action clear-bgp-instance-bestpath-vrf-afi-safi-rd-network {
        tailf:actionpoint ncsproxy {
          tailf:internal;
        }
        csc:xr-task "bgp";
        csc:cli-command "clear bgp instance <instance-name> bestpath vrf <vrf-all> <afi-safi-name> rd <rd> <network>";
        description
          "Choose a particular BGP instance.
           re-run BGP bestpath selection.
           Specify a VRF.
           Display routes with a specific route distinguisher.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf rd {
            mandatory true;
            type rd;
            description
              "Route distinguisher";
          }
          leaf network {
            mandatory true;
            type string;
            description
              "Address family modifier specific network";
          }
        }
      }
    }
  }
  augment "/ncs:devices/ncs:device/ncs:rpc" {
    container rpc-clear-bgp-instance-bestpath-vrf-afi-safi-network {
      tailf:ncs-device-type "netconf";
      tailf:display-when "not(../../ncs:module) or ../../ncs:module[ncs:name='Cisco-IOS-XR-ipv4-bgp-act']";
      tailf:action clear-bgp-instance-bestpath-vrf-afi-safi-network {
        tailf:actionpoint ncsproxy {
          tailf:internal;
        }
        csc:xr-task "bgp";
        csc:cli-command "clear bgp instance <instance-name> bestpath vrf <vrf-all> <afi-safi-name> <network>";
        description
          "Choose a particular BGP instance.
           re-run BGP bestpath selection.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf network {
            mandatory true;
            type string;
            description
              "Address family modifier specific network";
          }
        }
      }
    }
  }
  augment "/ncs:devices/ncs:device-group/ncs:ned-id/ncs:rpc" {
    container rpc-clear-bgp-instance-bestpath-vrf-afi-safi-network {
      tailf:ncs-device-type "netconf";
      tailf:display-when "/ncs:devices/ncs:device[ncs:name=current()/../../../ncs:member]/ncs:module[ncs:name='Cisco-IOS-XR-ipv4-bgp-act']";
      tailf:action clear-bgp-instance-bestpath-vrf-afi-safi-network {
        tailf:actionpoint ncsproxy {
          tailf:internal;
        }
        csc:xr-task "bgp";
        csc:cli-command "clear bgp instance <instance-name> bestpath vrf <vrf-all> <afi-safi-name> <network>";
        description
          "Choose a particular BGP instance.
           re-run BGP bestpath selection.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf network {
            mandatory true;
            type string;
            description
              "Address family modifier specific network";
          }
        }
      }
    }
  }
  augment "/ncs:devices/ncs:device/ncs:rpc" {
    container rpc-clear-bgp-instance-bestpath-vrf-afi-safi-ipv4-addr {
      tailf:ncs-device-type "netconf";
      tailf:display-when "not(../../ncs:module) or ../../ncs:module[ncs:name='Cisco-IOS-XR-ipv4-bgp-act']";
      tailf:action clear-bgp-instance-bestpath-vrf-afi-safi-ipv4-addr {
        tailf:actionpoint ncsproxy {
          tailf:internal;
        }
        csc:xr-task "bgp";
        csc:cli-command "clear bgp instance <instance-name> bestpath vrf <vrf-all> <afi-safi-name> <ipv4-addr>";
        description
          "Choose a particular BGP instance.
           re-run BGP bestpath selection.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv4-addr {
            mandatory true;
            type inet:ipv4-address;
            description
              "IPv4 network";
          }
        }
      }
    }
  }
  augment "/ncs:devices/ncs:device-group/ncs:ned-id/ncs:rpc" {
    container rpc-clear-bgp-instance-bestpath-vrf-afi-safi-ipv4-addr {
      tailf:ncs-device-type "netconf";
      tailf:display-when "/ncs:devices/ncs:device[ncs:name=current()/../../../ncs:member]/ncs:module[ncs:name='Cisco-IOS-XR-ipv4-bgp-act']";
      tailf:action clear-bgp-instance-bestpath-vrf-afi-safi-ipv4-addr {
        tailf:actionpoint ncsproxy {
          tailf:internal;
        }
        csc:xr-task "bgp";
        csc:cli-command "clear bgp instance <instance-name> bestpath vrf <vrf-all> <afi-safi-name> <ipv4-addr>";
        description
          "Choose a particular BGP instance.
           re-run BGP bestpath selection.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv4-addr {
            mandatory true;
            type inet:ipv4-address;
            description
              "IPv4 network";
          }
        }
      }
    }
  }
  augment "/ncs:devices/ncs:device/ncs:rpc" {
    container rpc-clear-bgp-instance-bestpath-vrf-afi-safi-ipv4-addr-ipv4-mask {
      tailf:ncs-device-type "netconf";
      tailf:display-when "not(../../ncs:module) or ../../ncs:module[ncs:name='Cisco-IOS-XR-ipv4-bgp-act']";
      tailf:action clear-bgp-instance-bestpath-vrf-afi-safi-ipv4-addr-ipv4-mask {
        tailf:actionpoint ncsproxy {
          tailf:internal;
        }
        csc:xr-task "bgp";
        csc:cli-command "clear bgp instance <instance-name> bestpath vrf <vrf-all> <afi-safi-name> <ipv4-addr> <ipv4-mask>";
        description
          "Choose a particular BGP instance.
           re-run BGP bestpath selection.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device-group/ncs:ned-id/ncs:rpc" {
    container rpc-clear-bgp-instance-bestpath-vrf-afi-safi-ipv4-addr-ipv4-mask {
      tailf:ncs-device-type "netconf";
      tailf:display-when "/ncs:devices/ncs:device[ncs:name=current()/../../../ncs:member]/ncs:module[ncs:name='Cisco-IOS-XR-ipv4-bgp-act']";
      tailf:action clear-bgp-instance-bestpath-vrf-afi-safi-ipv4-addr-ipv4-mask {
        tailf:actionpoint ncsproxy {
          tailf:internal;
        }
        csc:xr-task "bgp";
        csc:cli-command "clear bgp instance <instance-name> bestpath vrf <vrf-all> <afi-safi-name> <ipv4-addr> <ipv4-mask>";
        description
          "Choose a particular BGP instance.
           re-run BGP bestpath selection.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device/ncs:rpc" {
    container rpc-clear-bgp-instance-bestpath-vrf-afi-safi-ipv4-prefix {
      tailf:ncs-device-type "netconf";
      tailf:display-when "not(../../ncs:module) or ../../ncs:module[ncs:name='Cisco-IOS-XR-ipv4-bgp-act']";
      tailf:action clear-bgp-instance-bestpath-vrf-afi-safi-ipv4-prefix {
        tailf:actionpoint ncsproxy {
          tailf:internal;
        }
        csc:xr-task "bgp";
        csc:cli-command "clear bgp instance <instance-name> bestpath vrf <vrf-all> <afi-safi-name> <ipv4-prefix>";
        description
          "Choose a particular BGP instance.
           re-run BGP bestpath selection.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv4-prefix {
            mandatory true;
            type inet:ipv4-prefix;
            description
              "Fspec IPv4 Prefix";
          }
        }
      }
    }
  }
  augment "/ncs:devices/ncs:device-group/ncs:ned-id/ncs:rpc" {
    container rpc-clear-bgp-instance-bestpath-vrf-afi-safi-ipv4-prefix {
      tailf:ncs-device-type "netconf";
      tailf:display-when "/ncs:devices/ncs:device[ncs:name=current()/../../../ncs:member]/ncs:module[ncs:name='Cisco-IOS-XR-ipv4-bgp-act']";
      tailf:action clear-bgp-instance-bestpath-vrf-afi-safi-ipv4-prefix {
        tailf:actionpoint ncsproxy {
          tailf:internal;
        }
        csc:xr-task "bgp";
        csc:cli-command "clear bgp instance <instance-name> bestpath vrf <vrf-all> <afi-safi-name> <ipv4-prefix>";
        description
          "Choose a particular BGP instance.
           re-run BGP bestpath selection.
           Specify a VRF.
          ";
        input {
          leaf instance-name {
            mandatory true;
            type instance-name;
            description
              "instance name or all";
          }
          leaf vrf-all {
            mandatory true;
            type vrf-name;
            description
              "VRF name or all";
          }
          leaf afi-safi-name {
            mandatory true;
            type afi-safi-type;
            description
              "AFI and SAFI";
          }
          leaf ipv4-prefix {
            mandatory true;
            type inet:ipv4-prefix;
            description
              "Fspec IPv4 Prefix";
          }
        }
      }
    }
  }
  augment "/ncs:devices/ncs:device/ncs:rpc" {
    container rpc-clear-bgp-instance-bestpath-vrf-ip-prefix {
      tailf:ncs-device-type "netconf";
      tailf:display-when "not(../../ncs:module) or ../../ncs:module[ncs:name='Cisco-IOS-XR-ipv4-bgp-act']";
      tailf:action clear-bgp-instance-bestpath-vrf-ip-prefix {
        tailf:actionpoint ncsproxy {
          tailf:internal;
        }
        csc:xr-task "bgp";
        csc:cli-command "clear bgp instance <instance-name> bestpath vrf <vrf-all> <ip-prefix>";
        description
          "Choose a particular BGP instance.
           re-run BGP bestpath selection.
           Specify a VRF.
          ";
        input {
          leaf instance-name {
            mandatory true;
            type instance-name;
            description
              "instance name or all";
          }
          leaf vrf-all {
            mandatory true;
            type vrf-name;
            description
              "VRF name or all";
          }
          leaf ip-prefix {
            mandatory true;
            type inet:ip-prefix;
            description
              "Network and masklength";
          }
        }
      }
    }
  }
  augment "/ncs:devices/ncs:device-group/ncs:ned-id/ncs:rpc" {
    container rpc-clear-bgp-instance-bestpath-vrf-ip-prefix {
      tailf:ncs-device-type "netconf";
      tailf:display-when "/ncs:devices/ncs:device[ncs:name=current()/../../../ncs:member]/ncs:module[ncs:name='Cisco-IOS-XR-ipv4-bgp-act']";
      tailf:action clear-bgp-instance-bestpath-vrf-ip-prefix {
        tailf:actionpoint ncsproxy {
          tailf:internal;
        }
        csc:xr-task "bgp";
        csc:cli-command "clear bgp instance <instance-name> bestpath vrf <vrf-all> <ip-prefix>";
        description
          "Choose a particular BGP instance.
           re-run BGP bestpath selection.
           Specify a VRF.
          ";
        input {
          leaf instance-name {
            mandatory true;
            type instance-name;
            description
              "instance name or all";
          }
          leaf vrf-all {
            mandatory true;
            type vrf-name;
            description
              "VRF name or all";
          }
          leaf ip-prefix {
            mandatory true;
            type inet:ip-prefix;
            description
              "Network and masklength";
          }
        }
      }
    }
  }
  augment "/ncs:devices/ncs:device/ncs:rpc" {
    container rpc-clear-bgp-instance-bestpath-vrf-ip-addr {
      tailf:ncs-device-type "netconf";
      tailf:display-when "not(../../ncs:module) or ../../ncs:module[ncs:name='Cisco-IOS-XR-ipv4-bgp-act']";
      tailf:action clear-bgp-instance-bestpath-vrf-ip-addr {
        tailf:actionpoint ncsproxy {
          tailf:internal;
        }
        csc:xr-task "bgp";
        csc:cli-command "clear bgp instance <instance-name> bestpath vrf <vrf-all> <ip-addr>";
        description
          "Choose a particular BGP instance.
           re-run BGP bestpath selection.
           Specify a VRF.
          ";
        input {
          leaf instance-name {
            mandatory true;
            type instance-name;
            description
              "instance name or all";
          }
          leaf vrf-all {
            mandatory true;
            type vrf-name;
            description
              "VRF name or all";
          }
          leaf ip-addr {
            mandatory true;
            type inet:ip-address;
            description
              "Network";
          }
        }
      }
    }
  }
  augment "/ncs:devices/ncs:device-group/ncs:ned-id/ncs:rpc" {
    container rpc-clear-bgp-instance-bestpath-vrf-ip-addr {
      tailf:ncs-device-type "netconf";
      tailf:display-when "/ncs:devices/ncs:device[ncs:name=current()/../../../ncs:member]/ncs:module[ncs:name='Cisco-IOS-XR-ipv4-bgp-act']";
      tailf:action clear-bgp-instance-bestpath-vrf-ip-addr {
        tailf:actionpoint ncsproxy {
          tailf:internal;
        }
        csc:xr-task "bgp";
        csc:cli-command "clear bgp instance <instance-name> bestpath vrf <vrf-all> <ip-addr>";
        description
          "Choose a particular BGP instance.
           re-run BGP bestpath selection.
           Specify a VRF.
          ";
        input {
          leaf instance-name {
            mandatory true;
            type instance-name;
            description
              "instance name or all";
          }
          leaf vrf-all {
            mandatory true;
            type vrf-name;
            description
              "VRF name or all";
          }
          leaf ip-addr {
            mandatory true;
            type inet:ip-address;
            description
              "Network";
          }
        }
      }
    }
  }
  augment "/ncs:devices/ncs:device/ncs:rpc" {
    container rpc-clear-bgp-instance-bestpath-vrf-ip-addr-ip-netmask {
      tailf:ncs-device-type "netconf";
      tailf:display-when "not(../../ncs:module) or ../../ncs:module[ncs:name='Cisco-IOS-XR-ipv4-bgp-act']";
      tailf:action clear-bgp-instance-bestpath-vrf-ip-addr-ip-netmask {
        tailf:actionpoint ncsproxy {
          tailf:internal;
        }
        csc:xr-task "bgp";
        csc:cli-command "clear bgp instance <instance-name> bestpath vrf <vrf-all> <ip-addr> <ip-netmask>";
        description
          "Choose a particular BGP instance.
           re-run BGP bestpath selection.
           Specify a VRF.
          ";
        input {
          leaf instance-name {
            mandatory true;
            type instance-name;
            description
              "instance name or all";
          }
          leaf vrf-all {
            mandatory true;
            type vrf-name;
            description
              "VRF name or all";
          }
          leaf ip-addr {
            mandatory true;
            type inet:ip-address;
            description
              "Network";
          }
          leaf ip-netmask {
            mandatory true;
            type ip-netmask;
            description
              "Mask";
          }
        }
      }
    }
  }
  augment "/ncs:devices/ncs:device-group/ncs:ned-id/ncs:rpc" {
    container rpc-clear-bgp-instance-bestpath-vrf-ip-addr-ip-netmask {
      tailf:ncs-device-type "netconf";
      tailf:display-when "/ncs:devices/ncs:device[ncs:name=current()/../../../ncs:member]/ncs:module[ncs:name='Cisco-IOS-XR-ipv4-bgp-act']";
      tailf:action clear-bgp-instance-bestpath-vrf-ip-addr-ip-netmask {
        tailf:actionpoint ncsproxy {
          tailf:internal;
        }
        csc:xr-task "bgp";
        csc:cli-command "clear bgp instance <instance-name> bestpath vrf <vrf-all> <ip-addr> <ip-netmask>";
        description
          "Choose a particular BGP instance.
           re-run BGP bestpath selection.
           Specify a VRF.
          ";
        input {
          leaf instance-name {
            mandatory true;
            type instance-name;
            description
              "instance name or all";
          }
          leaf vrf-all {
            mandatory true;
            type vrf-name;
            description
              "VRF name or all";
          }
          leaf ip-addr {
            mandatory true;
            type inet:ip-address;
            description
              "Network";
          }
          leaf ip-netmask {
            mandatory true;
            type ip-netmask;
            description
              "Mask";
          }
        }
      }
    }
  }
  augment "/ncs:devices/ncs:device/ncs:rpc" {
    container rpc-clear-bgp-instance-bestpath-afi-safi-vrf-ipv6-prefix {
      tailf:ncs-device-type "netconf";
      tailf:display-when "not(../../ncs:module) or ../../ncs:module[ncs:name='Cisco-IOS-XR-ipv4-bgp-act']";
      tailf:action clear-bgp-instance-bestpath-afi-safi-vrf-ipv6-prefix {
        tailf:actionpoint ncsproxy {
          tailf:internal;
        }
        csc:xr-task "bgp";
        csc:cli-command "clear bgp instance <instance-name> bestpath <afi-safi-name> vrf <vrf-name> <ipv6-prefix>";
        description
          "Choose a particular BGP instance.
           re-run BGP bestpath selection.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
          leaf ipv6-prefix {
            mandatory true;
            type inet:ipv6-prefix;
            description
              "IPv6 network and masklength";
          }
        }
      }
    }
  }
  augment "/ncs:devices/ncs:device-group/ncs:ned-id/ncs:rpc" {
    container rpc-clear-bgp-instance-bestpath-afi-safi-vrf-ipv6-prefix {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-vrf-ipv6-prefix {
        tailf:actionpoint ncsproxy {
          tailf:internal;
        }
        csc:xr-task "bgp";
        csc:cli-command "clear bgp instance <instance-name> bestpath <afi-safi-name> vrf <vrf-name> <ipv6-prefix>";
        description
          "Choose a particular BGP instance.
           re-run BGP bestpath selection.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
          leaf ipv6-prefix {
            mandatory true;
            type inet:ipv6-prefix;
            description
              "IPv6 network and masklength";
          }
        }
      }
    }
  }
  augment "/ncs:devices/ncs:device/ncs:rpc" {
    container rpc-clear-bgp-instance-bestpath-afi-safi-vrf-ipv6-addr {
      tailf:ncs-device-type "netconf";
      tailf:display-when "not(../../ncs:module) or ../../ncs:module[ncs:name='Cisco-IOS-XR-ipv4-bgp-act']";
      tailf:action clear-bgp-instance-bestpath-afi-safi-vrf-ipv6-addr {
        tailf:actionpoint ncsproxy {
          tailf:internal;
        }
        csc:xr-task "bgp";
        csc:cli-command "clear bgp instance <instance-name> bestpath <afi-safi-name> vrf <vrf-name> <ipv6-addr>";
        description
          "Choose a particular BGP instance.
           re-run BGP bestpath selection.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
          leaf ipv6-addr {
            mandatory true;
            type inet:ipv6-address;
            description
              "IPv6 network";
          }
        }
      }
    }
  }
  augment "/ncs:devices/ncs:device-group/ncs:ned-id/ncs:rpc" {
    container rpc-clear-bgp-instance-bestpath-afi-safi-vrf-ipv6-addr {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-vrf-ipv6-addr {
        tailf:actionpoint ncsproxy {
          tailf:internal;
        }
        csc:xr-task "bgp";
        csc:cli-command "clear bgp instance <instance-name> bestpath <afi-safi-name> vrf <vrf-name> <ipv6-addr>";
        description
          "Choose a particular BGP instance.
           re-run BGP bestpath selection.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
          leaf ipv6-addr {
            mandatory true;
            type inet:ipv6-address;
            description
              "IPv6 network";
          }
        }
      }
    }
  }
  augment "/ncs:devices/ncs:device/ncs:rpc" {
    container rpc-clear-bgp-instance-bestpath-afi-safi-vrf-ipv6-addr-ipv6-netmask {
      tailf:ncs-device-type "netconf";
      tailf:display-when "not(../../ncs:module) or ../../ncs:module[ncs:name='Cisco-IOS-XR-ipv4-bgp-act']";
      tailf:action clear-bgp-instance-bestpath-afi-safi-vrf-ipv6-addr-ipv6-netmask {
        tailf:actionpoint ncsproxy {
          tailf:internal;
        }
        csc:xr-task "bgp";
        csc:cli-command "clear bgp instance <instance-name> bestpath <afi-safi-name> vrf <vrf-name> <ipv6-addr> <ipv6-netmask>";
        description
          "Choose a particular BGP instance.
           re-run BGP bestpath selection.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device-group/ncs:ned-id/ncs:rpc" {
    container rpc-clear-bgp-instance-bestpath-afi-safi-vrf-ipv6-addr-ipv6-netmask {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-vrf-ipv6-addr-ipv6-netmask {
        tailf:actionpoint ncsproxy {
          tailf:internal;
        }
        csc:xr-task "bgp";
        csc:cli-command "clear bgp instance <instance-name> bestpath <afi-safi-name> vrf <vrf-name> <ipv6-addr> <ipv6-netmask>";
        description
          "Choose a particular BGP instance.
           re-run BGP bestpath selection.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device/ncs:rpc" {
    container rpc-clear-bgp-instance-bestpath-afi-safi-rd-ipv6-prefix {
      tailf:ncs-device-type "netconf";
      tailf:display-when "not(../../ncs:module) or ../../ncs:module[ncs:name='Cisco-IOS-XR-ipv4-bgp-act']";
      tailf:action clear-bgp-instance-bestpath-afi-safi-rd-ipv6-prefix {
        tailf:actionpoint ncsproxy {
          tailf:internal;
        }
        csc:xr-task "bgp";
        csc:cli-command "clear bgp instance <instance-name> bestpath <afi-safi-name> rd <rd> <ipv6-prefix>";
        description
          "Choose a particular BGP instance.
           re-run BGP bestpath selection.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ipv6-prefix {
            mandatory true;
            type inet:ipv6-prefix;
            description
              "IPv6 network and masklength";
          }
        }
      }
    }
  }
  augment "/ncs:devices/ncs:device-group/ncs:ned-id/ncs:rpc" {
    container rpc-clear-bgp-instance-bestpath-afi-safi-rd-ipv6-prefix {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-rd-ipv6-prefix {
        tailf:actionpoint ncsproxy {
          tailf:internal;
        }
        csc:xr-task "bgp";
        csc:cli-command "clear bgp instance <instance-name> bestpath <afi-safi-name> rd <rd> <ipv6-prefix>";
        description
          "Choose a particular BGP instance.
           re-run BGP bestpath selection.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ipv6-prefix {
            mandatory true;
            type inet:ipv6-prefix;
            description
              "IPv6 network and masklength";
          }
        }
      }
    }
  }
  augment "/ncs:devices/ncs:device/ncs:rpc" {
    container rpc-clear-bgp-instance-bestpath-afi-safi-rd-ipv6-addr {
      tailf:ncs-device-type "netconf";
      tailf:display-when "not(../../ncs:module) or ../../ncs:module[ncs:name='Cisco-IOS-XR-ipv4-bgp-act']";
      tailf:action clear-bgp-instance-bestpath-afi-safi-rd-ipv6-addr {
        tailf:actionpoint ncsproxy {
          tailf:internal;
        }
        csc:xr-task "bgp";
        csc:cli-command "clear bgp instance <instance-name> bestpath <afi-safi-name> rd <rd> <ipv6-addr>";
        description
          "Choose a particular BGP instance.
           re-run BGP bestpath selection.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ipv6-addr {
            mandatory true;
            type inet:ipv6-address;
            description
              "IPv6 network";
          }
        }
      }
    }
  }
  augment "/ncs:devices/ncs:device-group/ncs:ned-id/ncs:rpc" {
    container rpc-clear-bgp-instance-bestpath-afi-safi-rd-ipv6-addr {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-rd-ipv6-addr {
        tailf:actionpoint ncsproxy {
          tailf:internal;
        }
        csc:xr-task "bgp";
        csc:cli-command "clear bgp instance <instance-name> bestpath <afi-safi-name> rd <rd> <ipv6-addr>";
        description
          "Choose a particular BGP instance.
           re-run BGP bestpath selection.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ipv6-addr {
            mandatory true;
            type inet:ipv6-address;
            description
              "IPv6 network";
          }
        }
      }
    }
  }
  augment "/ncs:devices/ncs:device/ncs:rpc" {
    container rpc-clear-bgp-instance-bestpath-afi-safi-rd-ipv6-addr-ipv6-netmask {
      tailf:ncs-device-type "netconf";
      tailf:display-when "not(../../ncs:module) or ../../ncs:module[ncs:name='Cisco-IOS-XR-ipv4-bgp-act']";
      tailf:action clear-bgp-instance-bestpath-afi-safi-rd-ipv6-addr-ipv6-netmask {
        tailf:actionpoint ncsproxy {
          tailf:internal;
        }
        csc:xr-task "bgp";
        csc:cli-command "clear bgp instance <instance-name> bestpath <afi-safi-name> rd <rd> <ipv6-addr> <ipv6-netmask>";
        description
          "Choose a particular BGP instance.
           re-run BGP bestpath selection.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device-group/ncs:ned-id/ncs:rpc" {
    container rpc-clear-bgp-instance-bestpath-afi-safi-rd-ipv6-addr-ipv6-netmask {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-rd-ipv6-addr-ipv6-netmask {
        tailf:actionpoint ncsproxy {
          tailf:internal;
        }
        csc:xr-task "bgp";
        csc:cli-command "clear bgp instance <instance-name> bestpath <afi-safi-name> rd <rd> <ipv6-addr> <ipv6-netmask>";
        description
          "Choose a particular BGP instance.
           re-run BGP bestpath selection.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device/ncs:rpc" {
    container rpc-clear-bgp-instance-bestpath-afi-safi-vrf-ipv4-addr-ipv4-mask {
      tailf:ncs-device-type "netconf";
      tailf:display-when "not(../../ncs:module) or ../../ncs:module[ncs:name='Cisco-IOS-XR-ipv4-bgp-act']";
      tailf:action clear-bgp-instance-bestpath-afi-safi-vrf-ipv4-addr-ipv4-mask {
        tailf:actionpoint ncsproxy {
          tailf:internal;
        }
        csc:xr-task "bgp";
        csc:cli-command "clear bgp instance <instance-name> bestpath <afi-safi-name> vrf <vrf-name> <ipv4-addr> <ipv4-mask>";
        description
          "Choose a particular BGP instance.
           re-run BGP bestpath selection.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device-group/ncs:ned-id/ncs:rpc" {
    container rpc-clear-bgp-instance-bestpath-afi-safi-vrf-ipv4-addr-ipv4-mask {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-vrf-ipv4-addr-ipv4-mask {
        tailf:actionpoint ncsproxy {
          tailf:internal;
        }
        csc:xr-task "bgp";
        csc:cli-command "clear bgp instance <instance-name> bestpath <afi-safi-name> vrf <vrf-name> <ipv4-addr> <ipv4-mask>";
        description
          "Choose a particular BGP instance.
           re-run BGP bestpath selection.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device/ncs:rpc" {
    container rpc-clear-bgp-instance-bestpath-afi-safi-rd-ipv4-addr-ipv4-mask {
      tailf:ncs-device-type "netconf";
      tailf:display-when "not(../../ncs:module) or ../../ncs:module[ncs:name='Cisco-IOS-XR-ipv4-bgp-act']";
      tailf:action clear-bgp-instance-bestpath-afi-safi-rd-ipv4-addr-ipv4-mask {
        tailf:actionpoint ncsproxy {
          tailf:internal;
        }
        csc:xr-task "bgp";
        csc:cli-command "clear bgp instance <instance-name> bestpath <afi-safi-name> rd <rd> <ipv4-addr> <ipv4-mask>";
        description
          "Choose a particular BGP instance.
           re-run BGP bestpath selection.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device-group/ncs:ned-id/ncs:rpc" {
    container rpc-clear-bgp-instance-bestpath-afi-safi-rd-ipv4-addr-ipv4-mask {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-rd-ipv4-addr-ipv4-mask {
        tailf:actionpoint ncsproxy {
          tailf:internal;
        }
        csc:xr-task "bgp";
        csc:cli-command "clear bgp instance <instance-name> bestpath <afi-safi-name> rd <rd> <ipv4-addr> <ipv4-mask>";
        description
          "Choose a particular BGP instance.
           re-run BGP bestpath selection.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device/ncs:rpc" {
    container rpc-clear-bgp-instance-bestpath-afi-safi-vrf-ipv4-prefix {
      tailf:ncs-device-type "netconf";
      tailf:display-when "not(../../ncs:module) or ../../ncs:module[ncs:name='Cisco-IOS-XR-ipv4-bgp-act']";
      tailf:action clear-bgp-instance-bestpath-afi-safi-vrf-ipv4-prefix {
        tailf:actionpoint ncsproxy {
          tailf:internal;
        }
        csc:xr-task "bgp";
        csc:cli-command "clear bgp instance <instance-name> bestpath <afi-safi-name> vrf <vrf-name> <ipv4-prefix>";
        description
          "Choose a particular BGP instance.
           re-run BGP bestpath selection.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
          leaf ipv4-prefix {
            mandatory true;
            type inet:ipv4-prefix;
            description
              "VPN Fspec Prefix";
          }
        }
      }
    }
  }
  augment "/ncs:devices/ncs:device-group/ncs:ned-id/ncs:rpc" {
    container rpc-clear-bgp-instance-bestpath-afi-safi-vrf-ipv4-prefix {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-vrf-ipv4-prefix {
        tailf:actionpoint ncsproxy {
          tailf:internal;
        }
        csc:xr-task "bgp";
        csc:cli-command "clear bgp instance <instance-name> bestpath <afi-safi-name> vrf <vrf-name> <ipv4-prefix>";
        description
          "Choose a particular BGP instance.
           re-run BGP bestpath selection.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
          leaf ipv4-prefix {
            mandatory true;
            type inet:ipv4-prefix;
            description
              "VPN Fspec Prefix";
          }
        }
      }
    }
  }
  augment "/ncs:devices/ncs:device/ncs:rpc" {
    container rpc-clear-bgp-instance-bestpath-afi-safi-mp2mp-ipv4-prefix {
      tailf:ncs-device-type "netconf";
      tailf:display-when "not(../../ncs:module) or ../../ncs:module[ncs:name='Cisco-IOS-XR-ipv4-bgp-act']";
      tailf:action clear-bgp-instance-bestpath-afi-safi-mp2mp-ipv4-prefix {
        tailf:actionpoint ncsproxy {
          tailf:internal;
        }
        csc:xr-task "bgp";
        csc:cli-command "clear bgp instance <instance-name> bestpath <afi-safi-name> mp2mp <mp2mp> <ipv4-prefix>";
        description
          "Choose a particular BGP instance.
           re-run BGP bestpath selection.
           Display routes for a specified Xconnect group:MP2MP.
          ";
        input {
          leaf instance-name {
            mandatory true;
            type instance-name;
            description
              "instance name or all";
          }
          leaf afi-safi-name {
            mandatory true;
            type afi-safi-type;
            description
              "AFI and SAFI";
          }
          leaf mp2mp {
            mandatory true;
            type string;
            description
              "Xconnect Group:mp2mp";
          }
          leaf ipv4-prefix {
            mandatory true;
            type inet:ipv4-prefix;
            description
              "L2VPN VPWS Prefix";
          }
        }
      }
    }
  }
  augment "/ncs:devices/ncs:device-group/ncs:ned-id/ncs:rpc" {
    container rpc-clear-bgp-instance-bestpath-afi-safi-mp2mp-ipv4-prefix {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-mp2mp-ipv4-prefix {
        tailf:actionpoint ncsproxy {
          tailf:internal;
        }
        csc:xr-task "bgp";
        csc:cli-command "clear bgp instance <instance-name> bestpath <afi-safi-name> mp2mp <mp2mp> <ipv4-prefix>";
        description
          "Choose a particular BGP instance.
           re-run BGP bestpath selection.
           Display routes for a specified Xconnect group:MP2MP.
          ";
        input {
          leaf instance-name {
            mandatory true;
            type instance-name;
            description
              "instance name or all";
          }
          leaf afi-safi-name {
            mandatory true;
            type afi-safi-type;
            description
              "AFI and SAFI";
          }
          leaf mp2mp {
            mandatory true;
            type string;
            description
              "Xconnect Group:mp2mp";
          }
          leaf ipv4-prefix {
            mandatory true;
            type inet:ipv4-prefix;
            description
              "L2VPN VPWS Prefix";
          }
        }
      }
    }
  }
  augment "/ncs:devices/ncs:device/ncs:rpc" {
    container rpc-clear-bgp-instance-bestpath-afi-safi-rd-ipv4-prefix {
      tailf:ncs-device-type "netconf";
      tailf:display-when "not(../../ncs:module) or ../../ncs:module[ncs:name='Cisco-IOS-XR-ipv4-bgp-act']";
      tailf:action clear-bgp-instance-bestpath-afi-safi-rd-ipv4-prefix {
        tailf:actionpoint ncsproxy {
          tailf:internal;
        }
        csc:xr-task "bgp";
        csc:cli-command "clear bgp instance <instance-name> bestpath <afi-safi-name> rd <rd> <ipv4-prefix>";
        description
          "Choose a particular BGP instance.
           re-run BGP bestpath selection.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ipv4-prefix {
            mandatory true;
            type inet:ipv4-prefix;
            description
              "L2VPN EVPN Prefix";
          }
        }
      }
    }
  }
  augment "/ncs:devices/ncs:device-group/ncs:ned-id/ncs:rpc" {
    container rpc-clear-bgp-instance-bestpath-afi-safi-rd-ipv4-prefix {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-rd-ipv4-prefix {
        tailf:actionpoint ncsproxy {
          tailf:internal;
        }
        csc:xr-task "bgp";
        csc:cli-command "clear bgp instance <instance-name> bestpath <afi-safi-name> rd <rd> <ipv4-prefix>";
        description
          "Choose a particular BGP instance.
           re-run BGP bestpath selection.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ipv4-prefix {
            mandatory true;
            type inet:ipv4-prefix;
            description
              "L2VPN EVPN Prefix";
          }
        }
      }
    }
  }
  augment "/ncs:devices/ncs:device/ncs:rpc" {
    container rpc-clear-bgp-instance-bestpath-afi-safi-bridge-domain-ipv4-prefix {
      tailf:ncs-device-type "netconf";
      tailf:display-when "not(../../ncs:module) or ../../ncs:module[ncs:name='Cisco-IOS-XR-ipv4-bgp-act']";
      tailf:action clear-bgp-instance-bestpath-afi-safi-bridge-domain-ipv4-prefix {
        tailf:actionpoint ncsproxy {
          tailf:internal;
        }
        csc:xr-task "bgp";
        csc:cli-command "clear bgp instance <instance-name> bestpath <afi-safi-name> bridge-domain <bridge-domain-name> <ipv4-prefix>";
        description
          "Choose a particular BGP instance.
           re-run BGP bestpath selection.
           Display routes for a specified Bridge Domain.
          ";
        input {
          leaf instance-name {
            mandatory true;
            type instance-name;
            description
              "instance name or all";
          }
          leaf afi-safi-name {
            mandatory true;
            type afi-safi-type;
            description
              "AFI and SAFI";
          }
          leaf bridge-domain-name {
            mandatory true;
            type string;
            description
              "Bridge Domain";
          }
          leaf ipv4-prefix {
            mandatory true;
            type inet:ipv4-prefix;
            description
              "L2VPN EVPN Prefix";
          }
        }
      }
    }
  }
  augment "/ncs:devices/ncs:device-group/ncs:ned-id/ncs:rpc" {
    container rpc-clear-bgp-instance-bestpath-afi-safi-bridge-domain-ipv4-prefix {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-bridge-domain-ipv4-prefix {
        tailf:actionpoint ncsproxy {
          tailf:internal;
        }
        csc:xr-task "bgp";
        csc:cli-command "clear bgp instance <instance-name> bestpath <afi-safi-name> bridge-domain <bridge-domain-name> <ipv4-prefix>";
        description
          "Choose a particular BGP instance.
           re-run BGP bestpath selection.
           Display routes for a specified Bridge Domain.
          ";
        input {
          leaf instance-name {
            mandatory true;
            type instance-name;
            description
              "instance name or all";
          }
          leaf afi-safi-name {
            mandatory true;
            type afi-safi-type;
            description
              "AFI and SAFI";
          }
          leaf bridge-domain-name {
            mandatory true;
            type string;
            description
              "Bridge Domain";
          }
          leaf ipv4-prefix {
            mandatory true;
            type inet:ipv4-prefix;
            description
              "L2VPN EVPN Prefix";
          }
        }
      }
    }
  }
  augment "/ncs:devices/ncs:device/ncs:rpc" {
    container rpc-clear-bgp-instance-bestpath-afi-safi-sr-policy-prefix {
      tailf:ncs-device-type "netconf";
      tailf:display-when "not(../../ncs:module) or ../../ncs:module[ncs:name='Cisco-IOS-XR-ipv4-bgp-act']";
      tailf:action clear-bgp-instance-bestpath-afi-safi-sr-policy-prefix {
        tailf:actionpoint ncsproxy {
          tailf:internal;
        }
        csc:xr-task "bgp";
        csc:cli-command "clear bgp instance <instance-name> bestpath <afi-safi-name> <sr-policy-prefix>";
        description
          "Choose a particular BGP instance.
           re-run BGP bestpath selection.
          ";
        input {
          leaf instance-name {
            mandatory true;
            type instance-name;
            description
              "instance name or all";
          }
          leaf afi-safi-name {
            mandatory true;
            type afi-safi-type;
            description
              "AFI and SAFI";
          }
          leaf sr-policy-prefix {
            mandatory true;
            type string;
            description
              "SR Policy prefix";
          }
        }
      }
    }
  }
  augment "/ncs:devices/ncs:device-group/ncs:ned-id/ncs:rpc" {
    container rpc-clear-bgp-instance-bestpath-afi-safi-sr-policy-prefix {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-sr-policy-prefix {
        tailf:actionpoint ncsproxy {
          tailf:internal;
        }
        csc:xr-task "bgp";
        csc:cli-command "clear bgp instance <instance-name> bestpath <afi-safi-name> <sr-policy-prefix>";
        description
          "Choose a particular BGP instance.
           re-run BGP bestpath selection.
          ";
        input {
          leaf instance-name {
            mandatory true;
            type instance-name;
            description
              "instance name or all";
          }
          leaf afi-safi-name {
            mandatory true;
            type afi-safi-type;
            description
              "AFI and SAFI";
          }
          leaf sr-policy-prefix {
            mandatory true;
            type string;
            description
              "SR Policy prefix";
          }
        }
      }
    }
  }
  augment "/ncs:devices/ncs:device/ncs:rpc" {
    container rpc-clear-bgp-instance-bestpath-afi-safi {
      tailf:ncs-device-type "netconf";
      tailf:display-when "not(../../ncs:module) or ../../ncs:module[ncs:name='Cisco-IOS-XR-ipv4-bgp-act']";
      tailf:action clear-bgp-instance-bestpath-afi-safi {
        tailf:actionpoint ncsproxy {
          tailf:internal;
        }
        csc:xr-task "bgp";
        csc:cli-command "clear bgp instance <instance-name> bestpath <afi-safi-name>";
        description
          "Choose a particular BGP instance.
           re-run BGP bestpath selection.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-bestpath-afi-safi {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi {
        tailf:actionpoint ncsproxy {
          tailf:internal;
        }
        csc:xr-task "bgp";
        csc:cli-command "clear bgp instance <instance-name> bestpath <afi-safi-name>";
        description
          "Choose a particular BGP instance.
           re-run BGP bestpath selection.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device/ncs:rpc" {
    container rpc-clear-bgp-instance-bestpath-afi-safi-vrf {
      tailf:ncs-device-type "netconf";
      tailf:display-when "not(../../ncs:module) or ../../ncs:module[ncs:name='Cisco-IOS-XR-ipv4-bgp-act']";
      tailf:action clear-bgp-instance-bestpath-afi-safi-vrf {
        tailf:actionpoint ncsproxy {
          tailf:internal;
        }
        csc:xr-task "bgp";
        csc:cli-command "clear bgp instance <instance-name> bestpath <afi-safi-name> vrf <vrf-name>";
        description
          "Choose a particular BGP instance.
           re-run BGP bestpath selection.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
        }
      }
    }
  }
  augment "/ncs:devices/ncs:device-group/ncs:ned-id/ncs:rpc" {
    container rpc-clear-bgp-instance-bestpath-afi-safi-vrf {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-vrf {
        tailf:actionpoint ncsproxy {
          tailf:internal;
        }
        csc:xr-task "bgp";
        csc:cli-command "clear bgp instance <instance-name> bestpath <afi-safi-name> vrf <vrf-name>";
        description
          "Choose a particular BGP instance.
           re-run BGP bestpath selection.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
        }
      }
    }
  }
  augment "/ncs:devices/ncs:device/ncs:rpc" {
    container rpc-clear-bgp-instance-bestpath-afi-safi-rd {
      tailf:ncs-device-type "netconf";
      tailf:display-when "not(../../ncs:module) or ../../ncs:module[ncs:name='Cisco-IOS-XR-ipv4-bgp-act']";
      tailf:action clear-bgp-instance-bestpath-afi-safi-rd {
        tailf:actionpoint ncsproxy {
          tailf:internal;
        }
        csc:xr-task "bgp";
        csc:cli-command "clear bgp instance <instance-name> bestpath <afi-safi-name> rd <rd>";
        description
          "Choose a particular BGP instance.
           re-run BGP bestpath selection.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
        }
      }
    }
  }
  augment "/ncs:devices/ncs:device-group/ncs:ned-id/ncs:rpc" {
    container rpc-clear-bgp-instance-bestpath-afi-safi-rd {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-rd {
        tailf:actionpoint ncsproxy {
          tailf:internal;
        }
        csc:xr-task "bgp";
        csc:cli-command "clear bgp instance <instance-name> bestpath <afi-safi-name> rd <rd>";
        description
          "Choose a particular BGP instance.
           re-run BGP bestpath selection.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
        }
      }
    }
  }
  augment "/ncs:devices/ncs:device/ncs:rpc" {
    container rpc-clear-bgp-instance-bestpath-afi-safi-ipv6-prefix {
      tailf:ncs-device-type "netconf";
      tailf:display-when "not(../../ncs:module) or ../../ncs:module[ncs:name='Cisco-IOS-XR-ipv4-bgp-act']";
      tailf:action clear-bgp-instance-bestpath-afi-safi-ipv6-prefix {
        tailf:actionpoint ncsproxy {
          tailf:internal;
        }
        csc:xr-task "bgp";
        csc:cli-command "clear bgp instance <instance-name> bestpath <afi-safi-name> <ipv6-prefix>";
        description
          "Choose a particular BGP instance.
           re-run BGP bestpath selection.
          ";
        input {
          leaf instance-name {
            mandatory true;
            type instance-name;
            description
              "instance name or all";
          }
          leaf afi-safi-name {
            mandatory true;
            type afi-safi-type;
            description
              "AFI and SAFI";
          }
          leaf ipv6-prefix {
            mandatory true;
            type inet:ipv6-prefix;
            description
              "IPv6 network and masklength";
          }
        }
      }
    }
  }
  augment "/ncs:devices/ncs:device-group/ncs:ned-id/ncs:rpc" {
    container rpc-clear-bgp-instance-bestpath-afi-safi-ipv6-prefix {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-ipv6-prefix {
        tailf:actionpoint ncsproxy {
          tailf:internal;
        }
        csc:xr-task "bgp";
        csc:cli-command "clear bgp instance <instance-name> bestpath <afi-safi-name> <ipv6-prefix>";
        description
          "Choose a particular BGP instance.
           re-run BGP bestpath selection.
          ";
        input {
          leaf instance-name {
            mandatory true;
            type instance-name;
            description
              "instance name or all";
          }
          leaf afi-safi-name {
            mandatory true;
            type afi-safi-type;
            description
              "AFI and SAFI";
          }
          leaf ipv6-prefix {
            mandatory true;
            type inet:ipv6-prefix;
            description
              "IPv6 network and masklength";
          }
        }
      }
    }
  }
  augment "/ncs:devices/ncs:device/ncs:rpc" {
    container rpc-clear-bgp-instance-bestpath-afi-safi-ipv6-addr {
      tailf:ncs-device-type "netconf";
      tailf:display-when "not(../../ncs:module) or ../../ncs:module[ncs:name='Cisco-IOS-XR-ipv4-bgp-act']";
      tailf:action clear-bgp-instance-bestpath-afi-safi-ipv6-addr {
        tailf:actionpoint ncsproxy {
          tailf:internal;
        }
        csc:xr-task "bgp";
        csc:cli-command "clear bgp instance <instance-name> bestpath <afi-safi-name> <ipv6-addr>";
        description
          "Choose a particular BGP instance.
           re-run BGP bestpath selection.
          ";
        input {
          leaf instance-name {
            mandatory true;
            type instance-name;
            description
              "instance name or all";
          }
          leaf afi-safi-name {
            mandatory true;
            type afi-safi-type;
            description
              "AFI and SAFI";
          }
          leaf ipv6-addr {
            mandatory true;
            type inet:ipv6-address;
            description
              "IPv6 network";
          }
        }
      }
    }
  }
  augment "/ncs:devices/ncs:device-group/ncs:ned-id/ncs:rpc" {
    container rpc-clear-bgp-instance-bestpath-afi-safi-ipv6-addr {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-ipv6-addr {
        tailf:actionpoint ncsproxy {
          tailf:internal;
        }
        csc:xr-task "bgp";
        csc:cli-command "clear bgp instance <instance-name> bestpath <afi-safi-name> <ipv6-addr>";
        description
          "Choose a particular BGP instance.
           re-run BGP bestpath selection.
          ";
        input {
          leaf instance-name {
            mandatory true;
            type instance-name;
            description
              "instance name or all";
          }
          leaf afi-safi-name {
            mandatory true;
            type afi-safi-type;
            description
              "AFI and SAFI";
          }
          leaf ipv6-addr {
            mandatory true;
            type inet:ipv6-address;
            description
              "IPv6 network";
          }
        }
      }
    }
  }
  augment "/ncs:devices/ncs:device/ncs:rpc" {
    container rpc-clear-bgp-instance-bestpath-afi-safi-ipv6-addr-ipv6-netmask {
      tailf:ncs-device-type "netconf";
      tailf:display-when "not(../../ncs:module) or ../../ncs:module[ncs:name='Cisco-IOS-XR-ipv4-bgp-act']";
      tailf:action clear-bgp-instance-bestpath-afi-safi-ipv6-addr-ipv6-netmask {
        tailf:actionpoint ncsproxy {
          tailf:internal;
        }
        csc:xr-task "bgp";
        csc:cli-command "clear bgp instance <instance-name> bestpath <afi-safi-name> <ipv6-addr> <ipv6-netmask>";
        description
          "Choose a particular BGP instance.
           re-run BGP bestpath selection.
          ";
        input {
          leaf instance-name {
            mandatory true;
            type instance-name;
            description
              "instance name or all";
          }
          leaf afi-safi-name {
            mandatory true;
            type afi-safi-type;
            description
              "AFI and SAFI";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device-group/ncs:ned-id/ncs:rpc" {
    container rpc-clear-bgp-instance-bestpath-afi-safi-ipv6-addr-ipv6-netmask {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-ipv6-addr-ipv6-netmask {
        tailf:actionpoint ncsproxy {
          tailf:internal;
        }
        csc:xr-task "bgp";
        csc:cli-command "clear bgp instance <instance-name> bestpath <afi-safi-name> <ipv6-addr> <ipv6-netmask>";
        description
          "Choose a particular BGP instance.
           re-run BGP bestpath selection.
          ";
        input {
          leaf instance-name {
            mandatory true;
            type instance-name;
            description
              "instance name or all";
          }
          leaf afi-safi-name {
            mandatory true;
            type afi-safi-type;
            description
              "AFI and SAFI";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device/ncs:rpc" {
    container rpc-clear-bgp-instance-bestpath-afi-safi-ipv4-tunnel-network {
      tailf:ncs-device-type "netconf";
      tailf:display-when "not(../../ncs:module) or ../../ncs:module[ncs:name='Cisco-IOS-XR-ipv4-bgp-act']";
      tailf:action clear-bgp-instance-bestpath-afi-safi-ipv4-tunnel-network {
        tailf:actionpoint ncsproxy {
          tailf:internal;
        }
        csc:xr-task "bgp";
        csc:cli-command "clear bgp instance <instance-name> bestpath <afi-safi-name> <ipv4-tunnel-network>";
        description
          "Choose a particular BGP instance.
           re-run BGP bestpath selection.
          ";
        input {
          leaf instance-name {
            mandatory true;
            type instance-name;
            description
              "instance name or all";
          }
          leaf afi-safi-name {
            mandatory true;
            type afi-safi-type;
            description
              "AFI and SAFI";
          }
          leaf ipv4-tunnel-network {
            mandatory true;
            type string;
            description
              "IPv4 Tunnel network <Tunnel-ID>:<IPv4 Address>";
          }
        }
      }
    }
  }
  augment "/ncs:devices/ncs:device-group/ncs:ned-id/ncs:rpc" {
    container rpc-clear-bgp-instance-bestpath-afi-safi-ipv4-tunnel-network {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-ipv4-tunnel-network {
        tailf:actionpoint ncsproxy {
          tailf:internal;
        }
        csc:xr-task "bgp";
        csc:cli-command "clear bgp instance <instance-name> bestpath <afi-safi-name> <ipv4-tunnel-network>";
        description
          "Choose a particular BGP instance.
           re-run BGP bestpath selection.
          ";
        input {
          leaf instance-name {
            mandatory true;
            type instance-name;
            description
              "instance name or all";
          }
          leaf afi-safi-name {
            mandatory true;
            type afi-safi-type;
            description
              "AFI and SAFI";
          }
          leaf ipv4-tunnel-network {
            mandatory true;
            type string;
            description
              "IPv4 Tunnel network <Tunnel-ID>:<IPv4 Address>";
          }
        }
      }
    }
  }
  augment "/ncs:devices/ncs:device/ncs:rpc" {
    container rpc-clear-bgp-instance-bestpath-afi-safi-rt-constraint-network {
      tailf:ncs-device-type "netconf";
      tailf:display-when "not(../../ncs:module) or ../../ncs:module[ncs:name='Cisco-IOS-XR-ipv4-bgp-act']";
      tailf:action clear-bgp-instance-bestpath-afi-safi-rt-constraint-network {
        tailf:actionpoint ncsproxy {
          tailf:internal;
        }
        csc:xr-task "bgp";
        csc:cli-command "clear bgp instance <instance-name> bestpath <afi-safi-name> <rt-constraint-network>";
        description
          "Choose a particular BGP instance.
           re-run BGP bestpath selection.
          ";
        input {
          leaf instance-name {
            mandatory true;
            type instance-name;
            description
              "instance name or all";
          }
          leaf afi-safi-name {
            mandatory true;
            type afi-safi-type;
            description
              "AFI and SAFI";
          }
          leaf rt-constraint-network {
            mandatory true;
            type string;
            description
              "RT-Constraint network";
          }
        }
      }
    }
  }
  augment "/ncs:devices/ncs:device-group/ncs:ned-id/ncs:rpc" {
    container rpc-clear-bgp-instance-bestpath-afi-safi-rt-constraint-network {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-rt-constraint-network {
        tailf:actionpoint ncsproxy {
          tailf:internal;
        }
        csc:xr-task "bgp";
        csc:cli-command "clear bgp instance <instance-name> bestpath <afi-safi-name> <rt-constraint-network>";
        description
          "Choose a particular BGP instance.
           re-run BGP bestpath selection.
          ";
        input {
          leaf instance-name {
            mandatory true;
            type instance-name;
            description
              "instance name or all";
          }
          leaf afi-safi-name {
            mandatory true;
            type afi-safi-type;
            description
              "AFI and SAFI";
          }
          leaf rt-constraint-network {
            mandatory true;
            type string;
            description
              "RT-Constraint network";
          }
        }
      }
    }
  }
  augment "/ncs:devices/ncs:device/ncs:rpc" {
    container rpc-clear-bgp-instance-bestpath-afi-safi-vrf-network {
      tailf:ncs-device-type "netconf";
      tailf:display-when "not(../../ncs:module) or ../../ncs:module[ncs:name='Cisco-IOS-XR-ipv4-bgp-act']";
      tailf:action clear-bgp-instance-bestpath-afi-safi-vrf-network {
        tailf:actionpoint ncsproxy {
          tailf:internal;
        }
        csc:xr-task "bgp";
        csc:cli-command "clear bgp instance <instance-name> bestpath <afi-safi-name> vrf <vrf-name> <network>";
        description
          "Choose a particular BGP instance.
           re-run BGP bestpath selection.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
          leaf network {
            mandatory true;
            type string;
            description
              "Address family modifier specific network";
          }
        }
      }
    }
  }
  augment "/ncs:devices/ncs:device-group/ncs:ned-id/ncs:rpc" {
    container rpc-clear-bgp-instance-bestpath-afi-safi-vrf-network {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-vrf-network {
        tailf:actionpoint ncsproxy {
          tailf:internal;
        }
        csc:xr-task "bgp";
        csc:cli-command "clear bgp instance <instance-name> bestpath <afi-safi-name> vrf <vrf-name> <network>";
        description
          "Choose a particular BGP instance.
           re-run BGP bestpath selection.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
          leaf network {
            mandatory true;
            type string;
            description
              "Address family modifier specific network";
          }
        }
      }
    }
  }
  augment "/ncs:devices/ncs:device/ncs:rpc" {
    container rpc-clear-bgp-instance-bestpath-afi-safi-rd-network {
      tailf:ncs-device-type "netconf";
      tailf:display-when "not(../../ncs:module) or ../../ncs:module[ncs:name='Cisco-IOS-XR-ipv4-bgp-act']";
      tailf:action clear-bgp-instance-bestpath-afi-safi-rd-network {
        tailf:actionpoint ncsproxy {
          tailf:internal;
        }
        csc:xr-task "bgp";
        csc:cli-command "clear bgp instance <instance-name> bestpath <afi-safi-name> rd <rd> <network>";
        description
          "Choose a particular BGP instance.
           re-run BGP bestpath selection.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf network {
            mandatory true;
            type string;
            description
              "Address family modifier specific network";
          }
        }
      }
    }
  }
  augment "/ncs:devices/ncs:device-group/ncs:ned-id/ncs:rpc" {
    container rpc-clear-bgp-instance-bestpath-afi-safi-rd-network {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-rd-network {
        tailf:actionpoint ncsproxy {
          tailf:internal;
        }
        csc:xr-task "bgp";
        csc:cli-command "clear bgp instance <instance-name> bestpath <afi-safi-name> rd <rd> <network>";
        description
          "Choose a particular BGP instance.
           re-run BGP bestpath selection.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf network {
            mandatory true;
            type string;
            description
              "Address family modifier specific network";
          }
        }
      }
    }
  }
  augment "/ncs:devices/ncs:device/ncs:rpc" {
    container rpc-clear-bgp-instance-bestpath-afi-safi-network {
      tailf:ncs-device-type "netconf";
      tailf:display-when "not(../../ncs:module) or ../../ncs:module[ncs:name='Cisco-IOS-XR-ipv4-bgp-act']";
      tailf:action clear-bgp-instance-bestpath-afi-safi-network {
        tailf:actionpoint ncsproxy {
          tailf:internal;
        }
        csc:xr-task "bgp";
        csc:cli-command "clear bgp instance <instance-name> bestpath <afi-safi-name> <network>";
        description
          "Choose a particular BGP instance.
           re-run BGP bestpath selection.
          ";
        input {
          leaf instance-name {
            mandatory true;
            type instance-name;
            description
              "instance name or all";
          }
          leaf afi-safi-name {
            mandatory true;
            type afi-safi-type;
            description
              "AFI and SAFI";
          }
          leaf network {
            mandatory true;
            type string;
            description
              "Address family modifier specific network";
          }
        }
      }
    }
  }
  augment "/ncs:devices/ncs:device-group/ncs:ned-id/ncs:rpc" {
    container rpc-clear-bgp-instance-bestpath-afi-safi-network {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-network {
        tailf:actionpoint ncsproxy {
          tailf:internal;
        }
        csc:xr-task "bgp";
        csc:cli-command "clear bgp instance <instance-name> bestpath <afi-safi-name> <network>";
        description
          "Choose a particular BGP instance.
           re-run BGP bestpath selection.
          ";
        input {
          leaf instance-name {
            mandatory true;
            type instance-name;
            description
              "instance name or all";
          }
          leaf afi-safi-name {
            mandatory true;
            type afi-safi-type;
            description
              "AFI and SAFI";
          }
          leaf network {
            mandatory true;
            type string;
            description
              "Address family modifier specific network";
          }
        }
      }
    }
  }
  augment "/ncs:devices/ncs:device/ncs:rpc" {
    container rpc-clear-bgp-instance-bestpath-afi-safi-vrf-ipv4-addr {
      tailf:ncs-device-type "netconf";
      tailf:display-when "not(../../ncs:module) or ../../ncs:module[ncs:name='Cisco-IOS-XR-ipv4-bgp-act']";
      tailf:action clear-bgp-instance-bestpath-afi-safi-vrf-ipv4-addr {
        tailf:actionpoint ncsproxy {
          tailf:internal;
        }
        csc:xr-task "bgp";
        csc:cli-command "clear bgp instance <instance-name> bestpath <afi-safi-name> vrf <vrf-name> <ipv4-addr>";
        description
          "Choose a particular BGP instance.
           re-run BGP bestpath selection.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
          leaf ipv4-addr {
            mandatory true;
            type inet:ipv4-address;
            description
              "IPv4 MDT network";
          }
        }
      }
    }
  }
  augment "/ncs:devices/ncs:device-group/ncs:ned-id/ncs:rpc" {
    container rpc-clear-bgp-instance-bestpath-afi-safi-vrf-ipv4-addr {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-vrf-ipv4-addr {
        tailf:actionpoint ncsproxy {
          tailf:internal;
        }
        csc:xr-task "bgp";
        csc:cli-command "clear bgp instance <instance-name> bestpath <afi-safi-name> vrf <vrf-name> <ipv4-addr>";
        description
          "Choose a particular BGP instance.
           re-run BGP bestpath selection.
           Display routes for a specified VRF.
          ";
        input {
          leaf instance-name {
            mandatory true;
            type instance-name;
            description
              "instance name or all";
          }
          leaf afi-safi-name {
            mandatory true;
            type afi-safi-type;
            description
              "AFI and SAFI";
          }
          leaf vrf-name {
            mandatory true;
            type string;
            description
              "VRF name";
          }
          leaf ipv4-addr {
            mandatory true;
            type inet:ipv4-address;
            description
              "IPv4 MDT network";
          }
        }
      }
    }
  }
  augment "/ncs:devices/ncs:device/ncs:rpc" {
    container rpc-clear-bgp-instance-bestpath-afi-safi-rd-ipv4-addr {
      tailf:ncs-device-type "netconf";
      tailf:display-when "not(../../ncs:module) or ../../ncs:module[ncs:name='Cisco-IOS-XR-ipv4-bgp-act']";
      tailf:action clear-bgp-instance-bestpath-afi-safi-rd-ipv4-addr {
        tailf:actionpoint ncsproxy {
          tailf:internal;
        }
        csc:xr-task "bgp";
        csc:cli-command "clear bgp instance <instance-name> bestpath <afi-safi-name> rd <rd> <ipv4-addr>";
        description
          "Choose a particular BGP instance.
           re-run BGP bestpath selection.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ipv4-addr {
            mandatory true;
            type inet:ipv4-address;
            description
              "IPv4 MDT network";
          }
        }
      }
    }
  }
  augment "/ncs:devices/ncs:device-group/ncs:ned-id/ncs:rpc" {
    container rpc-clear-bgp-instance-bestpath-afi-safi-rd-ipv4-addr {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-rd-ipv4-addr {
        tailf:actionpoint ncsproxy {
          tailf:internal;
        }
        csc:xr-task "bgp";
        csc:cli-command "clear bgp instance <instance-name> bestpath <afi-safi-name> rd <rd> <ipv4-addr>";
        description
          "Choose a particular BGP instance.
           re-run BGP bestpath selection.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ipv4-addr {
            mandatory true;
            type inet:ipv4-address;
            description
              "IPv4 MDT network";
          }
        }
      }
    }
  }
  augment "/ncs:devices/ncs:device/ncs:rpc" {
    container rpc-clear-bgp-instance-bestpath-afi-safi-ipv4-prefix {
      tailf:ncs-device-type "netconf";
      tailf:display-when "not(../../ncs:module) or ../../ncs:module[ncs:name='Cisco-IOS-XR-ipv4-bgp-act']";
      tailf:action clear-bgp-instance-bestpath-afi-safi-ipv4-prefix {
        tailf:actionpoint ncsproxy {
          tailf:internal;
        }
        csc:xr-task "bgp";
        csc:cli-command "clear bgp instance <instance-name> bestpath <afi-safi-name> <ipv4-prefix>";
        description
          "Choose a particular BGP instance.
           re-run BGP bestpath selection.
          ";
        input {
          leaf instance-name {
            mandatory true;
            type instance-name;
            description
              "instance name or all";
          }
          leaf afi-safi-name {
            mandatory true;
            type afi-safi-type;
            description
              "AFI and SAFI";
          }
          leaf ipv4-prefix {
            mandatory true;
            type inet:ipv4-prefix;
            description
              "IPv4 network and masklength";
          }
        }
      }
    }
  }
  augment "/ncs:devices/ncs:device-group/ncs:ned-id/ncs:rpc" {
    container rpc-clear-bgp-instance-bestpath-afi-safi-ipv4-prefix {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-ipv4-prefix {
        tailf:actionpoint ncsproxy {
          tailf:internal;
        }
        csc:xr-task "bgp";
        csc:cli-command "clear bgp instance <instance-name> bestpath <afi-safi-name> <ipv4-prefix>";
        description
          "Choose a particular BGP instance.
           re-run BGP bestpath selection.
          ";
        input {
          leaf instance-name {
            mandatory true;
            type instance-name;
            description
              "instance name or all";
          }
          leaf afi-safi-name {
            mandatory true;
            type afi-safi-type;
            description
              "AFI and SAFI";
          }
          leaf ipv4-prefix {
            mandatory true;
            type inet:ipv4-prefix;
            description
              "IPv4 network and masklength";
          }
        }
      }
    }
  }
  augment "/ncs:devices/ncs:device/ncs:rpc" {
    container rpc-clear-bgp-instance-bestpath-afi-safi-ipv4-addr {
      tailf:ncs-device-type "netconf";
      tailf:display-when "not(../../ncs:module) or ../../ncs:module[ncs:name='Cisco-IOS-XR-ipv4-bgp-act']";
      tailf:action clear-bgp-instance-bestpath-afi-safi-ipv4-addr {
        tailf:actionpoint ncsproxy {
          tailf:internal;
        }
        csc:xr-task "bgp";
        csc:cli-command "clear bgp instance <instance-name> bestpath <afi-safi-name> <ipv4-addr>";
        description
          "Choose a particular BGP instance.
           re-run BGP bestpath selection.
          ";
        input {
          leaf instance-name {
            mandatory true;
            type instance-name;
            description
              "instance name or all";
          }
          leaf afi-safi-name {
            mandatory true;
            type afi-safi-type;
            description
              "AFI and SAFI";
          }
          leaf ipv4-addr {
            mandatory true;
            type inet:ipv4-address;
            description
              "IPv4 network";
          }
        }
      }
    }
  }
  augment "/ncs:devices/ncs:device-group/ncs:ned-id/ncs:rpc" {
    container rpc-clear-bgp-instance-bestpath-afi-safi-ipv4-addr {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-ipv4-addr {
        tailf:actionpoint ncsproxy {
          tailf:internal;
        }
        csc:xr-task "bgp";
        csc:cli-command "clear bgp instance <instance-name> bestpath <afi-safi-name> <ipv4-addr>";
        description
          "Choose a particular BGP instance.
           re-run BGP bestpath selection.
          ";
        input {
          leaf instance-name {
            mandatory true;
            type instance-name;
            description
              "instance name or all";
          }
          leaf afi-safi-name {
            mandatory true;
            type afi-safi-type;
            description
              "AFI and SAFI";
          }
          leaf ipv4-addr {
            mandatory true;
            type inet:ipv4-address;
            description
              "IPv4 network";
          }
        }
      }
    }
  }
  augment "/ncs:devices/ncs:device/ncs:rpc" {
    container rpc-clear-bgp-instance-bestpath-afi-safi-ipv4-addr-ipv4-mask {
      tailf:ncs-device-type "netconf";
      tailf:display-when "not(../../ncs:module) or ../../ncs:module[ncs:name='Cisco-IOS-XR-ipv4-bgp-act']";
      tailf:action clear-bgp-instance-bestpath-afi-safi-ipv4-addr-ipv4-mask {
        tailf:actionpoint ncsproxy {
          tailf:internal;
        }
        csc:xr-task "bgp";
        csc:cli-command "clear bgp instance <instance-name> bestpath <afi-safi-name> <ipv4-addr> <ipv4-mask>";
        description
          "Choose a particular BGP instance.
           re-run BGP bestpath selection.
          ";
        input {
          leaf instance-name {
            mandatory true;
            type instance-name;
            description
              "instance name or all";
          }
          leaf afi-safi-name {
            mandatory true;
            type afi-safi-type;
            description
              "AFI and SAFI";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device-group/ncs:ned-id/ncs:rpc" {
    container rpc-clear-bgp-instance-bestpath-afi-safi-ipv4-addr-ipv4-mask {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-ipv4-addr-ipv4-mask {
        tailf:actionpoint ncsproxy {
          tailf:internal;
        }
        csc:xr-task "bgp";
        csc:cli-command "clear bgp instance <instance-name> bestpath <afi-safi-name> <ipv4-addr> <ipv4-mask>";
        description
          "Choose a particular BGP instance.
           re-run BGP bestpath selection.
          ";
        input {
          leaf instance-name {
            mandatory true;
            type instance-name;
            description
              "instance name or all";
          }
          leaf afi-safi-name {
            mandatory true;
            type afi-safi-type;
            description
              "AFI and SAFI";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device/ncs:rpc" {
    container rpc-clear-bgp-instance-bestpath-afi-safi-rd-ip-prefix {
      tailf:ncs-device-type "netconf";
      tailf:display-when "not(../../ncs:module) or ../../ncs:module[ncs:name='Cisco-IOS-XR-ipv4-bgp-act']";
      tailf:action clear-bgp-instance-bestpath-afi-safi-rd-ip-prefix {
        tailf:actionpoint ncsproxy {
          tailf:internal;
        }
        csc:xr-task "bgp";
        csc:cli-command "clear bgp instance <instance-name> bestpath <afi-safi-name> rd <rd> <ip-prefix>";
        description
          "Choose a particular BGP instance.
           re-run BGP bestpath selection.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ip-prefix {
            mandatory true;
            type inet:ip-prefix;
            description
              "Network and masklength";
          }
        }
      }
    }
  }
  augment "/ncs:devices/ncs:device-group/ncs:ned-id/ncs:rpc" {
    container rpc-clear-bgp-instance-bestpath-afi-safi-rd-ip-prefix {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-rd-ip-prefix {
        tailf:actionpoint ncsproxy {
          tailf:internal;
        }
        csc:xr-task "bgp";
        csc:cli-command "clear bgp instance <instance-name> bestpath <afi-safi-name> rd <rd> <ip-prefix>";
        description
          "Choose a particular BGP instance.
           re-run BGP bestpath selection.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ip-prefix {
            mandatory true;
            type inet:ip-prefix;
            description
              "Network and masklength";
          }
        }
      }
    }
  }
  augment "/ncs:devices/ncs:device/ncs:rpc" {
    container rpc-clear-bgp-instance-bestpath-afi-safi-rd-ip-addr {
      tailf:ncs-device-type "netconf";
      tailf:display-when "not(../../ncs:module) or ../../ncs:module[ncs:name='Cisco-IOS-XR-ipv4-bgp-act']";
      tailf:action clear-bgp-instance-bestpath-afi-safi-rd-ip-addr {
        tailf:actionpoint ncsproxy {
          tailf:internal;
        }
        csc:xr-task "bgp";
        csc:cli-command "clear bgp instance <instance-name> bestpath <afi-safi-name> rd <rd> <ip-addr>";
        description
          "Choose a particular BGP instance.
           re-run BGP bestpath selection.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ip-addr {
            mandatory true;
            type inet:ip-address;
            description
              "Network";
          }
        }
      }
    }
  }
  augment "/ncs:devices/ncs:device-group/ncs:ned-id/ncs:rpc" {
    container rpc-clear-bgp-instance-bestpath-afi-safi-rd-ip-addr {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-rd-ip-addr {
        tailf:actionpoint ncsproxy {
          tailf:internal;
        }
        csc:xr-task "bgp";
        csc:cli-command "clear bgp instance <instance-name> bestpath <afi-safi-name> rd <rd> <ip-addr>";
        description
          "Choose a particular BGP instance.
           re-run BGP bestpath selection.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ip-addr {
            mandatory true;
            type inet:ip-address;
            description
              "Network";
          }
        }
      }
    }
  }
  augment "/ncs:devices/ncs:device/ncs:rpc" {
    container rpc-clear-bgp-instance-bestpath-afi-safi-rd-ip-addr-ip-netmask {
      tailf:ncs-device-type "netconf";
      tailf:display-when "not(../../ncs:module) or ../../ncs:module[ncs:name='Cisco-IOS-XR-ipv4-bgp-act']";
      tailf:action clear-bgp-instance-bestpath-afi-safi-rd-ip-addr-ip-netmask {
        tailf:actionpoint ncsproxy {
          tailf:internal;
        }
        csc:xr-task "bgp";
        csc:cli-command "clear bgp instance <instance-name> bestpath <afi-safi-name> rd <rd> <ip-addr> <ip-netmask>";
        description
          "Choose a particular BGP instance.
           re-run BGP bestpath selection.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ip-addr {
            mandatory true;
            type inet:ip-address;
            description
              "Network";
          }
          leaf ip-netmask {
            mandatory true;
            type ip-netmask;
            description
              "Mask";
          }
        }
      }
    }
  }
  augment "/ncs:devices/ncs:device-group/ncs:ned-id/ncs:rpc" {
    container rpc-clear-bgp-instance-bestpath-afi-safi-rd-ip-addr-ip-netmask {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-rd-ip-addr-ip-netmask {
        tailf:actionpoint ncsproxy {
          tailf:internal;
        }
        csc:xr-task "bgp";
        csc:cli-command "clear bgp instance <instance-name> bestpath <afi-safi-name> rd <rd> <ip-addr> <ip-netmask>";
        description
          "Choose a particular BGP instance.
           re-run BGP bestpath selection.
           Display routes with a specific route distinguisher.
          ";
        input {
          leaf instance-name {
            mandatory true;
            type instance-name;
            description
              "instance name or all";
          }
          leaf afi-safi-name {
            mandatory true;
            type afi-safi-type;
            description
              "AFI and SAFI";
          }
          leaf rd {
            mandatory true;
            type rd;
            description
              "Route distinguisher";
          }
          leaf ip-addr {
            mandatory true;
            type inet:ip-address;
            description
              "Network";
          }
          leaf ip-netmask {
            mandatory true;
            type ip-netmask;
            description
              "Mask";
          }
        }
      }
    }
  }
  augment "/ncs:devices/ncs:device/ncs:rpc" {
    container rpc-clear-bgp-instance-bestpath-afi-safi-bridge-domain-ip-prefix {
      tailf:ncs-device-type "netconf";
      tailf:display-when "not(../../ncs:module) or ../../ncs:module[ncs:name='Cisco-IOS-XR-ipv4-bgp-act']";
      tailf:action clear-bgp-instance-bestpath-afi-safi-bridge-domain-ip-prefix {
        tailf:actionpoint ncsproxy {
          tailf:internal;
        }
        csc:xr-task "bgp";
        csc:cli-command "clear bgp instance <instance-name> bestpath <afi-safi-name> bridge-domain <bridge-domain-name> <ip-prefix>";
        description
          "Choose a particular BGP instance.
           re-run BGP bestpath selection.
           Display routes for a specified Bridge Domain.
          ";
        input {
          leaf instance-name {
            mandatory true;
            type instance-name;
            description
              "instance name or all";
          }
          leaf afi-safi-name {
            mandatory true;
            type afi-safi-type;
            description
              "AFI and SAFI";
          }
          leaf bridge-domain-name {
            mandatory true;
            type string;
            description
              "Bridge Domain";
          }
          leaf ip-prefix {
            mandatory true;
            type inet:ip-prefix;
            description
              "Network and masklength";
          }
        }
      }
    }
  }
  augment "/ncs:devices/ncs:device-group/ncs:ned-id/ncs:rpc" {
    container rpc-clear-bgp-instance-bestpath-afi-safi-bridge-domain-ip-prefix {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-bridge-domain-ip-prefix {
        tailf:actionpoint ncsproxy {
          tailf:internal;
        }
        csc:xr-task "bgp";
        csc:cli-command "clear bgp instance <instance-name> bestpath <afi-safi-name> bridge-domain <bridge-domain-name> <ip-prefix>";
        description
          "Choose a particular BGP instance.
           re-run BGP bestpath selection.
           Display routes for a specified Bridge Domain.
          ";
        input {
          leaf instance-name {
            mandatory true;
            type instance-name;
            description
              "instance name or all";
          }
          leaf afi-safi-name {
            mandatory true;
            type afi-safi-type;
            description
              "AFI and SAFI";
          }
          leaf bridge-domain-name {
            mandatory true;
            type string;
            description
              "Bridge Domain";
          }
          leaf ip-prefix {
            mandatory true;
            type inet:ip-prefix;
            description
              "Network and masklength";
          }
        }
      }
    }
  }
  augment "/ncs:devices/ncs:device/ncs:rpc" {
    container rpc-clear-bgp-instance-bestpath-afi-safi-bridge-domain-ip-addr {
      tailf:ncs-device-type "netconf";
      tailf:display-when "not(../../ncs:module) or ../../ncs:module[ncs:name='Cisco-IOS-XR-ipv4-bgp-act']";
      tailf:action clear-bgp-instance-bestpath-afi-safi-bridge-domain-ip-addr {
        tailf:actionpoint ncsproxy {
          tailf:internal;
        }
        csc:xr-task "bgp";
        csc:cli-command "clear bgp instance <instance-name> bestpath <afi-safi-name> bridge-domain <bridge-domain-name> <ip-addr>";
        description
          "Choose a particular BGP instance.
           re-run BGP bestpath selection.
           Display routes for a specified Bridge Domain.
          ";
        input {
          leaf instance-name {
            mandatory true;
            type instance-name;
            description
              "instance name or all";
          }
          leaf afi-safi-name {
            mandatory true;
            type afi-safi-type;
            description
              "AFI and SAFI";
          }
          leaf bridge-domain-name {
            mandatory true;
            type string;
            description
              "Bridge Domain";
          }
          leaf ip-addr {
            mandatory true;
            type inet:ip-address;
            description
              "Network";
          }
        }
      }
    }
  }
  augment "/ncs:devices/ncs:device-group/ncs:ned-id/ncs:rpc" {
    container rpc-clear-bgp-instance-bestpath-afi-safi-bridge-domain-ip-addr {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-bridge-domain-ip-addr {
        tailf:actionpoint ncsproxy {
          tailf:internal;
        }
        csc:xr-task "bgp";
        csc:cli-command "clear bgp instance <instance-name> bestpath <afi-safi-name> bridge-domain <bridge-domain-name> <ip-addr>";
        description
          "Choose a particular BGP instance.
           re-run BGP bestpath selection.
           Display routes for a specified Bridge Domain.
          ";
        input {
          leaf instance-name {
            mandatory true;
            type instance-name;
            description
              "instance name or all";
          }
          leaf afi-safi-name {
            mandatory true;
            type afi-safi-type;
            description
              "AFI and SAFI";
          }
          leaf bridge-domain-name {
            mandatory true;
            type string;
            description
              "Bridge Domain";
          }
          leaf ip-addr {
            mandatory true;
            type inet:ip-address;
            description
              "Network";
          }
        }
      }
    }
  }
  augment "/ncs:devices/ncs:device/ncs:rpc" {
    container rpc-clear-bgp-instance-bestpath-afi-safi-bridge-domain-ip-addr-ip-netmask {
      tailf:ncs-device-type "netconf";
      tailf:display-when "not(../../ncs:module) or ../../ncs:module[ncs:name='Cisco-IOS-XR-ipv4-bgp-act']";
      tailf:action clear-bgp-instance-bestpath-afi-safi-bridge-domain-ip-addr-ip-netmask {
        tailf:actionpoint ncsproxy {
          tailf:internal;
        }
        csc:xr-task "bgp";
        csc:cli-command "clear bgp instance <instance-name> bestpath <afi-safi-name> bridge-domain <bridge-domain-name> <ip-addr> <ip-netmask>";
        description
          "Choose a particular BGP instance.
           re-run BGP bestpath selection.
           Display routes for a specified Bridge Domain.
          ";
        input {
          leaf instance-name {
            mandatory true;
            type instance-name;
            description
              "instance name or all";
          }
          leaf afi-safi-name {
            mandatory true;
            type afi-safi-type;
            description
              "AFI and SAFI";
          }
          leaf bridge-domain-name {
            mandatory true;
            type string;
            description
              "Bridge Domain";
          }
          leaf ip-addr {
            mandatory true;
            type inet:ip-address;
            description
              "Network";
          }
          leaf ip-netmask {
            mandatory true;
            type ip-netmask;
            description
              "Mask";
          }
        }
      }
    }
  }
  augment "/ncs:devices/ncs:device-group/ncs:ned-id/ncs:rpc" {
    container rpc-clear-bgp-instance-bestpath-afi-safi-bridge-domain-ip-addr-ip-netmask {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-bridge-domain-ip-addr-ip-netmask {
        tailf:actionpoint ncsproxy {
          tailf:internal;
        }
        csc:xr-task "bgp";
        csc:cli-command "clear bgp instance <instance-name> bestpath <afi-safi-name> bridge-domain <bridge-domain-name> <ip-addr> <ip-netmask>";
        description
          "Choose a particular BGP instance.
           re-run BGP bestpath selection.
           Display routes for a specified Bridge Domain.
          ";
        input {
          leaf instance-name {
            mandatory true;
            type instance-name;
            description
              "instance name or all";
          }
          leaf afi-safi-name {
            mandatory true;
            type afi-safi-type;
            description
              "AFI and SAFI";
          }
          leaf bridge-domain-name {
            mandatory true;
            type string;
            description
              "Bridge Domain";
          }
          leaf ip-addr {
            mandatory true;
            type inet:ip-address;
            description
              "Network";
          }
          leaf ip-netmask {
            mandatory true;
            type ip-netmask;
            description
              "Mask";
          }
        }
      }
    }
  }
  augment "/ncs:devices/ncs:device/ncs:rpc" {
    container rpc-clear-bgp-instance-bestpath-afi-safi-ip-prefix {
      tailf:ncs-device-type "netconf";
      tailf:display-when "not(../../ncs:module) or ../../ncs:module[ncs:name='Cisco-IOS-XR-ipv4-bgp-act']";
      tailf:action clear-bgp-instance-bestpath-afi-safi-ip-prefix {
        tailf:actionpoint ncsproxy {
          tailf:internal;
        }
        csc:xr-task "bgp";
        csc:cli-command "clear bgp instance <instance-name> bestpath <afi-safi-name> <ip-prefix>";
        description
          "Choose a particular BGP instance.
           re-run BGP bestpath selection.
          ";
        input {
          leaf instance-name {
            mandatory true;
            type instance-name;
            description
              "instance name or all";
          }
          leaf afi-safi-name {
            mandatory true;
            type afi-safi-type;
            description
              "AFI and SAFI";
          }
          leaf ip-prefix {
            mandatory true;
            type inet:ip-prefix;
            description
              "Network and masklength";
          }
        }
      }
    }
  }
  augment "/ncs:devices/ncs:device-group/ncs:ned-id/ncs:rpc" {
    container rpc-clear-bgp-instance-bestpath-afi-safi-ip-prefix {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-ip-prefix {
        tailf:actionpoint ncsproxy {
          tailf:internal;
        }
        csc:xr-task "bgp";
        csc:cli-command "clear bgp instance <instance-name> bestpath <afi-safi-name> <ip-prefix>";
        description
          "Choose a particular BGP instance.
           re-run BGP bestpath selection.
          ";
        input {
          leaf instance-name {
            mandatory true;
            type instance-name;
            description
              "instance name or all";
          }
          leaf afi-safi-name {
            mandatory true;
            type afi-safi-type;
            description
              "AFI and SAFI";
          }
          leaf ip-prefix {
            mandatory true;
            type inet:ip-prefix;
            description
              "Network and masklength";
          }
        }
      }
    }
  }
  augment "/ncs:devices/ncs:device/ncs:rpc" {
    container rpc-clear-bgp-instance-bestpath-afi-safi-ip-addr {
      tailf:ncs-device-type "netconf";
      tailf:display-when "not(../../ncs:module) or ../../ncs:module[ncs:name='Cisco-IOS-XR-ipv4-bgp-act']";
      tailf:action clear-bgp-instance-bestpath-afi-safi-ip-addr {
        tailf:actionpoint ncsproxy {
          tailf:internal;
        }
        csc:xr-task "bgp";
        csc:cli-command "clear bgp instance <instance-name> bestpath <afi-safi-name> <ip-addr>";
        description
          "Choose a particular BGP instance.
           re-run BGP bestpath selection.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "Network";
          }
        }
      }
    }
  }
  augment "/ncs:devices/ncs:device-group/ncs:ned-id/ncs:rpc" {
    container rpc-clear-bgp-instance-bestpath-afi-safi-ip-addr {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-ip-addr {
        tailf:actionpoint ncsproxy {
          tailf:internal;
        }
        csc:xr-task "bgp";
        csc:cli-command "clear bgp instance <instance-name> bestpath <afi-safi-name> <ip-addr>";
        description
          "Choose a particular BGP instance.
           re-run BGP bestpath selection.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "Network";
          }
        }
      }
    }
  }
  augment "/ncs:devices/ncs:device/ncs:rpc" {
    container rpc-clear-bgp-instance-bestpath-afi-safi-ip-addr-ip-netmask {
      tailf:ncs-device-type "netconf";
      tailf:display-when "not(../../ncs:module) or ../../ncs:module[ncs:name='Cisco-IOS-XR-ipv4-bgp-act']";
      tailf:action clear-bgp-instance-bestpath-afi-safi-ip-addr-ip-netmask {
        tailf:actionpoint ncsproxy {
          tailf:internal;
        }
        csc:xr-task "bgp";
        csc:cli-command "clear bgp instance <instance-name> bestpath <afi-safi-name> <ip-addr> <ip-netmask>";
        description
          "Choose a particular BGP instance.
           re-run BGP bestpath selection.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "Network";
          }
          leaf ip-netmask {
            mandatory true;
            type ip-netmask;
            description
              "Mask";
          }
        }
      }
    }
  }
  augment "/ncs:devices/ncs:device-group/ncs:ned-id/ncs:rpc" {
    container rpc-clear-bgp-instance-bestpath-afi-safi-ip-addr-ip-netmask {
      tailf:ncs-device-type "netconf";
      tailf:display-when "/ncs:devices/ncs:device[ncs:name=current()/../../../ncs:member]/ncs:module[ncs:name='Cisco-IOS-XR-ipv4-bgp-act']";
      tailf:action clear-bgp-instance-bestpath-afi-safi-ip-addr-ip-netmask {
        tailf:actionpoint ncsproxy {
          tailf:internal;
        }
        csc:xr-task "bgp";
        csc:cli-command "clear bgp instance <instance-name> bestpath <afi-safi-name> <ip-addr> <ip-netmask>";
        description
          "Choose a particular BGP instance.
           re-run BGP bestpath selection.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "Network";
          }
          leaf ip-netmask {
            mandatory true;
            type ip-netmask;
            description
              "Mask";
          }
        }
      }
    }
  }
  augment "/ncs:devices/ncs:device/ncs:rpc" {
    container rpc-clear-bgp-instance-bestpath-ip-prefix {
      tailf:ncs-device-type "netconf";
      tailf:display-when "not(../../ncs:module) or ../../ncs:module[ncs:name='Cisco-IOS-XR-ipv4-bgp-act']";
      tailf:action clear-bgp-instance-bestpath-ip-prefix {
        tailf:actionpoint ncsproxy {
          tailf:internal;
        }
        csc:xr-task "bgp";
        csc:cli-command "clear bgp instance <instance-name> bestpath <ip-prefix>";
        description
          "Choose a particular BGP instance.
           re-run BGP bestpath selection.
          ";
        input {
          leaf instance-name {
            mandatory true;
            type instance-name;
            description
              "instance name or all";
          }
          leaf ip-prefix {
            mandatory true;
            type inet:ip-prefix;
            description
              "Network and masklength";
          }
        }
      }
    }
  }
  augment "/ncs:devices/ncs:device-group/ncs:ned-id/ncs:rpc" {
    container rpc-clear-bgp-instance-bestpath-ip-prefix {
      tailf:ncs-device-type "netconf";
      tailf:display-when "/ncs:devices/ncs:device[ncs:name=current()/../../../ncs:member]/ncs:module[ncs:name='Cisco-IOS-XR-ipv4-bgp-act']";
      tailf:action clear-bgp-instance-bestpath-ip-prefix {
        tailf:actionpoint ncsproxy {
          tailf:internal;
        }
        csc:xr-task "bgp";
        csc:cli-command "clear bgp instance <instance-name> bestpath <ip-prefix>";
        description
          "Choose a particular BGP instance.
           re-run BGP bestpath selection.
          ";
        input {
          leaf instance-name {
            mandatory true;
            type instance-name;
            description
              "instance name or all";
          }
          leaf ip-prefix {
            mandatory true;
            type inet:ip-prefix;
            description
              "Network and masklength";
          }
        }
      }
    }
  }
  augment "/ncs:devices/ncs:device/ncs:rpc" {
    container rpc-clear-bgp-instance-bestpath-ip-addr {
      tailf:ncs-device-type "netconf";
      tailf:display-when "not(../../ncs:module) or ../../ncs:module[ncs:name='Cisco-IOS-XR-ipv4-bgp-act']";
      tailf:action clear-bgp-instance-bestpath-ip-addr {
        tailf:actionpoint ncsproxy {
          tailf:internal;
        }
        csc:xr-task "bgp";
        csc:cli-command "clear bgp instance <instance-name> bestpath <ip-addr>";
        description
          "Choose a particular BGP instance.
           re-run BGP bestpath selection.
          ";
        input {
          leaf instance-name {
            mandatory true;
            type instance-name;
            description
              "instance name or all";
          }
          leaf ip-addr {
            mandatory true;
            type inet:ip-address;
            description
              "Network";
          }
        }
      }
    }
  }
  augment "/ncs:devices/ncs:device-group/ncs:ned-id/ncs:rpc" {
    container rpc-clear-bgp-instance-bestpath-ip-addr {
      tailf:ncs-device-type "netconf";
      tailf:display-when "/ncs:devices/ncs:device[ncs:name=current()/../../../ncs:member]/ncs:module[ncs:name='Cisco-IOS-XR-ipv4-bgp-act']";
      tailf:action clear-bgp-instance-bestpath-ip-addr {
        tailf:actionpoint ncsproxy {
          tailf:internal;
        }
        csc:xr-task "bgp";
        csc:cli-command "clear bgp instance <instance-name> bestpath <ip-addr>";
        description
          "Choose a particular BGP instance.
           re-run BGP bestpath selection.
          ";
        input {
          leaf instance-name {
            mandatory true;
            type instance-name;
            description
              "instance name or all";
          }
          leaf ip-addr {
            mandatory true;
            type inet:ip-address;
            description
              "Network";
          }
        }
      }
    }
  }
  augment "/ncs:devices/ncs:device/ncs:rpc" {
    container rpc-clear-bgp-instance-bestpath-ip-addr-ip-netmask {
      tailf:ncs-device-type "netconf";
      tailf:display-when "not(../../ncs:module) or ../../ncs:module[ncs:name='Cisco-IOS-XR-ipv4-bgp-act']";
      tailf:action clear-bgp-instance-bestpath-ip-addr-ip-netmask {
        tailf:actionpoint ncsproxy {
          tailf:internal;
        }
        csc:xr-task "bgp";
        csc:cli-command "clear bgp instance <instance-name> bestpath <ip-addr> <ip-netmask>";
        description
          "Choose a particular BGP instance.
           re-run BGP bestpath selection.
          ";
        input {
          leaf instance-name {
            mandatory true;
            type instance-name;
            description
              "instance name or all";
          }
          leaf ip-addr {
            mandatory true;
            type inet:ip-address;
            description
              "Network";
          }
          leaf ip-netmask {
            mandatory true;
            type ip-netmask;
            description
              "Mask";
          }
        }
      }
    }
  }
  augment "/ncs:devices/ncs:device-group/ncs:ned-id/ncs:rpc" {
    container rpc-clear-bgp-instance-bestpath-ip-addr-ip-netmask {
      tailf:ncs-device-type "netconf";
      tailf:display-when "/ncs:devices/ncs:device[ncs:name=current()/../../../ncs:member]/ncs:module[ncs:name='Cisco-IOS-XR-ipv4-bgp-act']";
      tailf:action clear-bgp-instance-bestpath-ip-addr-ip-netmask {
        tailf:actionpoint ncsproxy {
          tailf:internal;
        }
        csc:xr-task "bgp";
        csc:cli-command "clear bgp instance <instance-name> bestpath <ip-addr> <ip-netmask>";
        description
          "Choose a particular BGP instance.
           re-run BGP bestpath selection.
          ";
        input {
          leaf instance-name {
            mandatory true;
            type instance-name;
            description
              "instance name or all";
          }
          leaf ip-addr {
            mandatory true;
            type inet:ip-address;
            description
              "Network";
          }
          leaf ip-netmask {
            mandatory true;
            type ip-netmask;
            description
              "Mask";
          }
        }
      }
    }
  }
  augment "/ncs:devices/ncs:device/ncs:rpc" {
    container rpc-clear-bgp-instance-as {
      tailf:ncs-device-type "netconf";
      tailf:display-when "not(../../ncs:module) or ../../ncs:module[ncs:name='Cisco-IOS-XR-ipv4-bgp-act']";
      tailf:action clear-bgp-instance-as {
        tailf:actionpoint ncsproxy {
          tailf:internal;
        }
        csc:xr-task "bgp";
        csc:cli-command "clear bgp instance <instance-name> as <as-number>";
        description
          "Choose a particular BGP instance.
           Clear peers in a specific AS.
          ";
        input {
          leaf instance-name {
            mandatory true;
            type instance-name;
            description
              "instance name or all";
          }
          leaf as-number {
            mandatory true;
            type as-number;
            description
              "AS number";
          }
        }
      }
    }
  }
  augment "/ncs:devices/ncs:device-group/ncs:ned-id/ncs:rpc" {
    container rpc-clear-bgp-instance-as {
      tailf:ncs-device-type "netconf";
      tailf:display-when "/ncs:devices/ncs:device[ncs:name=current()/../../../ncs:member]/ncs:module[ncs:name='Cisco-IOS-XR-ipv4-bgp-act']";
      tailf:action clear-bgp-instance-as {
        tailf:actionpoint ncsproxy {
          tailf:internal;
        }
        csc:xr-task "bgp";
        csc:cli-command "clear bgp instance <instance-name> as <as-number>";
        description
          "Choose a particular BGP instance.
           Clear peers in a specific AS.
          ";
        input {
          leaf instance-name {
            mandatory true;
            type instance-name;
            description
              "instance name or all";
          }
          leaf as-number {
            mandatory true;
            type as-number;
            description
              "AS number";
          }
        }
      }
    }
  }
  augment "/ncs:devices/ncs:device/ncs:rpc" {
    container rpc-clear-bgp-instance-as-graceful {
      tailf:ncs-device-type "netconf";
      tailf:display-when "not(../../ncs:module) or ../../ncs:module[ncs:name='Cisco-IOS-XR-ipv4-bgp-act']";
      tailf:action clear-bgp-instance-as-graceful {
        tailf:actionpoint ncsproxy {
          tailf:internal;
        }
        csc:xr-task "bgp";
        csc:cli-command "clear bgp instance <instance-name> as <as-number> graceful";
        description
          "Choose a particular BGP instance.
           Clear peers in a specific AS.
           Clear with a hard reset and a graceful restart.
          ";
        input {
          leaf instance-name {
            mandatory true;
            type instance-name;
            description
              "instance name or all";
          }
          leaf as-number {
            mandatory true;
            type as-number;
            description
              "AS number";
          }
        }
      }
    }
  }
  augment "/ncs:devices/ncs:device-group/ncs:ned-id/ncs:rpc" {
    container rpc-clear-bgp-instance-as-graceful {
      tailf:ncs-device-type "netconf";
      tailf:display-when "/ncs:devices/ncs:device[ncs:name=current()/../../../ncs:member]/ncs:module[ncs:name='Cisco-IOS-XR-ipv4-bgp-act']";
      tailf:action clear-bgp-instance-as-graceful {
        tailf:actionpoint ncsproxy {
          tailf:internal;
        }
        csc:xr-task "bgp";
        csc:cli-command "clear bgp instance <instance-name> as <as-number> graceful";
        description
          "Choose a particular BGP instance.
           Clear peers in a specific AS.
           Clear with a hard reset and a graceful restart.
          ";
        input {
          leaf instance-name {
            mandatory true;
            type instance-name;
            description
              "instance name or all";
          }
          leaf as-number {
            mandatory true;
            type as-number;
            description
              "AS number";
          }
        }
      }
    }
  }
  augment "/ncs:devices/ncs:device/ncs:rpc" {
    container rpc-clear-bgp-instance-afi-safi-update-outq-update-group {
      tailf:ncs-device-type "netconf";
      tailf:display-when "not(../../ncs:module) or ../../ncs:module[ncs:name='Cisco-IOS-XR-ipv4-bgp-act']";
      tailf:action clear-bgp-instance-afi-safi-update-outq-update-group {
        tailf:actionpoint ncsproxy {
          tailf:internal;
        }
        csc:xr-task "bgp";
        csc:cli-command "clear bgp instance <instance-name> <afi-safi-name> update outq update-group <update-group>";
        description
          "Choose a particular BGP instance.
           Clear Update information (Do NOT execute without cisco support)(cisco-support).
           Clear Update generation OutQ counters (Do NOT execute without cisco support)(cisco-support).
           Update-group.
          ";
        input {
          leaf instance-name {
            mandatory true;
            type instance-name;
            description
              "instance name or all";
          }
          leaf afi-safi-name {
            mandatory true;
            type afi-safi-type;
            description
              "AFI and SAFI";
          }
          leaf update-group {
            mandatory true;
            type update-group-id;
            description
              "Update-group process ID <x.y>";
          }
        }
      }
    }
  }
  augment "/ncs:devices/ncs:device-group/ncs:ned-id/ncs:rpc" {
    container rpc-clear-bgp-instance-afi-safi-update-outq-update-group {
      tailf:ncs-device-type "netconf";
      tailf:display-when "/ncs:devices/ncs:device[ncs:name=current()/../../../ncs:member]/ncs:module[ncs:name='Cisco-IOS-XR-ipv4-bgp-act']";
      tailf:action clear-bgp-instance-afi-safi-update-outq-update-group {
        tailf:actionpoint ncsproxy {
          tailf:internal;
        }
        csc:xr-task "bgp";
        csc:cli-command "clear bgp instance <instance-name> <afi-safi-name> update outq update-group <update-group>";
        description
          "Choose a particular BGP instance.
           Clear Update information (Do NOT execute without cisco support)(cisco-support).
           Clear Update generation OutQ counters (Do NOT execute without cisco support)(cisco-support).
           Update-group.
          ";
        input {
          leaf instance-name {
            mandatory true;
            type instance-name;
            description
              "instance name or all";
          }
          leaf afi-safi-name {
            mandatory true;
            type afi-safi-type;
            description
              "AFI and SAFI";
          }
          leaf update-group {
            mandatory true;
            type update-group-id;
            description
              "Update-group process ID <x.y>";
          }
        }
      }
    }
  }
  augment "/ncs:devices/ncs:device/ncs:rpc" {
    container rpc-clear-bgp-instance-afi-safi-update-outq-update-group-update-parent {
      tailf:ncs-device-type "netconf";
      tailf:display-when "not(../../ncs:module) or ../../ncs:module[ncs:name='Cisco-IOS-XR-ipv4-bgp-act']";
      tailf:action clear-bgp-instance-afi-safi-update-outq-update-group-update-parent {
        tailf:actionpoint ncsproxy {
          tailf:internal;
        }
        csc:xr-task "bgp";
        csc:cli-command "clear bgp instance <instance-name> <afi-safi-name> update outq update-group <update-group> update-parent";
        description
          "Choose a particular BGP instance.
           Clear Update information (Do NOT execute without cisco support)(cisco-support).
           Clear Update generation OutQ counters (Do NOT execute without cisco support)(cisco-support).
           Update-group.
           Update parents' OutQ counters too.
          ";
        input {
          leaf instance-name {
            mandatory true;
            type instance-name;
            description
              "instance name or all";
          }
          leaf afi-safi-name {
            mandatory true;
            type afi-safi-type;
            description
              "AFI and SAFI";
          }
          leaf update-group {
            mandatory true;
            type update-group-id;
            description
              "Update-group process ID <x.y>";
          }
        }
      }
    }
  }
  augment "/ncs:devices/ncs:device-group/ncs:ned-id/ncs:rpc" {
    container rpc-clear-bgp-instance-afi-safi-update-outq-update-group-update-parent {
      tailf:ncs-device-type "netconf";
      tailf:display-when "/ncs:devices/ncs:device[ncs:name=current()/../../../ncs:member]/ncs:module[ncs:name='Cisco-IOS-XR-ipv4-bgp-act']";
      tailf:action clear-bgp-instance-afi-safi-update-outq-update-group-update-parent {
        tailf:actionpoint ncsproxy {
          tailf:internal;
        }
        csc:xr-task "bgp";
        csc:cli-command "clear bgp instance <instance-name> <afi-safi-name> update outq update-group <update-group> update-parent";
        description
          "Choose a particular BGP instance.
           Clear Update information (Do NOT execute without cisco support)(cisco-support).
           Clear Update generation OutQ counters (Do NOT execute without cisco support)(cisco-support).
           Update-group.
           Update parents' OutQ counters too.
          ";
        input {
          leaf instance-name {
            mandatory true;
            type instance-name;
            description
              "instance name or all";
          }
          leaf afi-safi-name {
            mandatory true;
            type afi-safi-type;
            description
              "AFI and SAFI";
          }
          leaf update-group {
            mandatory true;
            type update-group-id;
            description
              "Update-group process ID <x.y>";
          }
        }
      }
    }
  }
  augment "/ncs:devices/ncs:device/ncs:rpc" {
    container rpc-clear-bgp-instance-afi-safi-update-outq-update-group-sub-group-refresh-sub-group {
      tailf:ncs-device-type "netconf";
      tailf:display-when "not(../../ncs:module) or ../../ncs:module[ncs:name='Cisco-IOS-XR-ipv4-bgp-act']";
      tailf:action clear-bgp-instance-afi-safi-update-outq-update-group-sub-group-refresh-sub-group {
        tailf:actionpoint ncsproxy {
          tailf:internal;
        }
        csc:xr-task "bgp";
        csc:cli-command "clear bgp instance <instance-name> <afi-safi-name> update outq update-group <update-group> sub-group <refresh-sub-group>";
        description
          "Choose a particular BGP instance.
           Clear Update information (Do NOT execute without cisco support)(cisco-support).
           Clear Update generation OutQ counters (Do NOT execute without cisco support)(cisco-support).
           Update-group.
           Sub-group.
          ";
        input {
          leaf instance-name {
            mandatory true;
            type instance-name;
            description
              "instance name or all";
          }
          leaf afi-safi-name {
            mandatory true;
            type afi-safi-type;
            description
              "AFI and SAFI";
          }
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device-group/ncs:ned-id/ncs:rpc" {
    container rpc-clear-bgp-instance-afi-safi-update-outq-update-group-sub-group-refresh-sub-group {
      tailf:ncs-device-type "netconf";
      tailf:display-when "/ncs:devices/ncs:device[ncs:name=current()/../../../ncs:member]/ncs:module[ncs:name='Cisco-IOS-XR-ipv4-bgp-act']";
      tailf:action clear-bgp-instance-afi-safi-update-outq-update-group-sub-group-refresh-sub-group {
        tailf:actionpoint ncsproxy {
          tailf:internal;
        }
        csc:xr-task "bgp";
        csc:cli-command "clear bgp instance <instance-name> <afi-safi-name> update outq update-group <update-group> sub-group <refresh-sub-group>";
        description
          "Choose a particular BGP instance.
           Clear Update information (Do NOT execute without cisco support)(cisco-support).
           Clear Update generation OutQ counters (Do NOT execute without cisco support)(cisco-support).
           Update-group.
           Sub-group.
          ";
        input {
          leaf instance-name {
            mandatory true;
            type instance-name;
            description
              "instance name or all";
          }
          leaf afi-safi-name {
            mandatory true;
            type afi-safi-type;
            description
              "AFI and SAFI";
          }
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device/ncs:rpc" {
    container rpc-clear-bgp-instance-afi-safi-update-outq-update-group-sub-group-refresh-sub-group-update-parent {
      tailf:ncs-device-type "netconf";
      tailf:display-when "not(../../ncs:module) or ../../ncs:module[ncs:name='Cisco-IOS-XR-ipv4-bgp-act']";
      tailf:action clear-bgp-instance-afi-safi-update-outq-update-group-sub-group-refresh-sub-group-update-parent {
        tailf:actionpoint ncsproxy {
          tailf:internal;
        }
        csc:xr-task "bgp";
        csc:cli-command "clear bgp instance <instance-name> <afi-safi-name> update outq update-group <update-group> sub-group <refresh-sub-group> update-parent";
        description
          "Choose a particular BGP instance.
           Clear Update information (Do NOT execute without cisco support)(cisco-support).
           Clear Update generation OutQ counters (Do NOT execute without cisco support)(cisco-support).
           Update-group.
           Sub-group.
           Update parents' OutQ counters too.
          ";
        input {
          leaf instance-name {
            mandatory true;
            type instance-name;
            description
              "instance name or all";
          }
          leaf afi-safi-name {
            mandatory true;
            type afi-safi-type;
            description
              "AFI and SAFI";
          }
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device-group/ncs:ned-id/ncs:rpc" {
    container rpc-clear-bgp-instance-afi-safi-update-outq-update-group-sub-group-refresh-sub-group-update-parent {
      tailf:ncs-device-type "netconf";
      tailf:display-when "/ncs:devices/ncs:device[ncs:name=current()/../../../ncs:member]/ncs:module[ncs:name='Cisco-IOS-XR-ipv4-bgp-act']";
      tailf:action clear-bgp-instance-afi-safi-update-outq-update-group-sub-group-refresh-sub-group-update-parent {
        tailf:actionpoint ncsproxy {
          tailf:internal;
        }
        csc:xr-task "bgp";
        csc:cli-command "clear bgp instance <instance-name> <afi-safi-name> update outq update-group <update-group> sub-group <refresh-sub-group> update-parent";
        description
          "Choose a particular BGP instance.
           Clear Update information (Do NOT execute without cisco support)(cisco-support).
           Clear Update generation OutQ counters (Do NOT execute without cisco support)(cisco-support).
           Update-group.
           Sub-group.
           Update parents' OutQ counters too.
          ";
        input {
          leaf instance-name {
            mandatory true;
            type instance-name;
            description
              "instance name or all";
          }
          leaf afi-safi-name {
            mandatory true;
            type afi-safi-type;
            description
              "AFI and SAFI";
          }
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device/ncs:rpc" {
    container rpc-clear-bgp-instance-afi-safi-update-outq-update-group-sub-group {
      tailf:ncs-device-type "netconf";
      tailf:display-when "not(../../ncs:module) or ../../ncs:module[ncs:name='Cisco-IOS-XR-ipv4-bgp-act']";
      tailf:action clear-bgp-instance-afi-safi-update-outq-update-group-sub-group {
        tailf:actionpoint ncsproxy {
          tailf:internal;
        }
        csc:xr-task "bgp";
        csc:cli-command "clear bgp instance <instance-name> <afi-safi-name> update outq update-group <update-group> sub-group <sub-group>";
        description
          "Choose a particular BGP instance.
           Clear Update information (Do NOT execute without cisco support)(cisco-support).
           Clear Update generation OutQ counters (Do NOT execute without cisco support)(cisco-support).
           Update-group.
           Sub-group.
          ";
        input {
          leaf instance-name {
            mandatory true;
            type instance-name;
            description
              "instance name or all";
          }
          leaf afi-safi-name {
            mandatory true;
            type afi-safi-type;
            description
              "AFI and SAFI";
          }
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device-group/ncs:ned-id/ncs:rpc" {
    container rpc-clear-bgp-instance-afi-safi-update-outq-update-group-sub-group {
      tailf:ncs-device-type "netconf";
      tailf:display-when "/ncs:devices/ncs:device[ncs:name=current()/../../../ncs:member]/ncs:module[ncs:name='Cisco-IOS-XR-ipv4-bgp-act']";
      tailf:action clear-bgp-instance-afi-safi-update-outq-update-group-sub-group {
        tailf:actionpoint ncsproxy {
          tailf:internal;
        }
        csc:xr-task "bgp";
        csc:cli-command "clear bgp instance <instance-name> <afi-safi-name> update outq update-group <update-group> sub-group <sub-group>";
        description
          "Choose a particular BGP instance.
           Clear Update information (Do NOT execute without cisco support)(cisco-support).
           Clear Update generation OutQ counters (Do NOT execute without cisco support)(cisco-support).
           Update-group.
           Sub-group.
          ";
        input {
          leaf instance-name {
            mandatory true;
            type instance-name;
            description
              "instance name or all";
          }
          leaf afi-safi-name {
            mandatory true;
            type afi-safi-type;
            description
              "AFI and SAFI";
          }
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device/ncs:rpc" {
    container rpc-clear-bgp-instance-afi-safi-update-outq-update-group-sub-group-update-parent {
      tailf:ncs-device-type "netconf";
      tailf:display-when "not(../../ncs:module) or ../../ncs:module[ncs:name='Cisco-IOS-XR-ipv4-bgp-act']";
      tailf:action clear-bgp-instance-afi-safi-update-outq-update-group-sub-group-update-parent {
        tailf:actionpoint ncsproxy {
          tailf:internal;
        }
        csc:xr-task "bgp";
        csc:cli-command "clear bgp instance <instance-name> <afi-safi-name> update outq update-group <update-group> sub-group <sub-group> update-parent";
        description
          "Choose a particular BGP instance.
           Clear Update information (Do NOT execute without cisco support)(cisco-support).
           Clear Update generation OutQ counters (Do NOT execute without cisco support)(cisco-support).
           Update-group.
           Sub-group.
           Update parents' OutQ counters too.
          ";
        input {
          leaf instance-name {
            mandatory true;
            type instance-name;
            description
              "instance name or all";
          }
          leaf afi-safi-name {
            mandatory true;
            type afi-safi-type;
            description
              "AFI and SAFI";
          }
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device-group/ncs:ned-id/ncs:rpc" {
    container rpc-clear-bgp-instance-afi-safi-update-outq-update-group-sub-group-update-parent {
      tailf:ncs-device-type "netconf";
      tailf:display-when "/ncs:devices/ncs:device[ncs:name=current()/../../../ncs:member]/ncs:module[ncs:name='Cisco-IOS-XR-ipv4-bgp-act']";
      tailf:action clear-bgp-instance-afi-safi-update-outq-update-group-sub-group-update-parent {
        tailf:actionpoint ncsproxy {
          tailf:internal;
        }
        csc:xr-task "bgp";
        csc:cli-command "clear bgp instance <instance-name> <afi-safi-name> update outq update-group <update-group> sub-group <sub-group> update-parent";
        description
          "Choose a particular BGP instance.
           Clear Update information (Do NOT execute without cisco support)(cisco-support).
           Clear Update generation OutQ counters (Do NOT execute without cisco support)(cisco-support).
           Update-group.
           Sub-group.
           Update parents' OutQ counters too.
          ";
        input {
          leaf instance-name {
            mandatory true;
            type instance-name;
            description
              "instance name or all";
          }
          leaf afi-safi-name {
            mandatory true;
            type afi-safi-type;
            description
              "AFI and SAFI";
          }
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device/ncs:rpc" {
    container rpc-clear-bgp-instance-afi-safi-update-outq-neighbor-ip-addr {
      tailf:ncs-device-type "netconf";
      tailf:display-when "not(../../ncs:module) or ../../ncs:module[ncs:name='Cisco-IOS-XR-ipv4-bgp-act']";
      tailf:action clear-bgp-instance-afi-safi-update-outq-neighbor-ip-addr {
        tailf:actionpoint ncsproxy {
          tailf:internal;
        }
        csc:xr-task "bgp";
        csc:cli-command "clear bgp instance <instance-name> <afi-safi-name> update outq neighbor <ip-addr>";
        description
          "Choose a particular BGP instance.
           Clear Update information (Do NOT execute without cisco support)(cisco-support).
           Clear Update generation OutQ counters (Do NOT execute without cisco support)(cisco-support).
           Neighbor.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device-group/ncs:ned-id/ncs:rpc" {
    container rpc-clear-bgp-instance-afi-safi-update-outq-neighbor-ip-addr {
      tailf:ncs-device-type "netconf";
      tailf:display-when "/ncs:devices/ncs:device[ncs:name=current()/../../../ncs:member]/ncs:module[ncs:name='Cisco-IOS-XR-ipv4-bgp-act']";
      tailf:action clear-bgp-instance-afi-safi-update-outq-neighbor-ip-addr {
        tailf:actionpoint ncsproxy {
          tailf:internal;
        }
        csc:xr-task "bgp";
        csc:cli-command "clear bgp instance <instance-name> <afi-safi-name> update outq neighbor <ip-addr>";
        description
          "Choose a particular BGP instance.
           Clear Update information (Do NOT execute without cisco support)(cisco-support).
           Clear Update generation OutQ counters (Do NOT execute without cisco support)(cisco-support).
           Neighbor.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device/ncs:rpc" {
    container rpc-clear-bgp-instance-afi-safi-update-outq-neighbor-ip-addr-update-parent {
      tailf:ncs-device-type "netconf";
      tailf:display-when "not(../../ncs:module) or ../../ncs:module[ncs:name='Cisco-IOS-XR-ipv4-bgp-act']";
      tailf:action clear-bgp-instance-afi-safi-update-outq-neighbor-ip-addr-update-parent {
        tailf:actionpoint ncsproxy {
          tailf:internal;
        }
        csc:xr-task "bgp";
        csc:cli-command "clear bgp instance <instance-name> <afi-safi-name> update outq neighbor <ip-addr> update-parent";
        description
          "Choose a particular BGP instance.
           Clear Update information (Do NOT execute without cisco support)(cisco-support).
           Clear Update generation OutQ counters (Do NOT execute without cisco support)(cisco-support).
           Neighbor.
           Update parents' OutQ counters too.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device-group/ncs:ned-id/ncs:rpc" {
    container rpc-clear-bgp-instance-afi-safi-update-outq-neighbor-ip-addr-update-parent {
      tailf:ncs-device-type "netconf";
      tailf:display-when "/ncs:devices/ncs:device[ncs:name=current()/../../../ncs:member]/ncs:module[ncs:name='Cisco-IOS-XR-ipv4-bgp-act']";
      tailf:action clear-bgp-instance-afi-safi-update-outq-neighbor-ip-addr-update-parent {
        tailf:actionpoint ncsproxy {
          tailf:internal;
        }
        csc:xr-task "bgp";
        csc:cli-command "clear bgp instance <instance-name> <afi-safi-name> update outq neighbor <ip-addr> update-parent";
        description
          "Choose a particular BGP instance.
           Clear Update information (Do NOT execute without cisco support)(cisco-support).
           Clear Update generation OutQ counters (Do NOT execute without cisco support)(cisco-support).
           Neighbor.
           Update parents' OutQ counters too.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device/ncs:rpc" {
    container rpc-clear-bgp-instance-afi-safi-update-outq-neighbor-ip-addr-refresh {
      tailf:ncs-device-type "netconf";
      tailf:display-when "not(../../ncs:module) or ../../ncs:module[ncs:name='Cisco-IOS-XR-ipv4-bgp-act']";
      tailf:action clear-bgp-instance-afi-safi-update-outq-neighbor-ip-addr-refresh {
        tailf:actionpoint ncsproxy {
          tailf:internal;
        }
        csc:xr-task "bgp";
        csc:cli-command "clear bgp instance <instance-name> <afi-safi-name> update outq neighbor <ip-addr> refresh";
        description
          "Choose a particular BGP instance.
           Clear Update information (Do NOT execute without cisco support)(cisco-support).
           Clear Update generation OutQ counters (Do NOT execute without cisco support)(cisco-support).
           Neighbor.
           Refresh OutQ.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device-group/ncs:ned-id/ncs:rpc" {
    container rpc-clear-bgp-instance-afi-safi-update-outq-neighbor-ip-addr-refresh {
      tailf:ncs-device-type "netconf";
      tailf:display-when "/ncs:devices/ncs:device[ncs:name=current()/../../../ncs:member]/ncs:module[ncs:name='Cisco-IOS-XR-ipv4-bgp-act']";
      tailf:action clear-bgp-instance-afi-safi-update-outq-neighbor-ip-addr-refresh {
        tailf:actionpoint ncsproxy {
          tailf:internal;
        }
        csc:xr-task "bgp";
        csc:cli-command "clear bgp instance <instance-name> <afi-safi-name> update outq neighbor <ip-addr> refresh";
        description
          "Choose a particular BGP instance.
           Clear Update information (Do NOT execute without cisco support)(cisco-support).
           Clear Update generation OutQ counters (Do NOT execute without cisco support)(cisco-support).
           Neighbor.
           Refresh OutQ.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device/ncs:rpc" {
    container rpc-clear-bgp-instance-afi-safi-update-outq-neighbor-ip-addr-refresh-update-parent {
      tailf:ncs-device-type "netconf";
      tailf:display-when "not(../../ncs:module) or ../../ncs:module[ncs:name='Cisco-IOS-XR-ipv4-bgp-act']";
      tailf:action clear-bgp-instance-afi-safi-update-outq-neighbor-ip-addr-refresh-update-parent {
        tailf:actionpoint ncsproxy {
          tailf:internal;
        }
        csc:xr-task "bgp";
        csc:cli-command "clear bgp instance <instance-name> <afi-safi-name> update outq neighbor <ip-addr> refresh update-parent";
        description
          "Choose a particular BGP instance.
           Clear Update information (Do NOT execute without cisco support)(cisco-support).
           Clear Update generation OutQ counters (Do NOT execute without cisco support)(cisco-support).
           Neighbor.
           Refresh OutQ.
           Update parents' OutQ counters too.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device-group/ncs:ned-id/ncs:rpc" {
    container rpc-clear-bgp-instance-afi-safi-update-outq-neighbor-ip-addr-refresh-update-parent {
      tailf:ncs-device-type "netconf";
      tailf:display-when "/ncs:devices/ncs:device[ncs:name=current()/../../../ncs:member]/ncs:module[ncs:name='Cisco-IOS-XR-ipv4-bgp-act']";
      tailf:action clear-bgp-instance-afi-safi-update-outq-neighbor-ip-addr-refresh-update-parent {
        tailf:actionpoint ncsproxy {
          tailf:internal;
        }
        csc:xr-task "bgp";
        csc:cli-command "clear bgp instance <instance-name> <afi-safi-name> update outq neighbor <ip-addr> refresh update-parent";
        description
          "Choose a particular BGP instance.
           Clear Update information (Do NOT execute without cisco support)(cisco-support).
           Clear Update generation OutQ counters (Do NOT execute without cisco support)(cisco-support).
           Neighbor.
           Refresh OutQ.
           Update parents' OutQ counters too.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device/ncs:rpc" {
    container rpc-clear-bgp-instance-afi-safi-update-outq-address-family {
      tailf:ncs-device-type "netconf";
      tailf:display-when "not(../../ncs:module) or ../../ncs:module[ncs:name='Cisco-IOS-XR-ipv4-bgp-act']";
      tailf:action clear-bgp-instance-afi-safi-update-outq-address-family {
        tailf:actionpoint ncsproxy {
          tailf:internal;
        }
        csc:xr-task "bgp";
        csc:cli-command "clear bgp instance <instance-name> <afi-safi-name> update outq address-family";
        description
          "Choose a particular BGP instance.
           Clear Update information (Do NOT execute without cisco support)(cisco-support).
           Clear Update generation OutQ counters (Do NOT execute without cisco support)(cisco-support).
           Address-family.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-afi-safi-update-outq-address-family {
      tailf:ncs-device-type "netconf";
      tailf:display-when "/ncs:devices/ncs:device[ncs:name=current()/../../../ncs:member]/ncs:module[ncs:name='Cisco-IOS-XR-ipv4-bgp-act']";
      tailf:action clear-bgp-instance-afi-safi-update-outq-address-family {
        tailf:actionpoint ncsproxy {
          tailf:internal;
        }
        csc:xr-task "bgp";
        csc:cli-command "clear bgp instance <instance-name> <afi-safi-name> update outq address-family";
        description
          "Choose a particular BGP instance.
           Clear Update information (Do NOT execute without cisco support)(cisco-support).
           Clear Update generation OutQ counters (Do NOT execute without cisco support)(cisco-support).
           Address-family.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device/ncs:rpc" {
    container rpc-clear-bgp-instance-afi-safi-update-outq-address-family-update-parent {
      tailf:ncs-device-type "netconf";
      tailf:display-when "not(../../ncs:module) or ../../ncs:module[ncs:name='Cisco-IOS-XR-ipv4-bgp-act']";
      tailf:action clear-bgp-instance-afi-safi-update-outq-address-family-update-parent {
        tailf:actionpoint ncsproxy {
          tailf:internal;
        }
        csc:xr-task "bgp";
        csc:cli-command "clear bgp instance <instance-name> <afi-safi-name> update outq address-family update-parent";
        description
          "Choose a particular BGP instance.
           Clear Update information (Do NOT execute without cisco support)(cisco-support).
           Clear Update generation OutQ counters (Do NOT execute without cisco support)(cisco-support).
           Address-family.
           Update parents' OutQ counters too.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-afi-safi-update-outq-address-family-update-parent {
      tailf:ncs-device-type "netconf";
      tailf:display-when "/ncs:devices/ncs:device[ncs:name=current()/../../../ncs:member]/ncs:module[ncs:name='Cisco-IOS-XR-ipv4-bgp-act']";
      tailf:action clear-bgp-instance-afi-safi-update-outq-address-family-update-parent {
        tailf:actionpoint ncsproxy {
          tailf:internal;
        }
        csc:xr-task "bgp";
        csc:cli-command "clear bgp instance <instance-name> <afi-safi-name> update outq address-family update-parent";
        description
          "Choose a particular BGP instance.
           Clear Update information (Do NOT execute without cisco support)(cisco-support).
           Clear Update generation OutQ counters (Do NOT execute without cisco support)(cisco-support).
           Address-family.
           Update parents' OutQ counters too.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device/ncs:rpc" {
    container rpc-clear-bgp-instance-afi-safi-shutdown {
      tailf:ncs-device-type "netconf";
      tailf:display-when "not(../../ncs:module) or ../../ncs:module[ncs:name='Cisco-IOS-XR-ipv4-bgp-act']";
      tailf:action clear-bgp-instance-afi-safi-shutdown {
        tailf:actionpoint ncsproxy {
          tailf:internal;
        }
        csc:xr-task "bgp";
        csc:cli-command "clear bgp instance <instance-name> <afi-safi-name> shutdown";
        description
          "Choose a particular BGP instance.
           Clear all peers which were shut down due to low memory.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-afi-safi-shutdown {
      tailf:ncs-device-type "netconf";
      tailf:display-when "/ncs:devices/ncs:device[ncs:name=current()/../../../ncs:member]/ncs:module[ncs:name='Cisco-IOS-XR-ipv4-bgp-act']";
      tailf:action clear-bgp-instance-afi-safi-shutdown {
        tailf:actionpoint ncsproxy {
          tailf:internal;
        }
        csc:xr-task "bgp";
        csc:cli-command "clear bgp instance <instance-name> <afi-safi-name> shutdown";
        description
          "Choose a particular BGP instance.
           Clear all peers which were shut down due to low memory.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device/ncs:rpc" {
    container rpc-clear-bgp-instance-afi-safi-self-originated {
      tailf:ncs-device-type "netconf";
      tailf:display-when "not(../../ncs:module) or ../../ncs:module[ncs:name='Cisco-IOS-XR-ipv4-bgp-act']";
      tailf:action clear-bgp-instance-afi-safi-self-originated {
        tailf:actionpoint ncsproxy {
          tailf:internal;
        }
        csc:xr-task "bgp";
        csc:cli-command "clear bgp instance <instance-name> <afi-safi-name> self-originated";
        description
          "Choose a particular BGP instance.
           Clear redistributed, network and aggregate routes originated here.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-afi-safi-self-originated {
      tailf:ncs-device-type "netconf";
      tailf:display-when "/ncs:devices/ncs:device[ncs:name=current()/../../../ncs:member]/ncs:module[ncs:name='Cisco-IOS-XR-ipv4-bgp-act']";
      tailf:action clear-bgp-instance-afi-safi-self-originated {
        tailf:actionpoint ncsproxy {
          tailf:internal;
        }
        csc:xr-task "bgp";
        csc:cli-command "clear bgp instance <instance-name> <afi-safi-name> self-originated";
        description
          "Choose a particular BGP instance.
           Clear redistributed, network and aggregate routes originated here.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device/ncs:rpc" {
    container rpc-clear-bgp-instance-afi-safi-nexthop-registration-ip-addr {
      tailf:ncs-device-type "netconf";
      tailf:display-when "not(../../ncs:module) or ../../ncs:module[ncs:name='Cisco-IOS-XR-ipv4-bgp-act']";
      tailf:action clear-bgp-instance-afi-safi-nexthop-registration-ip-addr {
        tailf:actionpoint ncsproxy {
          tailf:internal;
        }
        csc:xr-task "bgp";
        csc:cli-command "clear bgp instance <instance-name> <afi-safi-name> nexthop registration <ip-addr>";
        description
          "Choose a particular BGP instance.
           Clear nexthop.
           Registration with RIB and reregister.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "Nexthop address";
          }
        }
      }
    }
  }
  augment "/ncs:devices/ncs:device-group/ncs:ned-id/ncs:rpc" {
    container rpc-clear-bgp-instance-afi-safi-nexthop-registration-ip-addr {
      tailf:ncs-device-type "netconf";
      tailf:display-when "/ncs:devices/ncs:device[ncs:name=current()/../../../ncs:member]/ncs:module[ncs:name='Cisco-IOS-XR-ipv4-bgp-act']";
      tailf:action clear-bgp-instance-afi-safi-nexthop-registration-ip-addr {
        tailf:actionpoint ncsproxy {
          tailf:internal;
        }
        csc:xr-task "bgp";
        csc:cli-command "clear bgp instance <instance-name> <afi-safi-name> nexthop registration <ip-addr>";
        description
          "Choose a particular BGP instance.
           Clear nexthop.
           Registration with RIB and reregister.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "Nexthop address";
          }
        }
      }
    }
  }
  augment "/ncs:devices/ncs:device/ncs:rpc" {
    container rpc-clear-bgp-instance-afi-safi-nexthop-performance-statistics {
      tailf:ncs-device-type "netconf";
      tailf:display-when "not(../../ncs:module) or ../../ncs:module[ncs:name='Cisco-IOS-XR-ipv4-bgp-act']";
      tailf:action clear-bgp-instance-afi-safi-nexthop-performance-statistics {
        tailf:actionpoint ncsproxy {
          tailf:internal;
        }
        csc:xr-task "bgp";
        csc:cli-command "clear bgp instance <instance-name> <afi-safi-name> nexthop performance-statistics";
        description
          "Choose a particular BGP instance.
           Clear nexthop.
           Performance statistics information related to processing.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-afi-safi-nexthop-performance-statistics {
      tailf:ncs-device-type "netconf";
      tailf:display-when "/ncs:devices/ncs:device[ncs:name=current()/../../../ncs:member]/ncs:module[ncs:name='Cisco-IOS-XR-ipv4-bgp-act']";
      tailf:action clear-bgp-instance-afi-safi-nexthop-performance-statistics {
        tailf:actionpoint ncsproxy {
          tailf:internal;
        }
        csc:xr-task "bgp";
        csc:cli-command "clear bgp instance <instance-name> <afi-safi-name> nexthop performance-statistics";
        description
          "Choose a particular BGP instance.
           Clear nexthop.
           Performance statistics information related to processing.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device/ncs:rpc" {
    container rpc-clear-bgp-instance-afi-safi-flap-statistics {
      tailf:ncs-device-type "netconf";
      tailf:display-when "not(../../ncs:module) or ../../ncs:module[ncs:name='Cisco-IOS-XR-ipv4-bgp-act']";
      tailf:action clear-bgp-instance-afi-safi-flap-statistics {
        tailf:actionpoint ncsproxy {
          tailf:internal;
        }
        csc:xr-task "bgp";
        csc:cli-command "clear bgp instance <instance-name> <afi-safi-name> flap-statistics";
        description
          "Choose a particular BGP instance.
           Clear flap statistics.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-afi-safi-flap-statistics {
      tailf:ncs-device-type "netconf";
      tailf:display-when "/ncs:devices/ncs:device[ncs:name=current()/../../../ncs:member]/ncs:module[ncs:name='Cisco-IOS-XR-ipv4-bgp-act']";
      tailf:action clear-bgp-instance-afi-safi-flap-statistics {
        tailf:actionpoint ncsproxy {
          tailf:internal;
        }
        csc:xr-task "bgp";
        csc:cli-command "clear bgp instance <instance-name> <afi-safi-name> flap-statistics";
        description
          "Choose a particular BGP instance.
           Clear flap statistics.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device/ncs:rpc" {
    container rpc-clear-bgp-instance-afi-safi-flap-statistics-route-policy {
      tailf:ncs-device-type "netconf";
      tailf:display-when "not(../../ncs:module) or ../../ncs:module[ncs:name='Cisco-IOS-XR-ipv4-bgp-act']";
      tailf:action clear-bgp-instance-afi-safi-flap-statistics-route-policy {
        tailf:actionpoint ncsproxy {
          tailf:internal;
        }
        csc:xr-task "bgp";
        csc:cli-command "clear bgp instance <instance-name> <afi-safi-name> flap-statistics route-policy <route-policy-name>";
        description
          "Choose a particular BGP instance.
           Clear flap statistics.
           Clear flap statistics for routes matching the route policy.
          ";
        input {
          leaf instance-name {
            mandatory true;
            type instance-name;
            description
              "instance name or all";
          }
          leaf afi-safi-name {
            mandatory true;
            type afi-safi-type;
            description
              "AFI and SAFI";
          }
          leaf route-policy-name {
            mandatory true;
            type string;
            description
              "Route Policy name";
          }
        }
      }
    }
  }
  augment "/ncs:devices/ncs:device-group/ncs:ned-id/ncs:rpc" {
    container rpc-clear-bgp-instance-afi-safi-flap-statistics-route-policy {
      tailf:ncs-device-type "netconf";
      tailf:display-when "/ncs:devices/ncs:device[ncs:name=current()/../../../ncs:member]/ncs:module[ncs:name='Cisco-IOS-XR-ipv4-bgp-act']";
      tailf:action clear-bgp-instance-afi-safi-flap-statistics-route-policy {
        tailf:actionpoint ncsproxy {
          tailf:internal;
        }
        csc:xr-task "bgp";
        csc:cli-command "clear bgp instance <instance-name> <afi-safi-name> flap-statistics route-policy <route-policy-name>";
        description
          "Choose a particular BGP instance.
           Clear flap statistics.
           Clear flap statistics for routes matching the route policy.
          ";
        input {
          leaf instance-name {
            mandatory true;
            type instance-name;
            description
              "instance name or all";
          }
          leaf afi-safi-name {
            mandatory true;
            type afi-safi-type;
            description
              "AFI and SAFI";
          }
          leaf route-policy-name {
            mandatory true;
            type string;
            description
              "Route Policy name";
          }
        }
      }
    }
  }
  augment "/ncs:devices/ncs:device/ncs:rpc" {
    container rpc-clear-bgp-instance-afi-safi-flap-statistics-regexp {
      tailf:ncs-device-type "netconf";
      tailf:display-when "not(../../ncs:module) or ../../ncs:module[ncs:name='Cisco-IOS-XR-ipv4-bgp-act']";
      tailf:action clear-bgp-instance-afi-safi-flap-statistics-regexp {
        tailf:actionpoint ncsproxy {
          tailf:internal;
        }
        csc:xr-task "bgp";
        csc:cli-command "clear bgp instance <instance-name> <afi-safi-name> flap-statistics regexp <regexp-pattern>";
        description
          "Choose a particular BGP instance.
           Clear flap statistics.
           Clear flap statistics for routes matching the regular expression.
          ";
        input {
          leaf instance-name {
            mandatory true;
            type instance-name;
            description
              "instance name or all";
          }
          leaf afi-safi-name {
            mandatory true;
            type afi-safi-type;
            description
              "AFI and SAFI";
          }
          leaf regexp-pattern {
            mandatory true;
            type string;
            description
              "A regular expression to match the BGP AS paths.  Use 'ctrl-v ?' to enter '?'";
          }
        }
      }
    }
  }
  augment "/ncs:devices/ncs:device-group/ncs:ned-id/ncs:rpc" {
    container rpc-clear-bgp-instance-afi-safi-flap-statistics-regexp {
      tailf:ncs-device-type "netconf";
      tailf:display-when "/ncs:devices/ncs:device[ncs:name=current()/../../../ncs:member]/ncs:module[ncs:name='Cisco-IOS-XR-ipv4-bgp-act']";
      tailf:action clear-bgp-instance-afi-safi-flap-statistics-regexp {
        tailf:actionpoint ncsproxy {
          tailf:internal;
        }
        csc:xr-task "bgp";
        csc:cli-command "clear bgp instance <instance-name> <afi-safi-name> flap-statistics regexp <regexp-pattern>";
        description
          "Choose a particular BGP instance.
           Clear flap statistics.
           Clear flap statistics for routes matching the regular expression.
          ";
        input {
          leaf instance-name {
            mandatory true;
            type instance-name;
            description
              "instance name or all";
          }
          leaf afi-safi-name {
            mandatory true;
            type afi-safi-type;
            description
              "AFI and SAFI";
          }
          leaf regexp-pattern {
            mandatory true;
            type string;
            description
              "A regular expression to match the BGP AS paths.  Use 'ctrl-v ?' to enter '?'";
          }
        }
      }
    }
  }
  augment "/ncs:devices/ncs:device/ncs:rpc" {
    container rpc-clear-bgp-instance-afi-safi-flap-statistics-ip-prefix {
      tailf:ncs-device-type "netconf";
      tailf:display-when "not(../../ncs:module) or ../../ncs:module[ncs:name='Cisco-IOS-XR-ipv4-bgp-act']";
      tailf:action clear-bgp-instance-afi-safi-flap-statistics-ip-prefix {
        tailf:actionpoint ncsproxy {
          tailf:internal;
        }
        csc:xr-task "bgp";
        csc:cli-command "clear bgp instance <instance-name> <afi-safi-name> flap-statistics <ip-prefix>";
        description
          "Choose a particular BGP instance.
           Clear flap statistics.
          ";
        input {
          leaf instance-name {
            mandatory true;
            type instance-name;
            description
              "instance name or all";
          }
          leaf afi-safi-name {
            mandatory true;
            type afi-safi-type;
            description
              "AFI and SAFI";
          }
          leaf ip-prefix {
            mandatory true;
            type inet:ip-prefix;
            description
              "Network and mask or masklength to clear flap statistics";
          }
        }
      }
    }
  }
  augment "/ncs:devices/ncs:device-group/ncs:ned-id/ncs:rpc" {
    container rpc-clear-bgp-instance-afi-safi-flap-statistics-ip-prefix {
      tailf:ncs-device-type "netconf";
      tailf:display-when "/ncs:devices/ncs:device[ncs:name=current()/../../../ncs:member]/ncs:module[ncs:name='Cisco-IOS-XR-ipv4-bgp-act']";
      tailf:action clear-bgp-instance-afi-safi-flap-statistics-ip-prefix {
        tailf:actionpoint ncsproxy {
          tailf:internal;
        }
        csc:xr-task "bgp";
        csc:cli-command "clear bgp instance <instance-name> <afi-safi-name> flap-statistics <ip-prefix>";
        description
          "Choose a particular BGP instance.
           Clear flap statistics.
          ";
        input {
          leaf instance-name {
            mandatory true;
            type instance-name;
            description
              "instance name or all";
          }
          leaf afi-safi-name {
            mandatory true;
            type afi-safi-type;
            description
              "AFI and SAFI";
          }
          leaf ip-prefix {
            mandatory true;
            type inet:ip-prefix;
            description
              "Network and mask or masklength to clear flap statistics";
          }
        }
      }
    }
  }
  augment "/ncs:devices/ncs:device/ncs:rpc" {
    container rpc-clear-bgp-instance-afi-safi-flap-statistics-ip-addr {
      tailf:ncs-device-type "netconf";
      tailf:display-when "not(../../ncs:module) or ../../ncs:module[ncs:name='Cisco-IOS-XR-ipv4-bgp-act']";
      tailf:action clear-bgp-instance-afi-safi-flap-statistics-ip-addr {
        tailf:actionpoint ncsproxy {
          tailf:internal;
        }
        csc:xr-task "bgp";
        csc:cli-command "clear bgp instance <instance-name> <afi-safi-name> flap-statistics <ip-addr>";
        description
          "Choose a particular BGP instance.
           Clear flap statistics.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device-group/ncs:ned-id/ncs:rpc" {
    container rpc-clear-bgp-instance-afi-safi-flap-statistics-ip-addr {
      tailf:ncs-device-type "netconf";
      tailf:display-when "/ncs:devices/ncs:device[ncs:name=current()/../../../ncs:member]/ncs:module[ncs:name='Cisco-IOS-XR-ipv4-bgp-act']";
      tailf:action clear-bgp-instance-afi-safi-flap-statistics-ip-addr {
        tailf:actionpoint ncsproxy {
          tailf:internal;
        }
        csc:xr-task "bgp";
        csc:cli-command "clear bgp instance <instance-name> <afi-safi-name> flap-statistics <ip-addr>";
        description
          "Choose a particular BGP instance.
           Clear flap statistics.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device/ncs:rpc" {
    container rpc-clear-bgp-instance-afi-safi-flap-statistics-ip-addr-ipv4-mask {
      tailf:ncs-device-type "netconf";
      tailf:display-when "not(../../ncs:module) or ../../ncs:module[ncs:name='Cisco-IOS-XR-ipv4-bgp-act']";
      tailf:action clear-bgp-instance-afi-safi-flap-statistics-ip-addr-ipv4-mask {
        tailf:actionpoint ncsproxy {
          tailf:internal;
        }
        csc:xr-task "bgp";
        csc:cli-command "clear bgp instance <instance-name> <afi-safi-name> flap-statistics <ip-addr> <ipv4-mask>";
        description
          "Choose a particular BGP instance.
           Clear flap statistics.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "BGP neighbor address to clear";
          }
          leaf ipv4-mask {
            mandatory true;
            type ipv4-netmask;
            description
              "Network and mask or masklength to clear flap statistics";
          }
        }
      }
    }
  }
  augment "/ncs:devices/ncs:device-group/ncs:ned-id/ncs:rpc" {
    container rpc-clear-bgp-instance-afi-safi-flap-statistics-ip-addr-ipv4-mask {
      tailf:ncs-device-type "netconf";
      tailf:display-when "/ncs:devices/ncs:device[ncs:name=current()/../../../ncs:member]/ncs:module[ncs:name='Cisco-IOS-XR-ipv4-bgp-act']";
      tailf:action clear-bgp-instance-afi-safi-flap-statistics-ip-addr-ipv4-mask {
        tailf:actionpoint ncsproxy {
          tailf:internal;
        }
        csc:xr-task "bgp";
        csc:cli-command "clear bgp instance <instance-name> <afi-safi-name> flap-statistics <ip-addr> <ipv4-mask>";
        description
          "Choose a particular BGP instance.
           Clear flap statistics.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "BGP neighbor address to clear";
          }
          leaf ipv4-mask {
            mandatory true;
            type ipv4-netmask;
            description
              "Network and mask or masklength to clear flap statistics";
          }
        }
      }
    }
  }
  augment "/ncs:devices/ncs:device/ncs:rpc" {
    container rpc-clear-bgp-instance-afi-safi-external-soft {
      tailf:ncs-device-type "netconf";
      tailf:display-when "not(../../ncs:module) or ../../ncs:module[ncs:name='Cisco-IOS-XR-ipv4-bgp-act']";
      tailf:action clear-bgp-instance-afi-safi-external-soft {
        tailf:actionpoint ncsproxy {
          tailf:internal;
        }
        csc:xr-task "bgp";
        csc:cli-command "clear bgp instance <instance-name> <afi-safi-name> external soft";
        description
          "Choose a particular BGP instance.
           Clear all external peers.
           Soft reconfig.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-afi-safi-external-soft {
      tailf:ncs-device-type "netconf";
      tailf:display-when "/ncs:devices/ncs:device[ncs:name=current()/../../../ncs:member]/ncs:module[ncs:name='Cisco-IOS-XR-ipv4-bgp-act']";
      tailf:action clear-bgp-instance-afi-safi-external-soft {
        tailf:actionpoint ncsproxy {
          tailf:internal;
        }
        csc:xr-task "bgp";
        csc:cli-command "clear bgp instance <instance-name> <afi-safi-name> external soft";
        description
          "Choose a particular BGP instance.
           Clear all external peers.
           Soft reconfig.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device/ncs:rpc" {
    container rpc-clear-bgp-instance-afi-safi-external-soft-out {
      tailf:ncs-device-type "netconf";
      tailf:display-when "not(../../ncs:module) or ../../ncs:module[ncs:name='Cisco-IOS-XR-ipv4-bgp-act']";
      tailf:action clear-bgp-instance-afi-safi-external-soft-out {
        tailf:actionpoint ncsproxy {
          tailf:internal;
        }
        csc:xr-task "bgp";
        csc:cli-command "clear bgp instance <instance-name> <afi-safi-name> external soft out";
        description
          "Choose a particular BGP instance.
           Clear all external peers.
           Soft reconfig.
           Soft reconfig outbound update.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-afi-safi-external-soft-out {
      tailf:ncs-device-type "netconf";
      tailf:display-when "/ncs:devices/ncs:device[ncs:name=current()/../../../ncs:member]/ncs:module[ncs:name='Cisco-IOS-XR-ipv4-bgp-act']";
      tailf:action clear-bgp-instance-afi-safi-external-soft-out {
        tailf:actionpoint ncsproxy {
          tailf:internal;
        }
        csc:xr-task "bgp";
        csc:cli-command "clear bgp instance <instance-name> <afi-safi-name> external soft out";
        description
          "Choose a particular BGP instance.
           Clear all external peers.
           Soft reconfig.
           Soft reconfig outbound update.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device/ncs:rpc" {
    container rpc-clear-bgp-instance-afi-safi-external-soft-in {
      tailf:ncs-device-type "netconf";
      tailf:display-when "not(../../ncs:module) or ../../ncs:module[ncs:name='Cisco-IOS-XR-ipv4-bgp-act']";
      tailf:action clear-bgp-instance-afi-safi-external-soft-in {
        tailf:actionpoint ncsproxy {
          tailf:internal;
        }
        csc:xr-task "bgp";
        csc:cli-command "clear bgp instance <instance-name> <afi-safi-name> external soft in";
        description
          "Choose a particular BGP instance.
           Clear all external peers.
           Soft reconfig.
           Soft reconfig inbound update.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-afi-safi-external-soft-in {
      tailf:ncs-device-type "netconf";
      tailf:display-when "/ncs:devices/ncs:device[ncs:name=current()/../../../ncs:member]/ncs:module[ncs:name='Cisco-IOS-XR-ipv4-bgp-act']";
      tailf:action clear-bgp-instance-afi-safi-external-soft-in {
        tailf:actionpoint ncsproxy {
          tailf:internal;
        }
        csc:xr-task "bgp";
        csc:cli-command "clear bgp instance <instance-name> <afi-safi-name> external soft in";
        description
          "Choose a particular BGP instance.
           Clear all external peers.
           Soft reconfig.
           Soft reconfig inbound update.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device/ncs:rpc" {
    container rpc-clear-bgp-instance-afi-safi-external-soft-in-prefix-filter {
      tailf:ncs-device-type "netconf";
      tailf:display-when "not(../../ncs:module) or ../../ncs:module[ncs:name='Cisco-IOS-XR-ipv4-bgp-act']";
      tailf:action clear-bgp-instance-afi-safi-external-soft-in-prefix-filter {
        tailf:actionpoint ncsproxy {
          tailf:internal;
        }
        csc:xr-task "bgp";
        csc:cli-command "clear bgp instance <instance-name> <afi-safi-name> external soft in prefix-filter";
        description
          "Choose a particular BGP instance.
           Clear all external peers.
           Soft reconfig.
           Soft reconfig inbound update.
           Push out prefix ORF and do inbound soft reconfig.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-afi-safi-external-soft-in-prefix-filter {
      tailf:ncs-device-type "netconf";
      tailf:display-when "/ncs:devices/ncs:device[ncs:name=current()/../../../ncs:member]/ncs:module[ncs:name='Cisco-IOS-XR-ipv4-bgp-act']";
      tailf:action clear-bgp-instance-afi-safi-external-soft-in-prefix-filter {
        tailf:actionpoint ncsproxy {
          tailf:internal;
        }
        csc:xr-task "bgp";
        csc:cli-command "clear bgp instance <instance-name> <afi-safi-name> external soft in prefix-filter";
        description
          "Choose a particular BGP instance.
           Clear all external peers.
           Soft reconfig.
           Soft reconfig inbound update.
           Push out prefix ORF and do inbound soft reconfig.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device/ncs:rpc" {
    container rpc-clear-bgp-instance-afi-safi-dampening {
      tailf:ncs-device-type "netconf";
      tailf:display-when "not(../../ncs:module) or ../../ncs:module[ncs:name='Cisco-IOS-XR-ipv4-bgp-act']";
      tailf:action clear-bgp-instance-afi-safi-dampening {
        tailf:actionpoint ncsproxy {
          tailf:internal;
        }
        csc:xr-task "bgp";
        csc:cli-command "clear bgp instance <instance-name> <afi-safi-name> dampening";
        description
          "Choose a particular BGP instance.
           Clear route flap dampening information.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-afi-safi-dampening {
      tailf:ncs-device-type "netconf";
      tailf:display-when "/ncs:devices/ncs:device[ncs:name=current()/../../../ncs:member]/ncs:module[ncs:name='Cisco-IOS-XR-ipv4-bgp-act']";
      tailf:action clear-bgp-instance-afi-safi-dampening {
        tailf:actionpoint ncsproxy {
          tailf:internal;
        }
        csc:xr-task "bgp";
        csc:cli-command "clear bgp instance <instance-name> <afi-safi-name> dampening";
        description
          "Choose a particular BGP instance.
           Clear route flap dampening information.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device/ncs:rpc" {
    container rpc-clear-bgp-instance-afi-safi-dampening-ip-prefix {
      tailf:ncs-device-type "netconf";
      tailf:display-when "not(../../ncs:module) or ../../ncs:module[ncs:name='Cisco-IOS-XR-ipv4-bgp-act']";
      tailf:action clear-bgp-instance-afi-safi-dampening-ip-prefix {
        tailf:actionpoint ncsproxy {
          tailf:internal;
        }
        csc:xr-task "bgp";
        csc:cli-command "clear bgp instance <instance-name> <afi-safi-name> dampening <ip-prefix>";
        description
          "Choose a particular BGP instance.
           Clear route flap dampening information.
          ";
        input {
          leaf instance-name {
            mandatory true;
            type instance-name;
            description
              "instance name or all";
          }
          leaf afi-safi-name {
            mandatory true;
            type afi-safi-type;
            description
              "AFI and SAFI";
          }
          leaf ip-prefix {
            mandatory true;
            type inet:ip-prefix;
            description
              "Network and mask or masklength to clear dampening information";
          }
        }
      }
    }
  }
  augment "/ncs:devices/ncs:device-group/ncs:ned-id/ncs:rpc" {
    container rpc-clear-bgp-instance-afi-safi-dampening-ip-prefix {
      tailf:ncs-device-type "netconf";
      tailf:display-when "/ncs:devices/ncs:device[ncs:name=current()/../../../ncs:member]/ncs:module[ncs:name='Cisco-IOS-XR-ipv4-bgp-act']";
      tailf:action clear-bgp-instance-afi-safi-dampening-ip-prefix {
        tailf:actionpoint ncsproxy {
          tailf:internal;
        }
        csc:xr-task "bgp";
        csc:cli-command "clear bgp instance <instance-name> <afi-safi-name> dampening <ip-prefix>";
        description
          "Choose a particular BGP instance.
           Clear route flap dampening information.
          ";
        input {
          leaf instance-name {
            mandatory true;
            type instance-name;
            description
              "instance name or all";
          }
          leaf afi-safi-name {
            mandatory true;
            type afi-safi-type;
            description
              "AFI and SAFI";
          }
          leaf ip-prefix {
            mandatory true;
            type inet:ip-prefix;
            description
              "Network and mask or masklength to clear dampening information";
          }
        }
      }
    }
  }
  augment "/ncs:devices/ncs:device/ncs:rpc" {
    container rpc-clear-bgp-instance-afi-safi-as-soft {
      tailf:ncs-device-type "netconf";
      tailf:display-when "not(../../ncs:module) or ../../ncs:module[ncs:name='Cisco-IOS-XR-ipv4-bgp-act']";
      tailf:action clear-bgp-instance-afi-safi-as-soft {
        tailf:actionpoint ncsproxy {
          tailf:internal;
        }
        csc:xr-task "bgp";
        csc:cli-command "clear bgp instance <instance-name> <afi-safi-name> as <as-number> soft";
        description
          "Choose a particular BGP instance.
           Clear peers in a specific AS.
           Soft reconfig.
          ";
        input {
          leaf instance-name {
            mandatory true;
            type instance-name;
            description
              "instance name or all";
          }
          leaf afi-safi-name {
            mandatory true;
            type afi-safi-type;
            description
              "AFI and SAFI";
          }
          leaf as-number {
            mandatory true;
            type as-number;
            description
              "AS number";
          }
        }
      }
    }
  }
  augment "/ncs:devices/ncs:device-group/ncs:ned-id/ncs:rpc" {
    container rpc-clear-bgp-instance-afi-safi-as-soft {
      tailf:ncs-device-type "netconf";
      tailf:display-when "/ncs:devices/ncs:device[ncs:name=current()/../../../ncs:member]/ncs:module[ncs:name='Cisco-IOS-XR-ipv4-bgp-act']";
      tailf:action clear-bgp-instance-afi-safi-as-soft {
        tailf:actionpoint ncsproxy {
          tailf:internal;
        }
        csc:xr-task "bgp";
        csc:cli-command "clear bgp instance <instance-name> <afi-safi-name> as <as-number> soft";
        description
          "Choose a particular BGP instance.
           Clear peers in a specific AS.
           Soft reconfig.
          ";
        input {
          leaf instance-name {
            mandatory true;
            type instance-name;
            description
              "instance name or all";
          }
          leaf afi-safi-name {
            mandatory true;
            type afi-safi-type;
            description
              "AFI and SAFI";
          }
          leaf as-number {
            mandatory true;
            type as-number;
            description
              "AS number";
          }
        }
      }
    }
  }
  augment "/ncs:devices/ncs:device/ncs:rpc" {
    container rpc-clear-bgp-instance-afi-safi-as-soft-out {
      tailf:ncs-device-type "netconf";
      tailf:display-when "not(../../ncs:module) or ../../ncs:module[ncs:name='Cisco-IOS-XR-ipv4-bgp-act']";
      tailf:action clear-bgp-instance-afi-safi-as-soft-out {
        tailf:actionpoint ncsproxy {
          tailf:internal;
        }
        csc:xr-task "bgp";
        csc:cli-command "clear bgp instance <instance-name> <afi-safi-name> as <as-number> soft out";
        description
          "Choose a particular BGP instance.
           Clear peers in a specific AS.
           Soft reconfig.
           Soft reconfig outbound update.
          ";
        input {
          leaf instance-name {
            mandatory true;
            type instance-name;
            description
              "instance name or all";
          }
          leaf afi-safi-name {
            mandatory true;
            type afi-safi-type;
            description
              "AFI and SAFI";
          }
          leaf as-number {
            mandatory true;
            type as-number;
            description
              "AS number";
          }
        }
      }
    }
  }
  augment "/ncs:devices/ncs:device-group/ncs:ned-id/ncs:rpc" {
    container rpc-clear-bgp-instance-afi-safi-as-soft-out {
      tailf:ncs-device-type "netconf";
      tailf:display-when "/ncs:devices/ncs:device[ncs:name=current()/../../../ncs:member]/ncs:module[ncs:name='Cisco-IOS-XR-ipv4-bgp-act']";
      tailf:action clear-bgp-instance-afi-safi-as-soft-out {
        tailf:actionpoint ncsproxy {
          tailf:internal;
        }
        csc:xr-task "bgp";
        csc:cli-command "clear bgp instance <instance-name> <afi-safi-name> as <as-number> soft out";
        description
          "Choose a particular BGP instance.
           Clear peers in a specific AS.
           Soft reconfig.
           Soft reconfig outbound update.
          ";
        input {
          leaf instance-name {
            mandatory true;
            type instance-name;
            description
              "instance name or all";
          }
          leaf afi-safi-name {
            mandatory true;
            type afi-safi-type;
            description
              "AFI and SAFI";
          }
          leaf as-number {
            mandatory true;
            type as-number;
            description
              "AS number";
          }
        }
      }
    }
  }
  augment "/ncs:devices/ncs:device/ncs:rpc" {
    container rpc-clear-bgp-instance-afi-safi-as-soft-in {
      tailf:ncs-device-type "netconf";
      tailf:display-when "not(../../ncs:module) or ../../ncs:module[ncs:name='Cisco-IOS-XR-ipv4-bgp-act']";
      tailf:action clear-bgp-instance-afi-safi-as-soft-in {
        tailf:actionpoint ncsproxy {
          tailf:internal;
        }
        csc:xr-task "bgp";
        csc:cli-command "clear bgp instance <instance-name> <afi-safi-name> as <as-number> soft in";
        description
          "Choose a particular BGP instance.
           Clear peers in a specific AS.
           Soft reconfig.
           Soft reconfig inbound update.
          ";
        input {
          leaf instance-name {
            mandatory true;
            type instance-name;
            description
              "instance name or all";
          }
          leaf afi-safi-name {
            mandatory true;
            type afi-safi-type;
            description
              "AFI and SAFI";
          }
          leaf as-number {
            mandatory true;
            type as-number;
            description
              "AS number";
          }
        }
      }
    }
  }
  augment "/ncs:devices/ncs:device-group/ncs:ned-id/ncs:rpc" {
    container rpc-clear-bgp-instance-afi-safi-as-soft-in {
      tailf:ncs-device-type "netconf";
      tailf:display-when "/ncs:devices/ncs:device[ncs:name=current()/../../../ncs:member]/ncs:module[ncs:name='Cisco-IOS-XR-ipv4-bgp-act']";
      tailf:action clear-bgp-instance-afi-safi-as-soft-in {
        tailf:actionpoint ncsproxy {
          tailf:internal;
        }
        csc:xr-task "bgp";
        csc:cli-command "clear bgp instance <instance-name> <afi-safi-name> as <as-number> soft in";
        description
          "Choose a particular BGP instance.
           Clear peers in a specific AS.
           Soft reconfig.
           Soft reconfig inbound update.
          ";
        input {
          leaf instance-name {
            mandatory true;
            type instance-name;
            description
              "instance name or all";
          }
          leaf afi-safi-name {
            mandatory true;
            type afi-safi-type;
            description
              "AFI and SAFI";
          }
          leaf as-number {
            mandatory true;
            type as-number;
            description
              "AS number";
          }
        }
      }
    }
  }
  augment "/ncs:devices/ncs:device/ncs:rpc" {
    container rpc-clear-bgp-instance-afi-safi-as-soft-in-prefix-filter {
      tailf:ncs-device-type "netconf";
      tailf:display-when "not(../../ncs:module) or ../../ncs:module[ncs:name='Cisco-IOS-XR-ipv4-bgp-act']";
      tailf:action clear-bgp-instance-afi-safi-as-soft-in-prefix-filter {
        tailf:actionpoint ncsproxy {
          tailf:internal;
        }
        csc:xr-task "bgp";
        csc:cli-command "clear bgp instance <instance-name> <afi-safi-name> as <as-number> soft in prefix-filter";
        description
          "Choose a particular BGP instance.
           Clear peers in a specific AS.
           Soft reconfig.
           Soft reconfig inbound update.
           Push out prefix ORF and do inbound soft reconfig.
          ";
        input {
          leaf instance-name {
            mandatory true;
            type instance-name;
            description
              "instance name or all";
          }
          leaf afi-safi-name {
            mandatory true;
            type afi-safi-type;
            description
              "AFI and SAFI";
          }
          leaf as-number {
            mandatory true;
            type as-number;
            description
              "AS number";
          }
        }
      }
    }
  }
  augment "/ncs:devices/ncs:device-group/ncs:ned-id/ncs:rpc" {
    container rpc-clear-bgp-instance-afi-safi-as-soft-in-prefix-filter {
      tailf:ncs-device-type "netconf";
      tailf:display-when "/ncs:devices/ncs:device[ncs:name=current()/../../../ncs:member]/ncs:module[ncs:name='Cisco-IOS-XR-ipv4-bgp-act']";
      tailf:action clear-bgp-instance-afi-safi-as-soft-in-prefix-filter {
        tailf:actionpoint ncsproxy {
          tailf:internal;
        }
        csc:xr-task "bgp";
        csc:cli-command "clear bgp instance <instance-name> <afi-safi-name> as <as-number> soft in prefix-filter";
        description
          "Choose a particular BGP instance.
           Clear peers in a specific AS.
           Soft reconfig.
           Soft reconfig inbound update.
           Push out prefix ORF and do inbound soft reconfig.
          ";
        input {
          leaf instance-name {
            mandatory true;
            type instance-name;
            description
              "instance name or all";
          }
          leaf afi-safi-name {
            mandatory true;
            type afi-safi-type;
            description
              "AFI and SAFI";
          }
          leaf as-number {
            mandatory true;
            type as-number;
            description
              "AS number";
          }
        }
      }
    }
  }
  augment "/ncs:devices/ncs:device/ncs:rpc" {
    container rpc-clear-bgp-instance-afi-safi-ip-addr-soft {
      tailf:ncs-device-type "netconf";
      tailf:display-when "not(../../ncs:module) or ../../ncs:module[ncs:name='Cisco-IOS-XR-ipv4-bgp-act']";
      tailf:action clear-bgp-instance-afi-safi-ip-addr-soft {
        tailf:actionpoint ncsproxy {
          tailf:internal;
        }
        csc:xr-task "bgp";
        csc:cli-command "clear bgp instance <instance-name> <afi-safi-name> <ip-addr> soft";
        description
          "Choose a particular BGP instance.
           Soft reconfig.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device-group/ncs:ned-id/ncs:rpc" {
    container rpc-clear-bgp-instance-afi-safi-ip-addr-soft {
      tailf:ncs-device-type "netconf";
      tailf:display-when "/ncs:devices/ncs:device[ncs:name=current()/../../../ncs:member]/ncs:module[ncs:name='Cisco-IOS-XR-ipv4-bgp-act']";
      tailf:action clear-bgp-instance-afi-safi-ip-addr-soft {
        tailf:actionpoint ncsproxy {
          tailf:internal;
        }
        csc:xr-task "bgp";
        csc:cli-command "clear bgp instance <instance-name> <afi-safi-name> <ip-addr> soft";
        description
          "Choose a particular BGP instance.
           Soft reconfig.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device/ncs:rpc" {
    container rpc-clear-bgp-instance-afi-safi-ip-addr-soft-out {
      tailf:ncs-device-type "netconf";
      tailf:display-when "not(../../ncs:module) or ../../ncs:module[ncs:name='Cisco-IOS-XR-ipv4-bgp-act']";
      tailf:action clear-bgp-instance-afi-safi-ip-addr-soft-out {
        tailf:actionpoint ncsproxy {
          tailf:internal;
        }
        csc:xr-task "bgp";
        csc:cli-command "clear bgp instance <instance-name> <afi-safi-name> <ip-addr> soft out";
        description
          "Choose a particular BGP instance.
           Soft reconfig.
           Soft reconfig outbound update.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device-group/ncs:ned-id/ncs:rpc" {
    container rpc-clear-bgp-instance-afi-safi-ip-addr-soft-out {
      tailf:ncs-device-type "netconf";
      tailf:display-when "/ncs:devices/ncs:device[ncs:name=current()/../../../ncs:member]/ncs:module[ncs:name='Cisco-IOS-XR-ipv4-bgp-act']";
      tailf:action clear-bgp-instance-afi-safi-ip-addr-soft-out {
        tailf:actionpoint ncsproxy {
          tailf:internal;
        }
        csc:xr-task "bgp";
        csc:cli-command "clear bgp instance <instance-name> <afi-safi-name> <ip-addr> soft out";
        description
          "Choose a particular BGP instance.
           Soft reconfig.
           Soft reconfig outbound update.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device/ncs:rpc" {
    container rpc-clear-bgp-instance-afi-safi-ip-addr-soft-in {
      tailf:ncs-device-type "netconf";
      tailf:display-when "not(../../ncs:module) or ../../ncs:module[ncs:name='Cisco-IOS-XR-ipv4-bgp-act']";
      tailf:action clear-bgp-instance-afi-safi-ip-addr-soft-in {
        tailf:actionpoint ncsproxy {
          tailf:internal;
        }
        csc:xr-task "bgp";
        csc:cli-command "clear bgp instance <instance-name> <afi-safi-name> <ip-addr> soft in";
        description
          "Choose a particular BGP instance.
           Soft reconfig.
           Soft reconfig inbound update.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device-group/ncs:ned-id/ncs:rpc" {
    container rpc-clear-bgp-instance-afi-safi-ip-addr-soft-in {
      tailf:ncs-device-type "netconf";
      tailf:display-when "/ncs:devices/ncs:device[ncs:name=current()/../../../ncs:member]/ncs:module[ncs:name='Cisco-IOS-XR-ipv4-bgp-act']";
      tailf:action clear-bgp-instance-afi-safi-ip-addr-soft-in {
        tailf:actionpoint ncsproxy {
          tailf:internal;
        }
        csc:xr-task "bgp";
        csc:cli-command "clear bgp instance <instance-name> <afi-safi-name> <ip-addr> soft in";
        description
          "Choose a particular BGP instance.
           Soft reconfig.
           Soft reconfig inbound update.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device/ncs:rpc" {
    container rpc-clear-bgp-instance-afi-safi-ip-addr-soft-in-prefix-filter {
      tailf:ncs-device-type "netconf";
      tailf:display-when "not(../../ncs:module) or ../../ncs:module[ncs:name='Cisco-IOS-XR-ipv4-bgp-act']";
      tailf:action clear-bgp-instance-afi-safi-ip-addr-soft-in-prefix-filter {
        tailf:actionpoint ncsproxy {
          tailf:internal;
        }
        csc:xr-task "bgp";
        csc:cli-command "clear bgp instance <instance-name> <afi-safi-name> <ip-addr> soft in prefix-filter";
        description
          "Choose a particular BGP instance.
           Soft reconfig.
           Soft reconfig inbound update.
           Push out prefix ORF and do inbound soft reconfig.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device-group/ncs:ned-id/ncs:rpc" {
    container rpc-clear-bgp-instance-afi-safi-ip-addr-soft-in-prefix-filter {
      tailf:ncs-device-type "netconf";
      tailf:display-when "/ncs:devices/ncs:device[ncs:name=current()/../../../ncs:member]/ncs:module[ncs:name='Cisco-IOS-XR-ipv4-bgp-act']";
      tailf:action clear-bgp-instance-afi-safi-ip-addr-soft-in-prefix-filter {
        tailf:actionpoint ncsproxy {
          tailf:internal;
        }
        csc:xr-task "bgp";
        csc:cli-command "clear bgp instance <instance-name> <afi-safi-name> <ip-addr> soft in prefix-filter";
        description
          "Choose a particular BGP instance.
           Soft reconfig.
           Soft reconfig inbound update.
           Push out prefix ORF and do inbound soft reconfig.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device/ncs:rpc" {
    container rpc-clear-bgp-instance-afi-safi-ip-addr-long-lived-stale {
      tailf:ncs-device-type "netconf";
      tailf:display-when "not(../../ncs:module) or ../../ncs:module[ncs:name='Cisco-IOS-XR-ipv4-bgp-act']";
      tailf:action clear-bgp-instance-afi-safi-ip-addr-long-lived-stale {
        tailf:actionpoint ncsproxy {
          tailf:internal;
        }
        csc:xr-task "bgp";
        csc:cli-command "clear bgp instance <instance-name> <afi-safi-name> <ip-addr> long-lived-stale";
        description
          "Choose a particular BGP instance.
           Clear long-lived-stale routes.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device-group/ncs:ned-id/ncs:rpc" {
    container rpc-clear-bgp-instance-afi-safi-ip-addr-long-lived-stale {
      tailf:ncs-device-type "netconf";
      tailf:display-when "/ncs:devices/ncs:device[ncs:name=current()/../../../ncs:member]/ncs:module[ncs:name='Cisco-IOS-XR-ipv4-bgp-act']";
      tailf:action clear-bgp-instance-afi-safi-ip-addr-long-lived-stale {
        tailf:actionpoint ncsproxy {
          tailf:internal;
        }
        csc:xr-task "bgp";
        csc:cli-command "clear bgp instance <instance-name> <afi-safi-name> <ip-addr> long-lived-stale";
        description
          "Choose a particular BGP instance.
           Clear long-lived-stale routes.
          ";
        input {
          leaf instance-name {
            mandatory true;
            type instance-name;
            description
              "instance name or all";
          }
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device/ncs:rpc" {
    container rpc-clear-bgp-instance-afi-safi-all-soft {
      tailf:ncs-device-type "netconf";
      tailf:display-when "not(../../ncs:module) or ../../ncs:module[ncs:name='Cisco-IOS-XR-ipv4-bgp-act']";
      tailf:action clear-bgp-instance-afi-safi-all-soft {
        tailf:actionpoint ncsproxy {
          tailf:internal;
        }
        csc:xr-task "bgp";
        csc:cli-command "clear bgp instance <instance-name> <afi-safi-name> * soft";
        description
          "Choose a particular BGP instance.
           Clear all peers and all routes from the BGP table.
           Soft reconfig.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-afi-safi-all-soft {
      tailf:ncs-device-type "netconf";
      tailf:display-when "/ncs:devices/ncs:device[ncs:name=current()/../../../ncs:member]/ncs:module[ncs:name='Cisco-IOS-XR-ipv4-bgp-act']";
      tailf:action clear-bgp-instance-afi-safi-all-soft {
        tailf:actionpoint ncsproxy {
          tailf:internal;
        }
        csc:xr-task "bgp";
        csc:cli-command "clear bgp instance <instance-name> <afi-safi-name> * soft";
        description
          "Choose a particular BGP instance.
           Clear all peers and all routes from the BGP table.
           Soft reconfig.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device/ncs:rpc" {
    container rpc-clear-bgp-instance-afi-safi-all-soft-out {
      tailf:ncs-device-type "netconf";
      tailf:display-when "not(../../ncs:module) or ../../ncs:module[ncs:name='Cisco-IOS-XR-ipv4-bgp-act']";
      tailf:action clear-bgp-instance-afi-safi-all-soft-out {
        tailf:actionpoint ncsproxy {
          tailf:internal;
        }
        csc:xr-task "bgp";
        csc:cli-command "clear bgp instance <instance-name> <afi-safi-name> * soft out";
        description
          "Choose a particular BGP instance.
           Clear all peers and all routes from the BGP table.
           Soft reconfig.
           Soft reconfig outbound update.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-afi-safi-all-soft-out {
      tailf:ncs-device-type "netconf";
      tailf:display-when "/ncs:devices/ncs:device[ncs:name=current()/../../../ncs:member]/ncs:module[ncs:name='Cisco-IOS-XR-ipv4-bgp-act']";
      tailf:action clear-bgp-instance-afi-safi-all-soft-out {
        tailf:actionpoint ncsproxy {
          tailf:internal;
        }
        csc:xr-task "bgp";
        csc:cli-command "clear bgp instance <instance-name> <afi-safi-name> * soft out";
        description
          "Choose a particular BGP instance.
           Clear all peers and all routes from the BGP table.
           Soft reconfig.
           Soft reconfig outbound update.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device/ncs:rpc" {
    container rpc-clear-bgp-instance-afi-safi-all-soft-in {
      tailf:ncs-device-type "netconf";
      tailf:display-when "not(../../ncs:module) or ../../ncs:module[ncs:name='Cisco-IOS-XR-ipv4-bgp-act']";
      tailf:action clear-bgp-instance-afi-safi-all-soft-in {
        tailf:actionpoint ncsproxy {
          tailf:internal;
        }
        csc:xr-task "bgp";
        csc:cli-command "clear bgp instance <instance-name> <afi-safi-name> * soft in";
        description
          "Choose a particular BGP instance.
           Clear all peers and all routes from the BGP table.
           Soft reconfig.
           Soft reconfig inbound update.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-afi-safi-all-soft-in {
      tailf:ncs-device-type "netconf";
      tailf:display-when "/ncs:devices/ncs:device[ncs:name=current()/../../../ncs:member]/ncs:module[ncs:name='Cisco-IOS-XR-ipv4-bgp-act']";
      tailf:action clear-bgp-instance-afi-safi-all-soft-in {
        tailf:actionpoint ncsproxy {
          tailf:internal;
        }
        csc:xr-task "bgp";
        csc:cli-command "clear bgp instance <instance-name> <afi-safi-name> * soft in";
        description
          "Choose a particular BGP instance.
           Clear all peers and all routes from the BGP table.
           Soft reconfig.
           Soft reconfig inbound update.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device/ncs:rpc" {
    container rpc-clear-bgp-instance-afi-safi-all-soft-in-prefix-filter {
      tailf:ncs-device-type "netconf";
      tailf:display-when "not(../../ncs:module) or ../../ncs:module[ncs:name='Cisco-IOS-XR-ipv4-bgp-act']";
      tailf:action clear-bgp-instance-afi-safi-all-soft-in-prefix-filter {
        tailf:actionpoint ncsproxy {
          tailf:internal;
        }
        csc:xr-task "bgp";
        csc:cli-command "clear bgp instance <instance-name> <afi-safi-name> * soft in prefix-filter";
        description
          "Choose a particular BGP instance.
           Clear all peers and all routes from the BGP table.
           Soft reconfig.
           Soft reconfig inbound update.
           Push out prefix ORF and do inbound soft reconfig.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device-group/ncs:ned-id/ncs:rpc" {
    container rpc-clear-bgp-instance-afi-safi-all-soft-in-prefix-filter {
      tailf:ncs-device-type "netconf";
      tailf:display-when "/ncs:devices/ncs:device[ncs:name=current()/../../../ncs:member]/ncs:module[ncs:name='Cisco-IOS-XR-ipv4-bgp-act']";
      tailf:action clear-bgp-instance-afi-safi-all-soft-in-prefix-filter {
        tailf:actionpoint ncsproxy {
          tailf:internal;
        }
        csc:xr-task "bgp";
        csc:cli-command "clear bgp instance <instance-name> <afi-safi-name> * soft in prefix-filter";
        description
          "Choose a particular BGP instance.
           Clear all peers and all routes from the BGP table.
           Soft reconfig.
           Soft reconfig inbound update.
           Push out prefix ORF and do inbound soft reconfig.
          ";
        input {
          leaf instance-name {
            mandatory true;
            type instance-name;
            description
              "instance name or all";
          }
          leaf afi-safi-name {
            mandatory true;
            type afi-safi-type;
            description
              "AFI and SAFI";
          }
        }
      }
    }
  }
  augment "/ncs:devices/ncs:device/ncs:rpc" {
    container rpc-clear-bgp-instance-ip-addr {
      tailf:ncs-device-type "netconf";
      tailf:display-when "not(../../ncs:module) or ../../ncs:module[ncs:name='Cisco-IOS-XR-ipv4-bgp-act']";
      tailf:action clear-bgp-instance-ip-addr {
        tailf:actionpoint ncsproxy {
          tailf:internal;
        }
        csc:xr-task "bgp";
        csc:cli-command "clear bgp instance <instance-name> <ip-addr>";
        description
          "Choose a particular BGP instance.
          ";
        input {
          leaf instance-name {
            mandatory true;
            type instance-name;
            description
              "instance name or all";
          }
          leaf ip-addr {
            mandatory true;
            type inet:ip-address;
            description
              "BGP neighbor address to clear";
          }
        }
      }
    }
  }
  augment "/ncs:devices/ncs:device-group/ncs:ned-id/ncs:rpc" {
    container rpc-clear-bgp-instance-ip-addr {
      tailf:ncs-device-type "netconf";
      tailf:display-when "/ncs:devices/ncs:device[ncs:name=current()/../../../ncs:member]/ncs:module[ncs:name='Cisco-IOS-XR-ipv4-bgp-act']";
      tailf:action clear-bgp-instance-ip-addr {
        tailf:actionpoint ncsproxy {
          tailf:internal;
        }
        csc:xr-task "bgp";
        csc:cli-command "clear bgp instance <instance-name> <ip-addr>";
        description
          "Choose a particular BGP instance.
          ";
        input {
          leaf instance-name {
            mandatory true;
            type instance-name;
            description
              "instance name or all";
          }
          leaf ip-addr {
            mandatory true;
            type inet:ip-address;
            description
              "BGP neighbor address to clear";
          }
        }
      }
    }
  }
  augment "/ncs:devices/ncs:device/ncs:rpc" {
    container rpc-clear-bgp-instance-ip-addr-long-lived-stale {
      tailf:ncs-device-type "netconf";
      tailf:display-when "not(../../ncs:module) or ../../ncs:module[ncs:name='Cisco-IOS-XR-ipv4-bgp-act']";
      tailf:action clear-bgp-instance-ip-addr-long-lived-stale {
        tailf:actionpoint ncsproxy {
          tailf:internal;
        }
        csc:xr-task "bgp";
        csc:cli-command "clear bgp instance <instance-name> <ip-addr> long-lived-stale";
        description
          "Choose a particular BGP instance.
           Clear long-lived-stale routes.
          ";
        input {
          leaf instance-name {
            mandatory true;
            type instance-name;
            description
              "instance name or all";
          }
          leaf ip-addr {
            mandatory true;
            type inet:ip-address;
            description
              "BGP neighbor address to clear";
          }
        }
      }
    }
  }
  augment "/ncs:devices/ncs:device-group/ncs:ned-id/ncs:rpc" {
    container rpc-clear-bgp-instance-ip-addr-long-lived-stale {
      tailf:ncs-device-type "netconf";
      tailf:display-when "/ncs:devices/ncs:device[ncs:name=current()/../../../ncs:member]/ncs:module[ncs:name='Cisco-IOS-XR-ipv4-bgp-act']";
      tailf:action clear-bgp-instance-ip-addr-long-lived-stale {
        tailf:actionpoint ncsproxy {
          tailf:internal;
        }
        csc:xr-task "bgp";
        csc:cli-command "clear bgp instance <instance-name> <ip-addr> long-lived-stale";
        description
          "Choose a particular BGP instance.
           Clear long-lived-stale routes.
          ";
        input {
          leaf instance-name {
            mandatory true;
            type instance-name;
            description
              "instance name or all";
          }
          leaf ip-addr {
            mandatory true;
            type inet:ip-address;
            description
              "BGP neighbor address to clear";
          }
        }
      }
    }
  }
  augment "/ncs:devices/ncs:device/ncs:rpc" {
    container rpc-clear-bgp-instance-ip-addr-graceful {
      tailf:ncs-device-type "netconf";
      tailf:display-when "not(../../ncs:module) or ../../ncs:module[ncs:name='Cisco-IOS-XR-ipv4-bgp-act']";
      tailf:action clear-bgp-instance-ip-addr-graceful {
        tailf:actionpoint ncsproxy {
          tailf:internal;
        }
        csc:xr-task "bgp";
        csc:cli-command "clear bgp instance <instance-name> <ip-addr> graceful";
        description
          "Choose a particular BGP instance.
           Clear with a hard reset and a graceful restart.
          ";
        input {
          leaf instance-name {
            mandatory true;
            type instance-name;
            description
              "instance name or all";
          }
          leaf ip-addr {
            mandatory true;
            type inet:ip-address;
            description
              "BGP neighbor address to clear";
          }
        }
      }
    }
  }
  augment "/ncs:devices/ncs:device-group/ncs:ned-id/ncs:rpc" {
    container rpc-clear-bgp-instance-ip-addr-graceful {
      tailf:ncs-device-type "netconf";
      tailf:display-when "/ncs:devices/ncs:device[ncs:name=current()/../../../ncs:member]/ncs:module[ncs:name='Cisco-IOS-XR-ipv4-bgp-act']";
      tailf:action clear-bgp-instance-ip-addr-graceful {
        tailf:actionpoint ncsproxy {
          tailf:internal;
        }
        csc:xr-task "bgp";
        csc:cli-command "clear bgp instance <instance-name> <ip-addr> graceful";
        description
          "Choose a particular BGP instance.
           Clear with a hard reset and a graceful restart.
          ";
        input {
          leaf instance-name {
            mandatory true;
            type instance-name;
            description
              "instance name or all";
          }
          leaf ip-addr {
            mandatory true;
            type inet:ip-address;
            description
              "BGP neighbor address to clear";
          }
        }
      }
    }
  }
  augment "/ncs:devices/ncs:device/ncs:rpc" {
    container rpc-clear-bgp-instance-all {
      tailf:ncs-device-type "netconf";
      tailf:display-when "not(../../ncs:module) or ../../ncs:module[ncs:name='Cisco-IOS-XR-ipv4-bgp-act']";
      tailf:action clear-bgp-instance-all {
        tailf:actionpoint ncsproxy {
          tailf:internal;
        }
        csc:xr-task "bgp";
        csc:cli-command "clear bgp instance <instance-name> *";
        description
          "Choose a particular BGP instance.
           Clear all peers and all routes from the BGP table.
          ";
        input {
          leaf instance-name {
            mandatory true;
            type instance-name;
            description
              "instance name or all";
          }
        }
      }
    }
  }
  augment "/ncs:devices/ncs:device-group/ncs:ned-id/ncs:rpc" {
    container rpc-clear-bgp-instance-all {
      tailf:ncs-device-type "netconf";
      tailf:display-when "/ncs:devices/ncs:device[ncs:name=current()/../../../ncs:member]/ncs:module[ncs:name='Cisco-IOS-XR-ipv4-bgp-act']";
      tailf:action clear-bgp-instance-all {
        tailf:actionpoint ncsproxy {
          tailf:internal;
        }
        csc:xr-task "bgp";
        csc:cli-command "clear bgp instance <instance-name> *";
        description
          "Choose a particular BGP instance.
           Clear all peers and all routes from the BGP table.
          ";
        input {
          leaf instance-name {
            mandatory true;
            type instance-name;
            description
              "instance name or all";
          }
        }
      }
    }
  }
  augment "/ncs:devices/ncs:device/ncs:rpc" {
    container rpc-clear-bgp-instance-all-graceful {
      tailf:ncs-device-type "netconf";
      tailf:display-when "not(../../ncs:module) or ../../ncs:module[ncs:name='Cisco-IOS-XR-ipv4-bgp-act']";
      tailf:action clear-bgp-instance-all-graceful {
        tailf:actionpoint ncsproxy {
          tailf:internal;
        }
        csc:xr-task "bgp";
        csc:cli-command "clear bgp instance <instance-name> * graceful";
        description
          "Choose a particular BGP instance.
           Clear all peers and all routes from the BGP table.
           Clear with a hard reset and a graceful restart.
          ";
        input {
          leaf instance-name {
            mandatory true;
            type instance-name;
            description
              "instance name or all";
          }
        }
      }
    }
  }
  augment "/ncs:devices/ncs:device-group/ncs:ned-id/ncs:rpc" {
    container rpc-clear-bgp-instance-all-graceful {
      tailf:ncs-device-type "netconf";
      tailf:display-when "/ncs:devices/ncs:device[ncs:name=current()/../../../ncs:member]/ncs:module[ncs:name='Cisco-IOS-XR-ipv4-bgp-act']";
      tailf:action clear-bgp-instance-all-graceful {
        tailf:actionpoint ncsproxy {
          tailf:internal;
        }
        csc:xr-task "bgp";
        csc:cli-command "clear bgp instance <instance-name> * graceful";
        description
          "Choose a particular BGP instance.
           Clear all peers and all routes from the BGP table.
           Clear with a hard reset and a graceful restart.
          ";
        input {
          leaf instance-name {
            mandatory true;
            type instance-name;
            description
              "instance name or all";
          }
        }
      }
    }
  }
  augment "/ncs:devices/ncs:device/ncs:rpc" {
    container rpc-clear-bgp-external {
      tailf:ncs-device-type "netconf";
      tailf:display-when "not(../../ncs:module) or ../../ncs:module[ncs:name='Cisco-IOS-XR-ipv4-bgp-act']";
      tailf:action clear-bgp-external {
        tailf:actionpoint ncsproxy {
          tailf:internal;
        }
        csc:xr-task "bgp";
        csc:cli-command "clear bgp external";
        description
          "Clear all external peers.
          ";
      }
    }
  }
  augment "/ncs:devices/ncs:device-group/ncs:ned-id/ncs:rpc" {
    container rpc-clear-bgp-external {
      tailf:ncs-device-type "netconf";
      tailf:display-when "/ncs:devices/ncs:device[ncs:name=current()/../../../ncs:member]/ncs:module[ncs:name='Cisco-IOS-XR-ipv4-bgp-act']";
      tailf:action clear-bgp-external {
        tailf:actionpoint ncsproxy {
          tailf:internal;
        }
        csc:xr-task "bgp";
        csc:cli-command "clear bgp external";
        description
          "Clear all external peers.
          ";
      }
    }
  }
  augment "/ncs:devices/ncs:device/ncs:rpc" {
    container rpc-clear-bgp-external-graceful {
      tailf:ncs-device-type "netconf";
      tailf:display-when "not(../../ncs:module) or ../../ncs:module[ncs:name='Cisco-IOS-XR-ipv4-bgp-act']";
      tailf:action clear-bgp-external-graceful {
        tailf:actionpoint ncsproxy {
          tailf:internal;
        }
        csc:xr-task "bgp";
        csc:cli-command "clear bgp external graceful";
        description
          "Clear all external peers.
           Clear with a hard reset and a graceful restart.
          ";
      }
    }
  }
  augment "/ncs:devices/ncs:device-group/ncs:ned-id/ncs:rpc" {
    container rpc-clear-bgp-external-graceful {
      tailf:ncs-device-type "netconf";
      tailf:display-when "/ncs:devices/ncs:device[ncs:name=current()/../../../ncs:member]/ncs:module[ncs:name='Cisco-IOS-XR-ipv4-bgp-act']";
      tailf:action clear-bgp-external-graceful {
        tailf:actionpoint ncsproxy {
          tailf:internal;
        }
        csc:xr-task "bgp";
        csc:cli-command "clear bgp external graceful";
        description
          "Clear all external peers.
           Clear with a hard reset and a graceful restart.
          ";
      }
    }
  }
  augment "/ncs:devices/ncs:device/ncs:rpc" {
    container rpc-clear-bgp-bestpath-vrf-afi-safi {
      tailf:ncs-device-type "netconf";
      tailf:display-when "not(../../ncs:module) or ../../ncs:module[ncs:name='Cisco-IOS-XR-ipv4-bgp-act']";
      tailf:action clear-bgp-bestpath-vrf-afi-safi {
        tailf:actionpoint ncsproxy {
          tailf:internal;
        }
        csc:xr-task "bgp";
        csc:cli-command "clear bgp bestpath vrf <vrf-all> <afi-safi-name>";
        description
          "re-run BGP bestpath selection.
           Specify a VRF.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device-group/ncs:ned-id/ncs:rpc" {
    container rpc-clear-bgp-bestpath-vrf-afi-safi {
      tailf:ncs-device-type "netconf";
      tailf:display-when "/ncs:devices/ncs:device[ncs:name=current()/../../../ncs:member]/ncs:module[ncs:name='Cisco-IOS-XR-ipv4-bgp-act']";
      tailf:action clear-bgp-bestpath-vrf-afi-safi {
        tailf:actionpoint ncsproxy {
          tailf:internal;
        }
        csc:xr-task "bgp";
        csc:cli-command "clear bgp bestpath vrf <vrf-all> <afi-safi-name>";
        description
          "re-run BGP bestpath selection.
           Specify a VRF.
          ";
        input {
          leaf vrf-all {
            mandatory true;
            type vrf-name;
            description
              "VRF name or all";
          }
          leaf afi-safi-name {
            mandatory true;
            type afi-safi-type;
            description
              "AFI and SAFI";
          }
        }
      }
    }
  }
  augment "/ncs:devices/ncs:device/ncs:rpc" {
    container rpc-clear-bgp-bestpath-vrf-afi-safi-vrf {
      tailf:ncs-device-type "netconf";
      tailf:display-when "not(../../ncs:module) or ../../ncs:module[ncs:name='Cisco-IOS-XR-ipv4-bgp-act']";
      tailf:action clear-bgp-bestpath-vrf-afi-safi-vrf {
        tailf:actionpoint ncsproxy {
          tailf:internal;
        }
        csc:xr-task "bgp";
        csc:cli-command "clear bgp bestpath vrf <vrf-all> <afi-safi-name> vrf <vrf-name>";
        description
          "re-run BGP bestpath selection.
           Specify a VRF.
           Display routes for a specified VRF.
          ";
        input {
          leaf vrf-all {
            mandatory true;
            type vrf-name;
            description
              "VRF name or all";
          }
          leaf afi-safi-name {
            mandatory true;
            type afi-safi-type;
            description
              "AFI and SAFI";
          }
          leaf vrf-name {
            mandatory true;
            type string;
            description
              "VRF name";
          }
        }
      }
    }
  }
  augment "/ncs:devices/ncs:device-group/ncs:ned-id/ncs:rpc" {
    container rpc-clear-bgp-bestpath-vrf-afi-safi-vrf {
      tailf:ncs-device-type "netconf";
      tailf:display-when "/ncs:devices/ncs:device[ncs:name=current()/../../../ncs:member]/ncs:module[ncs:name='Cisco-IOS-XR-ipv4-bgp-act']";
      tailf:action clear-bgp-bestpath-vrf-afi-safi-vrf {
        tailf:actionpoint ncsproxy {
          tailf:internal;
        }
        csc:xr-task "bgp";
        csc:cli-command "clear bgp bestpath vrf <vrf-all> <afi-safi-name> vrf <vrf-name>";
        description
          "re-run BGP bestpath selection.
           Specify a VRF.
           Display routes for a specified VRF.
          ";
        input {
          leaf vrf-all {
            mandatory true;
            type vrf-name;
            description
              "VRF name or all";
          }
          leaf afi-safi-name {
            mandatory true;
            type afi-safi-type;
            description
              "AFI and SAFI";
          }
          leaf vrf-name {
            mandatory true;
            type string;
            description
              "VRF name";
          }
        }
      }
    }
  }
  augment "/ncs:devices/ncs:device/ncs:rpc" {
    container rpc-clear-bgp-bestpath-vrf-afi-safi-rd {
      tailf:ncs-device-type "netconf";
      tailf:display-when "not(../../ncs:module) or ../../ncs:module[ncs:name='Cisco-IOS-XR-ipv4-bgp-act']";
      tailf:action clear-bgp-bestpath-vrf-afi-safi-rd {
        tailf:actionpoint ncsproxy {
          tailf:internal;
        }
        csc:xr-task "bgp";
        csc:cli-command "clear bgp bestpath vrf <vrf-all> <afi-safi-name> rd <rd>";
        description
          "re-run BGP bestpath selection.
           Specify a VRF.
           Display routes with a specific route distinguisher.
          ";
        input {
          leaf vrf-all {
            mandatory true;
            type vrf-name;
            description
              "VRF name or all";
          }
          leaf afi-safi-name {
            mandatory true;
            type afi-safi-type;
            description
              "AFI and SAFI";
          }
          leaf rd {
            mandatory true;
            type rd;
            description
              "Route distinguisher";
          }
        }
      }
    }
  }
  augment "/ncs:devices/ncs:device-group/ncs:ned-id/ncs:rpc" {
    container rpc-clear-bgp-bestpath-vrf-afi-safi-rd {
      tailf:ncs-device-type "netconf";
      tailf:display-when "/ncs:devices/ncs:device[ncs:name=current()/../../../ncs:member]/ncs:module[ncs:name='Cisco-IOS-XR-ipv4-bgp-act']";
      tailf:action clear-bgp-bestpath-vrf-afi-safi-rd {
        tailf:actionpoint ncsproxy {
          tailf:internal;
        }
        csc:xr-task "bgp";
        csc:cli-command "clear bgp bestpath vrf <vrf-all> <afi-safi-name> rd <rd>";
        description
          "re-run BGP bestpath selection.
           Specify a VRF.
           Display routes with a specific route distinguisher.
          ";
        input {
          leaf vrf-all {
            mandatory true;
            type vrf-name;
            description
              "VRF name or all";
          }
          leaf afi-safi-name {
            mandatory true;
            type afi-safi-type;
            description
              "AFI and SAFI";
          }
          leaf rd {
            mandatory true;
            type rd;
            description
              "Route distinguisher";
          }
        }
      }
    }
  }
  augment "/ncs:devices/ncs:device/ncs:rpc" {
    container rpc-clear-bgp-bestpath-vrf-afi-safi-ipv6-prefix {
      tailf:ncs-device-type "netconf";
      tailf:display-when "not(../../ncs:module) or ../../ncs:module[ncs:name='Cisco-IOS-XR-ipv4-bgp-act']";
      tailf:action clear-bgp-bestpath-vrf-afi-safi-ipv6-prefix {
        tailf:actionpoint ncsproxy {
          tailf:internal;
        }
        csc:xr-task "bgp";
        csc:cli-command "clear bgp bestpath vrf <vrf-all> <afi-safi-name> <ipv6-prefix>";
        description
          "re-run BGP bestpath selection.
           Specify a VRF.
          ";
        input {
          leaf vrf-all {
            mandatory true;
            type vrf-name;
            description
              "VRF name or all";
          }
          leaf afi-safi-name {
            mandatory true;
            type afi-safi-type;
            description
              "AFI and SAFI";
          }
          leaf ipv6-prefix {
            mandatory true;
            type inet:ipv6-prefix;
            description
              "IPv6 network and masklength";
          }
        }
      }
    }
  }
  augment "/ncs:devices/ncs:device-group/ncs:ned-id/ncs:rpc" {
    container rpc-clear-bgp-bestpath-vrf-afi-safi-ipv6-prefix {
      tailf:ncs-device-type "netconf";
      tailf:display-when "/ncs:devices/ncs:device[ncs:name=current()/../../../ncs:member]/ncs:module[ncs:name='Cisco-IOS-XR-ipv4-bgp-act']";
      tailf:action clear-bgp-bestpath-vrf-afi-safi-ipv6-prefix {
        tailf:actionpoint ncsproxy {
          tailf:internal;
        }
        csc:xr-task "bgp";
        csc:cli-command "clear bgp bestpath vrf <vrf-all> <afi-safi-name> <ipv6-prefix>";
        description
          "re-run BGP bestpath selection.
           Specify a VRF.
          ";
        input {
          leaf vrf-all {
            mandatory true;
            type vrf-name;
            description
              "VRF name or all";
          }
          leaf afi-safi-name {
            mandatory true;
            type afi-safi-type;
            description
              "AFI and SAFI";
          }
          leaf ipv6-prefix {
            mandatory true;
            type inet:ipv6-prefix;
            description
              "IPv6 network and masklength";
          }
        }
      }
    }
  }
  augment "/ncs:devices/ncs:device/ncs:rpc" {
    container rpc-clear-bgp-bestpath-vrf-afi-safi-ipv6-addr {
      tailf:ncs-device-type "netconf";
      tailf:display-when "not(../../ncs:module) or ../../ncs:module[ncs:name='Cisco-IOS-XR-ipv4-bgp-act']";
      tailf:action clear-bgp-bestpath-vrf-afi-safi-ipv6-addr {
        tailf:actionpoint ncsproxy {
          tailf:internal;
        }
        csc:xr-task "bgp";
        csc:cli-command "clear bgp bestpath vrf <vrf-all> <afi-safi-name> <ipv6-addr>";
        description
          "re-run BGP bestpath selection.
           Specify a VRF.
          ";
        input {
          leaf vrf-all {
            mandatory true;
            type vrf-name;
            description
              "VRF name or all";
          }
          leaf afi-safi-name {
            mandatory true;
            type afi-safi-type;
            description
              "AFI and SAFI";
          }
          leaf ipv6-addr {
            mandatory true;
            type inet:ipv6-address;
            description
              "IPv6 network";
          }
        }
      }
    }
  }
  augment "/ncs:devices/ncs:device-group/ncs:ned-id/ncs:rpc" {
    container rpc-clear-bgp-bestpath-vrf-afi-safi-ipv6-addr {
      tailf:ncs-device-type "netconf";
      tailf:display-when "/ncs:devices/ncs:device[ncs:name=current()/../../../ncs:member]/ncs:module[ncs:name='Cisco-IOS-XR-ipv4-bgp-act']";
      tailf:action clear-bgp-bestpath-vrf-afi-safi-ipv6-addr {
        tailf:actionpoint ncsproxy {
          tailf:internal;
        }
        csc:xr-task "bgp";
        csc:cli-command "clear bgp bestpath vrf <vrf-all> <afi-safi-name> <ipv6-addr>";
        description
          "re-run BGP bestpath selection.
           Specify a VRF.
          ";
        input {
          leaf vrf-all {
            mandatory true;
            type vrf-name;
            description
              "VRF name or all";
          }
          leaf afi-safi-name {
            mandatory true;
            type afi-safi-type;
            description
              "AFI and SAFI";
          }
          leaf ipv6-addr {
            mandatory true;
            type inet:ipv6-address;
            description
              "IPv6 network";
          }
        }
      }
    }
  }
  augment "/ncs:devices/ncs:device/ncs:rpc" {
    container rpc-clear-bgp-bestpath-vrf-afi-safi-ipv6-addr-ipv6-netmask {
      tailf:ncs-device-type "netconf";
      tailf:display-when "not(../../ncs:module) or ../../ncs:module[ncs:name='Cisco-IOS-XR-ipv4-bgp-act']";
      tailf:action clear-bgp-bestpath-vrf-afi-safi-ipv6-addr-ipv6-netmask {
        tailf:actionpoint ncsproxy {
          tailf:internal;
        }
        csc:xr-task "bgp";
        csc:cli-command "clear bgp bestpath vrf <vrf-all> <afi-safi-name> <ipv6-addr> <ipv6-netmask>";
        description
          "re-run BGP bestpath selection.
           Specify a VRF.
          ";
        input {
          leaf vrf-all {
            mandatory true;
            type vrf-name;
            description
              "VRF name or all";
          }
          leaf afi-safi-name {
            mandatory true;
            type afi-safi-type;
            description
              "AFI and SAFI";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device-group/ncs:ned-id/ncs:rpc" {
    container rpc-clear-bgp-bestpath-vrf-afi-safi-ipv6-addr-ipv6-netmask {
      tailf:ncs-device-type "netconf";
      tailf:display-when "/ncs:devices/ncs:device[ncs:name=current()/../../../ncs:member]/ncs:module[ncs:name='Cisco-IOS-XR-ipv4-bgp-act']";
      tailf:action clear-bgp-bestpath-vrf-afi-safi-ipv6-addr-ipv6-netmask {
        tailf:actionpoint ncsproxy {
          tailf:internal;
        }
        csc:xr-task "bgp";
        csc:cli-command "clear bgp bestpath vrf <vrf-all> <afi-safi-name> <ipv6-addr> <ipv6-netmask>";
        description
          "re-run BGP bestpath selection.
           Specify a VRF.
          ";
        input {
          leaf vrf-all {
            mandatory true;
            type vrf-name;
            description
              "VRF name or all";
          }
          leaf afi-safi-name {
            mandatory true;
            type afi-safi-type;
            description
              "AFI and SAFI";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device/ncs:rpc" {
    container rpc-clear-bgp-bestpath-vrf-afi-safi-vrf-network {
      tailf:ncs-device-type "netconf";
      tailf:display-when "not(../../ncs:module) or ../../ncs:module[ncs:name='Cisco-IOS-XR-ipv4-bgp-act']";
      tailf:action clear-bgp-bestpath-vrf-afi-safi-vrf-network {
        tailf:actionpoint ncsproxy {
          tailf:internal;
        }
        csc:xr-task "bgp";
        csc:cli-command "clear bgp bestpath vrf <vrf-all> <afi-safi-name> vrf <vrf-name> <network>";
        description
          "re-run BGP bestpath selection.
           Specify a VRF.
           Display routes for a specified VRF.
          ";
        input {
          leaf vrf-all {
            mandatory true;
            type vrf-name;
            description
              "VRF name or all";
          }
          leaf afi-safi-name {
            mandatory true;
            type afi-safi-type;
            description
              "AFI and SAFI";
          }
          leaf vrf-name {
            mandatory true;
            type string;
            description
              "VRF name";
          }
          leaf network {
            mandatory true;
            type string;
            description
              "Address family modifier specific network";
          }
        }
      }
    }
  }
  augment "/ncs:devices/ncs:device-group/ncs:ned-id/ncs:rpc" {
    container rpc-clear-bgp-bestpath-vrf-afi-safi-vrf-network {
      tailf:ncs-device-type "netconf";
      tailf:display-when "/ncs:devices/ncs:device[ncs:name=current()/../../../ncs:member]/ncs:module[ncs:name='Cisco-IOS-XR-ipv4-bgp-act']";
      tailf:action clear-bgp-bestpath-vrf-afi-safi-vrf-network {
        tailf:actionpoint ncsproxy {
          tailf:internal;
        }
        csc:xr-task "bgp";
        csc:cli-command "clear bgp bestpath vrf <vrf-all> <afi-safi-name> vrf <vrf-name> <network>";
        description
          "re-run BGP bestpath selection.
           Specify a VRF.
           Display routes for a specified VRF.
          ";
        input {
          leaf vrf-all {
            mandatory true;
            type vrf-name;
            description
              "VRF name or all";
          }
          leaf afi-safi-name {
            mandatory true;
            type afi-safi-type;
            description
              "AFI and SAFI";
          }
          leaf vrf-name {
            mandatory true;
            type string;
            description
              "VRF name";
          }
          leaf network {
            mandatory true;
            type string;
            description
              "Address family modifier specific network";
          }
        }
      }
    }
  }
  augment "/ncs:devices/ncs:device/ncs:rpc" {
    container rpc-clear-bgp-bestpath-vrf-afi-safi-rd-network {
      tailf:ncs-device-type "netconf";
      tailf:display-when "not(../../ncs:module) or ../../ncs:module[ncs:name='Cisco-IOS-XR-ipv4-bgp-act']";
      tailf:action clear-bgp-bestpath-vrf-afi-safi-rd-network {
        tailf:actionpoint ncsproxy {
          tailf:internal;
        }
        csc:xr-task "bgp";
        csc:cli-command "clear bgp bestpath vrf <vrf-all> <afi-safi-name> rd <rd> <network>";
        description
          "re-run BGP bestpath selection.
           Specify a VRF.
           Display routes with a specific route distinguisher.
          ";
        input {
          leaf vrf-all {
            mandatory true;
            type vrf-name;
            description
              "VRF name or all";
          }
          leaf afi-safi-name {
            mandatory true;
            type afi-safi-type;
            description
              "AFI and SAFI";
          }
          leaf rd {
            mandatory true;
            type rd;
            description
              "Route distinguisher";
          }
          leaf network {
            mandatory true;
            type string;
            description
              "Address family modifier specific network";
          }
        }
      }
    }
  }
  augment "/ncs:devices/ncs:device-group/ncs:ned-id/ncs:rpc" {
    container rpc-clear-bgp-bestpath-vrf-afi-safi-rd-network {
      tailf:ncs-device-type "netconf";
      tailf:display-when "/ncs:devices/ncs:device[ncs:name=current()/../../../ncs:member]/ncs:module[ncs:name='Cisco-IOS-XR-ipv4-bgp-act']";
      tailf:action clear-bgp-bestpath-vrf-afi-safi-rd-network {
        tailf:actionpoint ncsproxy {
          tailf:internal;
        }
        csc:xr-task "bgp";
        csc:cli-command "clear bgp bestpath vrf <vrf-all> <afi-safi-name> rd <rd> <network>";
        description
          "re-run BGP bestpath selection.
           Specify a VRF.
           Display routes with a specific route distinguisher.
          ";
        input {
          leaf vrf-all {
            mandatory true;
            type vrf-name;
            description
              "VRF name or all";
          }
          leaf afi-safi-name {
            mandatory true;
            type afi-safi-type;
            description
              "AFI and SAFI";
          }
          leaf rd {
            mandatory true;
            type rd;
            description
              "Route distinguisher";
          }
          leaf network {
            mandatory true;
            type string;
            description
              "Address family modifier specific network";
          }
        }
      }
    }
  }
  augment "/ncs:devices/ncs:device/ncs:rpc" {
    container rpc-clear-bgp-bestpath-vrf-afi-safi-network {
      tailf:ncs-device-type "netconf";
      tailf:display-when "not(../../ncs:module) or ../../ncs:module[ncs:name='Cisco-IOS-XR-ipv4-bgp-act']";
      tailf:action clear-bgp-bestpath-vrf-afi-safi-network {
        tailf:actionpoint ncsproxy {
          tailf:internal;
        }
        csc:xr-task "bgp";
        csc:cli-command "clear bgp bestpath vrf <vrf-all> <afi-safi-name> <network>";
        description
          "re-run BGP bestpath selection.
           Specify a VRF.
          ";
        input {
          leaf vrf-all {
            mandatory true;
            type vrf-name;
            description
              "VRF name or all";
          }
          leaf afi-safi-name {
            mandatory true;
            type afi-safi-type;
            description
              "AFI and SAFI";
          }
          leaf network {
            mandatory true;
            type string;
            description
              "Address family modifier specific network";
          }
        }
      }
    }
  }
  augment "/ncs:devices/ncs:device-group/ncs:ned-id/ncs:rpc" {
    container rpc-clear-bgp-bestpath-vrf-afi-safi-network {
      tailf:ncs-device-type "netconf";
      tailf:display-when "/ncs:devices/ncs:device[ncs:name=current()/../../../ncs:member]/ncs:module[ncs:name='Cisco-IOS-XR-ipv4-bgp-act']";
      tailf:action clear-bgp-bestpath-vrf-afi-safi-network {
        tailf:actionpoint ncsproxy {
          tailf:internal;
        }
        csc:xr-task "bgp";
        csc:cli-command "clear bgp bestpath vrf <vrf-all> <afi-safi-name> <network>";
        description
          "re-run BGP bestpath selection.
           Specify a VRF.
          ";
        input {
          leaf vrf-all {
            mandatory true;
            type vrf-name;
            description
              "VRF name or all";
          }
          leaf afi-safi-name {
            mandatory true;
            type afi-safi-type;
            description
              "AFI and SAFI";
          }
          leaf network {
            mandatory true;
            type string;
            description
              "Address family modifier specific network";
          }
        }
      }
    }
  }
  augment "/ncs:devices/ncs:device/ncs:rpc" {
    container rpc-clear-bgp-bestpath-vrf-afi-safi-ipv4-addr {
      tailf:ncs-device-type "netconf";
      tailf:display-when "not(../../ncs:module) or ../../ncs:module[ncs:name='Cisco-IOS-XR-ipv4-bgp-act']";
      tailf:action clear-bgp-bestpath-vrf-afi-safi-ipv4-addr {
        tailf:actionpoint ncsproxy {
          tailf:internal;
        }
        csc:xr-task "bgp";
        csc:cli-command "clear bgp bestpath vrf <vrf-all> <afi-safi-name> <ipv4-addr>";
        description
          "re-run BGP bestpath selection.
           Specify a VRF.
          ";
        input {
          leaf vrf-all {
            mandatory true;
            type vrf-name;
            description
              "VRF name or all";
          }
          leaf afi-safi-name {
            mandatory true;
            type afi-safi-type;
            description
              "AFI and SAFI";
          }
          leaf ipv4-addr {
            mandatory true;
            type inet:ipv4-address;
            description
              "IPv4 network";
          }
        }
      }
    }
  }
  augment "/ncs:devices/ncs:device-group/ncs:ned-id/ncs:rpc" {
    container rpc-clear-bgp-bestpath-vrf-afi-safi-ipv4-addr {
      tailf:ncs-device-type "netconf";
      tailf:display-when "/ncs:devices/ncs:device[ncs:name=current()/../../../ncs:member]/ncs:module[ncs:name='Cisco-IOS-XR-ipv4-bgp-act']";
      tailf:action clear-bgp-bestpath-vrf-afi-safi-ipv4-addr {
        tailf:actionpoint ncsproxy {
          tailf:internal;
        }
        csc:xr-task "bgp";
        csc:cli-command "clear bgp bestpath vrf <vrf-all> <afi-safi-name> <ipv4-addr>";
        description
          "re-run BGP bestpath selection.
           Specify a VRF.
          ";
        input {
          leaf vrf-all {
            mandatory true;
            type vrf-name;
            description
              "VRF name or all";
          }
          leaf afi-safi-name {
            mandatory true;
            type afi-safi-type;
            description
              "AFI and SAFI";
          }
          leaf ipv4-addr {
            mandatory true;
            type inet:ipv4-address;
            description
              "IPv4 network";
          }
        }
      }
    }
  }
  augment "/ncs:devices/ncs:device/ncs:rpc" {
    container rpc-clear-bgp-bestpath-vrf-afi-safi-ipv4-addr-ipv4-mask {
      tailf:ncs-device-type "netconf";
      tailf:display-when "not(../../ncs:module) or ../../ncs:module[ncs:name='Cisco-IOS-XR-ipv4-bgp-act']";
      tailf:action clear-bgp-bestpath-vrf-afi-safi-ipv4-addr-ipv4-mask {
        tailf:actionpoint ncsproxy {
          tailf:internal;
        }
        csc:xr-task "bgp";
        csc:cli-command "clear bgp bestpath vrf <vrf-all> <afi-safi-name> <ipv4-addr> <ipv4-mask>";
        description
          "re-run BGP bestpath selection.
           Specify a VRF.
          ";
        input {
          leaf vrf-all {
            mandatory true;
            type vrf-name;
            description
              "VRF name or all";
          }
          leaf afi-safi-name {
            mandatory true;
            type afi-safi-type;
            description
              "AFI and SAFI";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device-group/ncs:ned-id/ncs:rpc" {
    container rpc-clear-bgp-bestpath-vrf-afi-safi-ipv4-addr-ipv4-mask {
      tailf:ncs-device-type "netconf";
      tailf:display-when "/ncs:devices/ncs:device[ncs:name=current()/../../../ncs:member]/ncs:module[ncs:name='Cisco-IOS-XR-ipv4-bgp-act']";
      tailf:action clear-bgp-bestpath-vrf-afi-safi-ipv4-addr-ipv4-mask {
        tailf:actionpoint ncsproxy {
          tailf:internal;
        }
        csc:xr-task "bgp";
        csc:cli-command "clear bgp bestpath vrf <vrf-all> <afi-safi-name> <ipv4-addr> <ipv4-mask>";
        description
          "re-run BGP bestpath selection.
           Specify a VRF.
          ";
        input {
          leaf vrf-all {
            mandatory true;
            type vrf-name;
            description
              "VRF name or all";
          }
          leaf afi-safi-name {
            mandatory true;
            type afi-safi-type;
            description
              "AFI and SAFI";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device/ncs:rpc" {
    container rpc-clear-bgp-bestpath-vrf-afi-safi-ipv4-prefix {
      tailf:ncs-device-type "netconf";
      tailf:display-when "not(../../ncs:module) or ../../ncs:module[ncs:name='Cisco-IOS-XR-ipv4-bgp-act']";
      tailf:action clear-bgp-bestpath-vrf-afi-safi-ipv4-prefix {
        tailf:actionpoint ncsproxy {
          tailf:internal;
        }
        csc:xr-task "bgp";
        csc:cli-command "clear bgp bestpath vrf <vrf-all> <afi-safi-name> <ipv4-prefix>";
        description
          "re-run BGP bestpath selection.
           Specify a VRF.
          ";
        input {
          leaf vrf-all {
            mandatory true;
            type vrf-name;
            description
              "VRF name or all";
          }
          leaf afi-safi-name {
            mandatory true;
            type afi-safi-type;
            description
              "AFI and SAFI";
          }
          leaf ipv4-prefix {
            mandatory true;
            type inet:ipv4-prefix;
            description
              "Fspec IPv4 Prefix";
          }
        }
      }
    }
  }
  augment "/ncs:devices/ncs:device-group/ncs:ned-id/ncs:rpc" {
    container rpc-clear-bgp-bestpath-vrf-afi-safi-ipv4-prefix {
      tailf:ncs-device-type "netconf";
      tailf:display-when "/ncs:devices/ncs:device[ncs:name=current()/../../../ncs:member]/ncs:module[ncs:name='Cisco-IOS-XR-ipv4-bgp-act']";
      tailf:action clear-bgp-bestpath-vrf-afi-safi-ipv4-prefix {
        tailf:actionpoint ncsproxy {
          tailf:internal;
        }
        csc:xr-task "bgp";
        csc:cli-command "clear bgp bestpath vrf <vrf-all> <afi-safi-name> <ipv4-prefix>";
        description
          "re-run BGP bestpath selection.
           Specify a VRF.
          ";
        input {
          leaf vrf-all {
            mandatory true;
            type vrf-name;
            description
              "VRF name or all";
          }
          leaf afi-safi-name {
            mandatory true;
            type afi-safi-type;
            description
              "AFI and SAFI";
          }
          leaf ipv4-prefix {
            mandatory true;
            type inet:ipv4-prefix;
            description
              "Fspec IPv4 Prefix";
          }
        }
      }
    }
  }
  augment "/ncs:devices/ncs:device/ncs:rpc" {
    container rpc-clear-bgp-bestpath-vrf-ip-prefix {
      tailf:ncs-device-type "netconf";
      tailf:display-when "not(../../ncs:module) or ../../ncs:module[ncs:name='Cisco-IOS-XR-ipv4-bgp-act']";
      tailf:action clear-bgp-bestpath-vrf-ip-prefix {
        tailf:actionpoint ncsproxy {
          tailf:internal;
        }
        csc:xr-task "bgp";
        csc:cli-command "clear bgp bestpath vrf <vrf-all> <ip-prefix>";
        description
          "re-run BGP bestpath selection.
           Specify a VRF.
          ";
        input {
          leaf vrf-all {
            mandatory true;
            type vrf-name;
            description
              "VRF name or all";
          }
          leaf ip-prefix {
            mandatory true;
            type inet:ip-prefix;
            description
              "Network and masklength";
          }
        }
      }
    }
  }
  augment "/ncs:devices/ncs:device-group/ncs:ned-id/ncs:rpc" {
    container rpc-clear-bgp-bestpath-vrf-ip-prefix {
      tailf:ncs-device-type "netconf";
      tailf:display-when "/ncs:devices/ncs:device[ncs:name=current()/../../../ncs:member]/ncs:module[ncs:name='Cisco-IOS-XR-ipv4-bgp-act']";
      tailf:action clear-bgp-bestpath-vrf-ip-prefix {
        tailf:actionpoint ncsproxy {
          tailf:internal;
        }
        csc:xr-task "bgp";
        csc:cli-command "clear bgp bestpath vrf <vrf-all> <ip-prefix>";
        description
          "re-run BGP bestpath selection.
           Specify a VRF.
          ";
        input {
          leaf vrf-all {
            mandatory true;
            type vrf-name;
            description
              "VRF name or all";
          }
          leaf ip-prefix {
            mandatory true;
            type inet:ip-prefix;
            description
              "Network and masklength";
          }
        }
      }
    }
  }
  augment "/ncs:devices/ncs:device/ncs:rpc" {
    container rpc-clear-bgp-bestpath-vrf-ip-addr {
      tailf:ncs-device-type "netconf";
      tailf:display-when "not(../../ncs:module) or ../../ncs:module[ncs:name='Cisco-IOS-XR-ipv4-bgp-act']";
      tailf:action clear-bgp-bestpath-vrf-ip-addr {
        tailf:actionpoint ncsproxy {
          tailf:internal;
        }
        csc:xr-task "bgp";
        csc:cli-command "clear bgp bestpath vrf <vrf-all> <ip-addr>";
        description
          "re-run BGP bestpath selection.
           Specify a VRF.
          ";
        input {
          leaf vrf-all {
            mandatory true;
            type vrf-name;
            description
              "VRF name or all";
          }
          leaf ip-addr {
            mandatory true;
            type inet:ip-address;
            description
              "Network";
          }
        }
      }
    }
  }
  augment "/ncs:devices/ncs:device-group/ncs:ned-id/ncs:rpc" {
    container rpc-clear-bgp-bestpath-vrf-ip-addr {
      tailf:ncs-device-type "netconf";
      tailf:display-when "/ncs:devices/ncs:device[ncs:name=current()/../../../ncs:member]/ncs:module[ncs:name='Cisco-IOS-XR-ipv4-bgp-act']";
      tailf:action clear-bgp-bestpath-vrf-ip-addr {
        tailf:actionpoint ncsproxy {
          tailf:internal;
        }
        csc:xr-task "bgp";
        csc:cli-command "clear bgp bestpath vrf <vrf-all> <ip-addr>";
        description
          "re-run BGP bestpath selection.
           Specify a VRF.
          ";
        input {
          leaf vrf-all {
            mandatory true;
            type vrf-name;
            description
              "VRF name or all";
          }
          leaf ip-addr {
            mandatory true;
            type inet:ip-address;
            description
              "Network";
          }
        }
      }
    }
  }
  augment "/ncs:devices/ncs:device/ncs:rpc" {
    container rpc-clear-bgp-bestpath-vrf-ip-addr-ip-netmask {
      tailf:ncs-device-type "netconf";
      tailf:display-when "not(../../ncs:module) or ../../ncs:module[ncs:name='Cisco-IOS-XR-ipv4-bgp-act']";
      tailf:action clear-bgp-bestpath-vrf-ip-addr-ip-netmask {
        tailf:actionpoint ncsproxy {
          tailf:internal;
        }
        csc:xr-task "bgp";
        csc:cli-command "clear bgp bestpath vrf <vrf-all> <ip-addr> <ip-netmask>";
        description
          "re-run BGP bestpath selection.
           Specify a VRF.
          ";
        input {
          leaf vrf-all {
            mandatory true;
            type vrf-name;
            description
              "VRF name or all";
          }
          leaf ip-addr {
            mandatory true;
            type inet:ip-address;
            description
              "Network";
          }
          leaf ip-netmask {
            mandatory true;
            type ip-netmask;
            description
              "Mask";
          }
        }
      }
    }
  }
  augment "/ncs:devices/ncs:device-group/ncs:ned-id/ncs:rpc" {
    container rpc-clear-bgp-bestpath-vrf-ip-addr-ip-netmask {
      tailf:ncs-device-type "netconf";
      tailf:display-when "/ncs:devices/ncs:device[ncs:name=current()/../../../ncs:member]/ncs:module[ncs:name='Cisco-IOS-XR-ipv4-bgp-act']";
      tailf:action clear-bgp-bestpath-vrf-ip-addr-ip-netmask {
        tailf:actionpoint ncsproxy {
          tailf:internal;
        }
        csc:xr-task "bgp";
        csc:cli-command "clear bgp bestpath vrf <vrf-all> <ip-addr> <ip-netmask>";
        description
          "re-run BGP bestpath selection.
           Specify a VRF.
          ";
        input {
          leaf vrf-all {
            mandatory true;
            type vrf-name;
            description
              "VRF name or all";
          }
          leaf ip-addr {
            mandatory true;
            type inet:ip-address;
            description
              "Network";
          }
          leaf ip-netmask {
            mandatory true;
            type ip-netmask;
            description
              "Mask";
          }
        }
      }
    }
  }
  augment "/ncs:devices/ncs:device/ncs:rpc" {
    container rpc-clear-bgp-bestpath-afi-safi-vrf-ipv6-prefix {
      tailf:ncs-device-type "netconf";
      tailf:display-when "not(../../ncs:module) or ../../ncs:module[ncs:name='Cisco-IOS-XR-ipv4-bgp-act']";
      tailf:action clear-bgp-bestpath-afi-safi-vrf-ipv6-prefix {
        tailf:actionpoint ncsproxy {
          tailf:internal;
        }
        csc:xr-task "bgp";
        csc:cli-command "clear bgp bestpath <afi-safi-name> vrf <vrf-name> <ipv6-prefix>";
        description
          "re-run BGP bestpath selection.
           Display routes for a specified VRF.
          ";
        input {
          leaf afi-safi-name {
            mandatory true;
            type afi-safi-type;
            description
              "AFI and SAFI";
          }
          leaf vrf-name {
            mandatory true;
            type string;
            description
              "VRF name";
          }
          leaf ipv6-prefix {
            mandatory true;
            type inet:ipv6-prefix;
            description
              "IPv6 network and masklength";
          }
        }
      }
    }
  }
  augment "/ncs:devices/ncs:device-group/ncs:ned-id/ncs:rpc" {
    container rpc-clear-bgp-bestpath-afi-safi-vrf-ipv6-prefix {
      tailf:ncs-device-type "netconf";
      tailf:display-when "/ncs:devices/ncs:device[ncs:name=current()/../../../ncs:member]/ncs:module[ncs:name='Cisco-IOS-XR-ipv4-bgp-act']";
      tailf:action clear-bgp-bestpath-afi-safi-vrf-ipv6-prefix {
        tailf:actionpoint ncsproxy {
          tailf:internal;
        }
        csc:xr-task "bgp";
        csc:cli-command "clear bgp bestpath <afi-safi-name> vrf <vrf-name> <ipv6-prefix>";
        description
          "re-run BGP bestpath selection.
           Display routes for a specified VRF.
          ";
        input {
          leaf afi-safi-name {
            mandatory true;
            type afi-safi-type;
            description
              "AFI and SAFI";
          }
          leaf vrf-name {
            mandatory true;
            type string;
            description
              "VRF name";
          }
          leaf ipv6-prefix {
            mandatory true;
            type inet:ipv6-prefix;
            description
              "IPv6 network and masklength";
          }
        }
      }
    }
  }
  augment "/ncs:devices/ncs:device/ncs:rpc" {
    container rpc-clear-bgp-bestpath-afi-safi-vrf-ipv6-addr {
      tailf:ncs-device-type "netconf";
      tailf:display-when "not(../../ncs:module) or ../../ncs:module[ncs:name='Cisco-IOS-XR-ipv4-bgp-act']";
      tailf:action clear-bgp-bestpath-afi-safi-vrf-ipv6-addr {
        tailf:actionpoint ncsproxy {
          tailf:internal;
        }
        csc:xr-task "bgp";
        csc:cli-command "clear bgp bestpath <afi-safi-name> vrf <vrf-name> <ipv6-addr>";
        description
          "re-run BGP bestpath selection.
           Display routes for a specified VRF.
          ";
        input {
          leaf afi-safi-name {
            mandatory true;
            type afi-safi-type;
            description
              "AFI and SAFI";
          }
          leaf vrf-name {
            mandatory true;
            type string;
            description
              "VRF name";
          }
          leaf ipv6-addr {
            mandatory true;
            type inet:ipv6-address;
            description
              "IPv6 network";
          }
        }
      }
    }
  }
  augment "/ncs:devices/ncs:device-group/ncs:ned-id/ncs:rpc" {
    container rpc-clear-bgp-bestpath-afi-safi-vrf-ipv6-addr {
      tailf:ncs-device-type "netconf";
      tailf:display-when "/ncs:devices/ncs:device[ncs:name=current()/../../../ncs:member]/ncs:module[ncs:name='Cisco-IOS-XR-ipv4-bgp-act']";
      tailf:action clear-bgp-bestpath-afi-safi-vrf-ipv6-addr {
        tailf:actionpoint ncsproxy {
          tailf:internal;
        }
        csc:xr-task "bgp";
        csc:cli-command "clear bgp bestpath <afi-safi-name> vrf <vrf-name> <ipv6-addr>";
        description
          "re-run BGP bestpath selection.
           Display routes for a specified VRF.
          ";
        input {
          leaf afi-safi-name {
            mandatory true;
            type afi-safi-type;
            description
              "AFI and SAFI";
          }
          leaf vrf-name {
            mandatory true;
            type string;
            description
              "VRF name";
          }
          leaf ipv6-addr {
            mandatory true;
            type inet:ipv6-address;
            description
              "IPv6 network";
          }
        }
      }
    }
  }
  augment "/ncs:devices/ncs:device/ncs:rpc" {
    container rpc-clear-bgp-bestpath-afi-safi-vrf-ipv6-addr-ipv6-netmask {
      tailf:ncs-device-type "netconf";
      tailf:display-when "not(../../ncs:module) or ../../ncs:module[ncs:name='Cisco-IOS-XR-ipv4-bgp-act']";
      tailf:action clear-bgp-bestpath-afi-safi-vrf-ipv6-addr-ipv6-netmask {
        tailf:actionpoint ncsproxy {
          tailf:internal;
        }
        csc:xr-task "bgp";
        csc:cli-command "clear bgp bestpath <afi-safi-name> vrf <vrf-name> <ipv6-addr> <ipv6-netmask>";
        description
          "re-run BGP bestpath selection.
           Display routes for a specified VRF.
          ";
        input {
          leaf afi-safi-name {
            mandatory true;
            type afi-safi-type;
            description
              "AFI and SAFI";
          }
          leaf vrf-name {
            mandatory true;
            type string;
            description
              "VRF name";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device-group/ncs:ned-id/ncs:rpc" {
    container rpc-clear-bgp-bestpath-afi-safi-vrf-ipv6-addr-ipv6-netmask {
      tailf:ncs-device-type "netconf";
      tailf:display-when "/ncs:devices/ncs:device[ncs:name=current()/../../../ncs:member]/ncs:module[ncs:name='Cisco-IOS-XR-ipv4-bgp-act']";
      tailf:action clear-bgp-bestpath-afi-safi-vrf-ipv6-addr-ipv6-netmask {
        tailf:actionpoint ncsproxy {
          tailf:internal;
        }
        csc:xr-task "bgp";
        csc:cli-command "clear bgp bestpath <afi-safi-name> vrf <vrf-name> <ipv6-addr> <ipv6-netmask>";
        description
          "re-run BGP bestpath selection.
           Display routes for a specified VRF.
          ";
        input {
          leaf afi-safi-name {
            mandatory true;
            type afi-safi-type;
            description
              "AFI and SAFI";
          }
          leaf vrf-name {
            mandatory true;
            type string;
            description
              "VRF name";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device/ncs:rpc" {
    container rpc-clear-bgp-bestpath-afi-safi-rd-ipv6-prefix {
      tailf:ncs-device-type "netconf";
      tailf:display-when "not(../../ncs:module) or ../../ncs:module[ncs:name='Cisco-IOS-XR-ipv4-bgp-act']";
      tailf:action clear-bgp-bestpath-afi-safi-rd-ipv6-prefix {
        tailf:actionpoint ncsproxy {
          tailf:internal;
        }
        csc:xr-task "bgp";
        csc:cli-command "clear bgp bestpath <afi-safi-name> rd <rd> <ipv6-prefix>";
        description
          "re-run BGP bestpath selection.
           Display routes with a specific route distinguisher.
          ";
        input {
          leaf afi-safi-name {
            mandatory true;
            type afi-safi-type;
            description
              "AFI and SAFI";
          }
          leaf rd {
            mandatory true;
            type rd;
            description
              "Route distinguisher";
          }
          leaf ipv6-prefix {
            mandatory true;
            type inet:ipv6-prefix;
            description
              "IPv6 network and masklength";
          }
        }
      }
    }
  }
  augment "/ncs:devices/ncs:device-group/ncs:ned-id/ncs:rpc" {
    container rpc-clear-bgp-bestpath-afi-safi-rd-ipv6-prefix {
      tailf:ncs-device-type "netconf";
      tailf:display-when "/ncs:devices/ncs:device[ncs:name=current()/../../../ncs:member]/ncs:module[ncs:name='Cisco-IOS-XR-ipv4-bgp-act']";
      tailf:action clear-bgp-bestpath-afi-safi-rd-ipv6-prefix {
        tailf:actionpoint ncsproxy {
          tailf:internal;
        }
        csc:xr-task "bgp";
        csc:cli-command "clear bgp bestpath <afi-safi-name> rd <rd> <ipv6-prefix>";
        description
          "re-run BGP bestpath selection.
           Display routes with a specific route distinguisher.
          ";
        input {
          leaf afi-safi-name {
            mandatory true;
            type afi-safi-type;
            description
              "AFI and SAFI";
          }
          leaf rd {
            mandatory true;
            type rd;
            description
              "Route distinguisher";
          }
          leaf ipv6-prefix {
            mandatory true;
            type inet:ipv6-prefix;
            description
              "IPv6 network and masklength";
          }
        }
      }
    }
  }
  augment "/ncs:devices/ncs:device/ncs:rpc" {
    container rpc-clear-bgp-bestpath-afi-safi-rd-ipv6-addr {
      tailf:ncs-device-type "netconf";
      tailf:display-when "not(../../ncs:module) or ../../ncs:module[ncs:name='Cisco-IOS-XR-ipv4-bgp-act']";
      tailf:action clear-bgp-bestpath-afi-safi-rd-ipv6-addr {
        tailf:actionpoint ncsproxy {
          tailf:internal;
        }
        csc:xr-task "bgp";
        csc:cli-command "clear bgp bestpath <afi-safi-name> rd <rd> <ipv6-addr>";
        description
          "re-run BGP bestpath selection.
           Display routes with a specific route distinguisher.
          ";
        input {
          leaf afi-safi-name {
            mandatory true;
            type afi-safi-type;
            description
              "AFI and SAFI";
          }
          leaf rd {
            mandatory true;
            type rd;
            description
              "Route distinguisher";
          }
          leaf ipv6-addr {
            mandatory true;
            type inet:ipv6-address;
            description
              "IPv6 network";
          }
        }
      }
    }
  }
  augment "/ncs:devices/ncs:device-group/ncs:ned-id/ncs:rpc" {
    container rpc-clear-bgp-bestpath-afi-safi-rd-ipv6-addr {
      tailf:ncs-device-type "netconf";
      tailf:display-when "/ncs:devices/ncs:device[ncs:name=current()/../../../ncs:member]/ncs:module[ncs:name='Cisco-IOS-XR-ipv4-bgp-act']";
      tailf:action clear-bgp-bestpath-afi-safi-rd-ipv6-addr {
        tailf:actionpoint ncsproxy {
          tailf:internal;
        }
        csc:xr-task "bgp";
        csc:cli-command "clear bgp bestpath <afi-safi-name> rd <rd> <ipv6-addr>";
        description
          "re-run BGP bestpath selection.
           Display routes with a specific route distinguisher.
          ";
        input {
          leaf afi-safi-name {
            mandatory true;
            type afi-safi-type;
            description
              "AFI and SAFI";
          }
          leaf rd {
            mandatory true;
            type rd;
            description
              "Route distinguisher";
          }
          leaf ipv6-addr {
            mandatory true;
            type inet:ipv6-address;
            description
              "IPv6 network";
          }
        }
      }
    }
  }
  augment "/ncs:devices/ncs:device/ncs:rpc" {
    container rpc-clear-bgp-bestpath-afi-safi-rd-ipv6-addr-ipv6-netmask {
      tailf:ncs-device-type "netconf";
      tailf:display-when "not(../../ncs:module) or ../../ncs:module[ncs:name='Cisco-IOS-XR-ipv4-bgp-act']";
      tailf:action clear-bgp-bestpath-afi-safi-rd-ipv6-addr-ipv6-netmask {
        tailf:actionpoint ncsproxy {
          tailf:internal;
        }
        csc:xr-task "bgp";
        csc:cli-command "clear bgp bestpath <afi-safi-name> rd <rd> <ipv6-addr> <ipv6-netmask>";
        description
          "re-run BGP bestpath selection.
           Display routes with a specific route distinguisher.
          ";
        input {
          leaf afi-safi-name {
            mandatory true;
            type afi-safi-type;
            description
              "AFI and SAFI";
          }
          leaf rd {
            mandatory true;
            type rd;
            description
              "Route distinguisher";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device-group/ncs:ned-id/ncs:rpc" {
    container rpc-clear-bgp-bestpath-afi-safi-rd-ipv6-addr-ipv6-netmask {
      tailf:ncs-device-type "netconf";
      tailf:display-when "/ncs:devices/ncs:device[ncs:name=current()/../../../ncs:member]/ncs:module[ncs:name='Cisco-IOS-XR-ipv4-bgp-act']";
      tailf:action clear-bgp-bestpath-afi-safi-rd-ipv6-addr-ipv6-netmask {
        tailf:actionpoint ncsproxy {
          tailf:internal;
        }
        csc:xr-task "bgp";
        csc:cli-command "clear bgp bestpath <afi-safi-name> rd <rd> <ipv6-addr> <ipv6-netmask>";
        description
          "re-run BGP bestpath selection.
           Display routes with a specific route distinguisher.
          ";
        input {
          leaf afi-safi-name {
            mandatory true;
            type afi-safi-type;
            description
              "AFI and SAFI";
          }
          leaf rd {
            mandatory true;
            type rd;
            description
              "Route distinguisher";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device/ncs:rpc" {
    container rpc-clear-bgp-bestpath-afi-safi-vrf-ipv4-addr-ipv4-mask {
      tailf:ncs-device-type "netconf";
      tailf:display-when "not(../../ncs:module) or ../../ncs:module[ncs:name='Cisco-IOS-XR-ipv4-bgp-act']";
      tailf:action clear-bgp-bestpath-afi-safi-vrf-ipv4-addr-ipv4-mask {
        tailf:actionpoint ncsproxy {
          tailf:internal;
        }
        csc:xr-task "bgp";
        csc:cli-command "clear bgp bestpath <afi-safi-name> vrf <vrf-name> <ipv4-addr> <ipv4-mask>";
        description
          "re-run BGP bestpath selection.
           Display routes for a specified VRF.
          ";
        input {
          leaf afi-safi-name {
            mandatory true;
            type afi-safi-type;
            description
              "AFI and SAFI";
          }
          leaf vrf-name {
            mandatory true;
            type string;
            description
              "VRF name";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device-group/ncs:ned-id/ncs:rpc" {
    container rpc-clear-bgp-bestpath-afi-safi-vrf-ipv4-addr-ipv4-mask {
      tailf:ncs-device-type "netconf";
      tailf:display-when "/ncs:devices/ncs:device[ncs:name=current()/../../../ncs:member]/ncs:module[ncs:name='Cisco-IOS-XR-ipv4-bgp-act']";
      tailf:action clear-bgp-bestpath-afi-safi-vrf-ipv4-addr-ipv4-mask {
        tailf:actionpoint ncsproxy {
          tailf:internal;
        }
        csc:xr-task "bgp";
        csc:cli-command "clear bgp bestpath <afi-safi-name> vrf <vrf-name> <ipv4-addr> <ipv4-mask>";
        description
          "re-run BGP bestpath selection.
           Display routes for a specified VRF.
          ";
        input {
          leaf afi-safi-name {
            mandatory true;
            type afi-safi-type;
            description
              "AFI and SAFI";
          }
          leaf vrf-name {
            mandatory true;
            type string;
            description
              "VRF name";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device/ncs:rpc" {
    container rpc-clear-bgp-bestpath-afi-safi-rd-ipv4-addr-ipv4-mask {
      tailf:ncs-device-type "netconf";
      tailf:display-when "not(../../ncs:module) or ../../ncs:module[ncs:name='Cisco-IOS-XR-ipv4-bgp-act']";
      tailf:action clear-bgp-bestpath-afi-safi-rd-ipv4-addr-ipv4-mask {
        tailf:actionpoint ncsproxy {
          tailf:internal;
        }
        csc:xr-task "bgp";
        csc:cli-command "clear bgp bestpath <afi-safi-name> rd <rd> <ipv4-addr> <ipv4-mask>";
        description
          "re-run BGP bestpath selection.
           Display routes with a specific route distinguisher.
          ";
        input {
          leaf afi-safi-name {
            mandatory true;
            type afi-safi-type;
            description
              "AFI and SAFI";
          }
          leaf rd {
            mandatory true;
            type rd;
            description
              "Route distinguisher";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device-group/ncs:ned-id/ncs:rpc" {
    container rpc-clear-bgp-bestpath-afi-safi-rd-ipv4-addr-ipv4-mask {
      tailf:ncs-device-type "netconf";
      tailf:display-when "/ncs:devices/ncs:device[ncs:name=current()/../../../ncs:member]/ncs:module[ncs:name='Cisco-IOS-XR-ipv4-bgp-act']";
      tailf:action clear-bgp-bestpath-afi-safi-rd-ipv4-addr-ipv4-mask {
        tailf:actionpoint ncsproxy {
          tailf:internal;
        }
        csc:xr-task "bgp";
        csc:cli-command "clear bgp bestpath <afi-safi-name> rd <rd> <ipv4-addr> <ipv4-mask>";
        description
          "re-run BGP bestpath selection.
           Display routes with a specific route distinguisher.
          ";
        input {
          leaf afi-safi-name {
            mandatory true;
            type afi-safi-type;
            description
              "AFI and SAFI";
          }
          leaf rd {
            mandatory true;
            type rd;
            description
              "Route distinguisher";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device/ncs:rpc" {
    container rpc-clear-bgp-bestpath-afi-safi-vrf-ipv4-prefix {
      tailf:ncs-device-type "netconf";
      tailf:display-when "not(../../ncs:module) or ../../ncs:module[ncs:name='Cisco-IOS-XR-ipv4-bgp-act']";
      tailf:action clear-bgp-bestpath-afi-safi-vrf-ipv4-prefix {
        tailf:actionpoint ncsproxy {
          tailf:internal;
        }
        csc:xr-task "bgp";
        csc:cli-command "clear bgp bestpath <afi-safi-name> vrf <vrf-name> <ipv4-prefix>";
        description
          "re-run BGP bestpath selection.
           Display routes for a specified VRF.
          ";
        input {
          leaf afi-safi-name {
            mandatory true;
            type afi-safi-type;
            description
              "AFI and SAFI";
          }
          leaf vrf-name {
            mandatory true;
            type string;
            description
              "VRF name";
          }
          leaf ipv4-prefix {
            mandatory true;
            type inet:ipv4-prefix;
            description
              "VPN Fspec Prefix";
          }
        }
      }
    }
  }
  augment "/ncs:devices/ncs:device-group/ncs:ned-id/ncs:rpc" {
    container rpc-clear-bgp-bestpath-afi-safi-vrf-ipv4-prefix {
      tailf:ncs-device-type "netconf";
      tailf:display-when "/ncs:devices/ncs:device[ncs:name=current()/../../../ncs:member]/ncs:module[ncs:name='Cisco-IOS-XR-ipv4-bgp-act']";
      tailf:action clear-bgp-bestpath-afi-safi-vrf-ipv4-prefix {
        tailf:actionpoint ncsproxy {
          tailf:internal;
        }
        csc:xr-task "bgp";
        csc:cli-command "clear bgp bestpath <afi-safi-name> vrf <vrf-name> <ipv4-prefix>";
        description
          "re-run BGP bestpath selection.
           Display routes for a specified VRF.
          ";
        input {
          leaf afi-safi-name {
            mandatory true;
            type afi-safi-type;
            description
              "AFI and SAFI";
          }
          leaf vrf-name {
            mandatory true;
            type string;
            description
              "VRF name";
          }
          leaf ipv4-prefix {
            mandatory true;
            type inet:ipv4-prefix;
            description
              "VPN Fspec Prefix";
          }
        }
      }
    }
  }
  augment "/ncs:devices/ncs:device/ncs:rpc" {
    container rpc-clear-bgp-bestpath-afi-safi-mp2mp-ipv4-prefix {
      tailf:ncs-device-type "netconf";
      tailf:display-when "not(../../ncs:module) or ../../ncs:module[ncs:name='Cisco-IOS-XR-ipv4-bgp-act']";
      tailf:action clear-bgp-bestpath-afi-safi-mp2mp-ipv4-prefix {
        tailf:actionpoint ncsproxy {
          tailf:internal;
        }
        csc:xr-task "bgp";
        csc:cli-command "clear bgp bestpath <afi-safi-name> mp2mp <mp2mp> <ipv4-prefix>";
        description
          "re-run BGP bestpath selection.
           Display routes for a specified Xconnect group:MP2MP.
          ";
        input {
          leaf afi-safi-name {
            mandatory true;
            type afi-safi-type;
            description
              "AFI and SAFI";
          }
          leaf mp2mp {
            mandatory true;
            type string;
            description
              "Xconnect Group:mp2mp";
          }
          leaf ipv4-prefix {
            mandatory true;
            type inet:ipv4-prefix;
            description
              "L2VPN VPWS Prefix";
          }
        }
      }
    }
  }
  augment "/ncs:devices/ncs:device-group/ncs:ned-id/ncs:rpc" {
    container rpc-clear-bgp-bestpath-afi-safi-mp2mp-ipv4-prefix {
      tailf:ncs-device-type "netconf";
      tailf:display-when "/ncs:devices/ncs:device[ncs:name=current()/../../../ncs:member]/ncs:module[ncs:name='Cisco-IOS-XR-ipv4-bgp-act']";
      tailf:action clear-bgp-bestpath-afi-safi-mp2mp-ipv4-prefix {
        tailf:actionpoint ncsproxy {
          tailf:internal;
        }
        csc:xr-task "bgp";
        csc:cli-command "clear bgp bestpath <afi-safi-name> mp2mp <mp2mp> <ipv4-prefix>";
        description
          "re-run BGP bestpath selection.
           Display routes for a specified Xconnect group:MP2MP.
          ";
        input {
          leaf afi-safi-name {
            mandatory true;
            type afi-safi-type;
            description
              "AFI and SAFI";
          }
          leaf mp2mp {
            mandatory true;
            type string;
            description
              "Xconnect Group:mp2mp";
          }
          leaf ipv4-prefix {
            mandatory true;
            type inet:ipv4-prefix;
            description
              "L2VPN VPWS Prefix";
          }
        }
      }
    }
  }
  augment "/ncs:devices/ncs:device/ncs:rpc" {
    container rpc-clear-bgp-bestpath-afi-safi-rd-ipv4-prefix {
      tailf:ncs-device-type "netconf";
      tailf:display-when "not(../../ncs:module) or ../../ncs:module[ncs:name='Cisco-IOS-XR-ipv4-bgp-act']";
      tailf:action clear-bgp-bestpath-afi-safi-rd-ipv4-prefix {
        tailf:actionpoint ncsproxy {
          tailf:internal;
        }
        csc:xr-task "bgp";
        csc:cli-command "clear bgp bestpath <afi-safi-name> rd <rd> <ipv4-prefix>";
        description
          "re-run BGP bestpath selection.
           Display routes with a specific route distinguisher.
          ";
        input {
          leaf afi-safi-name {
            mandatory true;
            type afi-safi-type;
            description
              "AFI and SAFI";
          }
          leaf rd {
            mandatory true;
            type rd;
            description
              "Route distinguisher";
          }
          leaf ipv4-prefix {
            mandatory true;
            type inet:ipv4-prefix;
            description
              "L2VPN EVPN Prefix";
          }
        }
      }
    }
  }
  augment "/ncs:devices/ncs:device-group/ncs:ned-id/ncs:rpc" {
    container rpc-clear-bgp-bestpath-afi-safi-rd-ipv4-prefix {
      tailf:ncs-device-type "netconf";
      tailf:display-when "/ncs:devices/ncs:device[ncs:name=current()/../../../ncs:member]/ncs:module[ncs:name='Cisco-IOS-XR-ipv4-bgp-act']";
      tailf:action clear-bgp-bestpath-afi-safi-rd-ipv4-prefix {
        tailf:actionpoint ncsproxy {
          tailf:internal;
        }
        csc:xr-task "bgp";
        csc:cli-command "clear bgp bestpath <afi-safi-name> rd <rd> <ipv4-prefix>";
        description
          "re-run BGP bestpath selection.
           Display routes with a specific route distinguisher.
          ";
        input {
          leaf afi-safi-name {
            mandatory true;
            type afi-safi-type;
            description
              "AFI and SAFI";
          }
          leaf rd {
            mandatory true;
            type rd;
            description
              "Route distinguisher";
          }
          leaf ipv4-prefix {
            mandatory true;
            type inet:ipv4-prefix;
            description
              "L2VPN EVPN Prefix";
          }
        }
      }
    }
  }
  augment "/ncs:devices/ncs:device/ncs:rpc" {
    container rpc-clear-bgp-bestpath-afi-safi-bridge-domain-ipv4-prefix {
      tailf:ncs-device-type "netconf";
      tailf:display-when "not(../../ncs:module) or ../../ncs:module[ncs:name='Cisco-IOS-XR-ipv4-bgp-act']";
      tailf:action clear-bgp-bestpath-afi-safi-bridge-domain-ipv4-prefix {
        tailf:actionpoint ncsproxy {
          tailf:internal;
        }
        csc:xr-task "bgp";
        csc:cli-command "clear bgp bestpath <afi-safi-name> bridge-domain <bridge-domain-name> <ipv4-prefix>";
        description
          "re-run BGP bestpath selection.
           Display routes for a specified Bridge Domain.
          ";
        input {
          leaf afi-safi-name {
            mandatory true;
            type afi-safi-type;
            description
              "AFI and SAFI";
          }
          leaf bridge-domain-name {
            mandatory true;
            type string;
            description
              "Bridge Domain";
          }
          leaf ipv4-prefix {
            mandatory true;
            type inet:ipv4-prefix;
            description
              "L2VPN EVPN Prefix";
          }
        }
      }
    }
  }
  augment "/ncs:devices/ncs:device-group/ncs:ned-id/ncs:rpc" {
    container rpc-clear-bgp-bestpath-afi-safi-bridge-domain-ipv4-prefix {
      tailf:ncs-device-type "netconf";
      tailf:display-when "/ncs:devices/ncs:device[ncs:name=current()/../../../ncs:member]/ncs:module[ncs:name='Cisco-IOS-XR-ipv4-bgp-act']";
      tailf:action clear-bgp-bestpath-afi-safi-bridge-domain-ipv4-prefix {
        tailf:actionpoint ncsproxy {
          tailf:internal;
        }
        csc:xr-task "bgp";
        csc:cli-command "clear bgp bestpath <afi-safi-name> bridge-domain <bridge-domain-name> <ipv4-prefix>";
        description
          "re-run BGP bestpath selection.
           Display routes for a specified Bridge Domain.
          ";
        input {
          leaf afi-safi-name {
            mandatory true;
            type afi-safi-type;
            description
              "AFI and SAFI";
          }
          leaf bridge-domain-name {
            mandatory true;
            type string;
            description
              "Bridge Domain";
          }
          leaf ipv4-prefix {
            mandatory true;
            type inet:ipv4-prefix;
            description
              "L2VPN EVPN Prefix";
          }
        }
      }
    }
  }
  augment "/ncs:devices/ncs:device/ncs:rpc" {
    container rpc-clear-bgp-bestpath-afi-safi-sr-policy-prefix {
      tailf:ncs-device-type "netconf";
      tailf:display-when "not(../../ncs:module) or ../../ncs:module[ncs:name='Cisco-IOS-XR-ipv4-bgp-act']";
      tailf:action clear-bgp-bestpath-afi-safi-sr-policy-prefix {
        tailf:actionpoint ncsproxy {
          tailf:internal;
        }
        csc:xr-task "bgp";
        csc:cli-command "clear bgp bestpath <afi-safi-name> <sr-policy-prefix>";
        description
          "re-run BGP bestpath selection.
          ";
        input {
          leaf afi-safi-name {
            mandatory true;
            type afi-safi-type;
            description
              "AFI and SAFI";
          }
          leaf sr-policy-prefix {
            mandatory true;
            type string;
            description
              "SR Policy prefix";
          }
        }
      }
    }
  }
  augment "/ncs:devices/ncs:device-group/ncs:ned-id/ncs:rpc" {
    container rpc-clear-bgp-bestpath-afi-safi-sr-policy-prefix {
      tailf:ncs-device-type "netconf";
      tailf:display-when "/ncs:devices/ncs:device[ncs:name=current()/../../../ncs:member]/ncs:module[ncs:name='Cisco-IOS-XR-ipv4-bgp-act']";
      tailf:action clear-bgp-bestpath-afi-safi-sr-policy-prefix {
        tailf:actionpoint ncsproxy {
          tailf:internal;
        }
        csc:xr-task "bgp";
        csc:cli-command "clear bgp bestpath <afi-safi-name> <sr-policy-prefix>";
        description
          "re-run BGP bestpath selection.
          ";
        input {
          leaf afi-safi-name {
            mandatory true;
            type afi-safi-type;
            description
              "AFI and SAFI";
          }
          leaf sr-policy-prefix {
            mandatory true;
            type string;
            description
              "SR Policy prefix";
          }
        }
      }
    }
  }
  augment "/ncs:devices/ncs:device/ncs:rpc" {
    container rpc-clear-bgp-bestpath-afi-safi {
      tailf:ncs-device-type "netconf";
      tailf:display-when "not(../../ncs:module) or ../../ncs:module[ncs:name='Cisco-IOS-XR-ipv4-bgp-act']";
      tailf:action clear-bgp-bestpath-afi-safi {
        tailf:actionpoint ncsproxy {
          tailf:internal;
        }
        csc:xr-task "bgp";
        csc:cli-command "clear bgp bestpath <afi-safi-name>";
        description
          "re-run BGP bestpath selection.
          ";
        input {
          leaf afi-safi-name {
            mandatory true;
            type afi-safi-type;
            description
              "AFI and SAFI";
          }
        }
      }
    }
  }
  augment "/ncs:devices/ncs:device-group/ncs:ned-id/ncs:rpc" {
    container rpc-clear-bgp-bestpath-afi-safi {
      tailf:ncs-device-type "netconf";
      tailf:display-when "/ncs:devices/ncs:device[ncs:name=current()/../../../ncs:member]/ncs:module[ncs:name='Cisco-IOS-XR-ipv4-bgp-act']";
      tailf:action clear-bgp-bestpath-afi-safi {
        tailf:actionpoint ncsproxy {
          tailf:internal;
        }
        csc:xr-task "bgp";
        csc:cli-command "clear bgp bestpath <afi-safi-name>";
        description
          "re-run BGP bestpath selection.
          ";
        input {
          leaf afi-safi-name {
            mandatory true;
            type afi-safi-type;
            description
              "AFI and SAFI";
          }
        }
      }
    }
  }
  augment "/ncs:devices/ncs:device/ncs:rpc" {
    container rpc-clear-bgp-bestpath-afi-safi-vrf {
      tailf:ncs-device-type "netconf";
      tailf:display-when "not(../../ncs:module) or ../../ncs:module[ncs:name='Cisco-IOS-XR-ipv4-bgp-act']";
      tailf:action clear-bgp-bestpath-afi-safi-vrf {
        tailf:actionpoint ncsproxy {
          tailf:internal;
        }
        csc:xr-task "bgp";
        csc:cli-command "clear bgp bestpath <afi-safi-name> vrf <vrf-name>";
        description
          "re-run BGP bestpath selection.
           Display routes for a specified VRF.
          ";
        input {
          leaf afi-safi-name {
            mandatory true;
            type afi-safi-type;
            description
              "AFI and SAFI";
          }
          leaf vrf-name {
            mandatory true;
            type string;
            description
              "VRF name";
          }
        }
      }
    }
  }
  augment "/ncs:devices/ncs:device-group/ncs:ned-id/ncs:rpc" {
    container rpc-clear-bgp-bestpath-afi-safi-vrf {
      tailf:ncs-device-type "netconf";
      tailf:display-when "/ncs:devices/ncs:device[ncs:name=current()/../../../ncs:member]/ncs:module[ncs:name='Cisco-IOS-XR-ipv4-bgp-act']";
      tailf:action clear-bgp-bestpath-afi-safi-vrf {
        tailf:actionpoint ncsproxy {
          tailf:internal;
        }
        csc:xr-task "bgp";
        csc:cli-command "clear bgp bestpath <afi-safi-name> vrf <vrf-name>";
        description
          "re-run BGP bestpath selection.
           Display routes for a specified VRF.
          ";
        input {
          leaf afi-safi-name {
            mandatory true;
            type afi-safi-type;
            description
              "AFI and SAFI";
          }
          leaf vrf-name {
            mandatory true;
            type string;
            description
              "VRF name";
          }
        }
      }
    }
  }
  augment "/ncs:devices/ncs:device/ncs:rpc" {
    container rpc-clear-bgp-bestpath-afi-safi-rd {
      tailf:ncs-device-type "netconf";
      tailf:display-when "not(../../ncs:module) or ../../ncs:module[ncs:name='Cisco-IOS-XR-ipv4-bgp-act']";
      tailf:action clear-bgp-bestpath-afi-safi-rd {
        tailf:actionpoint ncsproxy {
          tailf:internal;
        }
        csc:xr-task "bgp";
        csc:cli-command "clear bgp bestpath <afi-safi-name> rd <rd>";
        description
          "re-run BGP bestpath selection.
           Display routes with a specific route distinguisher.
          ";
        input {
          leaf afi-safi-name {
            mandatory true;
            type afi-safi-type;
            description
              "AFI and SAFI";
          }
          leaf rd {
            mandatory true;
            type rd;
            description
              "Route distinguisher";
          }
        }
      }
    }
  }
  augment "/ncs:devices/ncs:device-group/ncs:ned-id/ncs:rpc" {
    container rpc-clear-bgp-bestpath-afi-safi-rd {
      tailf:ncs-device-type "netconf";
      tailf:display-when "/ncs:devices/ncs:device[ncs:name=current()/../../../ncs:member]/ncs:module[ncs:name='Cisco-IOS-XR-ipv4-bgp-act']";
      tailf:action clear-bgp-bestpath-afi-safi-rd {
        tailf:actionpoint ncsproxy {
          tailf:internal;
        }
        csc:xr-task "bgp";
        csc:cli-command "clear bgp bestpath <afi-safi-name> rd <rd>";
        description
          "re-run BGP bestpath selection.
           Display routes with a specific route distinguisher.
          ";
        input {
          leaf afi-safi-name {
            mandatory true;
            type afi-safi-type;
            description
              "AFI and SAFI";
          }
          leaf rd {
            mandatory true;
            type rd;
            description
              "Route distinguisher";
          }
        }
      }
    }
  }
  augment "/ncs:devices/ncs:device/ncs:rpc" {
    container rpc-clear-bgp-bestpath-afi-safi-ipv6-prefix {
      tailf:ncs-device-type "netconf";
      tailf:display-when "not(../../ncs:module) or ../../ncs:module[ncs:name='Cisco-IOS-XR-ipv4-bgp-act']";
      tailf:action clear-bgp-bestpath-afi-safi-ipv6-prefix {
        tailf:actionpoint ncsproxy {
          tailf:internal;
        }
        csc:xr-task "bgp";
        csc:cli-command "clear bgp bestpath <afi-safi-name> <ipv6-prefix>";
        description
          "re-run BGP bestpath selection.
          ";
        input {
          leaf afi-safi-name {
            mandatory true;
            type afi-safi-type;
            description
              "AFI and SAFI";
          }
          leaf ipv6-prefix {
            mandatory true;
            type inet:ipv6-prefix;
            description
              "IPv6 network and masklength";
          }
        }
      }
    }
  }
  augment "/ncs:devices/ncs:device-group/ncs:ned-id/ncs:rpc" {
    container rpc-clear-bgp-bestpath-afi-safi-ipv6-prefix {
      tailf:ncs-device-type "netconf";
      tailf:display-when "/ncs:devices/ncs:device[ncs:name=current()/../../../ncs:member]/ncs:module[ncs:name='Cisco-IOS-XR-ipv4-bgp-act']";
      tailf:action clear-bgp-bestpath-afi-safi-ipv6-prefix {
        tailf:actionpoint ncsproxy {
          tailf:internal;
        }
        csc:xr-task "bgp";
        csc:cli-command "clear bgp bestpath <afi-safi-name> <ipv6-prefix>";
        description
          "re-run BGP bestpath selection.
          ";
        input {
          leaf afi-safi-name {
            mandatory true;
            type afi-safi-type;
            description
              "AFI and SAFI";
          }
          leaf ipv6-prefix {
            mandatory true;
            type inet:ipv6-prefix;
            description
              "IPv6 network and masklength";
          }
        }
      }
    }
  }
  augment "/ncs:devices/ncs:device/ncs:rpc" {
    container rpc-clear-bgp-bestpath-afi-safi-ipv6-addr {
      tailf:ncs-device-type "netconf";
      tailf:display-when "not(../../ncs:module) or ../../ncs:module[ncs:name='Cisco-IOS-XR-ipv4-bgp-act']";
      tailf:action clear-bgp-bestpath-afi-safi-ipv6-addr {
        tailf:actionpoint ncsproxy {
          tailf:internal;
        }
        csc:xr-task "bgp";
        csc:cli-command "clear bgp bestpath <afi-safi-name> <ipv6-addr>";
        description
          "re-run BGP bestpath selection.
          ";
        input {
          leaf afi-safi-name {
            mandatory true;
            type afi-safi-type;
            description
              "AFI and SAFI";
          }
          leaf ipv6-addr {
            mandatory true;
            type inet:ipv6-address;
            description
              "IPv6 network";
          }
        }
      }
    }
  }
  augment "/ncs:devices/ncs:device-group/ncs:ned-id/ncs:rpc" {
    container rpc-clear-bgp-bestpath-afi-safi-ipv6-addr {
      tailf:ncs-device-type "netconf";
      tailf:display-when "/ncs:devices/ncs:device[ncs:name=current()/../../../ncs:member]/ncs:module[ncs:name='Cisco-IOS-XR-ipv4-bgp-act']";
      tailf:action clear-bgp-bestpath-afi-safi-ipv6-addr {
        tailf:actionpoint ncsproxy {
          tailf:internal;
        }
        csc:xr-task "bgp";
        csc:cli-command "clear bgp bestpath <afi-safi-name> <ipv6-addr>";
        description
          "re-run BGP bestpath selection.
          ";
        input {
          leaf afi-safi-name {
            mandatory true;
            type afi-safi-type;
            description
              "AFI and SAFI";
          }
          leaf ipv6-addr {
            mandatory true;
            type inet:ipv6-address;
            description
              "IPv6 network";
          }
        }
      }
    }
  }
  augment "/ncs:devices/ncs:device/ncs:rpc" {
    container rpc-clear-bgp-bestpath-afi-safi-ipv6-addr-ipv6-netmask {
      tailf:ncs-device-type "netconf";
      tailf:display-when "not(../../ncs:module) or ../../ncs:module[ncs:name='Cisco-IOS-XR-ipv4-bgp-act']";
      tailf:action clear-bgp-bestpath-afi-safi-ipv6-addr-ipv6-netmask {
        tailf:actionpoint ncsproxy {
          tailf:internal;
        }
        csc:xr-task "bgp";
        csc:cli-command "clear bgp bestpath <afi-safi-name> <ipv6-addr> <ipv6-netmask>";
        description
          "re-run BGP bestpath selection.
          ";
        input {
          leaf afi-safi-name {
            mandatory true;
            type afi-safi-type;
            description
              "AFI and SAFI";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device-group/ncs:ned-id/ncs:rpc" {
    container rpc-clear-bgp-bestpath-afi-safi-ipv6-addr-ipv6-netmask {
      tailf:ncs-device-type "netconf";
      tailf:display-when "/ncs:devices/ncs:device[ncs:name=current()/../../../ncs:member]/ncs:module[ncs:name='Cisco-IOS-XR-ipv4-bgp-act']";
      tailf:action clear-bgp-bestpath-afi-safi-ipv6-addr-ipv6-netmask {
        tailf:actionpoint ncsproxy {
          tailf:internal;
        }
        csc:xr-task "bgp";
        csc:cli-command "clear bgp bestpath <afi-safi-name> <ipv6-addr> <ipv6-netmask>";
        description
          "re-run BGP bestpath selection.
          ";
        input {
          leaf afi-safi-name {
            mandatory true;
            type afi-safi-type;
            description
              "AFI and SAFI";
          }
          leaf ipv6-addr {
            mandatory true;
            type inet:ipv6-address;
            description
              "IPv6 network";
          }
          leaf ipv6-netmask {
            mandatory true;
            type ipv6-netmask;
            description
              "IPv6 mask";
          }
        }
      }
    }
  }
  augment "/ncs:devices/ncs:device/ncs:rpc" {
    container rpc-clear-bgp-bestpath-afi-safi-ipv4-tunnel-network {
      tailf:ncs-device-type "netconf";
      tailf:display-when "not(../../ncs:module) or ../../ncs:module[ncs:name='Cisco-IOS-XR-ipv4-bgp-act']";
      tailf:action clear-bgp-bestpath-afi-safi-ipv4-tunnel-network {
        tailf:actionpoint ncsproxy {
          tailf:internal;
        }
        csc:xr-task "bgp";
        csc:cli-command "clear bgp bestpath <afi-safi-name> <ipv4-tunnel-network>";
        description
          "re-run BGP bestpath selection.
          ";
        input {
          leaf afi-safi-name {
            mandatory true;
            type afi-safi-type;
            description
              "AFI and SAFI";
          }
          leaf ipv4-tunnel-network {
            mandatory true;
            type string;
            description
              "IPv4 Tunnel network <Tunnel-ID>:<IPv4 Address>";
          }
        }
      }
    }
  }
  augment "/ncs:devices/ncs:device-group/ncs:ned-id/ncs:rpc" {
    container rpc-clear-bgp-bestpath-afi-safi-ipv4-tunnel-network {
      tailf:ncs-device-type "netconf";
      tailf:display-when "/ncs:devices/ncs:device[ncs:name=current()/../../../ncs:member]/ncs:module[ncs:name='Cisco-IOS-XR-ipv4-bgp-act']";
      tailf:action clear-bgp-bestpath-afi-safi-ipv4-tunnel-network {
        tailf:actionpoint ncsproxy {
          tailf:internal;
        }
        csc:xr-task "bgp";
        csc:cli-command "clear bgp bestpath <afi-safi-name> <ipv4-tunnel-network>";
        description
          "re-run BGP bestpath selection.
          ";
        input {
          leaf afi-safi-name {
            mandatory true;
            type afi-safi-type;
            description
              "AFI and SAFI";
          }
          leaf ipv4-tunnel-network {
            mandatory true;
            type string;
            description
              "IPv4 Tunnel network <Tunnel-ID>:<IPv4 Address>";
          }
        }
      }
    }
  }
  augment "/ncs:devices/ncs:device/ncs:rpc" {
    container rpc-clear-bgp-bestpath-afi-safi-rt-constraint-network {
      tailf:ncs-device-type "netconf";
      tailf:display-when "not(../../ncs:module) or ../../ncs:module[ncs:name='Cisco-IOS-XR-ipv4-bgp-act']";
      tailf:action clear-bgp-bestpath-afi-safi-rt-constraint-network {
        tailf:actionpoint ncsproxy {
          tailf:internal;
        }
        csc:xr-task "bgp";
        csc:cli-command "clear bgp bestpath <afi-safi-name> <rt-constraint-network>";
        description
          "re-run BGP bestpath selection.
          ";
        input {
          leaf afi-safi-name {
            mandatory true;
            type afi-safi-type;
            description
              "AFI and SAFI";
          }
          leaf rt-constraint-network {
            mandatory true;
            type string;
            description
              "RT-Constraint network";
          }
        }
      }
    }
  }
  augment "/ncs:devices/ncs:device-group/ncs:ned-id/ncs:rpc" {
    container rpc-clear-bgp-bestpath-afi-safi-rt-constraint-network {
      tailf:ncs-device-type "netconf";
      tailf:display-when "/ncs:devices/ncs:device[ncs:name=current()/../../../ncs:member]/ncs:module[ncs:name='Cisco-IOS-XR-ipv4-bgp-act']";
      tailf:action clear-bgp-bestpath-afi-safi-rt-constraint-network {
        tailf:actionpoint ncsproxy {
          tailf:internal;
        }
        csc:xr-task "bgp";
        csc:cli-command "clear bgp bestpath <afi-safi-name> <rt-constraint-network>";
        description
          "re-run BGP bestpath selection.
          ";
        input {
          leaf afi-safi-name {
            mandatory true;
            type afi-safi-type;
            description
              "AFI and SAFI";
          }
          leaf rt-constraint-network {
            mandatory true;
            type string;
            description
              "RT-Constraint network";
          }
        }
      }
    }
  }
  augment "/ncs:devices/ncs:device/ncs:rpc" {
    container rpc-clear-bgp-bestpath-afi-safi-vrf-network {
      tailf:ncs-device-type "netconf";
      tailf:display-when "not(../../ncs:module) or ../../ncs:module[ncs:name='Cisco-IOS-XR-ipv4-bgp-act']";
      tailf:action clear-bgp-bestpath-afi-safi-vrf-network {
        tailf:actionpoint ncsproxy {
          tailf:internal;
        }
        csc:xr-task "bgp";
        csc:cli-command "clear bgp bestpath <afi-safi-name> vrf <vrf-name> <network>";
        description
          "re-run BGP bestpath selection.
           Display routes for a specified VRF.
          ";
        input {
          leaf afi-safi-name {
            mandatory true;
            type afi-safi-type;
            description
              "AFI and SAFI";
          }
          leaf vrf-name {
            mandatory true;
            type string;
            description
              "VRF name";
          }
          leaf network {
            mandatory true;
            type string;
            description
              "Address family modifier specific network";
          }
        }
      }
    }
  }
  augment "/ncs:devices/ncs:device-group/ncs:ned-id/ncs:rpc" {
    container rpc-clear-bgp-bestpath-afi-safi-vrf-network {
      tailf:ncs-device-type "netconf";
      tailf:display-when "/ncs:devices/ncs:device[ncs:name=current()/../../../ncs:member]/ncs:module[ncs:name='Cisco-IOS-XR-ipv4-bgp-act']";
      tailf:action clear-bgp-bestpath-afi-safi-vrf-network {
        tailf:actionpoint ncsproxy {
          tailf:internal;
        }
        csc:xr-task "bgp";
        csc:cli-command "clear bgp bestpath <afi-safi-name> vrf <vrf-name> <network>";
        description
          "re-run BGP bestpath selection.
           Display routes for a specified VRF.
          ";
        input {
          leaf afi-safi-name {
            mandatory true;
            type afi-safi-type;
            description
              "AFI and SAFI";
          }
          leaf vrf-name {
            mandatory true;
            type string;
            description
              "VRF name";
          }
          leaf network {
            mandatory true;
            type string;
            description
              "Address family modifier specific network";
          }
        }
      }
    }
  }
  augment "/ncs:devices/ncs:device/ncs:rpc" {
    container rpc-clear-bgp-bestpath-afi-safi-rd-network {
      tailf:ncs-device-type "netconf";
      tailf:display-when "not(../../ncs:module) or ../../ncs:module[ncs:name='Cisco-IOS-XR-ipv4-bgp-act']";
      tailf:action clear-bgp-bestpath-afi-safi-rd-network {
        tailf:actionpoint ncsproxy {
          tailf:internal;
        }
        csc:xr-task "bgp";
        csc:cli-command "clear bgp bestpath <afi-safi-name> rd <rd> <network>";
        description
          "re-run BGP bestpath selection.
           Display routes with a specific route distinguisher.
          ";
        input {
          leaf afi-safi-name {
            mandatory true;
            type afi-safi-type;
            description
              "AFI and SAFI";
          }
          leaf rd {
            mandatory true;
            type rd;
            description
              "Route distinguisher";
          }
          leaf network {
            mandatory true;
            type string;
            description
              "Address family modifier specific network";
          }
        }
      }
    }
  }
  augment "/ncs:devices/ncs:device-group/ncs:ned-id/ncs:rpc" {
    container rpc-clear-bgp-bestpath-afi-safi-rd-network {
      tailf:ncs-device-type "netconf";
      tailf:display-when "/ncs:devices/ncs:device[ncs:name=current()/../../../ncs:member]/ncs:module[ncs:name='Cisco-IOS-XR-ipv4-bgp-act']";
      tailf:action clear-bgp-bestpath-afi-safi-rd-network {
        tailf:actionpoint ncsproxy {
          tailf:internal;
        }
        csc:xr-task "bgp";
        csc:cli-command "clear bgp bestpath <afi-safi-name> rd <rd> <network>";
        description
          "re-run BGP bestpath selection.
           Display routes with a specific route distinguisher.
          ";
        input {
          leaf afi-safi-name {
            mandatory true;
            type afi-safi-type;
            description
              "AFI and SAFI";
          }
          leaf rd {
            mandatory true;
            type rd;
            description
              "Route distinguisher";
          }
          leaf network {
            mandatory true;
            type string;
            description
              "Address family modifier specific network";
          }
        }
      }
    }
  }
  augment "/ncs:devices/ncs:device/ncs:rpc" {
    container rpc-clear-bgp-bestpath-afi-safi-network {
      tailf:ncs-device-type "netconf";
      tailf:display-when "not(../../ncs:module) or ../../ncs:module[ncs:name='Cisco-IOS-XR-ipv4-bgp-act']";
      tailf:action clear-bgp-bestpath-afi-safi-network {
        tailf:actionpoint ncsproxy {
          tailf:internal;
        }
        csc:xr-task "bgp";
        csc:cli-command "clear bgp bestpath <afi-safi-name> <network>";
        description
          "re-run BGP bestpath selection.
          ";
        input {
          leaf afi-safi-name {
            mandatory true;
            type afi-safi-type;
            description
              "AFI and SAFI";
          }
          leaf network {
            mandatory true;
            type string;
            description
              "Address family modifier specific network";
          }
        }
      }
    }
  }
  augment "/ncs:devices/ncs:device-group/ncs:ned-id/ncs:rpc" {
    container rpc-clear-bgp-bestpath-afi-safi-network {
      tailf:ncs-device-type "netconf";
      tailf:display-when "/ncs:devices/ncs:device[ncs:name=current()/../../../ncs:member]/ncs:module[ncs:name='Cisco-IOS-XR-ipv4-bgp-act']";
      tailf:action clear-bgp-bestpath-afi-safi-network {
        tailf:actionpoint ncsproxy {
          tailf:internal;
        }
        csc:xr-task "bgp";
        csc:cli-command "clear bgp bestpath <afi-safi-name> <network>";
        description
          "re-run BGP bestpath selection.
          ";
        input {
          leaf afi-safi-name {
            mandatory true;
            type afi-safi-type;
            description
              "AFI and SAFI";
          }
          leaf network {
            mandatory true;
            type string;
            description
              "Address family modifier specific network";
          }
        }
      }
    }
  }
  augment "/ncs:devices/ncs:device/ncs:rpc" {
    container rpc-clear-bgp-bestpath-afi-safi-vrf-ipv4-addr {
      tailf:ncs-device-type "netconf";
      tailf:display-when "not(../../ncs:module) or ../../ncs:module[ncs:name='Cisco-IOS-XR-ipv4-bgp-act']";
      tailf:action clear-bgp-bestpath-afi-safi-vrf-ipv4-addr {
        tailf:actionpoint ncsproxy {
          tailf:internal;
        }
        csc:xr-task "bgp";
        csc:cli-command "clear bgp bestpath <afi-safi-name> vrf <vrf-name> <ipv4-addr>";
        description
          "re-run BGP bestpath selection.
           Display routes for a specified VRF.
          ";
        input {
          leaf afi-safi-name {
            mandatory true;
            type afi-safi-type;
            description
              "AFI and SAFI";
          }
          leaf vrf-name {
            mandatory true;
            type string;
            description
              "VRF name";
          }
          leaf ipv4-addr {
            mandatory true;
            type inet:ipv4-address;
            description
              "IPv4 MDT network";
          }
        }
      }
    }
  }
  augment "/ncs:devices/ncs:device-group/ncs:ned-id/ncs:rpc" {
    container rpc-clear-bgp-bestpath-afi-safi-vrf-ipv4-addr {
      tailf:ncs-device-type "netconf";
      tailf:display-when "/ncs:devices/ncs:device[ncs:name=current()/../../../ncs:member]/ncs:module[ncs:name='Cisco-IOS-XR-ipv4-bgp-act']";
      tailf:action clear-bgp-bestpath-afi-safi-vrf-ipv4-addr {
        tailf:actionpoint ncsproxy {
          tailf:internal;
        }
        csc:xr-task "bgp";
        csc:cli-command "clear bgp bestpath <afi-safi-name> vrf <vrf-name> <ipv4-addr>";
        description
          "re-run BGP bestpath selection.
           Display routes for a specified VRF.
          ";
        input {
          leaf afi-safi-name {
            mandatory true;
            type afi-safi-type;
            description
              "AFI and SAFI";
          }
          leaf vrf-name {
            mandatory true;
            type string;
            description
              "VRF name";
          }
          leaf ipv4-addr {
            mandatory true;
            type inet:ipv4-address;
            description
              "IPv4 MDT network";
          }
        }
      }
    }
  }
  augment "/ncs:devices/ncs:device/ncs:rpc" {
    container rpc-clear-bgp-bestpath-afi-safi-rd-ipv4-addr {
      tailf:ncs-device-type "netconf";
      tailf:display-when "not(../../ncs:module) or ../../ncs:module[ncs:name='Cisco-IOS-XR-ipv4-bgp-act']";
      tailf:action clear-bgp-bestpath-afi-safi-rd-ipv4-addr {
        tailf:actionpoint ncsproxy {
          tailf:internal;
        }
        csc:xr-task "bgp";
        csc:cli-command "clear bgp bestpath <afi-safi-name> rd <rd> <ipv4-addr>";
        description
          "re-run BGP bestpath selection.
           Display routes with a specific route distinguisher.
          ";
        input {
          leaf afi-safi-name {
            mandatory true;
            type afi-safi-type;
            description
              "AFI and SAFI";
          }
          leaf rd {
            mandatory true;
            type rd;
            description
              "Route distinguisher";
          }
          leaf ipv4-addr {
            mandatory true;
            type inet:ipv4-address;
            description
              "IPv4 MDT network";
          }
        }
      }
    }
  }
  augment "/ncs:devices/ncs:device-group/ncs:ned-id/ncs:rpc" {
    container rpc-clear-bgp-bestpath-afi-safi-rd-ipv4-addr {
      tailf:ncs-device-type "netconf";
      tailf:display-when "/ncs:devices/ncs:device[ncs:name=current()/../../../ncs:member]/ncs:module[ncs:name='Cisco-IOS-XR-ipv4-bgp-act']";
      tailf:action clear-bgp-bestpath-afi-safi-rd-ipv4-addr {
        tailf:actionpoint ncsproxy {
          tailf:internal;
        }
        csc:xr-task "bgp";
        csc:cli-command "clear bgp bestpath <afi-safi-name> rd <rd> <ipv4-addr>";
        description
          "re-run BGP bestpath selection.
           Display routes with a specific route distinguisher.
          ";
        input {
          leaf afi-safi-name {
            mandatory true;
            type afi-safi-type;
            description
              "AFI and SAFI";
          }
          leaf rd {
            mandatory true;
            type rd;
            description
              "Route distinguisher";
          }
          leaf ipv4-addr {
            mandatory true;
            type inet:ipv4-address;
            description
              "IPv4 MDT network";
          }
        }
      }
    }
  }
  augment "/ncs:devices/ncs:device/ncs:rpc" {
    container rpc-clear-bgp-bestpath-afi-safi-ipv4-prefix {
      tailf:ncs-device-type "netconf";
      tailf:display-when "not(../../ncs:module) or ../../ncs:module[ncs:name='Cisco-IOS-XR-ipv4-bgp-act']";
      tailf:action clear-bgp-bestpath-afi-safi-ipv4-prefix {
        tailf:actionpoint ncsproxy {
          tailf:internal;
        }
        csc:xr-task "bgp";
        csc:cli-command "clear bgp bestpath <afi-safi-name> <ipv4-prefix>";
        description
          "re-run BGP bestpath selection.
          ";
        input {
          leaf afi-safi-name {
            mandatory true;
            type afi-safi-type;
            description
              "AFI and SAFI";
          }
          leaf ipv4-prefix {
            mandatory true;
            type inet:ipv4-prefix;
            description
              "IPv4 network and masklength";
          }
        }
      }
    }
  }
  augment "/ncs:devices/ncs:device-group/ncs:ned-id/ncs:rpc" {
    container rpc-clear-bgp-bestpath-afi-safi-ipv4-prefix {
      tailf:ncs-device-type "netconf";
      tailf:display-when "/ncs:devices/ncs:device[ncs:name=current()/../../../ncs:member]/ncs:module[ncs:name='Cisco-IOS-XR-ipv4-bgp-act']";
      tailf:action clear-bgp-bestpath-afi-safi-ipv4-prefix {
        tailf:actionpoint ncsproxy {
          tailf:internal;
        }
        csc:xr-task "bgp";
        csc:cli-command "clear bgp bestpath <afi-safi-name> <ipv4-prefix>";
        description
          "re-run BGP bestpath selection.
          ";
        input {
          leaf afi-safi-name {
            mandatory true;
            type afi-safi-type;
            description
              "AFI and SAFI";
          }
          leaf ipv4-prefix {
            mandatory true;
            type inet:ipv4-prefix;
            description
              "IPv4 network and masklength";
          }
        }
      }
    }
  }
  augment "/ncs:devices/ncs:device/ncs:rpc" {
    container rpc-clear-bgp-bestpath-afi-safi-ipv4-addr {
      tailf:ncs-device-type "netconf";
      tailf:display-when "not(../../ncs:module) or ../../ncs:module[ncs:name='Cisco-IOS-XR-ipv4-bgp-act']";
      tailf:action clear-bgp-bestpath-afi-safi-ipv4-addr {
        tailf:actionpoint ncsproxy {
          tailf:internal;
        }
        csc:xr-task "bgp";
        csc:cli-command "clear bgp bestpath <afi-safi-name> <ipv4-addr>";
        description
          "re-run BGP bestpath selection.
          ";
        input {
          leaf afi-safi-name {
            mandatory true;
            type afi-safi-type;
            description
              "AFI and SAFI";
          }
          leaf ipv4-addr {
            mandatory true;
            type inet:ipv4-address;
            description
              "IPv4 network";
          }
        }
      }
    }
  }
  augment "/ncs:devices/ncs:device-group/ncs:ned-id/ncs:rpc" {
    container rpc-clear-bgp-bestpath-afi-safi-ipv4-addr {
      tailf:ncs-device-type "netconf";
      tailf:display-when "/ncs:devices/ncs:device[ncs:name=current()/../../../ncs:member]/ncs:module[ncs:name='Cisco-IOS-XR-ipv4-bgp-act']";
      tailf:action clear-bgp-bestpath-afi-safi-ipv4-addr {
        tailf:actionpoint ncsproxy {
          tailf:internal;
        }
        csc:xr-task "bgp";
        csc:cli-command "clear bgp bestpath <afi-safi-name> <ipv4-addr>";
        description
          "re-run BGP bestpath selection.
          ";
        input {
          leaf afi-safi-name {
            mandatory true;
            type afi-safi-type;
            description
              "AFI and SAFI";
          }
          leaf ipv4-addr {
            mandatory true;
            type inet:ipv4-address;
            description
              "IPv4 network";
          }
        }
      }
    }
  }
  augment "/ncs:devices/ncs:device/ncs:rpc" {
    container rpc-clear-bgp-bestpath-afi-safi-ipv4-addr-ipv4-mask {
      tailf:ncs-device-type "netconf";
      tailf:display-when "not(../../ncs:module) or ../../ncs:module[ncs:name='Cisco-IOS-XR-ipv4-bgp-act']";
      tailf:action clear-bgp-bestpath-afi-safi-ipv4-addr-ipv4-mask {
        tailf:actionpoint ncsproxy {
          tailf:internal;
        }
        csc:xr-task "bgp";
        csc:cli-command "clear bgp bestpath <afi-safi-name> <ipv4-addr> <ipv4-mask>";
        description
          "re-run BGP bestpath selection.
          ";
        input {
          leaf afi-safi-name {
            mandatory true;
            type afi-safi-type;
            description
              "AFI and SAFI";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device-group/ncs:ned-id/ncs:rpc" {
    container rpc-clear-bgp-bestpath-afi-safi-ipv4-addr-ipv4-mask {
      tailf:ncs-device-type "netconf";
      tailf:display-when "/ncs:devices/ncs:device[ncs:name=current()/../../../ncs:member]/ncs:module[ncs:name='Cisco-IOS-XR-ipv4-bgp-act']";
      tailf:action clear-bgp-bestpath-afi-safi-ipv4-addr-ipv4-mask {
        tailf:actionpoint ncsproxy {
          tailf:internal;
        }
        csc:xr-task "bgp";
        csc:cli-command "clear bgp bestpath <afi-safi-name> <ipv4-addr> <ipv4-mask>";
        description
          "re-run BGP bestpath selection.
          ";
        input {
          leaf afi-safi-name {
            mandatory true;
            type afi-safi-type;
            description
              "AFI and SAFI";
          }
          leaf ipv4-addr {
            mandatory true;
            type inet:ipv4-address;
            description
              "IPv4 network";
          }
          leaf ipv4-mask {
            mandatory true;
            type ipv4-netmask;
            description
              "IPv4 mask";
          }
        }
      }
    }
  }
  augment "/ncs:devices/ncs:device/ncs:rpc" {
    container rpc-clear-bgp-bestpath-afi-safi-rd-ip-prefix {
      tailf:ncs-device-type "netconf";
      tailf:display-when "not(../../ncs:module) or ../../ncs:module[ncs:name='Cisco-IOS-XR-ipv4-bgp-act']";
      tailf:action clear-bgp-bestpath-afi-safi-rd-ip-prefix {
        tailf:actionpoint ncsproxy {
          tailf:internal;
        }
        csc:xr-task "bgp";
        csc:cli-command "clear bgp bestpath <afi-safi-name> rd <rd> <ip-prefix>";
        description
          "re-run BGP bestpath selection.
           Display routes with a specific route distinguisher.
          ";
        input {
          leaf afi-safi-name {
            mandatory true;
            type afi-safi-type;
            description
              "AFI and SAFI";
          }
          leaf rd {
            mandatory true;
            type rd;
            description
              "Route distinguisher";
          }
          leaf ip-prefix {
            mandatory true;
            type inet:ip-prefix;
            description
              "Network and masklength";
          }
        }
      }
    }
  }
  augment "/ncs:devices/ncs:device-group/ncs:ned-id/ncs:rpc" {
    container rpc-clear-bgp-bestpath-afi-safi-rd-ip-prefix {
      tailf:ncs-device-type "netconf";
      tailf:display-when "/ncs:devices/ncs:device[ncs:name=current()/../../../ncs:member]/ncs:module[ncs:name='Cisco-IOS-XR-ipv4-bgp-act']";
      tailf:action clear-bgp-bestpath-afi-safi-rd-ip-prefix {
        tailf:actionpoint ncsproxy {
          tailf:internal;
        }
        csc:xr-task "bgp";
        csc:cli-command "clear bgp bestpath <afi-safi-name> rd <rd> <ip-prefix>";
        description
          "re-run BGP bestpath selection.
           Display routes with a specific route distinguisher.
          ";
        input {
          leaf afi-safi-name {
            mandatory true;
            type afi-safi-type;
            description
              "AFI and SAFI";
          }
          leaf rd {
            mandatory true;
            type rd;
            description
              "Route distinguisher";
          }
          leaf ip-prefix {
            mandatory true;
            type inet:ip-prefix;
            description
              "Network and masklength";
          }
        }
      }
    }
  }
  augment "/ncs:devices/ncs:device/ncs:rpc" {
    container rpc-clear-bgp-bestpath-afi-safi-rd-ip-addr {
      tailf:ncs-device-type "netconf";
      tailf:display-when "not(../../ncs:module) or ../../ncs:module[ncs:name='Cisco-IOS-XR-ipv4-bgp-act']";
      tailf:action clear-bgp-bestpath-afi-safi-rd-ip-addr {
        tailf:actionpoint ncsproxy {
          tailf:internal;
        }
        csc:xr-task "bgp";
        csc:cli-command "clear bgp bestpath <afi-safi-name> rd <rd> <ip-addr>";
        description
          "re-run BGP bestpath selection.
           Display routes with a specific route distinguisher.
          ";
        input {
          leaf afi-safi-name {
            mandatory true;
            type afi-safi-type;
            description
              "AFI and SAFI";
          }
          leaf rd {
            mandatory true;
            type rd;
            description
              "Route distinguisher";
          }
          leaf ip-addr {
            mandatory true;
            type inet:ip-address;
            description
              "Network";
          }
        }
      }
    }
  }
  augment "/ncs:devices/ncs:device-group/ncs:ned-id/ncs:rpc" {
    container rpc-clear-bgp-bestpath-afi-safi-rd-ip-addr {
      tailf:ncs-device-type "netconf";
      tailf:display-when "/ncs:devices/ncs:device[ncs:name=current()/../../../ncs:member]/ncs:module[ncs:name='Cisco-IOS-XR-ipv4-bgp-act']";
      tailf:action clear-bgp-bestpath-afi-safi-rd-ip-addr {
        tailf:actionpoint ncsproxy {
          tailf:internal;
        }
        csc:xr-task "bgp";
        csc:cli-command "clear bgp bestpath <afi-safi-name> rd <rd> <ip-addr>";
        description
          "re-run BGP bestpath selection.
           Display routes with a specific route distinguisher.
          ";
        input {
          leaf afi-safi-name {
            mandatory true;
            type afi-safi-type;
            description
              "AFI and SAFI";
          }
          leaf rd {
            mandatory true;
            type rd;
            description
              "Route distinguisher";
          }
          leaf ip-addr {
            mandatory true;
            type inet:ip-address;
            description
              "Network";
          }
        }
      }
    }
  }
  augment "/ncs:devices/ncs:device/ncs:rpc" {
    container rpc-clear-bgp-bestpath-afi-safi-rd-ip-addr-ip-netmask {
      tailf:ncs-device-type "netconf";
      tailf:display-when "not(../../ncs:module) or ../../ncs:module[ncs:name='Cisco-IOS-XR-ipv4-bgp-act']";
      tailf:action clear-bgp-bestpath-afi-safi-rd-ip-addr-ip-netmask {
        tailf:actionpoint ncsproxy {
          tailf:internal;
        }
        csc:xr-task "bgp";
        csc:cli-command "clear bgp bestpath <afi-safi-name> rd <rd> <ip-addr> <ip-netmask>";
        description
          "re-run BGP bestpath selection.
           Display routes with a specific route distinguisher.
          ";
        input {
          leaf afi-safi-name {
            mandatory true;
            type afi-safi-type;
            description
              "AFI and SAFI";
          }
          leaf rd {
            mandatory true;
            type rd;
            description
              "Route distinguisher";
          }
          leaf ip-addr {
            mandatory true;
            type inet:ip-address;
            description
              "Network";
          }
          leaf ip-netmask {
            mandatory true;
            type ip-netmask;
            description
              "Mask";
          }
        }
      }
    }
  }
  augment "/ncs:devices/ncs:device-group/ncs:ned-id/ncs:rpc" {
    container rpc-clear-bgp-bestpath-afi-safi-rd-ip-addr-ip-netmask {
      tailf:ncs-device-type "netconf";
      tailf:display-when "/ncs:devices/ncs:device[ncs:name=current()/../../../ncs:member]/ncs:module[ncs:name='Cisco-IOS-XR-ipv4-bgp-act']";
      tailf:action clear-bgp-bestpath-afi-safi-rd-ip-addr-ip-netmask {
        tailf:actionpoint ncsproxy {
          tailf:internal;
        }
        csc:xr-task "bgp";
        csc:cli-command "clear bgp bestpath <afi-safi-name> rd <rd> <ip-addr> <ip-netmask>";
        description
          "re-run BGP bestpath selection.
           Display routes with a specific route distinguisher.
          ";
        input {
          leaf afi-safi-name {
            mandatory true;
            type afi-safi-type;
            description
              "AFI and SAFI";
          }
          leaf rd {
            mandatory true;
            type rd;
            description
              "Route distinguisher";
          }
          leaf ip-addr {
            mandatory true;
            type inet:ip-address;
            description
              "Network";
          }
          leaf ip-netmask {
            mandatory true;
            type ip-netmask;
            description
              "Mask";
          }
        }
      }
    }
  }
  augment "/ncs:devices/ncs:device/ncs:rpc" {
    container rpc-clear-bgp-bestpath-afi-safi-bridge-domain-ip-prefix {
      tailf:ncs-device-type "netconf";
      tailf:display-when "not(../../ncs:module) or ../../ncs:module[ncs:name='Cisco-IOS-XR-ipv4-bgp-act']";
      tailf:action clear-bgp-bestpath-afi-safi-bridge-domain-ip-prefix {
        tailf:actionpoint ncsproxy {
          tailf:internal;
        }
        csc:xr-task "bgp";
        csc:cli-command "clear bgp bestpath <afi-safi-name> bridge-domain <bridge-domain-name> <ip-prefix>";
        description
          "re-run BGP bestpath selection.
           Display routes for a specified Bridge Domain.
          ";
        input {
          leaf afi-safi-name {
            mandatory true;
            type afi-safi-type;
            description
              "AFI and SAFI";
          }
          leaf bridge-domain-name {
            mandatory true;
            type string;
            description
              "Bridge Domain";
          }
          leaf ip-prefix {
            mandatory true;
            type inet:ip-prefix;
            description
              "Network and masklength";
          }
        }
      }
    }
  }
  augment "/ncs:devices/ncs:device-group/ncs:ned-id/ncs:rpc" {
    container rpc-clear-bgp-bestpath-afi-safi-bridge-domain-ip-prefix {
      tailf:ncs-device-type "netconf";
      tailf:display-when "/ncs:devices/ncs:device[ncs:name=current()/../../../ncs:member]/ncs:module[ncs:name='Cisco-IOS-XR-ipv4-bgp-act']";
      tailf:action clear-bgp-bestpath-afi-safi-bridge-domain-ip-prefix {
        tailf:actionpoint ncsproxy {
          tailf:internal;
        }
        csc:xr-task "bgp";
        csc:cli-command "clear bgp bestpath <afi-safi-name> bridge-domain <bridge-domain-name> <ip-prefix>";
        description
          "re-run BGP bestpath selection.
           Display routes for a specified Bridge Domain.
          ";
        input {
          leaf afi-safi-name {
            mandatory true;
            type afi-safi-type;
            description
              "AFI and SAFI";
          }
          leaf bridge-domain-name {
            mandatory true;
            type string;
            description
              "Bridge Domain";
          }
          leaf ip-prefix {
            mandatory true;
            type inet:ip-prefix;
            description
              "Network and masklength";
          }
        }
      }
    }
  }
  augment "/ncs:devices/ncs:device/ncs:rpc" {
    container rpc-clear-bgp-bestpath-afi-safi-bridge-domain-ip-addr {
      tailf:ncs-device-type "netconf";
      tailf:display-when "not(../../ncs:module) or ../../ncs:module[ncs:name='Cisco-IOS-XR-ipv4-bgp-act']";
      tailf:action clear-bgp-bestpath-afi-safi-bridge-domain-ip-addr {
        tailf:actionpoint ncsproxy {
          tailf:internal;
        }
        csc:xr-task "bgp";
        csc:cli-command "clear bgp bestpath <afi-safi-name> bridge-domain <bridge-domain-name> <ip-addr>";
        description
          "re-run BGP bestpath selection.
           Display routes for a specified Bridge Domain.
          ";
        input {
          leaf afi-safi-name {
            mandatory true;
            type afi-safi-type;
            description
              "AFI and SAFI";
          }
          leaf bridge-domain-name {
            mandatory true;
            type string;
            description
              "Bridge Domain";
          }
          leaf ip-addr {
            mandatory true;
            type inet:ip-address;
            description
              "Network";
          }
        }
      }
    }
  }
  augment "/ncs:devices/ncs:device-group/ncs:ned-id/ncs:rpc" {
    container rpc-clear-bgp-bestpath-afi-safi-bridge-domain-ip-addr {
      tailf:ncs-device-type "netconf";
      tailf:display-when "/ncs:devices/ncs:device[ncs:name=current()/../../../ncs:member]/ncs:module[ncs:name='Cisco-IOS-XR-ipv4-bgp-act']";
      tailf:action clear-bgp-bestpath-afi-safi-bridge-domain-ip-addr {
        tailf:actionpoint ncsproxy {
          tailf:internal;
        }
        csc:xr-task "bgp";
        csc:cli-command "clear bgp bestpath <afi-safi-name> bridge-domain <bridge-domain-name> <ip-addr>";
        description
          "re-run BGP bestpath selection.
           Display routes for a specified Bridge Domain.
          ";
        input {
          leaf afi-safi-name {
            mandatory true;
            type afi-safi-type;
            description
              "AFI and SAFI";
          }
          leaf bridge-domain-name {
            mandatory true;
            type string;
            description
              "Bridge Domain";
          }
          leaf ip-addr {
            mandatory true;
            type inet:ip-address;
            description
              "Network";
          }
        }
      }
    }
  }
  augment "/ncs:devices/ncs:device/ncs:rpc" {
    container rpc-clear-bgp-bestpath-afi-safi-bridge-domain-ip-addr-ip-netmask {
      tailf:ncs-device-type "netconf";
      tailf:display-when "not(../../ncs:module) or ../../ncs:module[ncs:name='Cisco-IOS-XR-ipv4-bgp-act']";
      tailf:action clear-bgp-bestpath-afi-safi-bridge-domain-ip-addr-ip-netmask {
        tailf:actionpoint ncsproxy {
          tailf:internal;
        }
        csc:xr-task "bgp";
        csc:cli-command "clear bgp bestpath <afi-safi-name> bridge-domain <bridge-domain-name> <ip-addr> <ip-netmask>";
        description
          "re-run BGP bestpath selection.
           Display routes for a specified Bridge Domain.
          ";
        input {
          leaf afi-safi-name {
            mandatory true;
            type afi-safi-type;
            description
              "AFI and SAFI";
          }
          leaf bridge-domain-name {
            mandatory true;
            type string;
            description
              "Bridge Domain";
          }
          leaf ip-addr {
            mandatory true;
            type inet:ip-address;
            description
              "Network";
          }
          leaf ip-netmask {
            mandatory true;
            type ip-netmask;
            description
              "Mask";
          }
        }
      }
    }
  }
  augment "/ncs:devices/ncs:device-group/ncs:ned-id/ncs:rpc" {
    container rpc-clear-bgp-bestpath-afi-safi-bridge-domain-ip-addr-ip-netmask {
      tailf:ncs-device-type "netconf";
      tailf:display-when "/ncs:devices/ncs:device[ncs:name=current()/../../../ncs:member]/ncs:module[ncs:name='Cisco-IOS-XR-ipv4-bgp-act']";
      tailf:action clear-bgp-bestpath-afi-safi-bridge-domain-ip-addr-ip-netmask {
        tailf:actionpoint ncsproxy {
          tailf:internal;
        }
        csc:xr-task "bgp";
        csc:cli-command "clear bgp bestpath <afi-safi-name> bridge-domain <bridge-domain-name> <ip-addr> <ip-netmask>";
        description
          "re-run BGP bestpath selection.
           Display routes for a specified Bridge Domain.
          ";
        input {
          leaf afi-safi-name {
            mandatory true;
            type afi-safi-type;
            description
              "AFI and SAFI";
          }
          leaf bridge-domain-name {
            mandatory true;
            type string;
            description
              "Bridge Domain";
          }
          leaf ip-addr {
            mandatory true;
            type inet:ip-address;
            description
              "Network";
          }
          leaf ip-netmask {
            mandatory true;
            type ip-netmask;
            description
              "Mask";
          }
        }
      }
    }
  }
  augment "/ncs:devices/ncs:device/ncs:rpc" {
    container rpc-clear-bgp-bestpath-afi-safi-ip-prefix {
      tailf:ncs-device-type "netconf";
      tailf:display-when "not(../../ncs:module) or ../../ncs:module[ncs:name='Cisco-IOS-XR-ipv4-bgp-act']";
      tailf:action clear-bgp-bestpath-afi-safi-ip-prefix {
        tailf:actionpoint ncsproxy {
          tailf:internal;
        }
        csc:xr-task "bgp";
        csc:cli-command "clear bgp bestpath <afi-safi-name> <ip-prefix>";
        description
          "re-run BGP bestpath selection.
          ";
        input {
          leaf afi-safi-name {
            mandatory true;
            type afi-safi-type;
            description
              "AFI and SAFI";
          }
          leaf ip-prefix {
            mandatory true;
            type inet:ip-prefix;
            description
              "Network and masklength";
          }
        }
      }
    }
  }
  augment "/ncs:devices/ncs:device-group/ncs:ned-id/ncs:rpc" {
    container rpc-clear-bgp-bestpath-afi-safi-ip-prefix {
      tailf:ncs-device-type "netconf";
      tailf:display-when "/ncs:devices/ncs:device[ncs:name=current()/../../../ncs:member]/ncs:module[ncs:name='Cisco-IOS-XR-ipv4-bgp-act']";
      tailf:action clear-bgp-bestpath-afi-safi-ip-prefix {
        tailf:actionpoint ncsproxy {
          tailf:internal;
        }
        csc:xr-task "bgp";
        csc:cli-command "clear bgp bestpath <afi-safi-name> <ip-prefix>";
        description
          "re-run BGP bestpath selection.
          ";
        input {
          leaf afi-safi-name {
            mandatory true;
            type afi-safi-type;
            description
              "AFI and SAFI";
          }
          leaf ip-prefix {
            mandatory true;
            type inet:ip-prefix;
            description
              "Network and masklength";
          }
        }
      }
    }
  }
  augment "/ncs:devices/ncs:device/ncs:rpc" {
    container rpc-clear-bgp-bestpath-afi-safi-ip-addr {
      tailf:ncs-device-type "netconf";
      tailf:display-when "not(../../ncs:module) or ../../ncs:module[ncs:name='Cisco-IOS-XR-ipv4-bgp-act']";
      tailf:action clear-bgp-bestpath-afi-safi-ip-addr {
        tailf:actionpoint ncsproxy {
          tailf:internal;
        }
        csc:xr-task "bgp";
        csc:cli-command "clear bgp bestpath <afi-safi-name> <ip-addr>";
        description
          "re-run BGP bestpath selection.
          ";
        input {
          leaf afi-safi-name {
            mandatory true;
            type afi-safi-type;
            description
              "AFI and SAFI";
          }
          leaf ip-addr {
            mandatory true;
            type inet:ip-address;
            description
              "Network";
          }
        }
      }
    }
  }
  augment "/ncs:devices/ncs:device-group/ncs:ned-id/ncs:rpc" {
    container rpc-clear-bgp-bestpath-afi-safi-ip-addr {
      tailf:ncs-device-type "netconf";
      tailf:display-when "/ncs:devices/ncs:device[ncs:name=current()/../../../ncs:member]/ncs:module[ncs:name='Cisco-IOS-XR-ipv4-bgp-act']";
      tailf:action clear-bgp-bestpath-afi-safi-ip-addr {
        tailf:actionpoint ncsproxy {
          tailf:internal;
        }
        csc:xr-task "bgp";
        csc:cli-command "clear bgp bestpath <afi-safi-name> <ip-addr>";
        description
          "re-run BGP bestpath selection.
          ";
        input {
          leaf afi-safi-name {
            mandatory true;
            type afi-safi-type;
            description
              "AFI and SAFI";
          }
          leaf ip-addr {
            mandatory true;
            type inet:ip-address;
            description
              "Network";
          }
        }
      }
    }
  }
  augment "/ncs:devices/ncs:device/ncs:rpc" {
    container rpc-clear-bgp-bestpath-afi-safi-ip-addr-ip-netmask {
      tailf:ncs-device-type "netconf";
      tailf:display-when "not(../../ncs:module) or ../../ncs:module[ncs:name='Cisco-IOS-XR-ipv4-bgp-act']";
      tailf:action clear-bgp-bestpath-afi-safi-ip-addr-ip-netmask {
        tailf:actionpoint ncsproxy {
          tailf:internal;
        }
        csc:xr-task "bgp";
        csc:cli-command "clear bgp bestpath <afi-safi-name> <ip-addr> <ip-netmask>";
        description
          "re-run BGP bestpath selection.
          ";
        input {
          leaf afi-safi-name {
            mandatory true;
            type afi-safi-type;
            description
              "AFI and SAFI";
          }
          leaf ip-addr {
            mandatory true;
            type inet:ip-address;
            description
              "Network";
          }
          leaf ip-netmask {
            mandatory true;
            type ip-netmask;
            description
              "Mask";
          }
        }
      }
    }
  }
  augment "/ncs:devices/ncs:device-group/ncs:ned-id/ncs:rpc" {
    container rpc-clear-bgp-bestpath-afi-safi-ip-addr-ip-netmask {
      tailf:ncs-device-type "netconf";
      tailf:display-when "/ncs:devices/ncs:device[ncs:name=current()/../../../ncs:member]/ncs:module[ncs:name='Cisco-IOS-XR-ipv4-bgp-act']";
      tailf:action clear-bgp-bestpath-afi-safi-ip-addr-ip-netmask {
        tailf:actionpoint ncsproxy {
          tailf:internal;
        }
        csc:xr-task "bgp";
        csc:cli-command "clear bgp bestpath <afi-safi-name> <ip-addr> <ip-netmask>";
        description
          "re-run BGP bestpath selection.
          ";
        input {
          leaf afi-safi-name {
            mandatory true;
            type afi-safi-type;
            description
              "AFI and SAFI";
          }
          leaf ip-addr {
            mandatory true;
            type inet:ip-address;
            description
              "Network";
          }
          leaf ip-netmask {
            mandatory true;
            type ip-netmask;
            description
              "Mask";
          }
        }
      }
    }
  }
  augment "/ncs:devices/ncs:device/ncs:rpc" {
    container rpc-clear-bgp-bestpath-ip-prefix {
      tailf:ncs-device-type "netconf";
      tailf:display-when "not(../../ncs:module) or ../../ncs:module[ncs:name='Cisco-IOS-XR-ipv4-bgp-act']";
      tailf:action clear-bgp-bestpath-ip-prefix {
        tailf:actionpoint ncsproxy {
          tailf:internal;
        }
        csc:xr-task "bgp";
        csc:cli-command "clear bgp bestpath <ip-prefix>";
        description
          "re-run BGP bestpath selection.
          ";
        input {
          leaf ip-prefix {
            mandatory true;
            type inet:ip-prefix;
            description
              "Network and masklength";
          }
        }
      }
    }
  }
  augment "/ncs:devices/ncs:device-group/ncs:ned-id/ncs:rpc" {
    container rpc-clear-bgp-bestpath-ip-prefix {
      tailf:ncs-device-type "netconf";
      tailf:display-when "/ncs:devices/ncs:device[ncs:name=current()/../../../ncs:member]/ncs:module[ncs:name='Cisco-IOS-XR-ipv4-bgp-act']";
      tailf:action clear-bgp-bestpath-ip-prefix {
        tailf:actionpoint ncsproxy {
          tailf:internal;
        }
        csc:xr-task "bgp";
        csc:cli-command "clear bgp bestpath <ip-prefix>";
        description
          "re-run BGP bestpath selection.
          ";
        input {
          leaf ip-prefix {
            mandatory true;
            type inet:ip-prefix;
            description
              "Network and masklength";
          }
        }
      }
    }
  }
  augment "/ncs:devices/ncs:device/ncs:rpc" {
    container rpc-clear-bgp-bestpath-ip-addr {
      tailf:ncs-device-type "netconf";
      tailf:display-when "not(../../ncs:module) or ../../ncs:module[ncs:name='Cisco-IOS-XR-ipv4-bgp-act']";
      tailf:action clear-bgp-bestpath-ip-addr {
        tailf:actionpoint ncsproxy {
          tailf:internal;
        }
        csc:xr-task "bgp";
        csc:cli-command "clear bgp bestpath <ip-addr>";
        description
          "re-run BGP bestpath selection.
          ";
        input {
          leaf ip-addr {
            mandatory true;
            type inet:ip-address;
            description
              "Network";
          }
        }
      }
    }
  }
  augment "/ncs:devices/ncs:device-group/ncs:ned-id/ncs:rpc" {
    container rpc-clear-bgp-bestpath-ip-addr {
      tailf:ncs-device-type "netconf";
      tailf:display-when "/ncs:devices/ncs:device[ncs:name=current()/../../../ncs:member]/ncs:module[ncs:name='Cisco-IOS-XR-ipv4-bgp-act']";
      tailf:action clear-bgp-bestpath-ip-addr {
        tailf:actionpoint ncsproxy {
          tailf:internal;
        }
        csc:xr-task "bgp";
        csc:cli-command "clear bgp bestpath <ip-addr>";
        description
          "re-run BGP bestpath selection.
          ";
        input {
          leaf ip-addr {
            mandatory true;
            type inet:ip-address;
            description
              "Network";
          }
        }
      }
    }
  }
  augment "/ncs:devices/ncs:device/ncs:rpc" {
    container rpc-clear-bgp-bestpath-ip-addr-ip-netmask {
      tailf:ncs-device-type "netconf";
      tailf:display-when "not(../../ncs:module) or ../../ncs:module[ncs:name='Cisco-IOS-XR-ipv4-bgp-act']";
      tailf:action clear-bgp-bestpath-ip-addr-ip-netmask {
        tailf:actionpoint ncsproxy {
          tailf:internal;
        }
        csc:xr-task "bgp";
        csc:cli-command "clear bgp bestpath <ip-addr> <ip-netmask>";
        description
          "re-run BGP bestpath selection.
          ";
        input {
          leaf ip-addr {
            mandatory true;
            type inet:ip-address;
            description
              "Network";
          }
          leaf ip-netmask {
            mandatory true;
            type ip-netmask;
            description
              "Mask";
          }
        }
      }
    }
  }
  augment "/ncs:devices/ncs:device-group/ncs:ned-id/ncs:rpc" {
    container rpc-clear-bgp-bestpath-ip-addr-ip-netmask {
      tailf:ncs-device-type "netconf";
      tailf:display-when "/ncs:devices/ncs:device[ncs:name=current()/../../../ncs:member]/ncs:module[ncs:name='Cisco-IOS-XR-ipv4-bgp-act']";
      tailf:action clear-bgp-bestpath-ip-addr-ip-netmask {
        tailf:actionpoint ncsproxy {
          tailf:internal;
        }
        csc:xr-task "bgp";
        csc:cli-command "clear bgp bestpath <ip-addr> <ip-netmask>";
        description
          "re-run BGP bestpath selection.
          ";
        input {
          leaf ip-addr {
            mandatory true;
            type inet:ip-address;
            description
              "Network";
          }
          leaf ip-netmask {
            mandatory true;
            type ip-netmask;
            description
              "Mask";
          }
        }
      }
    }
  }
  augment "/ncs:devices/ncs:device/ncs:rpc" {
    container rpc-clear-bgp-as {
      tailf:ncs-device-type "netconf";
      tailf:display-when "not(../../ncs:module) or ../../ncs:module[ncs:name='Cisco-IOS-XR-ipv4-bgp-act']";
      tailf:action clear-bgp-as {
        tailf:actionpoint ncsproxy {
          tailf:internal;
        }
        csc:xr-task "bgp";
        csc:cli-command "clear bgp as <as-number>";
        description
          "Clear peers in a specific AS.
          ";
        input {
          leaf as-number {
            mandatory true;
            type as-number;
            description
              "AS number";
          }
        }
      }
    }
  }
  augment "/ncs:devices/ncs:device-group/ncs:ned-id/ncs:rpc" {
    container rpc-clear-bgp-as {
      tailf:ncs-device-type "netconf";
      tailf:display-when "/ncs:devices/ncs:device[ncs:name=current()/../../../ncs:member]/ncs:module[ncs:name='Cisco-IOS-XR-ipv4-bgp-act']";
      tailf:action clear-bgp-as {
        tailf:actionpoint ncsproxy {
          tailf:internal;
        }
        csc:xr-task "bgp";
        csc:cli-command "clear bgp as <as-number>";
        description
          "Clear peers in a specific AS.
          ";
        input {
          leaf as-number {
            mandatory true;
            type as-number;
            description
              "AS number";
          }
        }
      }
    }
  }
  augment "/ncs:devices/ncs:device/ncs:rpc" {
    container rpc-clear-bgp-as-graceful {
      tailf:ncs-device-type "netconf";
      tailf:display-when "not(../../ncs:module) or ../../ncs:module[ncs:name='Cisco-IOS-XR-ipv4-bgp-act']";
      tailf:action clear-bgp-as-graceful {
        tailf:actionpoint ncsproxy {
          tailf:internal;
        }
        csc:xr-task "bgp";
        csc:cli-command "clear bgp as <as-number> graceful";
        description
          "Clear peers in a specific AS.
           Clear with a hard reset and a graceful restart.
          ";
        input {
          leaf as-number {
            mandatory true;
            type as-number;
            description
              "AS number";
          }
        }
      }
    }
  }
  augment "/ncs:devices/ncs:device-group/ncs:ned-id/ncs:rpc" {
    container rpc-clear-bgp-as-graceful {
      tailf:ncs-device-type "netconf";
      tailf:display-when "/ncs:devices/ncs:device[ncs:name=current()/../../../ncs:member]/ncs:module[ncs:name='Cisco-IOS-XR-ipv4-bgp-act']";
      tailf:action clear-bgp-as-graceful {
        tailf:actionpoint ncsproxy {
          tailf:internal;
        }
        csc:xr-task "bgp";
        csc:cli-command "clear bgp as <as-number> graceful";
        description
          "Clear peers in a specific AS.
           Clear with a hard reset and a graceful restart.
          ";
        input {
          leaf as-number {
            mandatory true;
            type as-number;
            description
              "AS number";
          }
        }
      }
    }
  }
  augment "/ncs:devices/ncs:device/ncs:rpc" {
    container rpc-clear-bgp-afi-safi-update-outq-update-group {
      tailf:ncs-device-type "netconf";
      tailf:display-when "not(../../ncs:module) or ../../ncs:module[ncs:name='Cisco-IOS-XR-ipv4-bgp-act']";
      tailf:action clear-bgp-afi-safi-update-outq-update-group {
        tailf:actionpoint ncsproxy {
          tailf:internal;
        }
        csc:xr-task "bgp";
        csc:cli-command "clear bgp <afi-safi-name> update outq update-group <update-group>";
        description
          "Clear Update information (Do NOT execute without cisco support)(cisco-support).
           Clear Update generation OutQ counters (Do NOT execute without cisco support)(cisco-support).
           Update-group.
          ";
        input {
          leaf afi-safi-name {
            mandatory true;
            type afi-safi-type;
            description
              "AFI and SAFI";
          }
          leaf update-group {
            mandatory true;
            type update-group-id;
            description
              "Update-group process ID <x.y>";
          }
        }
      }
    }
  }
  augment "/ncs:devices/ncs:device-group/ncs:ned-id/ncs:rpc" {
    container rpc-clear-bgp-afi-safi-update-outq-update-group {
      tailf:ncs-device-type "netconf";
      tailf:display-when "/ncs:devices/ncs:device[ncs:name=current()/../../../ncs:member]/ncs:module[ncs:name='Cisco-IOS-XR-ipv4-bgp-act']";
      tailf:action clear-bgp-afi-safi-update-outq-update-group {
        tailf:actionpoint ncsproxy {
          tailf:internal;
        }
        csc:xr-task "bgp";
        csc:cli-command "clear bgp <afi-safi-name> update outq update-group <update-group>";
        description
          "Clear Update information (Do NOT execute without cisco support)(cisco-support).
           Clear Update generation OutQ counters (Do NOT execute without cisco support)(cisco-support).
           Update-group.
          ";
        input {
          leaf afi-safi-name {
            mandatory true;
            type afi-safi-type;
            description
              "AFI and SAFI";
          }
          leaf update-group {
            mandatory true;
            type update-group-id;
            description
              "Update-group process ID <x.y>";
          }
        }
      }
    }
  }
  augment "/ncs:devices/ncs:device/ncs:rpc" {
    container rpc-clear-bgp-afi-safi-update-outq-update-group-update-parent {
      tailf:ncs-device-type "netconf";
      tailf:display-when "not(../../ncs:module) or ../../ncs:module[ncs:name='Cisco-IOS-XR-ipv4-bgp-act']";
      tailf:action clear-bgp-afi-safi-update-outq-update-group-update-parent {
        tailf:actionpoint ncsproxy {
          tailf:internal;
        }
        csc:xr-task "bgp";
        csc:cli-command "clear bgp <afi-safi-name> update outq update-group <update-group> update-parent";
        description
          "Clear Update information (Do NOT execute without cisco support)(cisco-support).
           Clear Update generation OutQ counters (Do NOT execute without cisco support)(cisco-support).
           Update-group.
           Update parents' OutQ counters too.
          ";
        input {
          leaf afi-safi-name {
            mandatory true;
            type afi-safi-type;
            description
              "AFI and SAFI";
          }
          leaf update-group {
            mandatory true;
            type update-group-id;
            description
              "Update-group process ID <x.y>";
          }
        }
      }
    }
  }
  augment "/ncs:devices/ncs:device-group/ncs:ned-id/ncs:rpc" {
    container rpc-clear-bgp-afi-safi-update-outq-update-group-update-parent {
      tailf:ncs-device-type "netconf";
      tailf:display-when "/ncs:devices/ncs:device[ncs:name=current()/../../../ncs:member]/ncs:module[ncs:name='Cisco-IOS-XR-ipv4-bgp-act']";
      tailf:action clear-bgp-afi-safi-update-outq-update-group-update-parent {
        tailf:actionpoint ncsproxy {
          tailf:internal;
        }
        csc:xr-task "bgp";
        csc:cli-command "clear bgp <afi-safi-name> update outq update-group <update-group> update-parent";
        description
          "Clear Update information (Do NOT execute without cisco support)(cisco-support).
           Clear Update generation OutQ counters (Do NOT execute without cisco support)(cisco-support).
           Update-group.
           Update parents' OutQ counters too.
          ";
        input {
          leaf afi-safi-name {
            mandatory true;
            type afi-safi-type;
            description
              "AFI and SAFI";
          }
          leaf update-group {
            mandatory true;
            type update-group-id;
            description
              "Update-group process ID <x.y>";
          }
        }
      }
    }
  }
  augment "/ncs:devices/ncs:device/ncs:rpc" {
    container rpc-clear-bgp-afi-safi-update-outq-update-group-sub-group-refresh-sub-group {
      tailf:ncs-device-type "netconf";
      tailf:display-when "not(../../ncs:module) or ../../ncs:module[ncs:name='Cisco-IOS-XR-ipv4-bgp-act']";
      tailf:action clear-bgp-afi-safi-update-outq-update-group-sub-group-refresh-sub-group {
        tailf:actionpoint ncsproxy {
          tailf:internal;
        }
        csc:xr-task "bgp";
        csc:cli-command "clear bgp <afi-safi-name> update outq update-group <update-group> sub-group <refresh-sub-group>";
        description
          "Clear Update information (Do NOT execute without cisco support)(cisco-support).
           Clear Update generation OutQ counters (Do NOT execute without cisco support)(cisco-support).
           Update-group.
           Sub-group.
          ";
        input {
          leaf afi-safi-name {
            mandatory true;
            type afi-safi-type;
            description
              "AFI and SAFI";
          }
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device-group/ncs:ned-id/ncs:rpc" {
    container rpc-clear-bgp-afi-safi-update-outq-update-group-sub-group-refresh-sub-group {
      tailf:ncs-device-type "netconf";
      tailf:display-when "/ncs:devices/ncs:device[ncs:name=current()/../../../ncs:member]/ncs:module[ncs:name='Cisco-IOS-XR-ipv4-bgp-act']";
      tailf:action clear-bgp-afi-safi-update-outq-update-group-sub-group-refresh-sub-group {
        tailf:actionpoint ncsproxy {
          tailf:internal;
        }
        csc:xr-task "bgp";
        csc:cli-command "clear bgp <afi-safi-name> update outq update-group <update-group> sub-group <refresh-sub-group>";
        description
          "Clear Update information (Do NOT execute without cisco support)(cisco-support).
           Clear Update generation OutQ counters (Do NOT execute without cisco support)(cisco-support).
           Update-group.
           Sub-group.
          ";
        input {
          leaf afi-safi-name {
            mandatory true;
            type afi-safi-type;
            description
              "AFI and SAFI";
          }
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device/ncs:rpc" {
    container rpc-clear-bgp-afi-safi-update-outq-update-group-sub-group-refresh-sub-group-update-parent {
      tailf:ncs-device-type "netconf";
      tailf:display-when "not(../../ncs:module) or ../../ncs:module[ncs:name='Cisco-IOS-XR-ipv4-bgp-act']";
      tailf:action clear-bgp-afi-safi-update-outq-update-group-sub-group-refresh-sub-group-update-parent {
        tailf:actionpoint ncsproxy {
          tailf:internal;
        }
        csc:xr-task "bgp";
        csc:cli-command "clear bgp <afi-safi-name> update outq update-group <update-group> sub-group <refresh-sub-group> update-parent";
        description
          "Clear Update information (Do NOT execute without cisco support)(cisco-support).
           Clear Update generation OutQ counters (Do NOT execute without cisco support)(cisco-support).
           Update-group.
           Sub-group.
           Update parents' OutQ counters too.
          ";
        input {
          leaf afi-safi-name {
            mandatory true;
            type afi-safi-type;
            description
              "AFI and SAFI";
          }
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device-group/ncs:ned-id/ncs:rpc" {
    container rpc-clear-bgp-afi-safi-update-outq-update-group-sub-group-refresh-sub-group-update-parent {
      tailf:ncs-device-type "netconf";
      tailf:display-when "/ncs:devices/ncs:device[ncs:name=current()/../../../ncs:member]/ncs:module[ncs:name='Cisco-IOS-XR-ipv4-bgp-act']";
      tailf:action clear-bgp-afi-safi-update-outq-update-group-sub-group-refresh-sub-group-update-parent {
        tailf:actionpoint ncsproxy {
          tailf:internal;
        }
        csc:xr-task "bgp";
        csc:cli-command "clear bgp <afi-safi-name> update outq update-group <update-group> sub-group <refresh-sub-group> update-parent";
        description
          "Clear Update information (Do NOT execute without cisco support)(cisco-support).
           Clear Update generation OutQ counters (Do NOT execute without cisco support)(cisco-support).
           Update-group.
           Sub-group.
           Update parents' OutQ counters too.
          ";
        input {
          leaf afi-safi-name {
            mandatory true;
            type afi-safi-type;
            description
              "AFI and SAFI";
          }
          leaf update-group {
            mandatory true;
            type update-group-id;
            description
              "Update-group process ID <x.y>";
          }
          leaf refresh-sub-group {
            mandatory true;
            type refresh-sub-group-id;
            description
              "Refresh Sub-group process ID <x.y:z>";
          }
        }
      }
    }
  }
  augment "/ncs:devices/ncs:device/ncs:rpc" {
    container rpc-clear-bgp-afi-safi-update-outq-update-group-sub-group {
      tailf:ncs-device-type "netconf";
      tailf:display-when "not(../../ncs:module) or ../../ncs:module[ncs:name='Cisco-IOS-XR-ipv4-bgp-act']";
      tailf:action clear-bgp-afi-safi-update-outq-update-group-sub-group {
        tailf:actionpoint ncsproxy {
          tailf:internal;
        }
        csc:xr-task "bgp";
        csc:cli-command "clear bgp <afi-safi-name> update outq update-group <update-group> sub-group <sub-group>";
        description
          "Clear Update information (Do NOT execute without cisco support)(cisco-support).
           Clear Update generation OutQ counters (Do NOT execute without cisco support)(cisco-support).
           Update-group.
           Sub-group.
          ";
        input {
          leaf afi-safi-name {
            mandatory true;
            type afi-safi-type;
            description
              "AFI and SAFI";
          }
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device-group/ncs:ned-id/ncs:rpc" {
    container rpc-clear-bgp-afi-safi-update-outq-update-group-sub-group {
      tailf:ncs-device-type "netconf";
      tailf:display-when "/ncs:devices/ncs:device[ncs:name=current()/../../../ncs:member]/ncs:module[ncs:name='Cisco-IOS-XR-ipv4-bgp-act']";
      tailf:action clear-bgp-afi-safi-update-outq-update-group-sub-group {
        tailf:actionpoint ncsproxy {
          tailf:internal;
        }
        csc:xr-task "bgp";
        csc:cli-command "clear bgp <afi-safi-name> update outq update-group <update-group> sub-group <sub-group>";
        description
          "Clear Update information (Do NOT execute without cisco support)(cisco-support).
           Clear Update generation OutQ counters (Do NOT execute without cisco support)(cisco-support).
           Update-group.
           Sub-group.
          ";
        input {
          leaf afi-safi-name {
            mandatory true;
            type afi-safi-type;
            description
              "AFI and SAFI";
          }
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device/ncs:rpc" {
    container rpc-clear-bgp-afi-safi-update-outq-update-group-sub-group-update-parent {
      tailf:ncs-device-type "netconf";
      tailf:display-when "not(../../ncs:module) or ../../ncs:module[ncs:name='Cisco-IOS-XR-ipv4-bgp-act']";
      tailf:action clear-bgp-afi-safi-update-outq-update-group-sub-group-update-parent {
        tailf:actionpoint ncsproxy {
          tailf:internal;
        }
        csc:xr-task "bgp";
        csc:cli-command "clear bgp <afi-safi-name> update outq update-group <update-group> sub-group <sub-group> update-parent";
        description
          "Clear Update information (Do NOT execute without cisco support)(cisco-support).
           Clear Update generation OutQ counters (Do NOT execute without cisco support)(cisco-support).
           Update-group.
           Sub-group.
           Update parents' OutQ counters too.
          ";
        input {
          leaf afi-safi-name {
            mandatory true;
            type afi-safi-type;
            description
              "AFI and SAFI";
          }
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device-group/ncs:ned-id/ncs:rpc" {
    container rpc-clear-bgp-afi-safi-update-outq-update-group-sub-group-update-parent {
      tailf:ncs-device-type "netconf";
      tailf:display-when "/ncs:devices/ncs:device[ncs:name=current()/../../../ncs:member]/ncs:module[ncs:name='Cisco-IOS-XR-ipv4-bgp-act']";
      tailf:action clear-bgp-afi-safi-update-outq-update-group-sub-group-update-parent {
        tailf:actionpoint ncsproxy {
          tailf:internal;
        }
        csc:xr-task "bgp";
        csc:cli-command "clear bgp <afi-safi-name> update outq update-group <update-group> sub-group <sub-group> update-parent";
        description
          "Clear Update information (Do NOT execute without cisco support)(cisco-support).
           Clear Update generation OutQ counters (Do NOT execute without cisco support)(cisco-support).
           Update-group.
           Sub-group.
           Update parents' OutQ counters too.
          ";
        input {
          leaf afi-safi-name {
            mandatory true;
            type afi-safi-type;
            description
              "AFI and SAFI";
          }
          leaf update-group {
            mandatory true;
            type update-group-id;
            description
              "Update-group process ID <x.y>";
          }
          leaf sub-group {
            mandatory true;
            type update-group-id;
            description
              "Sub-group process ID <x.y>";
          }
        }
      }
    }
  }
  augment "/ncs:devices/ncs:device/ncs:rpc" {
    container rpc-clear-bgp-afi-safi-update-outq-neighbor-ip-addr {
      tailf:ncs-device-type "netconf";
      tailf:display-when "not(../../ncs:module) or ../../ncs:module[ncs:name='Cisco-IOS-XR-ipv4-bgp-act']";
      tailf:action clear-bgp-afi-safi-update-outq-neighbor-ip-addr {
        tailf:actionpoint ncsproxy {
          tailf:internal;
        }
        csc:xr-task "bgp";
        csc:cli-command "clear bgp <afi-safi-name> update outq neighbor <ip-addr>";
        description
          "Clear Update information (Do NOT execute without cisco support)(cisco-support).
           Clear Update generation OutQ counters (Do NOT execute without cisco support)(cisco-support).
           Neighbor.
          ";
        input {
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device-group/ncs:ned-id/ncs:rpc" {
    container rpc-clear-bgp-afi-safi-update-outq-neighbor-ip-addr {
      tailf:ncs-device-type "netconf";
      tailf:display-when "/ncs:devices/ncs:device[ncs:name=current()/../../../ncs:member]/ncs:module[ncs:name='Cisco-IOS-XR-ipv4-bgp-act']";
      tailf:action clear-bgp-afi-safi-update-outq-neighbor-ip-addr {
        tailf:actionpoint ncsproxy {
          tailf:internal;
        }
        csc:xr-task "bgp";
        csc:cli-command "clear bgp <afi-safi-name> update outq neighbor <ip-addr>";
        description
          "Clear Update information (Do NOT execute without cisco support)(cisco-support).
           Clear Update generation OutQ counters (Do NOT execute without cisco support)(cisco-support).
           Neighbor.
          ";
        input {
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device/ncs:rpc" {
    container rpc-clear-bgp-afi-safi-update-outq-neighbor-ip-addr-update-parent {
      tailf:ncs-device-type "netconf";
      tailf:display-when "not(../../ncs:module) or ../../ncs:module[ncs:name='Cisco-IOS-XR-ipv4-bgp-act']";
      tailf:action clear-bgp-afi-safi-update-outq-neighbor-ip-addr-update-parent {
        tailf:actionpoint ncsproxy {
          tailf:internal;
        }
        csc:xr-task "bgp";
        csc:cli-command "clear bgp <afi-safi-name> update outq neighbor <ip-addr> update-parent";
        description
          "Clear Update information (Do NOT execute without cisco support)(cisco-support).
           Clear Update generation OutQ counters (Do NOT execute without cisco support)(cisco-support).
           Neighbor.
           Update parents' OutQ counters too.
          ";
        input {
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device-group/ncs:ned-id/ncs:rpc" {
    container rpc-clear-bgp-afi-safi-update-outq-neighbor-ip-addr-update-parent {
      tailf:ncs-device-type "netconf";
      tailf:display-when "/ncs:devices/ncs:device[ncs:name=current()/../../../ncs:member]/ncs:module[ncs:name='Cisco-IOS-XR-ipv4-bgp-act']";
      tailf:action clear-bgp-afi-safi-update-outq-neighbor-ip-addr-update-parent {
        tailf:actionpoint ncsproxy {
          tailf:internal;
        }
        csc:xr-task "bgp";
        csc:cli-command "clear bgp <afi-safi-name> update outq neighbor <ip-addr> update-parent";
        description
          "Clear Update information (Do NOT execute without cisco support)(cisco-support).
           Clear Update generation OutQ counters (Do NOT execute without cisco support)(cisco-support).
           Neighbor.
           Update parents' OutQ counters too.
          ";
        input {
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device/ncs:rpc" {
    container rpc-clear-bgp-afi-safi-update-outq-neighbor-ip-addr-refresh {
      tailf:ncs-device-type "netconf";
      tailf:display-when "not(../../ncs:module) or ../../ncs:module[ncs:name='Cisco-IOS-XR-ipv4-bgp-act']";
      tailf:action clear-bgp-afi-safi-update-outq-neighbor-ip-addr-refresh {
        tailf:actionpoint ncsproxy {
          tailf:internal;
        }
        csc:xr-task "bgp";
        csc:cli-command "clear bgp <afi-safi-name> update outq neighbor <ip-addr> refresh";
        description
          "Clear Update information (Do NOT execute without cisco support)(cisco-support).
           Clear Update generation OutQ counters (Do NOT execute without cisco support)(cisco-support).
           Neighbor.
           Refresh OutQ.
          ";
        input {
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device-group/ncs:ned-id/ncs:rpc" {
    container rpc-clear-bgp-afi-safi-update-outq-neighbor-ip-addr-refresh {
      tailf:ncs-device-type "netconf";
      tailf:display-when "/ncs:devices/ncs:device[ncs:name=current()/../../../ncs:member]/ncs:module[ncs:name='Cisco-IOS-XR-ipv4-bgp-act']";
      tailf:action clear-bgp-afi-safi-update-outq-neighbor-ip-addr-refresh {
        tailf:actionpoint ncsproxy {
          tailf:internal;
        }
        csc:xr-task "bgp";
        csc:cli-command "clear bgp <afi-safi-name> update outq neighbor <ip-addr> refresh";
        description
          "Clear Update information (Do NOT execute without cisco support)(cisco-support).
           Clear Update generation OutQ counters (Do NOT execute without cisco support)(cisco-support).
           Neighbor.
           Refresh OutQ.
          ";
        input {
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device/ncs:rpc" {
    container rpc-clear-bgp-afi-safi-update-outq-neighbor-ip-addr-refresh-update-parent {
      tailf:ncs-device-type "netconf";
      tailf:display-when "not(../../ncs:module) or ../../ncs:module[ncs:name='Cisco-IOS-XR-ipv4-bgp-act']";
      tailf:action clear-bgp-afi-safi-update-outq-neighbor-ip-addr-refresh-update-parent {
        tailf:actionpoint ncsproxy {
          tailf:internal;
        }
        csc:xr-task "bgp";
        csc:cli-command "clear bgp <afi-safi-name> update outq neighbor <ip-addr> refresh update-parent";
        description
          "Clear Update information (Do NOT execute without cisco support)(cisco-support).
           Clear Update generation OutQ counters (Do NOT execute without cisco support)(cisco-support).
           Neighbor.
           Refresh OutQ.
           Update parents' OutQ counters too.
          ";
        input {
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device-group/ncs:ned-id/ncs:rpc" {
    container rpc-clear-bgp-afi-safi-update-outq-neighbor-ip-addr-refresh-update-parent {
      tailf:ncs-device-type "netconf";
      tailf:display-when "/ncs:devices/ncs:device[ncs:name=current()/../../../ncs:member]/ncs:module[ncs:name='Cisco-IOS-XR-ipv4-bgp-act']";
      tailf:action clear-bgp-afi-safi-update-outq-neighbor-ip-addr-refresh-update-parent {
        tailf:actionpoint ncsproxy {
          tailf:internal;
        }
        csc:xr-task "bgp";
        csc:cli-command "clear bgp <afi-safi-name> update outq neighbor <ip-addr> refresh update-parent";
        description
          "Clear Update information (Do NOT execute without cisco support)(cisco-support).
           Clear Update generation OutQ counters (Do NOT execute without cisco support)(cisco-support).
           Neighbor.
           Refresh OutQ.
           Update parents' OutQ counters too.
          ";
        input {
          leaf afi-safi-name {
            mandatory true;
            type afi-safi-type;
            description
              "AFI and SAFI";
          }
          leaf ip-addr {
            mandatory true;
            type inet:ip-address;
            description
              "Neighbor address";
          }
        }
      }
    }
  }
  augment "/ncs:devices/ncs:device/ncs:rpc" {
    container rpc-clear-bgp-afi-safi-update-outq-address-family {
      tailf:ncs-device-type "netconf";
      tailf:display-when "not(../../ncs:module) or ../../ncs:module[ncs:name='Cisco-IOS-XR-ipv4-bgp-act']";
      tailf:action clear-bgp-afi-safi-update-outq-address-family {
        tailf:actionpoint ncsproxy {
          tailf:internal;
        }
        csc:xr-task "bgp";
        csc:cli-command "clear bgp <afi-safi-name> update outq address-family";
        description
          "Clear Update information (Do NOT execute without cisco support)(cisco-support).
           Clear Update generation OutQ counters (Do NOT execute without cisco support)(cisco-support).
           Address-family.
          ";
        input {
          leaf afi-safi-name {
            mandatory true;
            type afi-safi-type;
            description
              "AFI and SAFI";
          }
        }
      }
    }
  }
  augment "/ncs:devices/ncs:device-group/ncs:ned-id/ncs:rpc" {
    container rpc-clear-bgp-afi-safi-update-outq-address-family {
      tailf:ncs-device-type "netconf";
      tailf:display-when "/ncs:devices/ncs:device[ncs:name=current()/../../../ncs:member]/ncs:module[ncs:name='Cisco-IOS-XR-ipv4-bgp-act']";
      tailf:action clear-bgp-afi-safi-update-outq-address-family {
        tailf:actionpoint ncsproxy {
          tailf:internal;
        }
        csc:xr-task "bgp";
        csc:cli-command "clear bgp <afi-safi-name> update outq address-family";
        description
          "Clear Update information (Do NOT execute without cisco support)(cisco-support).
           Clear Update generation OutQ counters (Do NOT execute without cisco support)(cisco-support).
           Address-family.
          ";
        input {
          leaf afi-safi-name {
            mandatory true;
            type afi-safi-type;
            description
              "AFI and SAFI";
          }
        }
      }
    }
  }
  augment "/ncs:devices/ncs:device/ncs:rpc" {
    container rpc-clear-bgp-afi-safi-update-outq-address-family-update-parent {
      tailf:ncs-device-type "netconf";
      tailf:display-when "not(../../ncs:module) or ../../ncs:module[ncs:name='Cisco-IOS-XR-ipv4-bgp-act']";
      tailf:action clear-bgp-afi-safi-update-outq-address-family-update-parent {
        tailf:actionpoint ncsproxy {
          tailf:internal;
        }
        csc:xr-task "bgp";
        csc:cli-command "clear bgp <afi-safi-name> update outq address-family update-parent";
        description
          "Clear Update information (Do NOT execute without cisco support)(cisco-support).
           Clear Update generation OutQ counters (Do NOT execute without cisco support)(cisco-support).
           Address-family.
           Update parents' OutQ counters too.
          ";
        input {
          leaf afi-safi-name {
            mandatory true;
            type afi-safi-type;
            description
              "AFI and SAFI";
          }
        }
      }
    }
  }
  augment "/ncs:devices/ncs:device-group/ncs:ned-id/ncs:rpc" {
    container rpc-clear-bgp-afi-safi-update-outq-address-family-update-parent {
      tailf:ncs-device-type "netconf";
      tailf:display-when "/ncs:devices/ncs:device[ncs:name=current()/../../../ncs:member]/ncs:module[ncs:name='Cisco-IOS-XR-ipv4-bgp-act']";
      tailf:action clear-bgp-afi-safi-update-outq-address-family-update-parent {
        tailf:actionpoint ncsproxy {
          tailf:internal;
        }
        csc:xr-task "bgp";
        csc:cli-command "clear bgp <afi-safi-name> update outq address-family update-parent";
        description
          "Clear Update information (Do NOT execute without cisco support)(cisco-support).
           Clear Update generation OutQ counters (Do NOT execute without cisco support)(cisco-support).
           Address-family.
           Update parents' OutQ counters too.
          ";
        input {
          leaf afi-safi-name {
            mandatory true;
            type afi-safi-type;
            description
              "AFI and SAFI";
          }
        }
      }
    }
  }
  augment "/ncs:devices/ncs:device/ncs:rpc" {
    container rpc-clear-bgp-afi-safi-shutdown {
      tailf:ncs-device-type "netconf";
      tailf:display-when "not(../../ncs:module) or ../../ncs:module[ncs:name='Cisco-IOS-XR-ipv4-bgp-act']";
      tailf:action clear-bgp-afi-safi-shutdown {
        tailf:actionpoint ncsproxy {
          tailf:internal;
        }
        csc:xr-task "bgp";
        csc:cli-command "clear bgp <afi-safi-name> shutdown";
        description
          "Clear all peers which were shut down due to low memory.
          ";
        input {
          leaf afi-safi-name {
            mandatory true;
            type afi-safi-type;
            description
              "AFI and SAFI";
          }
        }
      }
    }
  }
  augment "/ncs:devices/ncs:device-group/ncs:ned-id/ncs:rpc" {
    container rpc-clear-bgp-afi-safi-shutdown {
      tailf:ncs-device-type "netconf";
      tailf:display-when "/ncs:devices/ncs:device[ncs:name=current()/../../../ncs:member]/ncs:module[ncs:name='Cisco-IOS-XR-ipv4-bgp-act']";
      tailf:action clear-bgp-afi-safi-shutdown {
        tailf:actionpoint ncsproxy {
          tailf:internal;
        }
        csc:xr-task "bgp";
        csc:cli-command "clear bgp <afi-safi-name> shutdown";
        description
          "Clear all peers which were shut down due to low memory.
          ";
        input {
          leaf afi-safi-name {
            mandatory true;
            type afi-safi-type;
            description
              "AFI and SAFI";
          }
        }
      }
    }
  }
  augment "/ncs:devices/ncs:device/ncs:rpc" {
    container rpc-clear-bgp-afi-safi-self-originated {
      tailf:ncs-device-type "netconf";
      tailf:display-when "not(../../ncs:module) or ../../ncs:module[ncs:name='Cisco-IOS-XR-ipv4-bgp-act']";
      tailf:action clear-bgp-afi-safi-self-originated {
        tailf:actionpoint ncsproxy {
          tailf:internal;
        }
        csc:xr-task "bgp";
        csc:cli-command "clear bgp <afi-safi-name> self-originated";
        description
          "Clear redistributed, network and aggregate routes originated here.
          ";
        input {
          leaf afi-safi-name {
            mandatory true;
            type afi-safi-type;
            description
              "AFI and SAFI";
          }
        }
      }
    }
  }
  augment "/ncs:devices/ncs:device-group/ncs:ned-id/ncs:rpc" {
    container rpc-clear-bgp-afi-safi-self-originated {
      tailf:ncs-device-type "netconf";
      tailf:display-when "/ncs:devices/ncs:device[ncs:name=current()/../../../ncs:member]/ncs:module[ncs:name='Cisco-IOS-XR-ipv4-bgp-act']";
      tailf:action clear-bgp-afi-safi-self-originated {
        tailf:actionpoint ncsproxy {
          tailf:internal;
        }
        csc:xr-task "bgp";
        csc:cli-command "clear bgp <afi-safi-name> self-originated";
        description
          "Clear redistributed, network and aggregate routes originated here.
          ";
        input {
          leaf afi-safi-name {
            mandatory true;
            type afi-safi-type;
            description
              "AFI and SAFI";
          }
        }
      }
    }
  }
  augment "/ncs:devices/ncs:device/ncs:rpc" {
    container rpc-clear-bgp-afi-safi-nexthop-registration-ip-addr {
      tailf:ncs-device-type "netconf";
      tailf:display-when "not(../../ncs:module) or ../../ncs:module[ncs:name='Cisco-IOS-XR-ipv4-bgp-act']";
      tailf:action clear-bgp-afi-safi-nexthop-registration-ip-addr {
        tailf:actionpoint ncsproxy {
          tailf:internal;
        }
        csc:xr-task "bgp";
        csc:cli-command "clear bgp <afi-safi-name> nexthop registration <ip-addr>";
        description
          "Clear nexthop.
           Registration with RIB and reregister.
          ";
        input {
          leaf afi-safi-name {
            mandatory true;
            type afi-safi-type;
            description
              "AFI and SAFI";
          }
          leaf ip-addr {
            mandatory true;
            type inet:ip-address;
            description
              "Nexthop address";
          }
        }
      }
    }
  }
  augment "/ncs:devices/ncs:device-group/ncs:ned-id/ncs:rpc" {
    container rpc-clear-bgp-afi-safi-nexthop-registration-ip-addr {
      tailf:ncs-device-type "netconf";
      tailf:display-when "/ncs:devices/ncs:device[ncs:name=current()/../../../ncs:member]/ncs:module[ncs:name='Cisco-IOS-XR-ipv4-bgp-act']";
      tailf:action clear-bgp-afi-safi-nexthop-registration-ip-addr {
        tailf:actionpoint ncsproxy {
          tailf:internal;
        }
        csc:xr-task "bgp";
        csc:cli-command "clear bgp <afi-safi-name> nexthop registration <ip-addr>";
        description
          "Clear nexthop.
           Registration with RIB and reregister.
          ";
        input {
          leaf afi-safi-name {
            mandatory true;
            type afi-safi-type;
            description
              "AFI and SAFI";
          }
          leaf ip-addr {
            mandatory true;
            type inet:ip-address;
            description
              "Nexthop address";
          }
        }
      }
    }
  }
  augment "/ncs:devices/ncs:device/ncs:rpc" {
    container rpc-clear-bgp-afi-safi-nexthop-performance-statistics {
      tailf:ncs-device-type "netconf";
      tailf:display-when "not(../../ncs:module) or ../../ncs:module[ncs:name='Cisco-IOS-XR-ipv4-bgp-act']";
      tailf:action clear-bgp-afi-safi-nexthop-performance-statistics {
        tailf:actionpoint ncsproxy {
          tailf:internal;
        }
        csc:xr-task "bgp";
        csc:cli-command "clear bgp <afi-safi-name> nexthop performance-statistics";
        description
          "Clear nexthop.
           Performance statistics information related to processing.
          ";
        input {
          leaf afi-safi-name {
            mandatory true;
            type afi-safi-type;
            description
              "AFI and SAFI";
          }
        }
      }
    }
  }
  augment "/ncs:devices/ncs:device-group/ncs:ned-id/ncs:rpc" {
    container rpc-clear-bgp-afi-safi-nexthop-performance-statistics {
      tailf:ncs-device-type "netconf";
      tailf:display-when "/ncs:devices/ncs:device[ncs:name=current()/../../../ncs:member]/ncs:module[ncs:name='Cisco-IOS-XR-ipv4-bgp-act']";
      tailf:action clear-bgp-afi-safi-nexthop-performance-statistics {
        tailf:actionpoint ncsproxy {
          tailf:internal;
        }
        csc:xr-task "bgp";
        csc:cli-command "clear bgp <afi-safi-name> nexthop performance-statistics";
        description
          "Clear nexthop.
           Performance statistics information related to processing.
          ";
        input {
          leaf afi-safi-name {
            mandatory true;
            type afi-safi-type;
            description
              "AFI and SAFI";
          }
        }
      }
    }
  }
  augment "/ncs:devices/ncs:device/ncs:rpc" {
    container rpc-clear-bgp-afi-safi-flap-statistics {
      tailf:ncs-device-type "netconf";
      tailf:display-when "not(../../ncs:module) or ../../ncs:module[ncs:name='Cisco-IOS-XR-ipv4-bgp-act']";
      tailf:action clear-bgp-afi-safi-flap-statistics {
        tailf:actionpoint ncsproxy {
          tailf:internal;
        }
        csc:xr-task "bgp";
        csc:cli-command "clear bgp <afi-safi-name> flap-statistics";
        description
          "Clear flap statistics.
          ";
        input {
          leaf afi-safi-name {
            mandatory true;
            type afi-safi-type;
            description
              "AFI and SAFI";
          }
        }
      }
    }
  }
  augment "/ncs:devices/ncs:device-group/ncs:ned-id/ncs:rpc" {
    container rpc-clear-bgp-afi-safi-flap-statistics {
      tailf:ncs-device-type "netconf";
      tailf:display-when "/ncs:devices/ncs:device[ncs:name=current()/../../../ncs:member]/ncs:module[ncs:name='Cisco-IOS-XR-ipv4-bgp-act']";
      tailf:action clear-bgp-afi-safi-flap-statistics {
        tailf:actionpoint ncsproxy {
          tailf:internal;
        }
        csc:xr-task "bgp";
        csc:cli-command "clear bgp <afi-safi-name> flap-statistics";
        description
          "Clear flap statistics.
          ";
        input {
          leaf afi-safi-name {
            mandatory true;
            type afi-safi-type;
            description
              "AFI and SAFI";
          }
        }
      }
    }
  }
  augment "/ncs:devices/ncs:device/ncs:rpc" {
    container rpc-clear-bgp-afi-safi-flap-statistics-route-policy {
      tailf:ncs-device-type "netconf";
      tailf:display-when "not(../../ncs:module) or ../../ncs:module[ncs:name='Cisco-IOS-XR-ipv4-bgp-act']";
      tailf:action clear-bgp-afi-safi-flap-statistics-route-policy {
        tailf:actionpoint ncsproxy {
          tailf:internal;
        }
        csc:xr-task "bgp";
        csc:cli-command "clear bgp <afi-safi-name> flap-statistics route-policy <route-policy-name>";
        description
          "Clear flap statistics.
           Clear flap statistics for routes matching the route policy.
          ";
        input {
          leaf afi-safi-name {
            mandatory true;
            type afi-safi-type;
            description
              "AFI and SAFI";
          }
          leaf route-policy-name {
            mandatory true;
            type string;
            description
              "Route Policy name";
          }
        }
      }
    }
  }
  augment "/ncs:devices/ncs:device-group/ncs:ned-id/ncs:rpc" {
    container rpc-clear-bgp-afi-safi-flap-statistics-route-policy {
      tailf:ncs-device-type "netconf";
      tailf:display-when "/ncs:devices/ncs:device[ncs:name=current()/../../../ncs:member]/ncs:module[ncs:name='Cisco-IOS-XR-ipv4-bgp-act']";
      tailf:action clear-bgp-afi-safi-flap-statistics-route-policy {
        tailf:actionpoint ncsproxy {
          tailf:internal;
        }
        csc:xr-task "bgp";
        csc:cli-command "clear bgp <afi-safi-name> flap-statistics route-policy <route-policy-name>";
        description
          "Clear flap statistics.
           Clear flap statistics for routes matching the route policy.
          ";
        input {
          leaf afi-safi-name {
            mandatory true;
            type afi-safi-type;
            description
              "AFI and SAFI";
          }
          leaf route-policy-name {
            mandatory true;
            type string;
            description
              "Route Policy name";
          }
        }
      }
    }
  }
  augment "/ncs:devices/ncs:device/ncs:rpc" {
    container rpc-clear-bgp-afi-safi-flap-statistics-regexp {
      tailf:ncs-device-type "netconf";
      tailf:display-when "not(../../ncs:module) or ../../ncs:module[ncs:name='Cisco-IOS-XR-ipv4-bgp-act']";
      tailf:action clear-bgp-afi-safi-flap-statistics-regexp {
        tailf:actionpoint ncsproxy {
          tailf:internal;
        }
        csc:xr-task "bgp";
        csc:cli-command "clear bgp <afi-safi-name> flap-statistics regexp <regexp-pattern>";
        description
          "Clear flap statistics.
           Clear flap statistics for routes matching the regular expression.
          ";
        input {
          leaf afi-safi-name {
            mandatory true;
            type afi-safi-type;
            description
              "AFI and SAFI";
          }
          leaf regexp-pattern {
            mandatory true;
            type string;
            description
              "A regular expression to match the BGP AS paths.  Use 'ctrl-v ?' to enter '?'";
          }
        }
      }
    }
  }
  augment "/ncs:devices/ncs:device-group/ncs:ned-id/ncs:rpc" {
    container rpc-clear-bgp-afi-safi-flap-statistics-regexp {
      tailf:ncs-device-type "netconf";
      tailf:display-when "/ncs:devices/ncs:device[ncs:name=current()/../../../ncs:member]/ncs:module[ncs:name='Cisco-IOS-XR-ipv4-bgp-act']";
      tailf:action clear-bgp-afi-safi-flap-statistics-regexp {
        tailf:actionpoint ncsproxy {
          tailf:internal;
        }
        csc:xr-task "bgp";
        csc:cli-command "clear bgp <afi-safi-name> flap-statistics regexp <regexp-pattern>";
        description
          "Clear flap statistics.
           Clear flap statistics for routes matching the regular expression.
          ";
        input {
          leaf afi-safi-name {
            mandatory true;
            type afi-safi-type;
            description
              "AFI and SAFI";
          }
          leaf regexp-pattern {
            mandatory true;
            type string;
            description
              "A regular expression to match the BGP AS paths.  Use 'ctrl-v ?' to enter '?'";
          }
        }
      }
    }
  }
  augment "/ncs:devices/ncs:device/ncs:rpc" {
    container rpc-clear-bgp-afi-safi-flap-statistics-ip-prefix {
      tailf:ncs-device-type "netconf";
      tailf:display-when "not(../../ncs:module) or ../../ncs:module[ncs:name='Cisco-IOS-XR-ipv4-bgp-act']";
      tailf:action clear-bgp-afi-safi-flap-statistics-ip-prefix {
        tailf:actionpoint ncsproxy {
          tailf:internal;
        }
        csc:xr-task "bgp";
        csc:cli-command "clear bgp <afi-safi-name> flap-statistics <ip-prefix>";
        description
          "Clear flap statistics.
          ";
        input {
          leaf afi-safi-name {
            mandatory true;
            type afi-safi-type;
            description
              "AFI and SAFI";
          }
          leaf ip-prefix {
            mandatory true;
            type inet:ip-prefix;
            description
              "Network and mask or masklength to clear flap statistics";
          }
        }
      }
    }
  }
  augment "/ncs:devices/ncs:device-group/ncs:ned-id/ncs:rpc" {
    container rpc-clear-bgp-afi-safi-flap-statistics-ip-prefix {
      tailf:ncs-device-type "netconf";
      tailf:display-when "/ncs:devices/ncs:device[ncs:name=current()/../../../ncs:member]/ncs:module[ncs:name='Cisco-IOS-XR-ipv4-bgp-act']";
      tailf:action clear-bgp-afi-safi-flap-statistics-ip-prefix {
        tailf:actionpoint ncsproxy {
          tailf:internal;
        }
        csc:xr-task "bgp";
        csc:cli-command "clear bgp <afi-safi-name> flap-statistics <ip-prefix>";
        description
          "Clear flap statistics.
          ";
        input {
          leaf afi-safi-name {
            mandatory true;
            type afi-safi-type;
            description
              "AFI and SAFI";
          }
          leaf ip-prefix {
            mandatory true;
            type inet:ip-prefix;
            description
              "Network and mask or masklength to clear flap statistics";
          }
        }
      }
    }
  }
  augment "/ncs:devices/ncs:device/ncs:rpc" {
    container rpc-clear-bgp-afi-safi-flap-statistics-ip-addr {
      tailf:ncs-device-type "netconf";
      tailf:display-when "not(../../ncs:module) or ../../ncs:module[ncs:name='Cisco-IOS-XR-ipv4-bgp-act']";
      tailf:action clear-bgp-afi-safi-flap-statistics-ip-addr {
        tailf:actionpoint ncsproxy {
          tailf:internal;
        }
        csc:xr-task "bgp";
        csc:cli-command "clear bgp <afi-safi-name> flap-statistics <ip-addr>";
        description
          "Clear flap statistics.
          ";
        input {
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device-group/ncs:ned-id/ncs:rpc" {
    container rpc-clear-bgp-afi-safi-flap-statistics-ip-addr {
      tailf:ncs-device-type "netconf";
      tailf:display-when "/ncs:devices/ncs:device[ncs:name=current()/../../../ncs:member]/ncs:module[ncs:name='Cisco-IOS-XR-ipv4-bgp-act']";
      tailf:action clear-bgp-afi-safi-flap-statistics-ip-addr {
        tailf:actionpoint ncsproxy {
          tailf:internal;
        }
        csc:xr-task "bgp";
        csc:cli-command "clear bgp <afi-safi-name> flap-statistics <ip-addr>";
        description
          "Clear flap statistics.
          ";
        input {
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device/ncs:rpc" {
    container rpc-clear-bgp-afi-safi-flap-statistics-ip-addr-ipv4-mask {
      tailf:ncs-device-type "netconf";
      tailf:display-when "not(../../ncs:module) or ../../ncs:module[ncs:name='Cisco-IOS-XR-ipv4-bgp-act']";
      tailf:action clear-bgp-afi-safi-flap-statistics-ip-addr-ipv4-mask {
        tailf:actionpoint ncsproxy {
          tailf:internal;
        }
        csc:xr-task "bgp";
        csc:cli-command "clear bgp <afi-safi-name> flap-statistics <ip-addr> <ipv4-mask>";
        description
          "Clear flap statistics.
          ";
        input {
          leaf afi-safi-name {
            mandatory true;
            type afi-safi-type;
            description
              "AFI and SAFI";
          }
          leaf ip-addr {
            mandatory true;
            type inet:ip-address;
            description
              "BGP neighbor address to clear";
          }
          leaf ipv4-mask {
            mandatory true;
            type ipv4-netmask;
            description
              "Network and mask or masklength to clear flap statistics";
          }
        }
      }
    }
  }
  augment "/ncs:devices/ncs:device-group/ncs:ned-id/ncs:rpc" {
    container rpc-clear-bgp-afi-safi-flap-statistics-ip-addr-ipv4-mask {
      tailf:ncs-device-type "netconf";
      tailf:display-when "/ncs:devices/ncs:device[ncs:name=current()/../../../ncs:member]/ncs:module[ncs:name='Cisco-IOS-XR-ipv4-bgp-act']";
      tailf:action clear-bgp-afi-safi-flap-statistics-ip-addr-ipv4-mask {
        tailf:actionpoint ncsproxy {
          tailf:internal;
        }
        csc:xr-task "bgp";
        csc:cli-command "clear bgp <afi-safi-name> flap-statistics <ip-addr> <ipv4-mask>";
        description
          "Clear flap statistics.
          ";
        input {
          leaf afi-safi-name {
            mandatory true;
            type afi-safi-type;
            description
              "AFI and SAFI";
          }
          leaf ip-addr {
            mandatory true;
            type inet:ip-address;
            description
              "BGP neighbor address to clear";
          }
          leaf ipv4-mask {
            mandatory true;
            type ipv4-netmask;
            description
              "Network and mask or masklength to clear flap statistics";
          }
        }
      }
    }
  }
  augment "/ncs:devices/ncs:device/ncs:rpc" {
    container rpc-clear-bgp-afi-safi-external-soft {
      tailf:ncs-device-type "netconf";
      tailf:display-when "not(../../ncs:module) or ../../ncs:module[ncs:name='Cisco-IOS-XR-ipv4-bgp-act']";
      tailf:action clear-bgp-afi-safi-external-soft {
        tailf:actionpoint ncsproxy {
          tailf:internal;
        }
        csc:xr-task "bgp";
        csc:cli-command "clear bgp <afi-safi-name> external soft";
        description
          "Clear all external peers.
           Soft reconfig.
          ";
        input {
          leaf afi-safi-name {
            mandatory true;
            type afi-safi-type;
            description
              "AFI and SAFI";
          }
        }
      }
    }
  }
  augment "/ncs:devices/ncs:device-group/ncs:ned-id/ncs:rpc" {
    container rpc-clear-bgp-afi-safi-external-soft {
      tailf:ncs-device-type "netconf";
      tailf:display-when "/ncs:devices/ncs:device[ncs:name=current()/../../../ncs:member]/ncs:module[ncs:name='Cisco-IOS-XR-ipv4-bgp-act']";
      tailf:action clear-bgp-afi-safi-external-soft {
        tailf:actionpoint ncsproxy {
          tailf:internal;
        }
        csc:xr-task "bgp";
        csc:cli-command "clear bgp <afi-safi-name> external soft";
        description
          "Clear all external peers.
           Soft reconfig.
          ";
        input {
          leaf afi-safi-name {
            mandatory true;
            type afi-safi-type;
            description
              "AFI and SAFI";
          }
        }
      }
    }
  }
  augment "/ncs:devices/ncs:device/ncs:rpc" {
    container rpc-clear-bgp-afi-safi-external-soft-out {
      tailf:ncs-device-type "netconf";
      tailf:display-when "not(../../ncs:module) or ../../ncs:module[ncs:name='Cisco-IOS-XR-ipv4-bgp-act']";
      tailf:action clear-bgp-afi-safi-external-soft-out {
        tailf:actionpoint ncsproxy {
          tailf:internal;
        }
        csc:xr-task "bgp";
        csc:cli-command "clear bgp <afi-safi-name> external soft out";
        description
          "Clear all external peers.
           Soft reconfig.
           Soft reconfig outbound update.
          ";
        input {
          leaf afi-safi-name {
            mandatory true;
            type afi-safi-type;
            description
              "AFI and SAFI";
          }
        }
      }
    }
  }
  augment "/ncs:devices/ncs:device-group/ncs:ned-id/ncs:rpc" {
    container rpc-clear-bgp-afi-safi-external-soft-out {
      tailf:ncs-device-type "netconf";
      tailf:display-when "/ncs:devices/ncs:device[ncs:name=current()/../../../ncs:member]/ncs:module[ncs:name='Cisco-IOS-XR-ipv4-bgp-act']";
      tailf:action clear-bgp-afi-safi-external-soft-out {
        tailf:actionpoint ncsproxy {
          tailf:internal;
        }
        csc:xr-task "bgp";
        csc:cli-command "clear bgp <afi-safi-name> external soft out";
        description
          "Clear all external peers.
           Soft reconfig.
           Soft reconfig outbound update.
          ";
        input {
          leaf afi-safi-name {
            mandatory true;
            type afi-safi-type;
            description
              "AFI and SAFI";
          }
        }
      }
    }
  }
  augment "/ncs:devices/ncs:device/ncs:rpc" {
    container rpc-clear-bgp-afi-safi-external-soft-in {
      tailf:ncs-device-type "netconf";
      tailf:display-when "not(../../ncs:module) or ../../ncs:module[ncs:name='Cisco-IOS-XR-ipv4-bgp-act']";
      tailf:action clear-bgp-afi-safi-external-soft-in {
        tailf:actionpoint ncsproxy {
          tailf:internal;
        }
        csc:xr-task "bgp";
        csc:cli-command "clear bgp <afi-safi-name> external soft in";
        description
          "Clear all external peers.
           Soft reconfig.
           Soft reconfig inbound update.
          ";
        input {
          leaf afi-safi-name {
            mandatory true;
            type afi-safi-type;
            description
              "AFI and SAFI";
          }
        }
      }
    }
  }
  augment "/ncs:devices/ncs:device-group/ncs:ned-id/ncs:rpc" {
    container rpc-clear-bgp-afi-safi-external-soft-in {
      tailf:ncs-device-type "netconf";
      tailf:display-when "/ncs:devices/ncs:device[ncs:name=current()/../../../ncs:member]/ncs:module[ncs:name='Cisco-IOS-XR-ipv4-bgp-act']";
      tailf:action clear-bgp-afi-safi-external-soft-in {
        tailf:actionpoint ncsproxy {
          tailf:internal;
        }
        csc:xr-task "bgp";
        csc:cli-command "clear bgp <afi-safi-name> external soft in";
        description
          "Clear all external peers.
           Soft reconfig.
           Soft reconfig inbound update.
          ";
        input {
          leaf afi-safi-name {
            mandatory true;
            type afi-safi-type;
            description
              "AFI and SAFI";
          }
        }
      }
    }
  }
  augment "/ncs:devices/ncs:device/ncs:rpc" {
    container rpc-clear-bgp-afi-safi-external-soft-in-prefix-filter {
      tailf:ncs-device-type "netconf";
      tailf:display-when "not(../../ncs:module) or ../../ncs:module[ncs:name='Cisco-IOS-XR-ipv4-bgp-act']";
      tailf:action clear-bgp-afi-safi-external-soft-in-prefix-filter {
        tailf:actionpoint ncsproxy {
          tailf:internal;
        }
        csc:xr-task "bgp";
        csc:cli-command "clear bgp <afi-safi-name> external soft in prefix-filter";
        description
          "Clear all external peers.
           Soft reconfig.
           Soft reconfig inbound update.
           Push out prefix ORF and do inbound soft reconfig.
          ";
        input {
          leaf afi-safi-name {
            mandatory true;
            type afi-safi-type;
            description
              "AFI and SAFI";
          }
        }
      }
    }
  }
  augment "/ncs:devices/ncs:device-group/ncs:ned-id/ncs:rpc" {
    container rpc-clear-bgp-afi-safi-external-soft-in-prefix-filter {
      tailf:ncs-device-type "netconf";
      tailf:display-when "/ncs:devices/ncs:device[ncs:name=current()/../../../ncs:member]/ncs:module[ncs:name='Cisco-IOS-XR-ipv4-bgp-act']";
      tailf:action clear-bgp-afi-safi-external-soft-in-prefix-filter {
        tailf:actionpoint ncsproxy {
          tailf:internal;
        }
        csc:xr-task "bgp";
        csc:cli-command "clear bgp <afi-safi-name> external soft in prefix-filter";
        description
          "Clear all external peers.
           Soft reconfig.
           Soft reconfig inbound update.
           Push out prefix ORF and do inbound soft reconfig.
          ";
        input {
          leaf afi-safi-name {
            mandatory true;
            type afi-safi-type;
            description
              "AFI and SAFI";
          }
        }
      }
    }
  }
  augment "/ncs:devices/ncs:device/ncs:rpc" {
    container rpc-clear-bgp-afi-safi-dampening {
      tailf:ncs-device-type "netconf";
      tailf:display-when "not(../../ncs:module) or ../../ncs:module[ncs:name='Cisco-IOS-XR-ipv4-bgp-act']";
      tailf:action clear-bgp-afi-safi-dampening {
        tailf:actionpoint ncsproxy {
          tailf:internal;
        }
        csc:xr-task "bgp";
        csc:cli-command "clear bgp <afi-safi-name> dampening";
        description
          "Clear route flap dampening information.
          ";
        input {
          leaf afi-safi-name {
            mandatory true;
            type afi-safi-type;
            description
              "AFI and SAFI";
          }
        }
      }
    }
  }
  augment "/ncs:devices/ncs:device-group/ncs:ned-id/ncs:rpc" {
    container rpc-clear-bgp-afi-safi-dampening {
      tailf:ncs-device-type "netconf";
      tailf:display-when "/ncs:devices/ncs:device[ncs:name=current()/../../../ncs:member]/ncs:module[ncs:name='Cisco-IOS-XR-ipv4-bgp-act']";
      tailf:action clear-bgp-afi-safi-dampening {
        tailf:actionpoint ncsproxy {
          tailf:internal;
        }
        csc:xr-task "bgp";
        csc:cli-command "clear bgp <afi-safi-name> dampening";
        description
          "Clear route flap dampening information.
          ";
        input {
          leaf afi-safi-name {
            mandatory true;
            type afi-safi-type;
            description
              "AFI and SAFI";
          }
        }
      }
    }
  }
  augment "/ncs:devices/ncs:device/ncs:rpc" {
    container rpc-clear-bgp-afi-safi-dampening-ip-prefix {
      tailf:ncs-device-type "netconf";
      tailf:display-when "not(../../ncs:module) or ../../ncs:module[ncs:name='Cisco-IOS-XR-ipv4-bgp-act']";
      tailf:action clear-bgp-afi-safi-dampening-ip-prefix {
        tailf:actionpoint ncsproxy {
          tailf:internal;
        }
        csc:xr-task "bgp";
        csc:cli-command "clear bgp <afi-safi-name> dampening <ip-prefix>";
        description
          "Clear route flap dampening information.
          ";
        input {
          leaf afi-safi-name {
            mandatory true;
            type afi-safi-type;
            description
              "AFI and SAFI";
          }
          leaf ip-prefix {
            mandatory true;
            type inet:ip-prefix;
            description
              "Network and mask or masklength to clear dampening information";
          }
        }
      }
    }
  }
  augment "/ncs:devices/ncs:device-group/ncs:ned-id/ncs:rpc" {
    container rpc-clear-bgp-afi-safi-dampening-ip-prefix {
      tailf:ncs-device-type "netconf";
      tailf:display-when "/ncs:devices/ncs:device[ncs:name=current()/../../../ncs:member]/ncs:module[ncs:name='Cisco-IOS-XR-ipv4-bgp-act']";
      tailf:action clear-bgp-afi-safi-dampening-ip-prefix {
        tailf:actionpoint ncsproxy {
          tailf:internal;
        }
        csc:xr-task "bgp";
        csc:cli-command "clear bgp <afi-safi-name> dampening <ip-prefix>";
        description
          "Clear route flap dampening information.
          ";
        input {
          leaf afi-safi-name {
            mandatory true;
            type afi-safi-type;
            description
              "AFI and SAFI";
          }
          leaf ip-prefix {
            mandatory true;
            type inet:ip-prefix;
            description
              "Network and mask or masklength to clear dampening information";
          }
        }
      }
    }
  }
  augment "/ncs:devices/ncs:device/ncs:rpc" {
    container rpc-clear-bgp-afi-safi-as-soft {
      tailf:ncs-device-type "netconf";
      tailf:display-when "not(../../ncs:module) or ../../ncs:module[ncs:name='Cisco-IOS-XR-ipv4-bgp-act']";
      tailf:action clear-bgp-afi-safi-as-soft {
        tailf:actionpoint ncsproxy {
          tailf:internal;
        }
        csc:xr-task "bgp";
        csc:cli-command "clear bgp <afi-safi-name> as <as-number> soft";
        description
          "Clear peers in a specific AS.
           Soft reconfig.
          ";
        input {
          leaf afi-safi-name {
            mandatory true;
            type afi-safi-type;
            description
              "AFI and SAFI";
          }
          leaf as-number {
            mandatory true;
            type as-number;
            description
              "AS number";
          }
        }
      }
    }
  }
  augment "/ncs:devices/ncs:device-group/ncs:ned-id/ncs:rpc" {
    container rpc-clear-bgp-afi-safi-as-soft {
      tailf:ncs-device-type "netconf";
      tailf:display-when "/ncs:devices/ncs:device[ncs:name=current()/../../../ncs:member]/ncs:module[ncs:name='Cisco-IOS-XR-ipv4-bgp-act']";
      tailf:action clear-bgp-afi-safi-as-soft {
        tailf:actionpoint ncsproxy {
          tailf:internal;
        }
        csc:xr-task "bgp";
        csc:cli-command "clear bgp <afi-safi-name> as <as-number> soft";
        description
          "Clear peers in a specific AS.
           Soft reconfig.
          ";
        input {
          leaf afi-safi-name {
            mandatory true;
            type afi-safi-type;
            description
              "AFI and SAFI";
          }
          leaf as-number {
            mandatory true;
            type as-number;
            description
              "AS number";
          }
        }
      }
    }
  }
  augment "/ncs:devices/ncs:device/ncs:rpc" {
    container rpc-clear-bgp-afi-safi-as-soft-out {
      tailf:ncs-device-type "netconf";
      tailf:display-when "not(../../ncs:module) or ../../ncs:module[ncs:name='Cisco-IOS-XR-ipv4-bgp-act']";
      tailf:action clear-bgp-afi-safi-as-soft-out {
        tailf:actionpoint ncsproxy {
          tailf:internal;
        }
        csc:xr-task "bgp";
        csc:cli-command "clear bgp <afi-safi-name> as <as-number> soft out";
        description
          "Clear peers in a specific AS.
           Soft reconfig.
           Soft reconfig outbound update.
          ";
        input {
          leaf afi-safi-name {
            mandatory true;
            type afi-safi-type;
            description
              "AFI and SAFI";
          }
          leaf as-number {
            mandatory true;
            type as-number;
            description
              "AS number";
          }
        }
      }
    }
  }
  augment "/ncs:devices/ncs:device-group/ncs:ned-id/ncs:rpc" {
    container rpc-clear-bgp-afi-safi-as-soft-out {
      tailf:ncs-device-type "netconf";
      tailf:display-when "/ncs:devices/ncs:device[ncs:name=current()/../../../ncs:member]/ncs:module[ncs:name='Cisco-IOS-XR-ipv4-bgp-act']";
      tailf:action clear-bgp-afi-safi-as-soft-out {
        tailf:actionpoint ncsproxy {
          tailf:internal;
        }
        csc:xr-task "bgp";
        csc:cli-command "clear bgp <afi-safi-name> as <as-number> soft out";
        description
          "Clear peers in a specific AS.
           Soft reconfig.
           Soft reconfig outbound update.
          ";
        input {
          leaf afi-safi-name {
            mandatory true;
            type afi-safi-type;
            description
              "AFI and SAFI";
          }
          leaf as-number {
            mandatory true;
            type as-number;
            description
              "AS number";
          }
        }
      }
    }
  }
  augment "/ncs:devices/ncs:device/ncs:rpc" {
    container rpc-clear-bgp-afi-safi-as-soft-in {
      tailf:ncs-device-type "netconf";
      tailf:display-when "not(../../ncs:module) or ../../ncs:module[ncs:name='Cisco-IOS-XR-ipv4-bgp-act']";
      tailf:action clear-bgp-afi-safi-as-soft-in {
        tailf:actionpoint ncsproxy {
          tailf:internal;
        }
        csc:xr-task "bgp";
        csc:cli-command "clear bgp <afi-safi-name> as <as-number> soft in";
        description
          "Clear peers in a specific AS.
           Soft reconfig.
           Soft reconfig inbound update.
          ";
        input {
          leaf afi-safi-name {
            mandatory true;
            type afi-safi-type;
            description
              "AFI and SAFI";
          }
          leaf as-number {
            mandatory true;
            type as-number;
            description
              "AS number";
          }
        }
      }
    }
  }
  augment "/ncs:devices/ncs:device-group/ncs:ned-id/ncs:rpc" {
    container rpc-clear-bgp-afi-safi-as-soft-in {
      tailf:ncs-device-type "netconf";
      tailf:display-when "/ncs:devices/ncs:device[ncs:name=current()/../../../ncs:member]/ncs:module[ncs:name='Cisco-IOS-XR-ipv4-bgp-act']";
      tailf:action clear-bgp-afi-safi-as-soft-in {
        tailf:actionpoint ncsproxy {
          tailf:internal;
        }
        csc:xr-task "bgp";
        csc:cli-command "clear bgp <afi-safi-name> as <as-number> soft in";
        description
          "Clear peers in a specific AS.
           Soft reconfig.
           Soft reconfig inbound update.
          ";
        input {
          leaf afi-safi-name {
            mandatory true;
            type afi-safi-type;
            description
              "AFI and SAFI";
          }
          leaf as-number {
            mandatory true;
            type as-number;
            description
              "AS number";
          }
        }
      }
    }
  }
  augment "/ncs:devices/ncs:device/ncs:rpc" {
    container rpc-clear-bgp-afi-safi-as-soft-in-prefix-filter {
      tailf:ncs-device-type "netconf";
      tailf:display-when "not(../../ncs:module) or ../../ncs:module[ncs:name='Cisco-IOS-XR-ipv4-bgp-act']";
      tailf:action clear-bgp-afi-safi-as-soft-in-prefix-filter {
        tailf:actionpoint ncsproxy {
          tailf:internal;
        }
        csc:xr-task "bgp";
        csc:cli-command "clear bgp <afi-safi-name> as <as-number> soft in prefix-filter";
        description
          "Clear peers in a specific AS.
           Soft reconfig.
           Soft reconfig inbound update.
           Push out prefix ORF and do inbound soft reconfig.
          ";
        input {
          leaf afi-safi-name {
            mandatory true;
            type afi-safi-type;
            description
              "AFI and SAFI";
          }
          leaf as-number {
            mandatory true;
            type as-number;
            description
              "AS number";
          }
        }
      }
    }
  }
  augment "/ncs:devices/ncs:device-group/ncs:ned-id/ncs:rpc" {
    container rpc-clear-bgp-afi-safi-as-soft-in-prefix-filter {
      tailf:ncs-device-type "netconf";
      tailf:display-when "/ncs:devices/ncs:device[ncs:name=current()/../../../ncs:member]/ncs:module[ncs:name='Cisco-IOS-XR-ipv4-bgp-act']";
      tailf:action clear-bgp-afi-safi-as-soft-in-prefix-filter {
        tailf:actionpoint ncsproxy {
          tailf:internal;
        }
        csc:xr-task "bgp";
        csc:cli-command "clear bgp <afi-safi-name> as <as-number> soft in prefix-filter";
        description
          "Clear peers in a specific AS.
           Soft reconfig.
           Soft reconfig inbound update.
           Push out prefix ORF and do inbound soft reconfig.
          ";
        input {
          leaf afi-safi-name {
            mandatory true;
            type afi-safi-type;
            description
              "AFI and SAFI";
          }
          leaf as-number {
            mandatory true;
            type as-number;
            description
              "AS number";
          }
        }
      }
    }
  }
  augment "/ncs:devices/ncs:device/ncs:rpc" {
    container rpc-clear-bgp-afi-safi-ip-addr-soft {
      tailf:ncs-device-type "netconf";
      tailf:display-when "not(../../ncs:module) or ../../ncs:module[ncs:name='Cisco-IOS-XR-ipv4-bgp-act']";
      tailf:action clear-bgp-afi-safi-ip-addr-soft {
        tailf:actionpoint ncsproxy {
          tailf:internal;
        }
        csc:xr-task "bgp";
        csc:cli-command "clear bgp <afi-safi-name> <ip-addr> soft";
        description
          "Soft reconfig.
          ";
        input {
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device-group/ncs:ned-id/ncs:rpc" {
    container rpc-clear-bgp-afi-safi-ip-addr-soft {
      tailf:ncs-device-type "netconf";
      tailf:display-when "/ncs:devices/ncs:device[ncs:name=current()/../../../ncs:member]/ncs:module[ncs:name='Cisco-IOS-XR-ipv4-bgp-act']";
      tailf:action clear-bgp-afi-safi-ip-addr-soft {
        tailf:actionpoint ncsproxy {
          tailf:internal;
        }
        csc:xr-task "bgp";
        csc:cli-command "clear bgp <afi-safi-name> <ip-addr> soft";
        description
          "Soft reconfig.
          ";
        input {
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device/ncs:rpc" {
    container rpc-clear-bgp-afi-safi-ip-addr-soft-out {
      tailf:ncs-device-type "netconf";
      tailf:display-when "not(../../ncs:module) or ../../ncs:module[ncs:name='Cisco-IOS-XR-ipv4-bgp-act']";
      tailf:action clear-bgp-afi-safi-ip-addr-soft-out {
        tailf:actionpoint ncsproxy {
          tailf:internal;
        }
        csc:xr-task "bgp";
        csc:cli-command "clear bgp <afi-safi-name> <ip-addr> soft out";
        description
          "Soft reconfig.
           Soft reconfig outbound update.
          ";
        input {
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device-group/ncs:ned-id/ncs:rpc" {
    container rpc-clear-bgp-afi-safi-ip-addr-soft-out {
      tailf:ncs-device-type "netconf";
      tailf:display-when "/ncs:devices/ncs:device[ncs:name=current()/../../../ncs:member]/ncs:module[ncs:name='Cisco-IOS-XR-ipv4-bgp-act']";
      tailf:action clear-bgp-afi-safi-ip-addr-soft-out {
        tailf:actionpoint ncsproxy {
          tailf:internal;
        }
        csc:xr-task "bgp";
        csc:cli-command "clear bgp <afi-safi-name> <ip-addr> soft out";
        description
          "Soft reconfig.
           Soft reconfig outbound update.
          ";
        input {
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device/ncs:rpc" {
    container rpc-clear-bgp-afi-safi-ip-addr-soft-in {
      tailf:ncs-device-type "netconf";
      tailf:display-when "not(../../ncs:module) or ../../ncs:module[ncs:name='Cisco-IOS-XR-ipv4-bgp-act']";
      tailf:action clear-bgp-afi-safi-ip-addr-soft-in {
        tailf:actionpoint ncsproxy {
          tailf:internal;
        }
        csc:xr-task "bgp";
        csc:cli-command "clear bgp <afi-safi-name> <ip-addr> soft in";
        description
          "Soft reconfig.
           Soft reconfig inbound update.
          ";
        input {
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device-group/ncs:ned-id/ncs:rpc" {
    container rpc-clear-bgp-afi-safi-ip-addr-soft-in {
      tailf:ncs-device-type "netconf";
      tailf:display-when "/ncs:devices/ncs:device[ncs:name=current()/../../../ncs:member]/ncs:module[ncs:name='Cisco-IOS-XR-ipv4-bgp-act']";
      tailf:action clear-bgp-afi-safi-ip-addr-soft-in {
        tailf:actionpoint ncsproxy {
          tailf:internal;
        }
        csc:xr-task "bgp";
        csc:cli-command "clear bgp <afi-safi-name> <ip-addr> soft in";
        description
          "Soft reconfig.
           Soft reconfig inbound update.
          ";
        input {
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device/ncs:rpc" {
    container rpc-clear-bgp-afi-safi-ip-addr-soft-in-prefix-filter {
      tailf:ncs-device-type "netconf";
      tailf:display-when "not(../../ncs:module) or ../../ncs:module[ncs:name='Cisco-IOS-XR-ipv4-bgp-act']";
      tailf:action clear-bgp-afi-safi-ip-addr-soft-in-prefix-filter {
        tailf:actionpoint ncsproxy {
          tailf:internal;
        }
        csc:xr-task "bgp";
        csc:cli-command "clear bgp <afi-safi-name> <ip-addr> soft in prefix-filter";
        description
          "Soft reconfig.
           Soft reconfig inbound update.
           Push out prefix ORF and do inbound soft reconfig.
          ";
        input {
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device-group/ncs:ned-id/ncs:rpc" {
    container rpc-clear-bgp-afi-safi-ip-addr-soft-in-prefix-filter {
      tailf:ncs-device-type "netconf";
      tailf:display-when "/ncs:devices/ncs:device[ncs:name=current()/../../../ncs:member]/ncs:module[ncs:name='Cisco-IOS-XR-ipv4-bgp-act']";
      tailf:action clear-bgp-afi-safi-ip-addr-soft-in-prefix-filter {
        tailf:actionpoint ncsproxy {
          tailf:internal;
        }
        csc:xr-task "bgp";
        csc:cli-command "clear bgp <afi-safi-name> <ip-addr> soft in prefix-filter";
        description
          "Soft reconfig.
           Soft reconfig inbound update.
           Push out prefix ORF and do inbound soft reconfig.
          ";
        input {
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device/ncs:rpc" {
    container rpc-clear-bgp-afi-safi-ip-addr-long-lived-stale {
      tailf:ncs-device-type "netconf";
      tailf:display-when "not(../../ncs:module) or ../../ncs:module[ncs:name='Cisco-IOS-XR-ipv4-bgp-act']";
      tailf:action clear-bgp-afi-safi-ip-addr-long-lived-stale {
        tailf:actionpoint ncsproxy {
          tailf:internal;
        }
        csc:xr-task "bgp";
        csc:cli-command "clear bgp <afi-safi-name> <ip-addr> long-lived-stale";
        description
          "Clear long-lived-stale routes.
          ";
        input {
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device-group/ncs:ned-id/ncs:rpc" {
    container rpc-clear-bgp-afi-safi-ip-addr-long-lived-stale {
      tailf:ncs-device-type "netconf";
      tailf:display-when "/ncs:devices/ncs:device[ncs:name=current()/../../../ncs:member]/ncs:module[ncs:name='Cisco-IOS-XR-ipv4-bgp-act']";
      tailf:action clear-bgp-afi-safi-ip-addr-long-lived-stale {
        tailf:actionpoint ncsproxy {
          tailf:internal;
        }
        csc:xr-task "bgp";
        csc:cli-command "clear bgp <afi-safi-name> <ip-addr> long-lived-stale";
        description
          "Clear long-lived-stale routes.
          ";
        input {
          leaf afi-safi-name {
            mandatory true;
            type afi-safi-type;
            description
              "AFI and SAFI";
          }
          leaf ip-addr {
            mandatory true;
            type inet:ip-address;
            description
              "BGP neighbor address to clear";
          }
        }
      }
    }
  }
  augment "/ncs:devices/ncs:device/ncs:rpc" {
    container rpc-clear-bgp-afi-safi-all-soft {
      tailf:ncs-device-type "netconf";
      tailf:display-when "not(../../ncs:module) or ../../ncs:module[ncs:name='Cisco-IOS-XR-ipv4-bgp-act']";
      tailf:action clear-bgp-afi-safi-all-soft {
        tailf:actionpoint ncsproxy {
          tailf:internal;
        }
        csc:xr-task "bgp";
        csc:cli-command "clear bgp <afi-safi-name> * soft";
        description
          "Clear all peers and all routes from the BGP table.
           Soft reconfig.
          ";
        input {
          leaf afi-safi-name {
            mandatory true;
            type afi-safi-type;
            description
              "AFI and SAFI";
          }
        }
      }
    }
  }
  augment "/ncs:devices/ncs:device-group/ncs:ned-id/ncs:rpc" {
    container rpc-clear-bgp-afi-safi-all-soft {
      tailf:ncs-device-type "netconf";
      tailf:display-when "/ncs:devices/ncs:device[ncs:name=current()/../../../ncs:member]/ncs:module[ncs:name='Cisco-IOS-XR-ipv4-bgp-act']";
      tailf:action clear-bgp-afi-safi-all-soft {
        tailf:actionpoint ncsproxy {
          tailf:internal;
        }
        csc:xr-task "bgp";
        csc:cli-command "clear bgp <afi-safi-name> * soft";
        description
          "Clear all peers and all routes from the BGP table.
           Soft reconfig.
          ";
        input {
          leaf afi-safi-name {
            mandatory true;
            type afi-safi-type;
            description
              "AFI and SAFI";
          }
        }
      }
    }
  }
  augment "/ncs:devices/ncs:device/ncs:rpc" {
    container rpc-clear-bgp-afi-safi-all-soft-out {
      tailf:ncs-device-type "netconf";
      tailf:display-when "not(../../ncs:module) or ../../ncs:module[ncs:name='Cisco-IOS-XR-ipv4-bgp-act']";
      tailf:action clear-bgp-afi-safi-all-soft-out {
        tailf:actionpoint ncsproxy {
          tailf:internal;
        }
        csc:xr-task "bgp";
        csc:cli-command "clear bgp <afi-safi-name> * soft out";
        description
          "Clear all peers and all routes from the BGP table.
           Soft reconfig.
           Soft reconfig outbound update.
          ";
        input {
          leaf afi-safi-name {
            mandatory true;
            type afi-safi-type;
            description
              "AFI and SAFI";
          }
        }
      }
    }
  }
  augment "/ncs:devices/ncs:device-group/ncs:ned-id/ncs:rpc" {
    container rpc-clear-bgp-afi-safi-all-soft-out {
      tailf:ncs-device-type "netconf";
      tailf:display-when "/ncs:devices/ncs:device[ncs:name=current()/../../../ncs:member]/ncs:module[ncs:name='Cisco-IOS-XR-ipv4-bgp-act']";
      tailf:action clear-bgp-afi-safi-all-soft-out {
        tailf:actionpoint ncsproxy {
          tailf:internal;
        }
        csc:xr-task "bgp";
        csc:cli-command "clear bgp <afi-safi-name> * soft out";
        description
          "Clear all peers and all routes from the BGP table.
           Soft reconfig.
           Soft reconfig outbound update.
          ";
        input {
          leaf afi-safi-name {
            mandatory true;
            type afi-safi-type;
            description
              "AFI and SAFI";
          }
        }
      }
    }
  }
  augment "/ncs:devices/ncs:device/ncs:rpc" {
    container rpc-clear-bgp-afi-safi-all-soft-in {
      tailf:ncs-device-type "netconf";
      tailf:display-when "not(../../ncs:module) or ../../ncs:module[ncs:name='Cisco-IOS-XR-ipv4-bgp-act']";
      tailf:action clear-bgp-afi-safi-all-soft-in {
        tailf:actionpoint ncsproxy {
          tailf:internal;
        }
        csc:xr-task "bgp";
        csc:cli-command "clear bgp <afi-safi-name> * soft in";
        description
          "Clear all peers and all routes from the BGP table.
           Soft reconfig.
           Soft reconfig inbound update.
          ";
        input {
          leaf afi-safi-name {
            mandatory true;
            type afi-safi-type;
            description
              "AFI and SAFI";
          }
        }
      }
    }
  }
  augment "/ncs:devices/ncs:device-group/ncs:ned-id/ncs:rpc" {
    container rpc-clear-bgp-afi-safi-all-soft-in {
      tailf:ncs-device-type "netconf";
      tailf:display-when "/ncs:devices/ncs:device[ncs:name=current()/../../../ncs:member]/ncs:module[ncs:name='Cisco-IOS-XR-ipv4-bgp-act']";
      tailf:action clear-bgp-afi-safi-all-soft-in {
        tailf:actionpoint ncsproxy {
          tailf:internal;
        }
        csc:xr-task "bgp";
        csc:cli-command "clear bgp <afi-safi-name> * soft in";
        description
          "Clear all peers and all routes from the BGP table.
           Soft reconfig.
           Soft reconfig inbound update.
          ";
        input {
          leaf afi-safi-name {
            mandatory true;
            type afi-safi-type;
            description
              "AFI and SAFI";
          }
        }
      }
    }
  }
  augment "/ncs:devices/ncs:device/ncs:rpc" {
    container rpc-clear-bgp-afi-safi-all-soft-in-prefix-filter {
      tailf:ncs-device-type "netconf";
      tailf:display-when "not(../../ncs:module) or ../../ncs:module[ncs:name='Cisco-IOS-XR-ipv4-bgp-act']";
      tailf:action clear-bgp-afi-safi-all-soft-in-prefix-filter {
        tailf:actionpoint ncsproxy {
          tailf:internal;
        }
        csc:xr-task "bgp";
        csc:cli-command "clear bgp <afi-safi-name> * soft in prefix-filter";
        description
          "Clear all peers and all routes from the BGP table.
           Soft reconfig.
           Soft reconfig inbound update.
           Push out prefix ORF and do inbound soft reconfig.
          ";
        input {
          leaf afi-safi-name {
            mandatory true;
            type afi-safi-type;
            description
              "AFI and SAFI";
          }
        }
      }
    }
  }
  augment "/ncs:devices/ncs:device-group/ncs:ned-id/ncs:rpc" {
    container rpc-clear-bgp-afi-safi-all-soft-in-prefix-filter {
      tailf:ncs-device-type "netconf";
      tailf:display-when "/ncs:devices/ncs:device[ncs:name=current()/../../../ncs:member]/ncs:module[ncs:name='Cisco-IOS-XR-ipv4-bgp-act']";
      tailf:action clear-bgp-afi-safi-all-soft-in-prefix-filter {
        tailf:actionpoint ncsproxy {
          tailf:internal;
        }
        csc:xr-task "bgp";
        csc:cli-command "clear bgp <afi-safi-name> * soft in prefix-filter";
        description
          "Clear all peers and all routes from the BGP table.
           Soft reconfig.
           Soft reconfig inbound update.
           Push out prefix ORF and do inbound soft reconfig.
          ";
        input {
          leaf afi-safi-name {
            mandatory true;
            type afi-safi-type;
            description
              "AFI and SAFI";
          }
        }
      }
    }
  }
  augment "/ncs:devices/ncs:device/ncs:rpc" {
    container rpc-clear-bgp-ip-addr {
      tailf:ncs-device-type "netconf";
      tailf:display-when "not(../../ncs:module) or ../../ncs:module[ncs:name='Cisco-IOS-XR-ipv4-bgp-act']";
      tailf:action clear-bgp-ip-addr {
        tailf:actionpoint ncsproxy {
          tailf:internal;
        }
        csc:xr-task "bgp";
        csc:cli-command "clear bgp <ip-addr>";
        description
          "BGP neighbor address to clear.
          ";
        input {
          leaf ip-addr {
            mandatory true;
            type inet:ip-address;
            description
              "BGP neighbor address to clear";
          }
        }
      }
    }
  }
  augment "/ncs:devices/ncs:device-group/ncs:ned-id/ncs:rpc" {
    container rpc-clear-bgp-ip-addr {
      tailf:ncs-device-type "netconf";
      tailf:display-when "/ncs:devices/ncs:device[ncs:name=current()/../../../ncs:member]/ncs:module[ncs:name='Cisco-IOS-XR-ipv4-bgp-act']";
      tailf:action clear-bgp-ip-addr {
        tailf:actionpoint ncsproxy {
          tailf:internal;
        }
        csc:xr-task "bgp";
        csc:cli-command "clear bgp <ip-addr>";
        description
          "BGP neighbor address to clear.
          ";
        input {
          leaf ip-addr {
            mandatory true;
            type inet:ip-address;
            description
              "BGP neighbor address to clear";
          }
        }
      }
    }
  }
  augment "/ncs:devices/ncs:device/ncs:rpc" {
    container rpc-clear-bgp-ip-addr-long-lived-stale {
      tailf:ncs-device-type "netconf";
      tailf:display-when "not(../../ncs:module) or ../../ncs:module[ncs:name='Cisco-IOS-XR-ipv4-bgp-act']";
      tailf:action clear-bgp-ip-addr-long-lived-stale {
        tailf:actionpoint ncsproxy {
          tailf:internal;
        }
        csc:xr-task "bgp";
        csc:cli-command "clear bgp <ip-addr> long-lived-stale";
        description
          "BGP neighbor address to clear.
           Clear long-lived-stale routes.
          ";
        input {
          leaf ip-addr {
            mandatory true;
            type inet:ip-address;
            description
              "BGP neighbor address to clear";
          }
        }
      }
    }
  }
  augment "/ncs:devices/ncs:device-group/ncs:ned-id/ncs:rpc" {
    container rpc-clear-bgp-ip-addr-long-lived-stale {
      tailf:ncs-device-type "netconf";
      tailf:display-when "/ncs:devices/ncs:device[ncs:name=current()/../../../ncs:member]/ncs:module[ncs:name='Cisco-IOS-XR-ipv4-bgp-act']";
      tailf:action clear-bgp-ip-addr-long-lived-stale {
        tailf:actionpoint ncsproxy {
          tailf:internal;
        }
        csc:xr-task "bgp";
        csc:cli-command "clear bgp <ip-addr> long-lived-stale";
        description
          "BGP neighbor address to clear.
           Clear long-lived-stale routes.
          ";
        input {
          leaf ip-addr {
            mandatory true;
            type inet:ip-address;
            description
              "BGP neighbor address to clear";
          }
        }
      }
    }
  }
  augment "/ncs:devices/ncs:device/ncs:rpc" {
    container rpc-clear-bgp-ip-addr-graceful {
      tailf:ncs-device-type "netconf";
      tailf:display-when "not(../../ncs:module) or ../../ncs:module[ncs:name='Cisco-IOS-XR-ipv4-bgp-act']";
      tailf:action clear-bgp-ip-addr-graceful {
        tailf:actionpoint ncsproxy {
          tailf:internal;
        }
        csc:xr-task "bgp";
        csc:cli-command "clear bgp <ip-addr> graceful";
        description
          "BGP neighbor address to clear.
           Clear with a hard reset and a graceful restart.
          ";
        input {
          leaf ip-addr {
            mandatory true;
            type inet:ip-address;
            description
              "BGP neighbor address to clear";
          }
        }
      }
    }
  }
  augment "/ncs:devices/ncs:device-group/ncs:ned-id/ncs:rpc" {
    container rpc-clear-bgp-ip-addr-graceful {
      tailf:ncs-device-type "netconf";
      tailf:display-when "/ncs:devices/ncs:device[ncs:name=current()/../../../ncs:member]/ncs:module[ncs:name='Cisco-IOS-XR-ipv4-bgp-act']";
      tailf:action clear-bgp-ip-addr-graceful {
        tailf:actionpoint ncsproxy {
          tailf:internal;
        }
        csc:xr-task "bgp";
        csc:cli-command "clear bgp <ip-addr> graceful";
        description
          "BGP neighbor address to clear.
           Clear with a hard reset and a graceful restart.
          ";
        input {
          leaf ip-addr {
            mandatory true;
            type inet:ip-address;
            description
              "BGP neighbor address to clear";
          }
        }
      }
    }
  }
  augment "/ncs:devices/ncs:device/ncs:rpc" {
    container rpc-clear-bgp-all {
      tailf:ncs-device-type "netconf";
      tailf:display-when "not(../../ncs:module) or ../../ncs:module[ncs:name='Cisco-IOS-XR-ipv4-bgp-act']";
      tailf:action clear-bgp-all {
        tailf:actionpoint ncsproxy {
          tailf:internal;
        }
        csc:xr-task "bgp";
        csc:cli-command "clear bgp *";
        description
          "Clear all peers and all routes from the BGP table.
          ";
      }
    }
  }
  augment "/ncs:devices/ncs:device-group/ncs:ned-id/ncs:rpc" {
    container rpc-clear-bgp-all {
      tailf:ncs-device-type "netconf";
      tailf:display-when "/ncs:devices/ncs:device[ncs:name=current()/../../../ncs:member]/ncs:module[ncs:name='Cisco-IOS-XR-ipv4-bgp-act']";
      tailf:action clear-bgp-all {
        tailf:actionpoint ncsproxy {
          tailf:internal;
        }
        csc:xr-task "bgp";
        csc:cli-command "clear bgp *";
        description
          "Clear all peers and all routes from the BGP table.
          ";
      }
    }
  }
  augment "/ncs:devices/ncs:device/ncs:rpc" {
    container rpc-clear-bgp-all-graceful {
      tailf:ncs-device-type "netconf";
      tailf:display-when "not(../../ncs:module) or ../../ncs:module[ncs:name='Cisco-IOS-XR-ipv4-bgp-act']";
      tailf:action clear-bgp-all-graceful {
        tailf:actionpoint ncsproxy {
          tailf:internal;
        }
        csc:xr-task "bgp";
        csc:cli-command "clear bgp * graceful";
        description
          "Clear all peers and all routes from the BGP table.
           Clear with a hard reset and a graceful restart.
          ";
      }
    }
  }
  augment "/ncs:devices/ncs:device-group/ncs:ned-id/ncs:rpc" {
    container rpc-clear-bgp-all-graceful {
      tailf:ncs-device-type "netconf";
      tailf:display-when "/ncs:devices/ncs:device[ncs:name=current()/../../../ncs:member]/ncs:module[ncs:name='Cisco-IOS-XR-ipv4-bgp-act']";
      tailf:action clear-bgp-all-graceful {
        tailf:actionpoint ncsproxy {
          tailf:internal;
        }
        csc:xr-task "bgp";
        csc:cli-command "clear bgp * graceful";
        description
          "Clear all peers and all routes from the BGP table.
           Clear with a hard reset and a graceful restart.
          ";
      }
    }
  }
}
