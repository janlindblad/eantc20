module Cisco-IOS-XR-sysmgr-act {
  // Generated by yanger -t ncs
  tailf:mount-id f5500-nc-1.0:f5500-nc-1.0;
  tailf:ncs-device-type "netconf";

  namespace "http://cisco.com/ns/yang/Cisco-IOS-XR-sysmgr-act";
  prefix Cisco-IOS-XR-sysmgr-act;

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR sysmgr action package configuration.

     Copyright (c) 2016-2017 by Cisco Systems, Inc.
     All rights reserved.";

  revision 2017-03-03 {
    description
      "IOS XR 6.3.1 revision.";
  }

  augment "/ncs:devices/ncs:device/ncs:rpc" {
    container rpc-sysmgr-process-restart {
      tailf:ncs-device-type "netconf";
      tailf:display-when "not(../../ncs:module) or ../../ncs:module[ncs:name='Cisco-IOS-XR-sysmgr-act']";
      tailf:action sysmgr-process-restart {
        tailf:actionpoint ncsproxy {
          tailf:internal;
        }
        description
          "Restart an XR process";
        input {
          leaf process-name {
            description
              "XR process name or Job Id e.g. bgp, ospf";
            type string;
            mandatory true;
          }
          leaf location {
            description
              "XR node identifier e.g. 0/RP0/CPU0, 0/0/CPU0";
            type string;
          }
        }
      }
    }
  }
  augment "/ncs:devices/ncs:device-group/ncs:ned-id/ncs:rpc" {
    container rpc-sysmgr-process-restart {
      tailf:ncs-device-type "netconf";
      tailf:display-when "/ncs:devices/ncs:device[ncs:name=current()/../../../ncs:member]/ncs:module[ncs:name='Cisco-IOS-XR-sysmgr-act']";
      tailf:action sysmgr-process-restart {
        tailf:actionpoint ncsproxy {
          tailf:internal;
        }
        description
          "Restart an XR process";
        input {
          leaf process-name {
            description
              "XR process name or Job Id e.g. bgp, ospf";
            type string;
            mandatory true;
          }
          leaf location {
            description
              "XR node identifier e.g. 0/RP0/CPU0, 0/0/CPU0";
            type string;
          }
        }
      }
    }
  }
}
