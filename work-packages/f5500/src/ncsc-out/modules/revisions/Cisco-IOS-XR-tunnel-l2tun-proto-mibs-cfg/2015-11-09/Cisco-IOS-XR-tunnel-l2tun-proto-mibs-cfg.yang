module Cisco-IOS-XR-tunnel-l2tun-proto-mibs-cfg {
  // Generated by yanger -t ncs
  tailf:mount-id f5500-nc-1.0:f5500-nc-1.0;
  tailf:ncs-device-type "netconf";

  namespace "http://cisco.com/ns/yang/Cisco-IOS-XR-tunnel-l2tun-proto-mibs-cfg";
  prefix Cisco-IOS-XR-tunnel-l2tun-proto-mibs-cfg;

  import Cisco-IOS-XR-snmp-agent-cfg {
    prefix a1;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR tunnel-l2tun-proto-mibs package configuration.

     This YANG module augments the
       Cisco-IOS-XR-snmp-agent-cfg
     module with configuration data.

     Copyright (c) 2013-2018 by Cisco Systems, Inc.
     All rights reserved.";

  revision 2015-11-09 {
    description
      "IOS XR 6.0 revision.";
  }

  augment "/ncs:devices/ncs:template/ncs:ned-id/ncs:config/a1:snmp/a1:notification" {
    container l2tun {
      description
        "Enable SNMP l2tun traps";
      leaf tunnel-up {
        type string;
        description
          "Enable L2TUN tunnel UP traps";
      }
      leaf tunnel-down {
        type string;
        description
          "Enable L2TUN tunnel DOWN traps";
      }
      leaf pseudowire-status {
        type string;
        description
          "Enable traps for L2TPv3 PW status";
      }
      leaf sessions {
        type string;
        description
          "Enable L2TUN sessions traps";
      }
    }
    description
      "This augment extends the configuration data of
       'Cisco-IOS-XR-snmp-agent-cfg'";
  }
  augment "/ncs:devices/ncs:device/ncs:live-status/a1:snmp/a1:notification" {
    container l2tun {
      tailf:ncs-device-type "netconf";
      tailf:display-when "not(../../../../ncs:module) or ../../../../ncs:module[ncs:name='Cisco-IOS-XR-tunnel-l2tun-proto-mibs-cfg'] or (../../../../ncs:live-status-protocol[not(ncs:capability)]) or (../../../../ncs:live-status-protocol/ncs:capability/ncs:module[.='Cisco-IOS-XR-tunnel-l2tun-proto-mibs-cfg'])";
      description
        "Enable SNMP l2tun traps";
      leaf tunnel-up {
        type boolean;
        description
          "Enable L2TUN tunnel UP traps";
      }
      leaf tunnel-down {
        type boolean;
        description
          "Enable L2TUN tunnel DOWN traps";
      }
      leaf pseudowire-status {
        type boolean;
        description
          "Enable traps for L2TPv3 PW status";
      }
      leaf sessions {
        type boolean;
        description
          "Enable L2TUN sessions traps";
      }
    }
    description
      "This augment extends the configuration data of
       'Cisco-IOS-XR-snmp-agent-cfg'";
  }
  augment "/ncs:devices/ncs:device/ncs:config/a1:snmp/a1:notification" {
    container l2tun {
      tailf:ncs-device-type "netconf";
      tailf:display-when "not(../../../../ncs:module) or ../../../../ncs:module[ncs:name='Cisco-IOS-XR-tunnel-l2tun-proto-mibs-cfg']";
      description
        "Enable SNMP l2tun traps";
      leaf tunnel-up {
        type boolean;
        description
          "Enable L2TUN tunnel UP traps";
      }
      leaf tunnel-down {
        type boolean;
        description
          "Enable L2TUN tunnel DOWN traps";
      }
      leaf pseudowire-status {
        type boolean;
        description
          "Enable traps for L2TPv3 PW status";
      }
      leaf sessions {
        type boolean;
        description
          "Enable L2TUN sessions traps";
      }
    }
    description
      "This augment extends the configuration data of
       'Cisco-IOS-XR-snmp-agent-cfg'";
  }
}
