module Cisco-IOS-XR-sysadmin-card-mgr {
  // Generated by yanger -t ncs
  tailf:mount-id f5500-nc-1.0:f5500-nc-1.0;
  tailf:ncs-device-type "netconf";

  namespace "http://www.cisco.com/ns/yang/Cisco-IOS-XR-sysadmin-card-mgr";
  prefix Cisco-IOS-XR-sysadmin-card-mgr;

  import Cisco-IOS-XR-sysadmin-show-trace {
    prefix show_trace;
  }
  import Cisco-IOS-XR-sysadmin-types {
    prefix calvados;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains definitions
     for the Calvados model objects.

     The 'card_mgr' module provides support for access to detail card HW information like power status, card state, inventory info, etc.

     Copyright (c) 2012-2018 by Cisco Systems, Inc.
     All rights reserved.";

  revision 2018-04-09 {
    description
      "Required changes for ConfD 6.4.5";
  }

  typedef HexOffset {
    type string;
  }

  typedef endHexOffset {
    type string;
  }

  typedef startHexOffset {
    type string;
  }

  grouping ncs_template_card_mgr-group {
    container card_mgr {
      uses show_trace:ncs_template_traceable;
      uses ncs_template_inventory-group;
      uses ncs_template_event-hist-group;
      uses ncs_template_notif-hist-group;
      uses ncs_template_oir-hist-group;
      uses ncs_template_iofpga-group;
      uses ncs_template_bootldr-group;
    }
  }

  grouping ncs_template_inventory-group {
    // NCS drop config false container inventory
  }

  grouping ncs_template_inventory-summary-group {
    // NCS drop config false container summary
  }

  grouping ncs_template_inventory-detail-group {
    // NCS drop config false container detail
  }

  grouping ncs_template_event-hist-group {
    // NCS drop config false container 'event-history'
  }

  grouping ncs_template_event-hist-group-brief {
    list location {
      // NCS patched for predictable order
      ordered-by user;
      key "location";
      leaf location {
        type string;
      }
      container card_event_hist_brief {
        leaf-list card_event_hist_brief_values {
          // NCS patched for predictable order
          ordered-by user;
          type string;
        }
      }
    }
  }

  grouping ncs_template_event-hist-group-detail {
    list location {
      // NCS patched for predictable order
      ordered-by user;
      key "location";
      leaf location {
        type string;
      }
      container card_event_hist_detail {
        leaf-list card_event_hist_detail_values {
          // NCS patched for predictable order
          ordered-by user;
          type string;
        }
      }
    }
  }

  grouping ncs_template_notif-hist-group {
    // NCS drop config false container 'notif-history'
  }

  grouping ncs_template_notif-hist-group-brief {
    list location {
      // NCS patched for predictable order
      ordered-by user;
      key "location";
      leaf location {
        type string;
      }
      container card_notif_hist_brief {
        leaf-list card_notif_hist_brief_values {
          // NCS patched for predictable order
          ordered-by user;
          type string;
        }
      }
    }
  }

  grouping ncs_template_notif-hist-group-detail {
    list location {
      // NCS patched for predictable order
      ordered-by user;
      key "location";
      leaf location {
        type string;
      }
      container card_notif_hist_detail {
        leaf-list card_notif_hist_detail_values {
          // NCS patched for predictable order
          ordered-by user;
          type string;
        }
      }
    }
  }

  grouping ncs_template_oir-hist-group {
    // NCS drop config false container 'oir-history'
  }

  grouping ncs_template_iofpga-group {
    // NCS drop config false container iofpga
  }

  grouping ncs_template_iofpga-register-group {
    // NCS drop config false container register
  }

  grouping ncs_template_cpu-register-group {
    // NCS drop config false container cpu
  }

  grouping ncs_template_mb-register-group {
    // NCS drop config false container mb
  }

  grouping ncs_template_dc-register-group {
    // NCS drop config false container dc
  }

  grouping ncs_template_iofpga-block-number-group {
    // NCS drop config false list iofpga_block_number
  }

  grouping ncs_template_iofpga-offset-group {
    // NCS drop config false list iofpga_offset
  }

  grouping ncs_template_iofpga-address-group {
    // NCS drop config false list iofpga_address
  }

  grouping ncs_template_iofpga-flash-group {
    // NCS drop config false container flash
  }

  grouping ncs_template_iofpga-flash-info-group {
    // NCS drop config false container info
  }

  grouping ncs_template_iofpga-flash-status-group {
    // NCS drop config false container status
  }

  grouping ncs_template_bootldr-group {
    // NCS drop config false container bootloader
  }

  grouping ncs_template_bootldr-flash-group {
    // NCS drop config false container flash
  }

  grouping ncs_template_bootldr-flash-info-group {
    // NCS drop config false container info
  }

  grouping ncs_template_bootldr-flash-status-group {
    // NCS drop config false container status
  }

  grouping ncs_rpc_notif_card_mgr-group {
    container card_mgr {
      uses show_trace:ncs_rpc_notif_traceable;
      uses ncs_rpc_notif_inventory-group;
      uses ncs_rpc_notif_event-hist-group;
      uses ncs_rpc_notif_notif-hist-group;
      uses ncs_rpc_notif_oir-hist-group;
      uses ncs_rpc_notif_iofpga-group;
      uses ncs_rpc_notif_bootldr-group;
    }
  }

  grouping ncs_rpc_notif_inventory-group {
    container inventory {
      config false;
      uses ncs_rpc_notif_inventory-summary-group;
      uses ncs_rpc_notif_inventory-detail-group;
    }
  }

  grouping ncs_rpc_notif_inventory-summary-group {
    container summary {
      config false;
      list card_mgr_inv_summary {
        key "location";
        leaf location {
          type string;
          mandatory true;
        }
        leaf card_mgr_inv_PID_string {
          type string;
        }
        leaf card_mgr_inv_slot_number {
          type uint32;
        }
        leaf card_mgr_inv_serial_number {
          type string;
        }
        leaf card_mgr_inv_hw_version {
          type string;
        }
        leaf card_mgr_inv_card_state {
          type string;
        }
      }
    }
  }

  grouping ncs_rpc_notif_inventory-detail-group {
    container detail {
      config false;
      list card_mgr_inv_detail {
        key "location";
        leaf location {
          type string;
        }
        container card_mgr_inv_detail_list {
          leaf-list card_mgr_inv_detail_values {
            type string;
          }
        }
      }
    }
  }

  grouping ncs_rpc_notif_event-hist-group {
    container event-history {
      config false;
      container brief {
        config false;
        uses ncs_rpc_notif_event-hist-group-brief;
      }
      container detail {
        config false;
        uses ncs_rpc_notif_event-hist-group-detail;
      }
    }
  }

  grouping ncs_rpc_notif_event-hist-group-brief {
    list location {
      key "location";
      leaf location {
        type string;
      }
      container card_event_hist_brief {
        leaf-list card_event_hist_brief_values {
          type string;
        }
      }
    }
  }

  grouping ncs_rpc_notif_event-hist-group-detail {
    list location {
      key "location";
      leaf location {
        type string;
      }
      container card_event_hist_detail {
        leaf-list card_event_hist_detail_values {
          type string;
        }
      }
    }
  }

  grouping ncs_rpc_notif_notif-hist-group {
    container notif-history {
      config false;
      container brief {
        config false;
        uses ncs_rpc_notif_notif-hist-group-brief;
      }
      container detail {
        config false;
        uses ncs_rpc_notif_notif-hist-group-detail;
      }
    }
  }

  grouping ncs_rpc_notif_notif-hist-group-brief {
    list location {
      key "location";
      leaf location {
        type string;
      }
      container card_notif_hist_brief {
        leaf-list card_notif_hist_brief_values {
          type string;
        }
      }
    }
  }

  grouping ncs_rpc_notif_notif-hist-group-detail {
    list location {
      key "location";
      leaf location {
        type string;
      }
      container card_notif_hist_detail {
        leaf-list card_notif_hist_detail_values {
          type string;
        }
      }
    }
  }

  grouping ncs_rpc_notif_oir-hist-group {
    container oir-history {
      config false;
      list rack {
        key "rack";
        leaf rack {
          type string;
        }
        container card_oir_hist {
          leaf-list card_oir_events {
            type string;
          }
        }
      }
    }
  }

  grouping ncs_rpc_notif_iofpga-group {
    container iofpga {
      config false;
      uses ncs_rpc_notif_iofpga-register-group;
      uses ncs_rpc_notif_iofpga-flash-group;
    }
  }

  grouping ncs_rpc_notif_iofpga-register-group {
    container register {
      config false;
      uses ncs_rpc_notif_cpu-register-group;
      uses ncs_rpc_notif_mb-register-group;
      uses ncs_rpc_notif_dc-register-group;
    }
  }

  grouping ncs_rpc_notif_cpu-register-group {
    container cpu {
      config false;
      list register_location {
        config false;
        key "register_location";
        leaf register_location {
          type string;
        }
        uses ncs_rpc_notif_iofpga-block-number-group;
        uses ncs_rpc_notif_iofpga-offset-group;
        uses ncs_rpc_notif_iofpga-address-group;
      }
    }
  }

  grouping ncs_rpc_notif_mb-register-group {
    container mb {
      config false;
      list register_location {
        config false;
        key "register_location";
        leaf register_location {
          type string;
        }
        uses ncs_rpc_notif_iofpga-block-number-group;
        uses ncs_rpc_notif_iofpga-offset-group;
        uses ncs_rpc_notif_iofpga-address-group;
      }
    }
  }

  grouping ncs_rpc_notif_dc-register-group {
    container dc {
      config false;
      list register_location {
        config false;
        key "register_location";
        leaf register_location {
          type string;
        }
        uses ncs_rpc_notif_iofpga-block-number-group;
        uses ncs_rpc_notif_iofpga-offset-group;
        uses ncs_rpc_notif_iofpga-address-group;
      }
    }
  }

  grouping ncs_rpc_notif_iofpga-block-number-group {
    list iofpga_block_number {
      config false;
      key "iofpga_block_num";
      leaf iofpga_block_num {
        type uint32;
      }
      leaf block_location {
        type string;
      }
      leaf iofpga_block_nm {
        type string;
      }
      list iofpga_register_number {
        key "index";
        leaf index {
          type uint32;
        }
        leaf iofpga_register_name {
          type string;
        }
        list iofpga_data {
          leaf name {
            type string;
          }
          leaf offset {
            type uint32;
          }
          leaf value {
            type uint32;
          }
        }
      }
    }
  }

  grouping ncs_rpc_notif_iofpga-offset-group {
    list iofpga_offset {
      config false;
      key "hex_offset";
      leaf hex_offset {
        type HexOffset;
      }
      list iofpga_reg_offset_data {
        leaf iofpga_reg_off_addr {
          type uint32;
        }
        leaf reg_off_value {
          type string;
        }
      }
    }
  }

  grouping ncs_rpc_notif_iofpga-address-group {
    list iofpga_address {
      config false;
      key "start_hex_addr end_hex_addr";
      leaf start_hex_addr {
        type startHexOffset;
      }
      leaf end_hex_addr {
        type endHexOffset;
      }
      list iofpga_reg_range_addr_list {
        key "iofpga_reg_range_addr";
        leaf iofpga_reg_range_addr {
          type uint32;
        }
        list iofpga_reg_data {
          leaf iofpga_reg_addr {
            type uint32;
          }
          leaf reg_value {
            type string;
          }
        }
      }
    }
  }

  grouping ncs_rpc_notif_iofpga-flash-group {
    container flash {
      config false;
      uses ncs_rpc_notif_iofpga-flash-info-group;
      uses ncs_rpc_notif_iofpga-flash-status-group;
    }
  }

  grouping ncs_rpc_notif_iofpga-flash-info-group {
    container info {
      config false;
      list flash_location {
        key "flash_location";
        leaf flash_location {
          type calvados:location-id;
        }
        container iofpga_flash_info {
          leaf-list iofpga_flash_info_values {
            type string;
          }
        }
      }
    }
  }

  grouping ncs_rpc_notif_iofpga-flash-status-group {
    container status {
      config false;
      list flash_location {
        key "flash_location";
        leaf flash_location {
          type calvados:location-id;
        }
        container iofpga_flash_status {
          leaf-list iofpga_flash_status_values {
            type string;
          }
        }
      }
    }
  }

  grouping ncs_rpc_notif_bootldr-group {
    container bootloader {
      config false;
      uses ncs_rpc_notif_bootldr-flash-group;
    }
  }

  grouping ncs_rpc_notif_bootldr-flash-group {
    container flash {
      config false;
      uses ncs_rpc_notif_bootldr-flash-info-group;
      uses ncs_rpc_notif_bootldr-flash-status-group;
    }
  }

  grouping ncs_rpc_notif_bootldr-flash-info-group {
    container info {
      config false;
      list flash_location {
        key "flash_location";
        leaf flash_location {
          type calvados:location-id;
        }
        container bootldr_flash_info {
          leaf-list bootldr_flash_info_values {
            type string;
          }
        }
      }
    }
  }

  grouping ncs_rpc_notif_bootldr-flash-status-group {
    container status {
      config false;
      list flash_location {
        key "flash_location";
        leaf flash_location {
          type calvados:location-id;
        }
        container bootldr_flash_status {
          leaf-list bootldr_flash_status_values {
            type string;
          }
        }
      }
    }
  }

  grouping live_ncs_card_mgr-group {
    container card_mgr {
      uses show_trace:live_ncs_traceable;
      uses live_ncs_inventory-group;
      uses live_ncs_event-hist-group;
      uses live_ncs_notif-hist-group;
      uses live_ncs_oir-hist-group;
      uses live_ncs_iofpga-group;
      uses live_ncs_bootldr-group;
    }
  }

  grouping live_ncs_inventory-group {
    container inventory {
      uses live_ncs_inventory-summary-group;
      uses live_ncs_inventory-detail-group;
    }
  }

  grouping live_ncs_inventory-summary-group {
    container summary {
      list card_mgr_inv_summary {
        key "location";
        leaf location {
          type string;
          // NCS drop mandatory statement
        }
        leaf card_mgr_inv_PID_string {
          type string;
        }
        leaf card_mgr_inv_slot_number {
          type uint32;
        }
        leaf card_mgr_inv_serial_number {
          type string;
        }
        leaf card_mgr_inv_hw_version {
          type string;
        }
        leaf card_mgr_inv_card_state {
          type string;
        }
      }
    }
  }

  grouping live_ncs_inventory-detail-group {
    container detail {
      list card_mgr_inv_detail {
        key "location";
        leaf location {
          type string;
        }
        container card_mgr_inv_detail_list {
          leaf-list card_mgr_inv_detail_values {
            type string;
          }
        }
      }
    }
  }

  grouping live_ncs_event-hist-group {
    container event-history {
      container brief {
        uses live_ncs_event-hist-group-brief;
      }
      container detail {
        uses live_ncs_event-hist-group-detail;
      }
    }
  }

  grouping live_ncs_event-hist-group-brief {
    list location {
      key "location";
      leaf location {
        type string;
      }
      container card_event_hist_brief {
        leaf-list card_event_hist_brief_values {
          type string;
        }
      }
    }
  }

  grouping live_ncs_event-hist-group-detail {
    list location {
      key "location";
      leaf location {
        type string;
      }
      container card_event_hist_detail {
        leaf-list card_event_hist_detail_values {
          type string;
        }
      }
    }
  }

  grouping live_ncs_notif-hist-group {
    container notif-history {
      container brief {
        uses live_ncs_notif-hist-group-brief;
      }
      container detail {
        uses live_ncs_notif-hist-group-detail;
      }
    }
  }

  grouping live_ncs_notif-hist-group-brief {
    list location {
      key "location";
      leaf location {
        type string;
      }
      container card_notif_hist_brief {
        leaf-list card_notif_hist_brief_values {
          type string;
        }
      }
    }
  }

  grouping live_ncs_notif-hist-group-detail {
    list location {
      key "location";
      leaf location {
        type string;
      }
      container card_notif_hist_detail {
        leaf-list card_notif_hist_detail_values {
          type string;
        }
      }
    }
  }

  grouping live_ncs_oir-hist-group {
    container oir-history {
      list rack {
        key "rack";
        leaf rack {
          type string;
        }
        container card_oir_hist {
          leaf-list card_oir_events {
            type string;
          }
        }
      }
    }
  }

  grouping live_ncs_iofpga-group {
    container iofpga {
      uses live_ncs_iofpga-register-group;
      uses live_ncs_iofpga-flash-group;
    }
  }

  grouping live_ncs_iofpga-register-group {
    container register {
      uses live_ncs_cpu-register-group;
      uses live_ncs_mb-register-group;
      uses live_ncs_dc-register-group;
    }
  }

  grouping live_ncs_cpu-register-group {
    container cpu {
      list register_location {
        key "register_location";
        leaf register_location {
          type string;
        }
        uses live_ncs_iofpga-block-number-group;
        uses live_ncs_iofpga-offset-group;
        uses live_ncs_iofpga-address-group;
      }
    }
  }

  grouping live_ncs_mb-register-group {
    container mb {
      list register_location {
        key "register_location";
        leaf register_location {
          type string;
        }
        uses live_ncs_iofpga-block-number-group;
        uses live_ncs_iofpga-offset-group;
        uses live_ncs_iofpga-address-group;
      }
    }
  }

  grouping live_ncs_dc-register-group {
    container dc {
      list register_location {
        key "register_location";
        leaf register_location {
          type string;
        }
        uses live_ncs_iofpga-block-number-group;
        uses live_ncs_iofpga-offset-group;
        uses live_ncs_iofpga-address-group;
      }
    }
  }

  grouping live_ncs_iofpga-block-number-group {
    list iofpga_block_number {
      key "iofpga_block_num";
      leaf iofpga_block_num {
        type uint32;
      }
      leaf block_location {
        type string;
      }
      leaf iofpga_block_nm {
        type string;
      }
      list iofpga_register_number {
        key "index";
        leaf index {
          type uint32;
        }
        leaf iofpga_register_name {
          type string;
        }
        list iofpga_data {
          leaf name {
            type string;
          }
          leaf offset {
            type uint32;
          }
          leaf value {
            type uint32;
          }
        }
      }
    }
  }

  grouping live_ncs_iofpga-offset-group {
    list iofpga_offset {
      key "hex_offset";
      leaf hex_offset {
        type HexOffset;
      }
      list iofpga_reg_offset_data {
        leaf iofpga_reg_off_addr {
          type uint32;
        }
        leaf reg_off_value {
          type string;
        }
      }
    }
  }

  grouping live_ncs_iofpga-address-group {
    list iofpga_address {
      key "start_hex_addr end_hex_addr";
      leaf start_hex_addr {
        type startHexOffset;
      }
      leaf end_hex_addr {
        type endHexOffset;
      }
      list iofpga_reg_range_addr_list {
        key "iofpga_reg_range_addr";
        leaf iofpga_reg_range_addr {
          type uint32;
        }
        list iofpga_reg_data {
          leaf iofpga_reg_addr {
            type uint32;
          }
          leaf reg_value {
            type string;
          }
        }
      }
    }
  }

  grouping live_ncs_iofpga-flash-group {
    container flash {
      uses live_ncs_iofpga-flash-info-group;
      uses live_ncs_iofpga-flash-status-group;
    }
  }

  grouping live_ncs_iofpga-flash-info-group {
    container info {
      list flash_location {
        key "flash_location";
        leaf flash_location {
          type calvados:location-id;
        }
        container iofpga_flash_info {
          leaf-list iofpga_flash_info_values {
            type string;
          }
        }
      }
    }
  }

  grouping live_ncs_iofpga-flash-status-group {
    container status {
      list flash_location {
        key "flash_location";
        leaf flash_location {
          type calvados:location-id;
        }
        container iofpga_flash_status {
          leaf-list iofpga_flash_status_values {
            type string;
          }
        }
      }
    }
  }

  grouping live_ncs_bootldr-group {
    container bootloader {
      uses live_ncs_bootldr-flash-group;
    }
  }

  grouping live_ncs_bootldr-flash-group {
    container flash {
      uses live_ncs_bootldr-flash-info-group;
      uses live_ncs_bootldr-flash-status-group;
    }
  }

  grouping live_ncs_bootldr-flash-info-group {
    container info {
      list flash_location {
        key "flash_location";
        leaf flash_location {
          type calvados:location-id;
        }
        container bootldr_flash_info {
          leaf-list bootldr_flash_info_values {
            type string;
          }
        }
      }
    }
  }

  grouping live_ncs_bootldr-flash-status-group {
    container status {
      list flash_location {
        key "flash_location";
        leaf flash_location {
          type calvados:location-id;
        }
        container bootldr_flash_status {
          leaf-list bootldr_flash_status_values {
            type string;
          }
        }
      }
    }
  }

  grouping card_mgr-group {
    container card_mgr {
      uses show_trace:traceable;
      uses inventory-group;
      uses event-hist-group;
      uses notif-hist-group;
      uses oir-hist-group;
      uses iofpga-group;
      uses bootldr-group;
    }
  }

  grouping inventory-group {
    // NCS drop config false container inventory
  }

  grouping inventory-summary-group {
    // NCS drop config false container summary
  }

  grouping inventory-detail-group {
    // NCS drop config false container detail
  }

  grouping event-hist-group {
    // NCS drop config false container 'event-history'
  }

  grouping event-hist-group-brief {
    list location {
      key "location";
      leaf location {
        type string;
      }
      container card_event_hist_brief {
        leaf-list card_event_hist_brief_values {
          type string;
        }
      }
    }
  }

  grouping event-hist-group-detail {
    list location {
      key "location";
      leaf location {
        type string;
      }
      container card_event_hist_detail {
        leaf-list card_event_hist_detail_values {
          type string;
        }
      }
    }
  }

  grouping notif-hist-group {
    // NCS drop config false container 'notif-history'
  }

  grouping notif-hist-group-brief {
    list location {
      key "location";
      leaf location {
        type string;
      }
      container card_notif_hist_brief {
        leaf-list card_notif_hist_brief_values {
          type string;
        }
      }
    }
  }

  grouping notif-hist-group-detail {
    list location {
      key "location";
      leaf location {
        type string;
      }
      container card_notif_hist_detail {
        leaf-list card_notif_hist_detail_values {
          type string;
        }
      }
    }
  }

  grouping oir-hist-group {
    // NCS drop config false container 'oir-history'
  }

  grouping iofpga-group {
    // NCS drop config false container iofpga
  }

  grouping iofpga-register-group {
    // NCS drop config false container register
  }

  grouping cpu-register-group {
    // NCS drop config false container cpu
  }

  grouping mb-register-group {
    // NCS drop config false container mb
  }

  grouping dc-register-group {
    // NCS drop config false container dc
  }

  grouping iofpga-block-number-group {
    // NCS drop config false list iofpga_block_number
  }

  grouping iofpga-offset-group {
    // NCS drop config false list iofpga_offset
  }

  grouping iofpga-address-group {
    // NCS drop config false list iofpga_address
  }

  grouping iofpga-flash-group {
    // NCS drop config false container flash
  }

  grouping iofpga-flash-info-group {
    // NCS drop config false container info
  }

  grouping iofpga-flash-status-group {
    // NCS drop config false container status
  }

  grouping bootldr-group {
    // NCS drop config false container bootloader
  }

  grouping bootldr-flash-group {
    // NCS drop config false container flash
  }

  grouping bootldr-flash-info-group {
    // NCS drop config false container info
  }

  grouping bootldr-flash-status-group {
    // NCS drop config false container status
  }
}
