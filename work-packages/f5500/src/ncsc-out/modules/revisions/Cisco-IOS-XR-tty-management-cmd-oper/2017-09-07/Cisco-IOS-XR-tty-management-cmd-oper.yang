module Cisco-IOS-XR-tty-management-cmd-oper {
  // Generated by yanger -t ncs
  tailf:mount-id f5500-nc-1.0:f5500-nc-1.0;
  tailf:ncs-device-type "netconf";

  namespace "http://cisco.com/ns/yang/Cisco-IOS-XR-tty-management-cmd-oper";
  prefix Cisco-IOS-XR-tty-management-cmd-oper;

  include Cisco-IOS-XR-tty-management-cmd-oper-sub1 {
    revision-date 2017-09-07;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR tty-management-cmd package operational data.

     This module contains definitions
     for the following management objects:
       show-users: Show users statistics

     Copyright (c) 2013-2018 by Cisco Systems, Inc.
     All rights reserved.";

  revision 2017-09-07 {
    description
      "Fixed type translation error.";
  }
  revision 2015-11-09 {
    description
      "IOS XR 6.0 revision.";
  }

  augment "/ncs:devices/ncs:device/ncs:config" {
    // NCS drop config false container 'show-users'
  }
  augment "/ncs:devices/ncs:device/ncs:live-status" {
    container show-users {
      tailf:ncs-device-type "netconf";
      tailf:display-when "not(../../ncs:module) or ../../ncs:module[ncs:name='Cisco-IOS-XR-tty-management-cmd-oper'] or (../../ncs:live-status-protocol[not(ncs:capability)]) or (../../ncs:live-status-protocol/ncs:capability/ncs:module[.='Cisco-IOS-XR-tty-management-cmd-oper'])";
      description
        "Show users statistics";
      container sessions {
        description
          "Show users statistics";
        list session {
          key "session-id";
          description
            "Show users statistics";
          leaf session-id {
            type uint32;
            description
              "Session Id";
          }
          uses live_ncs_SHOWUSERS-ENTRY;
        }
      }
    }
  }
  augment "/ncs:devices/ncs:template/ncs:ned-id/ncs:config" {
    // NCS drop config false container 'show-users'
  }
}
