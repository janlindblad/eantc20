module Cisco-IOS-XR-plat-chas-invmgr-ng-oper {
  // Generated by yanger -t ncs
  tailf:mount-id f5500-nc-1.0:f5500-nc-1.0;
  tailf:ncs-device-type "netconf";

  namespace "http://cisco.com/ns/yang/Cisco-IOS-XR-plat-chas-invmgr-ng-oper";
  prefix Cisco-IOS-XR-plat-chas-invmgr-ng-oper;

  import Cisco-IOS-XR-types {
    prefix xr;
  }
  include Cisco-IOS-XR-plat-chas-invmgr-ng-oper-sub2 {
    revision-date 2018-01-22;
  }
  include Cisco-IOS-XR-plat-chas-invmgr-ng-oper-sub1 {
    revision-date 2018-01-22;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR plat-chas-invmgr-ng package operational data.

     This module contains definitions
     for the following management objects:
       platform: Platform information
       platform-inventory: platform inventory

     Copyright (c) 2013-2018 by Cisco Systems, Inc.
     All rights reserved.";

  revision 2018-01-22 {
    description
      "Fixing incorrect spelling for node-description in module.";
  }
  revision 2015-11-09 {
    description
      "IOS XR 6.0 revision.";
  }

  grouping ncs_template_STATE {
    description
      "Common node of instance, slot";
    container state {
      description
        "State information";
      uses ncs_template_PLATFORM-INFO;
    }
  }

  grouping ncs_template_PORT-SLOT-TABLE {
    description
      "Common node of card, module";
    container port-slots {
      description
        "Table of port slots";
      list port-slot {
        // NCS patched for predictable order
        ordered-by user;
        key "name";
        description
          "Port slot number";
        leaf name {
          type string;
          description
            "Port slot name";
        }
        uses ncs_template_PORT-TABLE;
        uses ncs_template_SENSOR-TABLE;
        uses ncs_template_ATTRIBUTES;
      }
    }
  }

  grouping ncs_template_SLOT-TABLE {
    description
      "Common node of rack, rack";
    container slots {
      description
        "Table of slots";
      list slot {
        // NCS patched for predictable order
        ordered-by user;
        key "name";
        description
          "Slot name";
        container cards {
          description
            "Table of cards";
          list card {
            // NCS patched for predictable order
            ordered-by user;
            key "name";
            description
              "Card number";
            container hardware-information {
              description
                "HardwareInformationDir";
              container processor-information {
                description
                  "ProcesorInformation";
                uses ncs_template_INV-PROCESSOR;
              }
              container motherboard-information {
                description
                  "MotherboardInformation";
                uses ncs_template_INV-XML-MOTHERBOARD-INFO;
              }
              container bootflash-information {
                description
                  "BootflashInformation";
                uses ncs_template_INV-BOOTFLASH;
              }
              container disk-information {
                description
                  "DiskInformation";
                uses ncs_template_INV-XML-DISK-INFO;
              }
            }
            container sub-slots {
              description
                "Table of subslots";
              list sub-slot {
                // NCS patched for predictable order
                ordered-by user;
                key "name";
                description
                  "Subslot number";
                container module {
                  description
                    "Module of a subslot";
                  uses ncs_template_PORT-SLOT-TABLE;
                  uses ncs_template_SENSOR-TABLE;
                  uses ncs_template_ATTRIBUTES;
                }
                leaf name {
                  type string;
                  description
                    "Subslot name";
                }
                uses ncs_template_ATTRIBUTES;
              }
            }
            leaf name {
              type string;
              description
                "Card name";
            }
            uses ncs_template_PORT-TABLE;
            uses ncs_template_PORT-SLOT-TABLE;
            uses ncs_template_HW-COMPONENT-TABLE;
            uses ncs_template_SENSOR-TABLE;
            uses ncs_template_ATTRIBUTES;
          }
        }
        leaf name {
          type string;
          description
            "Slot name";
        }
        uses ncs_template_ATTRIBUTES;
      }
    }
  }

  grouping ncs_template_PLATFORM-COMMON-SLOT-TABLE {
    description
      "Common node of rack, rackCommon node of rack,
       rack";
    container slots {
      description
        "Table of slots";
      list slot {
        // NCS patched for predictable order
        ordered-by user;
        key "slot-name";
        description
          "Slot name";
        container instances {
          description
            "Table of Instances";
          list instance {
            // NCS patched for predictable order
            ordered-by user;
            key "instance-name";
            description
              "Instance name";
            leaf instance-name {
              type string;
              description
                "Instance name";
            }
            uses ncs_template_STATE;
          }
        }
        container vm {
          description
            "VM information";
          uses ncs_template_VM-INFO;
        }
        leaf slot-name {
          type string;
          description
            "Slot name";
        }
        uses ncs_template_STATE;
      }
    }
  }

  grouping ncs_template_SENSOR-TABLE {
    description
      "Common node of card, module, hw-component,
       port-slot, ports";
    container sensors {
      description
        "Table of sensors";
      list sensor {
        // NCS patched for predictable order
        ordered-by user;
        key "name";
        description
          "Sensor number";
        leaf name {
          type string;
          description
            "Sensor name";
        }
        uses ncs_template_ATTRIBUTES;
      }
    }
  }

  grouping ncs_template_PORT-TABLE {
    description
      "Common node of port-slot, card";
    container portses {
      description
        "Table of port slots";
      list ports {
        // NCS patched for predictable order
        ordered-by user;
        key "name";
        description
          "Port number";
        leaf name {
          type string;
          description
            "Port name";
        }
        uses ncs_template_HW-COMPONENT-TABLE;
        uses ncs_template_SENSOR-TABLE;
        uses ncs_template_ATTRIBUTES;
      }
    }
  }

  grouping ncs_template_HW-COMPONENT-TABLE {
    description
      "Common node of card, ports";
    container hw-components {
      description
        "Table of  HW components ";
      list hw-component {
        // NCS patched for predictable order
        ordered-by user;
        key "name";
        description
          "HW component number";
        leaf name {
          type string;
          description
            "HW component name";
        }
        uses ncs_template_SENSOR-TABLE;
        uses ncs_template_ATTRIBUTES;
      }
    }
  }

  grouping ncs_template_ATTRIBUTES {
    description
      "Common node of rack, rack, slot, card, sub-slot,
       module, port-slot, hw-component, sensor, ports";
    container attributes {
      description
        "Attributes";
      container basic-info {
        description
          "Entity attributes";
        uses ncs_template_INV-XML-ENTITY-BASIC-INFO;
      }
      container fru-info {
        description
          "Field Replaceable Unit (FRU) attributes";
        uses ncs_template_INV-XML-FRU-INFO;
      }
    }
  }

  grouping ncs_rpc_notif_STATE {
    description
      "Common node of instance, slot";
    container state {
      description
        "State information";
      uses ncs_rpc_notif_PLATFORM-INFO;
    }
  }

  grouping ncs_rpc_notif_PORT-SLOT-TABLE {
    description
      "Common node of card, module";
    container port-slots {
      description
        "Table of port slots";
      list port-slot {
        key "name";
        description
          "Port slot number";
        leaf name {
          type xr:Cisco-ios-xr-string;
          description
            "Port slot name";
        }
        uses ncs_rpc_notif_PORT-TABLE;
        uses ncs_rpc_notif_SENSOR-TABLE;
        uses ncs_rpc_notif_ATTRIBUTES;
      }
    }
  }

  grouping ncs_rpc_notif_SLOT-TABLE {
    description
      "Common node of rack, rack";
    container slots {
      description
        "Table of slots";
      list slot {
        key "name";
        description
          "Slot name";
        container cards {
          description
            "Table of cards";
          list card {
            key "name";
            description
              "Card number";
            container hardware-information {
              description
                "HardwareInformationDir";
              container processor-information {
                description
                  "ProcesorInformation";
                uses ncs_rpc_notif_INV-PROCESSOR;
              }
              container motherboard-information {
                description
                  "MotherboardInformation";
                uses ncs_rpc_notif_INV-XML-MOTHERBOARD-INFO;
              }
              container bootflash-information {
                description
                  "BootflashInformation";
                uses ncs_rpc_notif_INV-BOOTFLASH;
              }
              container disk-information {
                description
                  "DiskInformation";
                uses ncs_rpc_notif_INV-XML-DISK-INFO;
              }
            }
            container sub-slots {
              description
                "Table of subslots";
              list sub-slot {
                key "name";
                description
                  "Subslot number";
                container module {
                  description
                    "Module of a subslot";
                  uses ncs_rpc_notif_PORT-SLOT-TABLE;
                  uses ncs_rpc_notif_SENSOR-TABLE;
                  uses ncs_rpc_notif_ATTRIBUTES;
                }
                leaf name {
                  type xr:Cisco-ios-xr-string;
                  description
                    "Subslot name";
                }
                uses ncs_rpc_notif_ATTRIBUTES;
              }
            }
            leaf name {
              type xr:Cisco-ios-xr-string;
              description
                "Card name";
            }
            uses ncs_rpc_notif_PORT-TABLE;
            uses ncs_rpc_notif_PORT-SLOT-TABLE;
            uses ncs_rpc_notif_HW-COMPONENT-TABLE;
            uses ncs_rpc_notif_SENSOR-TABLE;
            uses ncs_rpc_notif_ATTRIBUTES;
          }
        }
        leaf name {
          type xr:Cisco-ios-xr-string;
          description
            "Slot name";
        }
        uses ncs_rpc_notif_ATTRIBUTES;
      }
    }
  }

  grouping ncs_rpc_notif_PLATFORM-COMMON-SLOT-TABLE {
    description
      "Common node of rack, rackCommon node of rack,
       rack";
    container slots {
      description
        "Table of slots";
      list slot {
        key "slot-name";
        description
          "Slot name";
        container instances {
          description
            "Table of Instances";
          list instance {
            key "instance-name";
            description
              "Instance name";
            leaf instance-name {
              type string;
              description
                "Instance name";
            }
            uses ncs_rpc_notif_STATE;
          }
        }
        container vm {
          description
            "VM information";
          uses ncs_rpc_notif_VM-INFO;
        }
        leaf slot-name {
          type xr:Cisco-ios-xr-string;
          description
            "Slot name";
        }
        uses ncs_rpc_notif_STATE;
      }
    }
  }

  grouping ncs_rpc_notif_SENSOR-TABLE {
    description
      "Common node of card, module, hw-component,
       port-slot, ports";
    container sensors {
      description
        "Table of sensors";
      list sensor {
        key "name";
        description
          "Sensor number";
        leaf name {
          type xr:Cisco-ios-xr-string;
          description
            "Sensor name";
        }
        uses ncs_rpc_notif_ATTRIBUTES;
      }
    }
  }

  grouping ncs_rpc_notif_PORT-TABLE {
    description
      "Common node of port-slot, card";
    container portses {
      description
        "Table of port slots";
      list ports {
        key "name";
        description
          "Port number";
        leaf name {
          type xr:Cisco-ios-xr-string;
          description
            "Port name";
        }
        uses ncs_rpc_notif_HW-COMPONENT-TABLE;
        uses ncs_rpc_notif_SENSOR-TABLE;
        uses ncs_rpc_notif_ATTRIBUTES;
      }
    }
  }

  grouping ncs_rpc_notif_HW-COMPONENT-TABLE {
    description
      "Common node of card, ports";
    container hw-components {
      description
        "Table of  HW components ";
      list hw-component {
        key "name";
        description
          "HW component number";
        leaf name {
          type xr:Cisco-ios-xr-string;
          description
            "HW component name";
        }
        uses ncs_rpc_notif_SENSOR-TABLE;
        uses ncs_rpc_notif_ATTRIBUTES;
      }
    }
  }

  grouping ncs_rpc_notif_ATTRIBUTES {
    description
      "Common node of rack, rack, slot, card, sub-slot,
       module, port-slot, hw-component, sensor, ports";
    container attributes {
      description
        "Attributes";
      container basic-info {
        description
          "Entity attributes";
        uses ncs_rpc_notif_INV-XML-ENTITY-BASIC-INFO;
      }
      container fru-info {
        description
          "Field Replaceable Unit (FRU) attributes";
        uses ncs_rpc_notif_INV-XML-FRU-INFO;
      }
    }
  }

  grouping live_ncs_STATE {
    description
      "Common node of instance, slot";
    container state {
      description
        "State information";
      uses live_ncs_PLATFORM-INFO;
    }
  }

  grouping live_ncs_PORT-SLOT-TABLE {
    description
      "Common node of card, module";
    container port-slots {
      description
        "Table of port slots";
      list port-slot {
        key "name";
        description
          "Port slot number";
        leaf name {
          type xr:Cisco-ios-xr-string;
          description
            "Port slot name";
        }
        uses live_ncs_PORT-TABLE;
        uses live_ncs_SENSOR-TABLE;
        uses live_ncs_ATTRIBUTES;
      }
    }
  }

  grouping live_ncs_SLOT-TABLE {
    description
      "Common node of rack, rack";
    container slots {
      description
        "Table of slots";
      list slot {
        key "name";
        description
          "Slot name";
        container cards {
          description
            "Table of cards";
          list card {
            key "name";
            description
              "Card number";
            container hardware-information {
              description
                "HardwareInformationDir";
              container processor-information {
                description
                  "ProcesorInformation";
                uses live_ncs_INV-PROCESSOR;
              }
              container motherboard-information {
                description
                  "MotherboardInformation";
                uses live_ncs_INV-XML-MOTHERBOARD-INFO;
              }
              container bootflash-information {
                description
                  "BootflashInformation";
                uses live_ncs_INV-BOOTFLASH;
              }
              container disk-information {
                description
                  "DiskInformation";
                uses live_ncs_INV-XML-DISK-INFO;
              }
            }
            container sub-slots {
              description
                "Table of subslots";
              list sub-slot {
                key "name";
                description
                  "Subslot number";
                container module {
                  description
                    "Module of a subslot";
                  uses live_ncs_PORT-SLOT-TABLE;
                  uses live_ncs_SENSOR-TABLE;
                  uses live_ncs_ATTRIBUTES;
                }
                leaf name {
                  type xr:Cisco-ios-xr-string;
                  description
                    "Subslot name";
                }
                uses live_ncs_ATTRIBUTES;
              }
            }
            leaf name {
              type xr:Cisco-ios-xr-string;
              description
                "Card name";
            }
            uses live_ncs_PORT-TABLE;
            uses live_ncs_PORT-SLOT-TABLE;
            uses live_ncs_HW-COMPONENT-TABLE;
            uses live_ncs_SENSOR-TABLE;
            uses live_ncs_ATTRIBUTES;
          }
        }
        leaf name {
          type xr:Cisco-ios-xr-string;
          description
            "Slot name";
        }
        uses live_ncs_ATTRIBUTES;
      }
    }
  }

  grouping live_ncs_PLATFORM-COMMON-SLOT-TABLE {
    description
      "Common node of rack, rackCommon node of rack,
       rack";
    container slots {
      description
        "Table of slots";
      list slot {
        key "slot-name";
        description
          "Slot name";
        container instances {
          description
            "Table of Instances";
          list instance {
            key "instance-name";
            description
              "Instance name";
            leaf instance-name {
              type string;
              description
                "Instance name";
            }
            uses live_ncs_STATE;
          }
        }
        container vm {
          description
            "VM information";
          uses live_ncs_VM-INFO;
        }
        leaf slot-name {
          type xr:Cisco-ios-xr-string;
          description
            "Slot name";
        }
        uses live_ncs_STATE;
      }
    }
  }

  grouping live_ncs_SENSOR-TABLE {
    description
      "Common node of card, module, hw-component,
       port-slot, ports";
    container sensors {
      description
        "Table of sensors";
      list sensor {
        key "name";
        description
          "Sensor number";
        leaf name {
          type xr:Cisco-ios-xr-string;
          description
            "Sensor name";
        }
        uses live_ncs_ATTRIBUTES;
      }
    }
  }

  grouping live_ncs_PORT-TABLE {
    description
      "Common node of port-slot, card";
    container portses {
      description
        "Table of port slots";
      list ports {
        key "name";
        description
          "Port number";
        leaf name {
          type xr:Cisco-ios-xr-string;
          description
            "Port name";
        }
        uses live_ncs_HW-COMPONENT-TABLE;
        uses live_ncs_SENSOR-TABLE;
        uses live_ncs_ATTRIBUTES;
      }
    }
  }

  grouping live_ncs_HW-COMPONENT-TABLE {
    description
      "Common node of card, ports";
    container hw-components {
      description
        "Table of  HW components ";
      list hw-component {
        key "name";
        description
          "HW component number";
        leaf name {
          type xr:Cisco-ios-xr-string;
          description
            "HW component name";
        }
        uses live_ncs_SENSOR-TABLE;
        uses live_ncs_ATTRIBUTES;
      }
    }
  }

  grouping live_ncs_ATTRIBUTES {
    description
      "Common node of rack, rack, slot, card, sub-slot,
       module, port-slot, hw-component, sensor, ports";
    container attributes {
      description
        "Attributes";
      container basic-info {
        description
          "Entity attributes";
        uses live_ncs_INV-XML-ENTITY-BASIC-INFO;
      }
      container fru-info {
        description
          "Field Replaceable Unit (FRU) attributes";
        uses live_ncs_INV-XML-FRU-INFO;
      }
    }
  }

  grouping STATE {
    description
      "Common node of instance, slot";
    container state {
      description
        "State information";
      uses PLATFORM-INFO;
    }
  }

  grouping PORT-SLOT-TABLE {
    description
      "Common node of card, module";
    container port-slots {
      description
        "Table of port slots";
      list port-slot {
        key "name";
        description
          "Port slot number";
        leaf name {
          type xr:Cisco-ios-xr-string;
          description
            "Port slot name";
        }
        uses PORT-TABLE;
        uses SENSOR-TABLE;
        uses ATTRIBUTES;
      }
    }
  }

  grouping SLOT-TABLE {
    description
      "Common node of rack, rack";
    container slots {
      description
        "Table of slots";
      list slot {
        key "name";
        description
          "Slot name";
        container cards {
          description
            "Table of cards";
          list card {
            key "name";
            description
              "Card number";
            container hardware-information {
              description
                "HardwareInformationDir";
              container processor-information {
                description
                  "ProcesorInformation";
                uses INV-PROCESSOR;
              }
              container motherboard-information {
                description
                  "MotherboardInformation";
                uses INV-XML-MOTHERBOARD-INFO;
              }
              container bootflash-information {
                description
                  "BootflashInformation";
                uses INV-BOOTFLASH;
              }
              container disk-information {
                description
                  "DiskInformation";
                uses INV-XML-DISK-INFO;
              }
            }
            container sub-slots {
              description
                "Table of subslots";
              list sub-slot {
                key "name";
                description
                  "Subslot number";
                container module {
                  description
                    "Module of a subslot";
                  uses PORT-SLOT-TABLE;
                  uses SENSOR-TABLE;
                  uses ATTRIBUTES;
                }
                leaf name {
                  type xr:Cisco-ios-xr-string;
                  description
                    "Subslot name";
                }
                uses ATTRIBUTES;
              }
            }
            leaf name {
              type xr:Cisco-ios-xr-string;
              description
                "Card name";
            }
            uses PORT-TABLE;
            uses PORT-SLOT-TABLE;
            uses HW-COMPONENT-TABLE;
            uses SENSOR-TABLE;
            uses ATTRIBUTES;
          }
        }
        leaf name {
          type xr:Cisco-ios-xr-string;
          description
            "Slot name";
        }
        uses ATTRIBUTES;
      }
    }
  }

  grouping PLATFORM-COMMON-SLOT-TABLE {
    description
      "Common node of rack, rackCommon node of rack,
       rack";
    container slots {
      description
        "Table of slots";
      list slot {
        key "slot-name";
        description
          "Slot name";
        container instances {
          description
            "Table of Instances";
          list instance {
            key "instance-name";
            description
              "Instance name";
            leaf instance-name {
              type string;
              description
                "Instance name";
            }
            uses STATE;
          }
        }
        container vm {
          description
            "VM information";
          uses VM-INFO;
        }
        leaf slot-name {
          type xr:Cisco-ios-xr-string;
          description
            "Slot name";
        }
        uses STATE;
      }
    }
  }

  grouping SENSOR-TABLE {
    description
      "Common node of card, module, hw-component,
       port-slot, ports";
    container sensors {
      description
        "Table of sensors";
      list sensor {
        key "name";
        description
          "Sensor number";
        leaf name {
          type xr:Cisco-ios-xr-string;
          description
            "Sensor name";
        }
        uses ATTRIBUTES;
      }
    }
  }

  grouping PORT-TABLE {
    description
      "Common node of port-slot, card";
    container portses {
      description
        "Table of port slots";
      list ports {
        key "name";
        description
          "Port number";
        leaf name {
          type xr:Cisco-ios-xr-string;
          description
            "Port name";
        }
        uses HW-COMPONENT-TABLE;
        uses SENSOR-TABLE;
        uses ATTRIBUTES;
      }
    }
  }

  grouping HW-COMPONENT-TABLE {
    description
      "Common node of card, ports";
    container hw-components {
      description
        "Table of  HW components ";
      list hw-component {
        key "name";
        description
          "HW component number";
        leaf name {
          type xr:Cisco-ios-xr-string;
          description
            "HW component name";
        }
        uses SENSOR-TABLE;
        uses ATTRIBUTES;
      }
    }
  }

  grouping ATTRIBUTES {
    description
      "Common node of rack, rack, slot, card, sub-slot,
       module, port-slot, hw-component, sensor, ports";
    container attributes {
      description
        "Attributes";
      container basic-info {
        description
          "Entity attributes";
        uses INV-XML-ENTITY-BASIC-INFO;
      }
      container fru-info {
        description
          "Field Replaceable Unit (FRU) attributes";
        uses INV-XML-FRU-INFO;
      }
    }
  }

  augment "/ncs:devices/ncs:device/ncs:config" {
    // NCS drop config false container platform
    // NCS drop config false container 'platform-inventory'
  }
  augment "/ncs:devices/ncs:device/ncs:live-status" {
    container platform {
      tailf:ncs-device-type "netconf";
      tailf:display-when "not(../../ncs:module) or ../../ncs:module[ncs:name='Cisco-IOS-XR-plat-chas-invmgr-ng-oper'] or (../../ncs:live-status-protocol[not(ncs:capability)]) or (../../ncs:live-status-protocol/ncs:capability/ncs:module[.='Cisco-IOS-XR-plat-chas-invmgr-ng-oper'])";
      description
        "Platform information";
      container racks {
        description
          "Table of racks";
        list rack {
          key "rack-name";
          description
            "Rack name";
          leaf rack-name {
            type xr:Cisco-ios-xr-string;
            description
              "Rack name";
          }
          uses live_ncs_PLATFORM-COMMON-SLOT-TABLE;
        }
      }
    }
    container platform-inventory {
      tailf:ncs-device-type "netconf";
      tailf:display-when "not(../../ncs:module) or ../../ncs:module[ncs:name='Cisco-IOS-XR-plat-chas-invmgr-ng-oper'] or (../../ncs:live-status-protocol[not(ncs:capability)]) or (../../ncs:live-status-protocol/ncs:capability/ncs:module[.='Cisco-IOS-XR-plat-chas-invmgr-ng-oper'])";
      description
        "platform inventory";
      container racks {
        description
          "Table of racks";
        list rack {
          key "name";
          description
            "Rack name";
          leaf name {
            type xr:Cisco-ios-xr-string;
            description
              "Rack name";
          }
          uses live_ncs_SLOT-TABLE;
          uses live_ncs_ATTRIBUTES;
        }
      }
    }
  }
  augment "/ncs:devices/ncs:template/ncs:ned-id/ncs:config" {
    // NCS drop config false container platform
    // NCS drop config false container 'platform-inventory'
  }
}
