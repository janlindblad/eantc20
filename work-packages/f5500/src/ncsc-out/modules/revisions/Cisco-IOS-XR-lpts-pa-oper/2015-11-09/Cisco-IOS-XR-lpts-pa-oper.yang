module Cisco-IOS-XR-lpts-pa-oper {
  // Generated by yanger -t ncs
  tailf:mount-id f5500-nc-1.0:f5500-nc-1.0;
  tailf:ncs-device-type "netconf";

  namespace "http://cisco.com/ns/yang/Cisco-IOS-XR-lpts-pa-oper";
  prefix Cisco-IOS-XR-lpts-pa-oper;

  import Cisco-IOS-XR-types {
    prefix xr;
  }
  include Cisco-IOS-XR-lpts-pa-oper-sub1 {
    revision-date 2015-11-09;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR lpts-pa package operational data.

     This module contains definitions
     for the following management objects:
       lpts-pa: lpts pre-ifib data

     Copyright (c) 2013-2018 by Cisco Systems, Inc.
     All rights reserved.";

  revision 2015-11-09 {
    description
      "IOS XR 6.0 revision.";
  }

  augment "/ncs:devices/ncs:device/ncs:config" {
    // NCS drop config false container 'lpts-pa'
  }
  augment "/ncs:devices/ncs:device/ncs:live-status" {
    container lpts-pa {
      tailf:ncs-device-type "netconf";
      tailf:display-when "not(../../ncs:module) or ../../ncs:module[ncs:name='Cisco-IOS-XR-lpts-pa-oper'] or (../../ncs:live-status-protocol[not(ncs:capability)]) or (../../ncs:live-status-protocol/ncs:capability/ncs:module[.='Cisco-IOS-XR-lpts-pa-oper'])";
      description
        "lpts pre-ifib data";
      container entry-xr {
        description
          "lpts pa bindings";
        list entry {
          key "entry";
          description
            "Data for single PA Binding";
          leaf entry {
            type xr:Cisco-ios-xr-string;
            description
              "Single Binding entry";
          }
          uses live_ncs_BINDING-ENTRY;
        }
      }
      container entries {
        description
          "lpts pa clients";
        list entry {
          key "entry";
          description
            "Data for single PA Client";
          leaf entry {
            type xr:Cisco-ios-xr-string;
            description
              "Single Client entry";
          }
          uses live_ncs_CLIENT-ENTRY;
        }
      }
    }
  }
  augment "/ncs:devices/ncs:template/ncs:ned-id/ncs:config" {
    // NCS drop config false container 'lpts-pa'
  }
}
