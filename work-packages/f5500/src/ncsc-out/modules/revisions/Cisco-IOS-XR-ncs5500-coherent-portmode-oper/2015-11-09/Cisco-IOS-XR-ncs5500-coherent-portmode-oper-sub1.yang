submodule Cisco-IOS-XR-ncs5500-coherent-portmode-oper-sub1 {
  // Generated by yanger -t ncs
  tailf:mount-id f5500-nc-1.0:f5500-nc-1.0;

  belongs-to Cisco-IOS-XR-ncs5500-coherent-portmode-oper {
    prefix Cisco-IOS-XR-ncs5500-coherent-portmode-oper-sub1;
  }

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ncs5500-coherent-portmode package operational data.

     Copyright (c) 2013-2018 by Cisco Systems, Inc.
     All rights reserved.";

  revision 2015-11-09 {
    description
      "IOS XR 6.0 revision.";
  }

  grouping ncs_template_PORTMODE-INFO {
    description
      "portmode entry of optics controller";
    leaf intf-name {
      type string;
      description
        "intf name";
    }
    leaf speed {
      type string;
      description
        "speed";
    }
    leaf fec {
      type string;
      description
        "fec";
    }
    leaf diff {
      type string;
      description
        "diff";
    }
    leaf modulation {
      type string;
      description
        "modulation";
    }
  }

  grouping ncs_rpc_notif_PORTMODE-INFO {
    description
      "portmode entry of optics controller";
    leaf intf-name {
      type string {
        length "0..128";
      }
      description
        "intf name";
    }
    leaf speed {
      type string {
        length "0..128";
      }
      description
        "speed";
    }
    leaf fec {
      type string {
        length "0..128";
      }
      description
        "fec";
    }
    leaf diff {
      type string {
        length "0..128";
      }
      description
        "diff";
    }
    leaf modulation {
      type string {
        length "0..128";
      }
      description
        "modulation";
    }
  }

  grouping live_ncs_PORTMODE-INFO {
    description
      "portmode entry of optics controller";
    leaf intf-name {
      type string {
        length "0..128";
      }
      description
        "intf name";
    }
    leaf speed {
      type string {
        length "0..128";
      }
      description
        "speed";
    }
    leaf fec {
      type string {
        length "0..128";
      }
      description
        "fec";
    }
    leaf diff {
      type string {
        length "0..128";
      }
      description
        "diff";
    }
    leaf modulation {
      type string {
        length "0..128";
      }
      description
        "modulation";
    }
  }

  grouping PORTMODE-INFO {
    description
      "portmode entry of optics controller";
    leaf intf-name {
      type string {
        length "0..128";
      }
      description
        "intf name";
    }
    leaf speed {
      type string {
        length "0..128";
      }
      description
        "speed";
    }
    leaf fec {
      type string {
        length "0..128";
      }
      description
        "fec";
    }
    leaf diff {
      type string {
        length "0..128";
      }
      description
        "diff";
    }
    leaf modulation {
      type string {
        length "0..128";
      }
      description
        "modulation";
    }
  }
}
