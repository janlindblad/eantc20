module Cisco-IOS-XR-lib-keychain-act {
  // Generated by yanger -t ncs
  tailf:mount-id f5500-nc-1.0:f5500-nc-1.0;
  tailf:ncs-device-type "netconf";

  namespace "http://cisco.com/ns/yang/Cisco-IOS-XR-lib-keychain-act";
  prefix Cisco-IOS-XR-lib-keychain-act;

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2017 by Cisco Systems, Inc.
     All rights reserved.";

  revision 2017-04-17 {
    description
      "IOS XR 6.3.1 revision.";
  }

  grouping ncs_template_MASTER-KEY {
    leaf old-key {
      description
        "key already added/key to be replaced";
      type string;
      // NCS drop mandatory statement
    }
    leaf new-key {
      description
        "New master key to be added ";
      type string;
      // NCS drop mandatory statement
    }
  }

  grouping ncs_rpc_notif_MASTER-KEY {
    leaf old-key {
      description
        "key already added/key to be replaced";
      type string;
      mandatory true;
    }
    leaf new-key {
      description
        "New master key to be added ";
      type string;
      mandatory true;
    }
  }

  grouping live_ncs_MASTER-KEY {
    leaf old-key {
      description
        "key already added/key to be replaced";
      type string;
      // NCS drop mandatory statement
    }
    leaf new-key {
      description
        "New master key to be added ";
      type string;
      // NCS drop mandatory statement
    }
  }

  grouping MASTER-KEY {
    leaf old-key {
      description
        "key already added/key to be replaced";
      type string;
      mandatory true;
    }
    leaf new-key {
      description
        "New master key to be added ";
      type string;
      mandatory true;
    }
  }

  augment "/ncs:devices/ncs:device/ncs:rpc" {
    container rpc-master-key-update {
      tailf:ncs-device-type "netconf";
      tailf:display-when "not(../../ncs:module) or ../../ncs:module[ncs:name='Cisco-IOS-XR-lib-keychain-act']";
      tailf:action master-key-update {
        tailf:actionpoint ncsproxy {
          tailf:internal;
        }
        description
          "To update master key";
        input {
          uses ncs_rpc_notif_MASTER-KEY;
        }
      }
    }
  }
  augment "/ncs:devices/ncs:device-group/ncs:ned-id/ncs:rpc" {
    container rpc-master-key-update {
      tailf:ncs-device-type "netconf";
      tailf:display-when "/ncs:devices/ncs:device[ncs:name=current()/../../../ncs:member]/ncs:module[ncs:name='Cisco-IOS-XR-lib-keychain-act']";
      tailf:action master-key-update {
        tailf:actionpoint ncsproxy {
          tailf:internal;
        }
        description
          "To update master key";
        input {
          uses ncs_rpc_notif_MASTER-KEY;
        }
      }
    }
  }
  augment "/ncs:devices/ncs:device/ncs:rpc" {
    container rpc-master-key-delete {
      tailf:ncs-device-type "netconf";
      tailf:display-when "not(../../ncs:module) or ../../ncs:module[ncs:name='Cisco-IOS-XR-lib-keychain-act']";
      tailf:action master-key-delete {
        tailf:actionpoint ncsproxy {
          tailf:internal;
        }
        description
          "Remove Master key";
      }
    }
  }
  augment "/ncs:devices/ncs:device-group/ncs:ned-id/ncs:rpc" {
    container rpc-master-key-delete {
      tailf:ncs-device-type "netconf";
      tailf:display-when "/ncs:devices/ncs:device[ncs:name=current()/../../../ncs:member]/ncs:module[ncs:name='Cisco-IOS-XR-lib-keychain-act']";
      tailf:action master-key-delete {
        tailf:actionpoint ncsproxy {
          tailf:internal;
        }
        description
          "Remove Master key";
      }
    }
  }
  augment "/ncs:devices/ncs:device/ncs:rpc" {
    container rpc-master-key-add {
      tailf:ncs-device-type "netconf";
      tailf:display-when "not(../../ncs:module) or ../../ncs:module[ncs:name='Cisco-IOS-XR-lib-keychain-act']";
      tailf:action master-key-add {
        tailf:actionpoint ncsproxy {
          tailf:internal;
        }
        description
          "To add a new master key";
        input {
          leaf new-key {
            description
              "New master key to be added";
            type string;
          }
        }
      }
    }
  }
  augment "/ncs:devices/ncs:device-group/ncs:ned-id/ncs:rpc" {
    container rpc-master-key-add {
      tailf:ncs-device-type "netconf";
      tailf:display-when "/ncs:devices/ncs:device[ncs:name=current()/../../../ncs:member]/ncs:module[ncs:name='Cisco-IOS-XR-lib-keychain-act']";
      tailf:action master-key-add {
        tailf:actionpoint ncsproxy {
          tailf:internal;
        }
        description
          "To add a new master key";
        input {
          leaf new-key {
            description
              "New master key to be added";
            type string;
          }
        }
      }
    }
  }
}
