module Cisco-IOS-XR-ip-iarm-vrf-cfg {
  // Generated by yanger -t ncs
  tailf:mount-id f5500-nc-1.0:f5500-nc-1.0;
  tailf:ncs-device-type "netconf";

  namespace "http://cisco.com/ns/yang/Cisco-IOS-XR-ip-iarm-vrf-cfg";
  prefix Cisco-IOS-XR-ip-iarm-vrf-cfg;

  import Cisco-IOS-XR-types {
    prefix xr;
  }
  import Cisco-IOS-XR-infra-rsi-cfg {
    prefix a1;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ip-iarm-vrf package configuration.

     This YANG module augments the
       Cisco-IOS-XR-infra-rsi-cfg
     module with configuration data.

     Copyright (c) 2013-2018 by Cisco Systems, Inc.
     All rights reserved.";

  revision 2015-11-09 {
    description
      "IOS XR 6.0 revision.";
  }

  grouping ncs_template_INTERFACE {
    description
      "Common node of ipv4, ipv6";
    leaf interface {
      type string;
      description
        "Default multicast host interface name";
    }
  }

  grouping ncs_rpc_notif_INTERFACE {
    description
      "Common node of ipv4, ipv6";
    leaf interface {
      type xr:Interface-name;
      description
        "Default multicast host interface name";
    }
  }

  grouping live_ncs_INTERFACE {
    description
      "Common node of ipv4, ipv6";
    leaf interface {
      type xr:Interface-name;
      description
        "Default multicast host interface name";
    }
  }

  grouping INTERFACE {
    description
      "Common node of ipv4, ipv6";
    leaf interface {
      type xr:Interface-name;
      description
        "Default multicast host interface name";
    }
  }

  augment "/ncs:devices/ncs:template/ncs:ned-id/ncs:config/a1:vrfs/a1:vrf" {
    container multicast-host {
      description
        "Multicast host stack configuration";
      container ipv4 {
        description
          "IPv4 configuration";
        uses ncs_template_INTERFACE;
      }
      container ipv6 {
        description
          "IPv6 configuration";
        uses ncs_template_INTERFACE;
      }
    }
    description
      "This augment extends the configuration data of
       'Cisco-IOS-XR-infra-rsi-cfg'";
  }
  augment "/ncs:devices/ncs:device/ncs:live-status/a1:vrfs/a1:vrf" {
    container multicast-host {
      tailf:ncs-device-type "netconf";
      tailf:display-when "not(../../../../ncs:module) or ../../../../ncs:module[ncs:name='Cisco-IOS-XR-ip-iarm-vrf-cfg'] or (../../../../ncs:live-status-protocol[not(ncs:capability)]) or (../../../../ncs:live-status-protocol/ncs:capability/ncs:module[.='Cisco-IOS-XR-ip-iarm-vrf-cfg'])";
      description
        "Multicast host stack configuration";
      container ipv4 {
        description
          "IPv4 configuration";
        uses live_ncs_INTERFACE;
      }
      container ipv6 {
        description
          "IPv6 configuration";
        uses live_ncs_INTERFACE;
      }
    }
    description
      "This augment extends the configuration data of
       'Cisco-IOS-XR-infra-rsi-cfg'";
  }
  augment "/ncs:devices/ncs:device/ncs:config/a1:vrfs/a1:vrf" {
    container multicast-host {
      tailf:ncs-device-type "netconf";
      tailf:display-when "not(../../../../ncs:module) or ../../../../ncs:module[ncs:name='Cisco-IOS-XR-ip-iarm-vrf-cfg']";
      description
        "Multicast host stack configuration";
      container ipv4 {
        description
          "IPv4 configuration";
        uses INTERFACE;
      }
      container ipv6 {
        description
          "IPv6 configuration";
        uses INTERFACE;
      }
    }
    description
      "This augment extends the configuration data of
       'Cisco-IOS-XR-infra-rsi-cfg'";
  }
}
