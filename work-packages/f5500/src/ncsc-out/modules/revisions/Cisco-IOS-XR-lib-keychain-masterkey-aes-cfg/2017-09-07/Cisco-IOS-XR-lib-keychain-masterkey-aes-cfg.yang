module Cisco-IOS-XR-lib-keychain-masterkey-aes-cfg {
  // Generated by yanger -t ncs
  tailf:mount-id f5500-nc-1.0:f5500-nc-1.0;
  tailf:ncs-device-type "netconf";

  namespace "http://cisco.com/ns/yang/Cisco-IOS-XR-lib-keychain-masterkey-aes-cfg";
  prefix Cisco-IOS-XR-lib-keychain-masterkey-aes-cfg;

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR lib-keychain-masterkey-aes package configuration.

     This module contains definitions
     for the following management objects:
       password: Configure masterkey

     Copyright (c) 2013-2018 by Cisco Systems, Inc.
     All rights reserved.";

  revision 2017-09-07 {
    description
      "Fixed type translation error.";
  }
  revision 2015-11-09 {
    description
      "IOS XR 6.0 revision.";
  }

  typedef Key-encryption {
    type enumeration {
      enum "type6" {
        value 2;
        description
          "Type6";
      }
    }
    description
      "Key encryption";
  }

  augment "/ncs:devices/ncs:device/ncs:config" {
    container password {
      tailf:ncs-device-type "netconf";
      tailf:display-when "not(../../ncs:module) or ../../ncs:module[ncs:name='Cisco-IOS-XR-lib-keychain-masterkey-aes-cfg']";
      description
        "Configure masterkey";
      container encryption {
        description
          "Enable password encryption";
        leaf aes {
          type Key-encryption;
          description
            "encryption type used to store key";
        }
      }
    }
  }
  augment "/ncs:devices/ncs:device/ncs:live-status" {
    container password {
      tailf:ncs-device-type "netconf";
      tailf:display-when "not(../../ncs:module) or ../../ncs:module[ncs:name='Cisco-IOS-XR-lib-keychain-masterkey-aes-cfg'] or (../../ncs:live-status-protocol[not(ncs:capability)]) or (../../ncs:live-status-protocol/ncs:capability/ncs:module[.='Cisco-IOS-XR-lib-keychain-masterkey-aes-cfg'])";
      description
        "Configure masterkey";
      container encryption {
        description
          "Enable password encryption";
        leaf aes {
          type Key-encryption;
          description
            "encryption type used to store key";
        }
      }
    }
  }
  augment "/ncs:devices/ncs:template/ncs:ned-id/ncs:config" {
    container password {
      description
        "Configure masterkey";
      container encryption {
        description
          "Enable password encryption";
        leaf aes {
          type string;
          description
            "encryption type used to store key";
        }
      }
    }
  }
}
