module SNMP-NOTIFICATION-MIB {
  // Generated by yanger -t ncs
  tailf:mount-id f5500-nc-1.0:f5500-nc-1.0;
  tailf:ncs-device-type "netconf";

  namespace "http://tail-f.com/ns/mibs/SNMP-NOTIFICATION-MIB/200210140000Z";
  prefix SNMP-NOTIFICATION-MIB;
  // NCS drop tailf:id
  tailf:snmp-mib-module-name SNMP-NOTIFICATION-MIB;

  import ietf-yang-types {
    prefix yang;
  }
  import tailf-common {
    prefix tailf;
  }
  import SNMPv2-TC {
    prefix SNMPv2_TC;
  }
  import SNMP-TARGET-MIB {
    prefix SNMP_TARGET_MIB;
  }
  import "f5500-nc-1.0" {
    prefix "f5500-nc-1.0";
  }
  import tailf-ncs {
    prefix ncs;
  }

  revision 2002-10-14 {
    description
      "";
  }

  typedef snmpNotifyFilterTypeType {
    type enumeration {
      enum "included" {
        value 1;
      }
      enum "excluded" {
        value 2;
      }
    }
  }

  typedef snmpNotifyFilterMaskType {
    type tailf:hex-list {
      pattern '(((([0-9A-Fa-f]{2}):){0,15}([0-9A-Fa-f]{2}))){0,1}';
      tailf:value-length "min .. 16";
    }
  }

  typedef snmpNotifyFilterProfileNameType {
    type string {
      length "1 .. 32";
    }
  }

  typedef snmpTargetParamsNameType {
    type string {
      length "1 .. 32";
    }
  }

  typedef snmpNotifyTypeType {
    type enumeration {
      enum "trap" {
        value 1;
      }
      enum "inform" {
        value 2;
      }
    }
  }

  typedef snmpNotifyNameType {
    type string {
      length "1 .. 32";
    }
  }

  augment "/ncs:devices/ncs:device/ncs:config" {
    container SNMP-NOTIFICATION-MIB {
      tailf:ncs-device-type "netconf";
      tailf:display-when "not(../../ncs:module) or ../../ncs:module[ncs:name='SNMP-NOTIFICATION-MIB']";
      container snmpNotifyTable {
        list snmpNotifyEntry {
          key "snmpNotifyName";
          tailf:sort-order snmp-implied;
          tailf:snmp-oid "1.3.6.1.6.3.13.1.1";
          leaf snmpNotifyName {
            type snmpNotifyNameType;
            tailf:snmp-oid "1.3.6.1.6.3.13.1.1.1.1";
          }
          leaf snmpNotifyTag {
            type SNMP_TARGET_MIB:SnmpTagValue;
            tailf:snmp-oid "1.3.6.1.6.3.13.1.1.1.2";
          }
          leaf snmpNotifyType {
            type snmpNotifyTypeType;
            tailf:snmp-oid "1.3.6.1.6.3.13.1.1.1.3";
            default "trap";
          }
          leaf snmpNotifyStorageType {
            type SNMPv2_TC:StorageType;
            tailf:snmp-oid "1.3.6.1.6.3.13.1.1.1.4";
            default "nonVolatile";
          }
        }
      }
      // NCS drop fully hidden container snmpNotifyFilterProfileTable
      // NCS drop fully hidden container snmpNotifyFilterTable
    }
  }
  augment "/ncs:devices/ncs:device/ncs:live-status" {
    container SNMP-NOTIFICATION-MIB {
      tailf:ncs-device-type "netconf";
      tailf:display-when "not(../../ncs:module) or ../../ncs:module[ncs:name='SNMP-NOTIFICATION-MIB'] or (../../ncs:live-status-protocol[not(ncs:capability)]) or (../../ncs:live-status-protocol/ncs:capability/ncs:module[.='SNMP-NOTIFICATION-MIB'])";
      container snmpNotifyTable {
        list snmpNotifyEntry {
          key "snmpNotifyName";
          tailf:sort-order snmp-implied;
          tailf:snmp-oid "1.3.6.1.6.3.13.1.1";
          leaf snmpNotifyName {
            type snmpNotifyNameType;
            tailf:snmp-oid "1.3.6.1.6.3.13.1.1.1.1";
          }
          leaf snmpNotifyTag {
            type SNMP_TARGET_MIB:SnmpTagValue;
            tailf:snmp-oid "1.3.6.1.6.3.13.1.1.1.2";
          }
          leaf snmpNotifyType {
            type snmpNotifyTypeType;
            tailf:snmp-oid "1.3.6.1.6.3.13.1.1.1.3";
            // NCS drop default statement
          }
          leaf snmpNotifyStorageType {
            type SNMPv2_TC:StorageType;
            tailf:snmp-oid "1.3.6.1.6.3.13.1.1.1.4";
            // NCS drop default statement
          }
        }
      }
      // NCS drop fully hidden container snmpNotifyFilterProfileTable
      // NCS drop fully hidden container snmpNotifyFilterTable
    }
  }
  augment "/ncs:devices/ncs:template/ncs:ned-id/ncs:config" {
    container SNMP-NOTIFICATION-MIB {
      container snmpNotifyTable {
        list snmpNotifyEntry {
          // NCS patched for predictable order
          ordered-by user;
          key "snmpNotifyName";
          leaf snmpNotifyName {
            type string;
          }
          leaf snmpNotifyTag {
            type string;
          }
          leaf snmpNotifyType {
            type string;
            // NCS drop default statement
          }
          leaf snmpNotifyStorageType {
            type string;
            // NCS drop default statement
          }
        }
      }
      // NCS drop fully hidden container snmpNotifyFilterProfileTable
      // NCS drop fully hidden container snmpNotifyFilterTable
    }
  }
}
