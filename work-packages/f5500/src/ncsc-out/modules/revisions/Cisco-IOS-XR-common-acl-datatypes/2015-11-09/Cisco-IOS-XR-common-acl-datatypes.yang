module Cisco-IOS-XR-common-acl-datatypes {
  // Generated by yanger -t ncs
  tailf:mount-id f5500-nc-1.0:f5500-nc-1.0;
  tailf:ncs-device-type "netconf";

  namespace "http://cisco.com/ns/yang/Cisco-IOS-XR-common-acl-datatypes";
  prefix Cisco-IOS-XR-common-acl-datatypes;

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of generally useful
     derived YANG data types.

     Copyright (c) 2013-2018 by Cisco Systems, Inc.
     All rights reserved.";

  revision 2015-11-09 {
    description
      "IOS XR 6.0 revision.";
  }

  typedef Acl-sequence-number-range {
    type uint32 {
      range "1..2147483646";
    }
    description
      "Acl sequence number range";
  }

  typedef Acl-usage-app-id-enum {
    type enumeration {
      enum "pfilter" {
        value 1;
        description
          "General Usage Statistics";
      }
      enum "bgp" {
        value 2;
        description
          "Usage staistics related to BGP Traffic";
      }
      enum "ospf" {
        value 3;
        description
          "Usage staistics related to OSPF Traffic";
      }
    }
    description
      "Acl usage app id enum";
  }
}
