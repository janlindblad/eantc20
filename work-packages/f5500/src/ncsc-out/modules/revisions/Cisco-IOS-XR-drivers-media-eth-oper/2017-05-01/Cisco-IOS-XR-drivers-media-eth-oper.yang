module Cisco-IOS-XR-drivers-media-eth-oper {
  // Generated by yanger -t ncs
  tailf:mount-id f5500-nc-1.0:f5500-nc-1.0;
  tailf:ncs-device-type "netconf";

  namespace "http://cisco.com/ns/yang/Cisco-IOS-XR-drivers-media-eth-oper";
  prefix Cisco-IOS-XR-drivers-media-eth-oper;

  import Cisco-IOS-XR-types {
    prefix xr;
  }
  include Cisco-IOS-XR-drivers-media-eth-oper-sub1 {
    revision-date 2017-05-01;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR drivers-media-eth package operational data.

     This module contains definitions
     for the following management objects:
       ethernet-interface: Ethernet operational data

     Copyright (c) 2013-2018 by Cisco Systems, Inc.
     All rights reserved.";

  revision 2017-05-01 {
    description
      "Fixing backward compatibility error in module.";
  }
  revision 2017-04-04 {
    description
      "Added new fields to phy data.";
  }
  revision 2015-01-07 {
    description
      "IOS XR 5.3.1 revision.";
  }

  augment "/ncs:devices/ncs:device/ncs:config" {
    // NCS drop config false container 'ethernet-interface'
  }
  augment "/ncs:devices/ncs:device/ncs:live-status" {
    container ethernet-interface {
      tailf:ncs-device-type "netconf";
      tailf:display-when "not(../../ncs:module) or ../../ncs:module[ncs:name='Cisco-IOS-XR-drivers-media-eth-oper'] or (../../ncs:live-status-protocol[not(ncs:capability)]) or (../../ncs:live-status-protocol/ncs:capability/ncs:module[.='Cisco-IOS-XR-drivers-media-eth-oper'])";
      description
        "Ethernet operational data";
      container statistics {
        description
          "Ethernet controller statistics table";
        list statistic {
          key "interface-name";
          description
            "Ethernet statistics information";
          leaf interface-name {
            type xr:Interface-name;
            description
              "The name of the interface";
          }
          uses live_ncs_ETHERNET-PORT-STATS-TYPE;
        }
      }
      container interfaces {
        description
          "Ethernet controller info table";
        list interface {
          key "interface-name";
          description
            "Ethernet controller information";
          leaf interface-name {
            type xr:Interface-name;
            description
              "The name of the interface";
          }
          uses live_ncs_ETHERNET-CONTROLLER-DRIVER-BAG-V2-TYPE;
        }
      }
      container berts {
        description
          "Ethernet controller BERT table";
        list bert {
          key "interface-name";
          description
            "Ethernet BERT information";
          leaf interface-name {
            type xr:Interface-name;
            description
              "The name of the interface";
          }
          uses live_ncs_ETH-SHOWCTRL-BERT;
        }
      }
    }
  }
  augment "/ncs:devices/ncs:template/ncs:ned-id/ncs:config" {
    // NCS drop config false container 'ethernet-interface'
  }
}
