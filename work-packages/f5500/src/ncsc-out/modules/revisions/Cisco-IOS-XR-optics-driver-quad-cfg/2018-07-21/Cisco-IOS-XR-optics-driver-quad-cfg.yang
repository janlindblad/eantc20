module Cisco-IOS-XR-optics-driver-quad-cfg {
  // Generated by yanger -t ncs
  tailf:mount-id f5500-nc-1.0:f5500-nc-1.0;
  tailf:ncs-device-type "netconf";

  namespace "http://cisco.com/ns/yang/Cisco-IOS-XR-optics-driver-quad-cfg";
  prefix Cisco-IOS-XR-optics-driver-quad-cfg;

  import Cisco-IOS-XR-types {
    prefix xr;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR optics-driver-quad package configuration.

     This module contains definitions
     for the following management objects:
       node: HW module Quad Config

     Copyright (c) 2013-2018 by Cisco Systems, Inc.
     All rights reserved.";

  revision 2018-07-21 {
    description
      "Schema added.";
  }
  revision 2015-11-09 {
    description
      "IOS XR 6.0 revision.";
  }

  augment "/ncs:devices/ncs:device/ncs:config" {
    container node {
      tailf:ncs-device-type "netconf";
      tailf:display-when "not(../../ncs:module) or ../../ncs:module[ncs:name='Cisco-IOS-XR-optics-driver-quad-cfg']";
      description
        "HW module Quad Config";
      container acts {
        description
          "none";
        list act {
          key "node-name";
          description
            "Nodename";
          container quad-configs {
            description
              "quad configuration";
            list quad-config {
              key "id1";
              description
                "none";
              container mode {
                description
                  "select mode 10g or 25g for a quad(group of 4
                   ports).";
                leaf speed {
                  type string;
                  description
                    "speed 10g or 25g";
                }
              }
              leaf id1 {
                type uint32;
                description
                  "none";
              }
            }
          }
          leaf node-name {
            type xr:Cisco-ios-xr-string;
            description
              "NodeName";
          }
        }
      }
    }
  }
  augment "/ncs:devices/ncs:device/ncs:live-status" {
    container node {
      tailf:ncs-device-type "netconf";
      tailf:display-when "not(../../ncs:module) or ../../ncs:module[ncs:name='Cisco-IOS-XR-optics-driver-quad-cfg'] or (../../ncs:live-status-protocol[not(ncs:capability)]) or (../../ncs:live-status-protocol/ncs:capability/ncs:module[.='Cisco-IOS-XR-optics-driver-quad-cfg'])";
      description
        "HW module Quad Config";
      container acts {
        description
          "none";
        list act {
          key "node-name";
          description
            "Nodename";
          container quad-configs {
            description
              "quad configuration";
            list quad-config {
              key "id1";
              description
                "none";
              container mode {
                description
                  "select mode 10g or 25g for a quad(group of 4
                   ports).";
                leaf speed {
                  type string;
                  description
                    "speed 10g or 25g";
                }
              }
              leaf id1 {
                type uint32;
                description
                  "none";
              }
            }
          }
          leaf node-name {
            type xr:Cisco-ios-xr-string;
            description
              "NodeName";
          }
        }
      }
    }
  }
  augment "/ncs:devices/ncs:template/ncs:ned-id/ncs:config" {
    container node {
      description
        "HW module Quad Config";
      container acts {
        description
          "none";
        list act {
          // NCS patched for predictable order
          ordered-by user;
          key "node-name";
          description
            "Nodename";
          container quad-configs {
            description
              "quad configuration";
            list quad-config {
              // NCS patched for predictable order
              ordered-by user;
              key "id1";
              description
                "none";
              container mode {
                description
                  "select mode 10g or 25g for a quad(group of 4
                   ports).";
                leaf speed {
                  type string;
                  description
                    "speed 10g or 25g";
                }
              }
              leaf id1 {
                type string;
                description
                  "none";
              }
            }
          }
          leaf node-name {
            type string;
            description
              "NodeName";
          }
        }
      }
    }
  }
}
