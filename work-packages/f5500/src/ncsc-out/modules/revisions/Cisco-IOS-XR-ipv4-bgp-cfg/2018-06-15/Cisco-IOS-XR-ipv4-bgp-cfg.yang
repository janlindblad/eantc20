module Cisco-IOS-XR-ipv4-bgp-cfg {
  // Generated by yanger -t ncs
  tailf:mount-id f5500-nc-1.0:f5500-nc-1.0;
  tailf:ncs-device-type "netconf";

  namespace "http://cisco.com/ns/yang/Cisco-IOS-XR-ipv4-bgp-cfg";
  prefix Cisco-IOS-XR-ipv4-bgp-cfg;

  import ietf-inet-types {
    prefix inet;
  }
  import Cisco-IOS-XR-types {
    prefix xr;
  }
  import Cisco-IOS-XR-ipv4-bgp-datatypes {
    prefix dt1;
  }
  import Cisco-IOS-XR-infra-rsi-cfg {
    prefix a1;
  }
  import Cisco-IOS-XR-snmp-agent-cfg {
    prefix a2;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ipv4-bgp package configuration.

     This module contains definitions
     for the following management objects:
       asn-format: Autonomous system number format
       bgp: bgp
       bmp-server-all: bmp server all
       bmp-servers: bmp servers

     This YANG module augments the
       Cisco-IOS-XR-infra-rsi-cfg,
       Cisco-IOS-XR-snmp-agent-cfg
     modules with configuration data.

     Copyright (c) 2013-2018 by Cisco Systems, Inc.
     All rights reserved.";

  revision 2018-06-15 {
    description
      "Allow min..max in range when min == max.";
  }
  revision 2018-01-18 {
    description
      "Added AO option for neighbor";
  }
  revision 2017-11-05 {
    description
      "Corrected boolean values in when statements.";
  }
  revision 2017-09-07 {
    description
      "Fixed type translation error.";
  }
  revision 2017-07-31 {
    description
      "Fixed missing augmentation from multiple MDA parent.";
  }
  revision 2017-06-26 {
    description
      "Change identifiers to be more readable.";
  }
  revision 2017-06-01 {
    description
      "Revision description string.";
  }
  revision 2017-05-01 {
    description
      "Fixing backward compatibility error in module.";
  }
  revision 2015-08-27 {
    description
      "IOS XR 5.3.2 revision.";
  }

  typedef Bgp-global-as-range {
    type uint32 {
      range "0..4294967295";
    }
    description
      "Bgp global as range";
  }

  typedef Bgp-global-route-distinguisher {
    type enumeration {
      enum "as" {
        value 2;
        description
          "AS format RD";
      }
      enum "four-byte-as" {
        value 3;
        description
          "4-byte AS format RD";
      }
      enum "ipv4-address" {
        value 4;
        description
          "IPv4 address format RD";
      }
    }
    description
      "Bgp global route distinguisher";
  }

  typedef Bgp-global-extcomm-asn-index {
    type uint32 {
      range "0..4294967295";
    }
    description
      "Bgp global extcomm asn index";
  }

  typedef Bgp-global-extcomm-v4-addr-index {
    type uint32 {
      range "0..65535";
    }
    description
      "Bgp global extcomm v4 addr index";
  }

  typedef Bgp-cluster-id {
    type enumeration {
      enum "number" {
        value 1;
        description
          "Number";
      }
      enum "ipv4-address" {
        value 2;
        description
          "IPv4 Address";
      }
    }
    description
      "Bgp cluster id";
  }

  typedef Bgp-site-of-origin {
    type enumeration {
      enum "as" {
        value 0;
        description
          "AS format SoO";
      }
      enum "ipv4-address" {
        value 1;
        description
          "IPv4 address format SoO";
      }
      enum "four-byte-as" {
        value 2;
        description
          "4-byte AS format SoO";
      }
    }
    description
      "Bgp site of origin";
  }

  typedef Bgp-tcp-mode {
    type enumeration {
      enum "either" {
        value 0;
        description
          "Either active or passive mode";
      }
      enum "active-only" {
        value 1;
        description
          "Active mode only";
      }
      enum "passive-only" {
        value 2;
        description
          "Passive mode only";
      }
    }
    description
      "Bgp tcp mode";
  }

  typedef Bgp-adv-rt {
    type enumeration {
      enum "bgp-regular-rt" {
        value 0;
        description
          "Regular RT type";
      }
      enum "bgp-stitching-rt" {
        value 1;
        description
          "Stitching RT type";
      }
    }
    description
      "Bgp adv rt";
  }

  typedef Bgp-route-distinguisher {
    type enumeration {
      enum "auto" {
        value 1;
        description
          "Automatically assigned";
      }
      enum "as" {
        value 2;
        description
          "AS format RD";
      }
      enum "four-byte-as" {
        value 3;
        description
          "4-byte AS format RD";
      }
      enum "ipv4-address" {
        value 4;
        description
          "IPv4 address format RD";
      }
    }
    description
      "Bgp route distinguisher";
  }

  typedef Bgp-aigp-cfg {
    type enumeration {
      enum "enable" {
        value 1;
        description
          "Enable AIGP";
      }
      enum "disable" {
        value 2;
        description
          "Disable AIGP";
      }
    }
    description
      "Bgp aigp cfg";
  }

  typedef Bgp-af-encapsulation {
    type enumeration {
      enum "vx-lan" {
        value 1;
        description
          "VxLAN encapsulation type";
      }
    }
    description
      "Bgp af encapsulation";
  }

  typedef Bgp-reorg-opt {
    type enumeration {
      enum "bgp-cfg-adv" {
        value 1;
        description
          "Advertise translated routes";
      }
      enum "bgp-cfg-adv-reorg" {
        value 2;
        description
          "Advertise Reorig routes";
      }
      enum "bgp-cfg-adv-disable" {
        value 3;
        description
          "Disable adv of routes";
      }
      enum "bgp-cfg-adv-local" {
        value 4;
        description
          "Advertise local routes";
      }
      enum "bgp-cfg-adv-def-vrf-imp-disable" {
        value 5;
        description
          "Disable adv of Def VRF Imported routes";
      }
      enum "bgp-cfg-adv-vrf-re-imp-disable" {
        value 6;
        description
          "Disable adv of VRF ReImported routes";
      }
      enum "bgp-cfg-adv-vrf-evpn-re-imp-disable" {
        value 7;
        description
          "Disable adv of VRF EVPN extranet Imported
           routes";
      }
    }
    description
      "Bgp reorg opt";
  }

  typedef Bgp-rpki-transport {
    type enumeration {
      enum "tcp" {
        value 0;
        description
          "TCP Transport";
      }
      enum "ssh" {
        value 1;
        description
          "SSH Transport";
      }
    }
    description
      "Bgp rpki transport";
  }

  typedef Bgp-asn {
    type enumeration {
      enum "as-plain" {
        value 1;
        description
          "AS plain format";
      }
      enum "asdot" {
        value 2;
        description
          "AS dot format";
      }
    }
    description
      "Bgp asn";
  }

  typedef Bgp-orf {
    type enumeration {
      enum "none" {
        value 0;
        description
          "No capability to send or receive";
      }
      enum "receive" {
        value 1;
        description
          "Receive ORF capability";
      }
      enum "send" {
        value 2;
        description
          "Send ORF capability";
      }
      enum "both" {
        value 3;
        description
          "Send and receive ORF capability";
      }
    }
    description
      "Bgp orf";
  }

  typedef Route-target-addr-index {
    type uint32 {
      range "0..65535";
    }
    description
      "Route target addr index";
  }

  typedef Bgp-flowspec-validation-cfg {
    type enumeration {
      enum "enable" {
        value 1;
        description
          "Enable Flowspec validation";
      }
      enum "disable" {
        value 2;
        description
          "Disable Flowspec validation";
      }
      enum "redirect-nexhop-disable" {
        value 3;
        description
          "Disable Flowspec redirect nexthop validation";
      }
    }
    description
      "Bgp flowspec validation cfg";
  }

  typedef Bgp-aigp-cfg-poi {
    type enumeration {
      enum "pre-best-path" {
        value 1;
        description
          "AIGP Pre-bestpath POI";
      }
      enum "igp-cost" {
        value 2;
        description
          "AIGP igp-cost POI";
      }
    }
    description
      "Bgp aigp cfg poi";
  }

  typedef Bgp-send-mcast-attr-cfg {
    type enumeration {
      enum "enable" {
        value 1;
        description
          "Enable SendMcastAttr";
      }
      enum "disable" {
        value 2;
        description
          "Disable SendMcastAttr";
      }
    }
    description
      "Bgp send mcast attr cfg";
  }

  typedef Bmp-route-direction {
    type enumeration {
      enum "inbound" {
        value 1;
        description
          "Pickup routes at inbound direction from peer";
      }
    }
    description
      "Bmp route direction";
  }

  typedef Route-target-as-index {
    type uint32 {
      range "0..4294967295";
    }
    description
      "Route target as index";
  }

  typedef Bgp-bfd-enable-mode {
    type enumeration {
      enum "disable" {
        value 0;
        description
          "Disable Mode - Prevent inheritance";
      }
      enum "default" {
        value 1;
        description
          "Default Mode - Default BFD behavior";
      }
      enum "strict" {
        value 2;
        description
          "Strict Mode - Hold down adj until BFD session
           up";
      }
    }
    description
      "Bgp bfd enable mode";
  }

  typedef Bgp-rnh-install-format {
    type enumeration {
      enum "ext-comm" {
        value 0;
        description
          "Install RNH as opaque and extcomm";
      }
      enum "ext-comm-only" {
        value 1;
        description
          "Install RNH as extcomm only";
      }
    }
    description
      "Bgp rnh install format";
  }

  typedef Bgp-vrf-route-target {
    type enumeration {
      enum "as" {
        value 0;
        description
          "AS format RT";
      }
      enum "ipv4-address" {
        value 1;
        description
          "IPv4 address format RT";
      }
      enum "four-byte-as" {
        value 2;
        description
          "4-byte AS format RT";
      }
    }
    description
      "Bgp vrf route target";
  }

  typedef Bgp-signal {
    type enumeration {
      enum "bgp-disable" {
        value 1;
        description
          "Signalling BGP disable";
      }
      enum "ldp-disable" {
        value 2;
        description
          "Signalling LDP disable";
      }
    }
    description
      "Bgp signal";
  }

  typedef Bgp-ebgp-send-dmz-enable-mode {
    type enumeration {
      enum "disable" {
        value 0;
        description
          "Disable Mode - Prevent inheritance";
      }
      enum "default" {
        value 1;
        description
          "Default Mode - Send dmz link bandwidth value to
           ebgp neighbor";
      }
      enum "cumulative" {
        value 2;
        description
          "Strict Mode - Send cumulative dmz link
           bandwidth value to ebgp neighbor";
      }
    }
    description
      "Bgp ebgp send dmz enable mode";
  }

  typedef Bgp-default-metric-range {
    type uint32 {
      range "0..4294967295";
    }
    description
      "Bgp default metric range";
  }

  typedef Bmp-policy-select {
    type enumeration {
      enum "post-policy" {
        value 2;
        description
          "Pickup routes after policy application";
      }
    }
    description
      "Bmp policy select";
  }

  typedef Bgp-nbrgr {
    type enumeration {
      enum "true" {
        value 0;
        description
          "NBR has enabled Graceful Restart capability";
      }
      enum "false" {
        value 1;
        description
          "NBR has disabled Graceful Restart capability";
      }
    }
    description
      "Bgp nbrgr";
  }

  typedef Bgp-mvpn-sfs-select {
    type enumeration {
      enum "all-paths" {
        value 1;
        description
          "Select all paths as single forwarder PE";
      }
      enum "highest-ip-address" {
        value 2;
        description
          "Select PE with highest address as single
           forwarder PE";
      }
    }
    description
      "Bgp mvpn sfs select";
  }

  grouping ncs_template_ADVERTISE-DISABLE {
    description
      "Common node of neighbor-group-af, neighbor-af,
       vrf-neighbor-af, af-group-af";
    container advertise-disable {
      description
        "Disable Advertise Of Routes to the peer";
      leaf af-name {
        type string;
        description
          "Address family";
      }
      leaf reorg-option {
        type string;
        description
          "Reorigination option";
      }
      leaf rt-type {
        type string;
        description
          "RT type";
      }
    }
  }

  grouping ncs_template_TABLE-POLICY {
    description
      "Common node of global-af, vrf-global-af";
    leaf table-policy {
      type string;
      description
        "Configure policy for installation of routes to
         RIB";
    }
  }

  grouping ncs_template_MAXIMUM-PREFIXES {
    description
      "Common node of global-af, vrf-global-afCommon
       node of neighbor-group-af, neighbor-af,
       vrf-neighbor-af, af-group-af";
    container maximum-prefixes {
      presence "Indicates a maximum-prefixes node is configured.";
      description
        "Maximum number of prefixes to accept from this
         peer";
      leaf prefix-limit {
        type string;
        // NCS drop mandatory statement
        description
          "Maximum prefixes limit";
      }
      leaf warning-percentage {
        type string;
        // NCS drop default statement
        description
          "Threshold value (%) at which to generate a
           warning message.";
      }
      leaf warning-only {
        type string;
        // NCS drop default statement
        description
          "TRUE to only give a warning message when limit
           is exceeded.  FALSE to accept max prefix limit
           only.";
      }
      leaf restart-time {
        type string;
        // NCS drop default statement
        description
          "Restart interval";
      }
      leaf discard-extra-paths {
        type string;
        // NCS drop default statement
        description
          "Discard extra paths when limit is exceeded";
      }
    }
  }

  grouping ncs_template_DISTANCE {
    description
      "Common node of global-af, vrf-global-af";
    container distance {
      presence "Indicates a distance node is configured.";
      description
        "Define an administrative distance";
      leaf external-routes {
        type string;
        // NCS drop mandatory statement
        description
          "Distance for routes external to the AS";
      }
      leaf internal-routes {
        type string;
        // NCS drop mandatory statement
        description
          "Distance for routes internal to the AS";
      }
      leaf local-routes {
        type string;
        // NCS drop mandatory statement
        description
          "Distance for local routes";
      }
    }
  }

  grouping ncs_template_UPDATE-SOURCE-INTERFACE {
    description
      "Common node of neighbor-group, neighbor,
       vrf-neighbor, session-group";
    leaf update-source-interface {
      type string;
      description
        "Select an interface to configure";
    }
  }

  grouping ncs_template_MULTI-PATH-AS-PATH-IGNORE-ONWARDS {
    description
      "Common node of global, vrf-global";
    leaf multi-path-as-path-ignore-onwards {
      type empty;
      description
        "Change default multi-route selection criteria to
         ignore everything onwards as-path check";
    }
  }

  grouping ncs_template_PROPAGATE-DMZ-LINK-BANDWIDTH {
    description
      "Common node of neighbor-group, neighbor,
       vrf-neighbor, session-group";
    leaf propagate-dmz-link-bandwidth {
      type string;
      description
        "TRUE to propagate DMZ link bandwidth.  FALSE to
         not propagate and to prevent inheritance from a
         parent";
    }
  }

  grouping ncs_template_DISABLE-AUTO-SOFT-RESET {
    description
      "Common node of global, vrf-global";
    leaf disable-auto-soft-reset {
      type empty;
      description
        "Disable automatic soft peer reset on policy
         reconfiguration";
    }
  }

  grouping ncs_template_MSG-LOG-IN {
    description
      "Common node of neighbor-group, neighbor,
       vrf-neighbor, session-group";
    container msg-log-in {
      description
        "Message log inbound";
      leaf msg-buf-count {
        type string;
        description
          "Inbound message log buffer size";
      }
      leaf msg-log-disable {
        type string;
        description
          "Disable inbound message logging";
      }
      leaf msg-log-inherit-disable {
        type string;
        description
          "TRUE, to prevent this entity from having a
           inbound message logging if parent has one";
      }
    }
  }

  grouping ncs_template_DISABLE-ENFORCE-FIRST-AS {
    description
      "Common node of global, vrf-global";
    leaf disable-enforce-first-as {
      type empty;
      description
        "Disable enforce the first AS for EBGP routes";
    }
  }

  grouping ncs_template_ROUTE-TARGET-TABLE {
    description
      "Common node of import-route-targets,
       export-route-targets";
    container route-targets {
      description
        "Route target table";
      list route-target {
        // NCS patched for predictable order
        ordered-by user;
        // NCS drop must statement
        key "type";
        description
          "Route target";
        leaf type {
          type string;
          description
            "Type of RT";
        }
        list as-or-four-byte-as {
          // NCS patched for predictable order
          ordered-by user;
          // NCS drop when statement
          key "as-xx as as-index stitching-rt";
          description
            "as or four byte as";
          leaf as-xx {
            type string;
            description
              "AS number";
          }
          leaf as {
            type string;
            description
              "AS number";
          }
          leaf as-index {
            type string;
            description
              "AS number Index";
          }
          leaf stitching-rt {
            type string;
            description
              "Stitching RT";
          }
        }
        list ipv4-address {
          // NCS patched for predictable order
          ordered-by user;
          // NCS drop when statement
          key "address address-index stitching-rt";
          description
            "ipv4 address";
          leaf address {
            type string;
            description
              "IP address";
          }
          leaf address-index {
            type string;
            description
              "IP address Index";
          }
          leaf stitching-rt {
            type string;
            description
              "Stitching RT";
          }
        }
      }
    }
  }

  grouping ncs_template_REMOTE-AS {
    description
      "Common node of neighbor-group, neighbor,
       vrf-neighbor, session-group";
    container remote-as {
      description
        "Set remote AS";
      leaf as-xx {
        type string;
        description
          "xx of AS number xx.yy";
      }
      leaf as-yy {
        type string;
        description
          "yy of AS number xx.yy";
      }
    }
  }

  grouping ncs_template_ADDITIONAL-PATHS-SEND {
    description
      "Common node of global-af, vrf-global-af";
    leaf additional-paths-send {
      type string;
      description
        "Advertise additional paths Send capability";
    }
  }

  grouping ncs_template_UPDATE-IN-FILTERING {
    description
      "Common node of neighbor-group, neighbor,
       vrf-neighbor, session-group";
    container update-in-filtering {
      description
        "Inbound update filtering";
      container update-in-filtering-message-buffers {
        presence "Indicates a update-in-filtering-message-buffers node is configured.";
        description
          "Message buffers to store filtered updates";
        leaf number-of-buffers {
          type string;
          // NCS drop mandatory statement
          description
            "Number of message buffers";
        }
        leaf non-circular-buffer {
          type string;
          // NCS drop mandatory statement
          description
            "TRUE to configure non-circular buffer";
        }
      }
      leaf enable {
        type empty;
        description
          "Configure inbound update filtering";
      }
      leaf update-in-filtering-attribute-filter-group {
        type string;
        description
          "Attribute-filter group name for update
           filtering";
      }
      leaf update-in-filtering-syslog-disable {
        type empty;
        description
          "Disable inbound update filtering syslog
           messages";
      }
    }
  }

  grouping ncs_template_SHUTDOWN {
    description
      "Common node of neighbor-group, neighbor,
       vrf-neighbor, session-group";
    leaf shutdown {
      type string;
      description
        "TRUE to shutdown this entity, FALSE to prevent
         this entity from being shutdown even if the
         parent is.";
    }
  }

  grouping ncs_template_BMP-ACTIVATE-TABLE {
    description
      "Common node of neighbor-group, neighbor,
       vrf-neighbor, session-group";
    container bmp-activates {
      description
        "Enable BMP logging for this neighbor";
      list bmp-activate {
        // NCS patched for predictable order
        ordered-by user;
        key "server-id";
        description
          "Enable BMP logging for this particular server";
        leaf server-id {
          type string;
          description
            "BMP Server ID";
        }
      }
    }
  }

  grouping ncs_template_ADVERTISE-VRF-IMP-DISABLE-V4 {
    description
      "Common node of neighbor-group-af, neighbor-af,
       vrf-neighbor-af, af-group-af";
    container advertise-vrf-imp-disable-v4 {
      description
        "Disable Advertise Of VRF ReImported Routes";
      leaf af-name {
        type string;
        description
          "Address family";
      }
      leaf adv-option {
        type string;
        description
          "Advertise option";
      }
      leaf rt-type {
        type string;
        description
          "RT type";
      }
    }
  }

  grouping ncs_template_ADVERTISE-VRF-IMP-DISABLE-V6 {
    description
      "Common node of neighbor-group-af, neighbor-af,
       vrf-neighbor-af, af-group-af";
    container advertise-vrf-imp-disable-v6 {
      description
        "Disable Advertise Of VRF ReImported Routes";
      leaf af-name {
        type string;
        description
          "Address family";
      }
      leaf adv-option {
        type string;
        description
          "Advertise option";
      }
      leaf rt-type {
        type string;
        description
          "RT type";
      }
    }
  }

  grouping ncs_template_SITE-OF-ORIGIN {
    description
      "Common node of neighbor-group-af, vrf-neighbor-af
       , af-group-af";
    container site-of-origin {
      description
        "Site-of-Origin extended community associated
         with the neighbor";
      leaf type {
        type string;
        description
          "Type of Extended community";
      }
      leaf as-xx {
        // NCS drop when statement
        type string;
        description
          "AS number";
      }
      leaf as {
        // NCS drop when statement
        type string;
        description
          "AS number";
      }
      leaf as-index {
        // NCS drop when statement
        type string;
        description
          "AS number Index";
      }
      leaf address {
        // NCS drop when statement
        type string;
        description
          "IP address";
      }
      leaf address-index {
        // NCS drop when statement
        type string;
        description
          "IP address Index";
      }
    }
  }

  grouping ncs_template_ROUTE-POLICY-OUT {
    description
      "Common node of neighbor-group-af, neighbor-af,
       vrf-neighbor-af, af-group-af";
    leaf route-policy-out {
      type string;
      description
        "Route policy name to apply to outbound routes";
    }
  }

  grouping ncs_template_SEGMENT-ROUTING {
    description
      "Common node of global-af, vrf-global-af";
    container segment-routing {
      description
        "Segment-routing Configurations";
      container srv6 {
        description
          "SRv6 Configurations";
        leaf enable {
          type empty;
          description
            "Enable SRv6 configuration submode";
        }
        leaf srv6sid-allocation-mode {
          type string;
          description
            "SID allocation mode: per-ce  Set per CE SID
             mode,per-vrf Set per VRF SID mode";
        }
        leaf locator-name {
          type string;
          description
            "Configure Locator name for SID allocation";
        }
      }
    }
  }

  grouping ncs_template_ADVERTISE-V4 {
    description
      "Common node of neighbor-group-af, neighbor-af,
       vrf-neighbor-af, af-group-af";
    container advertise-v4 {
      description
        "Advertise Translated Routes to the peer";
      leaf af-name {
        type string;
        description
          "Address family";
      }
      leaf reorg-option {
        type string;
        description
          "Reorigination option";
      }
      leaf rt-type {
        type string;
        description
          "RT type";
      }
    }
  }

  grouping ncs_template_ADVERTISE-V6 {
    description
      "Common node of neighbor-group-af, neighbor-af,
       vrf-neighbor-af, af-group-af";
    container advertise-v6 {
      description
        "Advertise Translated Routes to the peer";
      leaf af-name {
        type string;
        description
          "Address family";
      }
      leaf reorg-option {
        type string;
        description
          "Reorigination option";
      }
      leaf rt-type {
        type string;
        description
          "RT type";
      }
    }
  }

  grouping ncs_template_DEFAULT-ORIGINATE {
    description
      "Common node of neighbor-group-af, neighbor-af,
       vrf-neighbor-af, af-group-af";
    container default-originate {
      description
        "Originate default route to this neighbor";
      leaf enable {
        type string;
        // NCS drop default statement
        description
          "FALSE to prevent default-originate from, being
           inherited from a parent. TRUE otherwise.";
      }
      leaf route-policy-name {
        type string;
        description
          "Route policy name to specify criteria to
           originate default.";
      }
    }
  }

  grouping ncs_template_IDLE-WATCH-TIME {
    description
      "Common node of neighbor-group, neighbor,
       vrf-neighbor, session-group";
    leaf idle-watch-time {
      type string;
      units "second";
      description
        "Time to wait for deleteing IDLE state Dynamic
         peer";
    }
  }

  grouping ncs_template_TIMERS {
    description
      "Common node of neighbor-group, neighbor,
       vrf-neighbor, session-group";
    container timers {
      description
        "BGP per neighbor timers.";
      leaf keepalive-interval {
        type string;
        // NCS drop default statement
        description
          "Keepalive interval";
      }
      leaf hold-time {
        type string;
        // NCS drop default statement
        description
          "Hold time.  Specify 0 to disable
           keepalives/hold time";
      }
      leaf min-accept-hold-time {
        type string;
        // NCS drop default statement
        description
          "Minimum acceptable hold time.  Specify 0 to
           disable keepalives/hold time";
      }
    }
  }

  grouping ncs_template_NEXT-HOP-MPLS-FWD-IBGP {
    description
      "Common node of global, vrf-global";
    leaf next-hop-mpls-fwd-ibgp {
      type empty;
      description
        "Enable mpls forwarding path for ibgp learnt
         nexthops";
    }
  }

  grouping ncs_template_DISABLE-FAST-EXTERNAL-FALLOVER {
    description
      "Common node of global, vrf-global";
    leaf disable-fast-external-fallover {
      type empty;
      description
        "Disable immediate reset session if a link to a
         directly connected external peer goes down";
    }
  }

  grouping ncs_template_SEND-COMMUNITY-EBGP {
    description
      "Common node of neighbor-group-af, neighbor-af,
       vrf-neighbor-af, af-group-af";
    leaf send-community-ebgp {
      type string;
      description
        "TRUE to send communities to the external
         neighbor/neighbor-group/af-group.  FALSE not to
         send and to prevent inheritance from a parent";
    }
  }

  grouping ncs_template_ADDITIONAL-PATHS-RECEIVE-CAPABILITY {
    description
      "Common node of neighbor-group, neighbor,
       vrf-neighbor, session-group";
    leaf additional-paths-receive-capability {
      type string;
      description
        "Advertise additional paths Receive capability";
    }
  }

  grouping ncs_template_SEND-EXT-COMMUNITY-EBGP {
    description
      "Common node of neighbor-group-af, neighbor-af,
       vrf-neighbor-af, af-group-af";
    leaf send-ext-community-ebgp {
      type string;
      description
        "TRUE to send extended communities to the
         external neighbor/neighbor-group/af-group.
         FALSE not to send and to prevent inheritance
         from a parent";
    }
  }

  grouping ncs_template_AF-GROUP {
    description
      "Common node of neighbor-group-af, neighbor-af,
       vrf-neighbor-af";
    leaf af-group {
      type string;
      description
        "Inherit configuration for this address-family
         from an AF-group";
    }
  }

  grouping ncs_template_ROUTE-POLICY-IN {
    description
      "Common node of neighbor-group-af, neighbor-af,
       vrf-neighbor-af, af-group-af";
    leaf route-policy-in {
      type string;
      description
        "Route policy name to apply to inbound routes";
    }
  }

  grouping ncs_template_LABEL-MODE {
    description
      "Common node of global-af, vrf-global-af";
    container label-mode {
      presence "enable label-mode";
      description
        "BGP 6PE/MPLS-VPN label allocation mode";
      leaf label-allocation-mode {
        type string;
        description
          "Label allocation mode: per-ce  Set per CE label
           mode, per-vrf Set per VRF label mode,
           per-prefix Set per Prefix label mode (for
           MPLS-VPN only)";
      }
      leaf route-policy-name {
        type string;
        description
          "Label mode route policy name";
      }
    }
  }

  grouping ncs_template_APP-ROUTE-TABLE {
    description
      "Common node of global-af, vrf-global-af";
    container application-routes {
      description
        "Redistribute information for Application routes.";
      list application-route {
        // NCS patched for predictable order
        ordered-by user;
        key "instance-name";
        description
          "Redistribute application routes";
        leaf instance-name {
          type string;
          description
            "OnePK application name";
        }
        leaf default-metric {
          type string;
          description
            "Default metric";
        }
        leaf route-policy-name {
          type string;
          description
            "Route policy name";
        }
        leaf not-used {
          type string;
          description
            "Not used";
        }
      }
    }
  }

  grouping ncs_template_DEFAULT-INFO-ORIGINATE {
    description
      "Common node of global, vrf-global";
    leaf default-info-originate {
      type empty;
      description
        "Control distribution of default information";
    }
  }

  grouping ncs_template_ENFORCE-FIRST-AS {
    description
      "Common node of neighbor-group, neighbor,
       vrf-neighbor, session-group";
    leaf enforce-first-as {
      type string;
      description
        "TRUE to enforce first AS; FALSE to not enforce
         first AS.";
    }
  }

  grouping ncs_template_SOFT-RECONFIGURATION {
    description
      "Common node of neighbor-group-af, neighbor-af,
       vrf-neighbor-af, af-group-af";
    container soft-reconfiguration {
      description
        "Enable/disable inbound soft reconfiguration for
         this neighbor/neighbor-group/af-group";
      leaf inbound-soft {
        type string;
        // NCS drop default statement
        description
          "FALSE to prohibit inbound soft reconfiguration.
           TRUE otherwise.";
      }
      leaf soft-always {
        type string;
        // NCS drop default statement
        description
          "TRUE to always use soft reconfig, even if route
           refresh is supported.  FALSE otherwise.";
      }
    }
  }

  grouping ncs_template_NEIGHBOR-GRACEFUL-RESTART {
    description
      "Common node of neighbor-group, neighbor,
       vrf-neighbor, session-group";
    leaf neighbor-graceful-restart {
      type string;
      description
        "TRUE to Enable graceful restart supportfor
         neighbor.  FALSE to disable graceful restart
         support for neighbor.";
    }
  }

  grouping ncs_template_ADVERTISE-DEF-IMP-DISABLE-V4 {
    description
      "Common node of neighbor-group-af, neighbor-af,
       vrf-neighbor-af, af-group-af";
    container advertise-def-imp-disable-v4 {
      description
        "Disable Advertise Of Default VRF Imported Routes";
      leaf af-name {
        type string;
        description
          "Address family";
      }
      leaf adv-option {
        type string;
        description
          "Advertise option";
      }
      leaf rt-type {
        type string;
        description
          "RT type";
      }
    }
  }

  grouping ncs_template_ADVERTISE-DEF-IMP-DISABLE-V6 {
    description
      "Common node of neighbor-group-af, neighbor-af,
       vrf-neighbor-af, af-group-af";
    container advertise-def-imp-disable-v6 {
      description
        "Disable Advertise Of Default VRF Imported Routes";
      leaf af-name {
        type string;
        description
          "Address family";
      }
      leaf adv-option {
        type string;
        description
          "Advertise option";
      }
      leaf rt-type {
        type string;
        description
          "RT type";
      }
    }
  }

  grouping ncs_template_LOCAL-ADDRESS {
    description
      "Common node of neighbor-group, neighbor,
       vrf-neighbor, session-group";
    container local-address {
      description
        "Local ip address";
      leaf local-address-disable {
        type string;
        description
          "TRUE to prevent this entity from having a local
           address if the parent has one.FALSE to specify
           local ip address";
      }
      leaf local-ip-address {
        // NCS drop when statement
        type string;
        description
          "Local ip address for neighbor";
      }
    }
  }

  grouping ncs_template_AS-OVERRIDE {
    description
      "Common node of neighbor-group-af, neighbor-af,
       vrf-neighbor-af, af-group-af";
    leaf as-override {
      type string;
      // NCS drop default statement
      description
        "TRUE to override matching AS-number while
         sending update. FALSE to prevent as-override
         from being inherited from the parent";
    }
  }

  grouping ncs_template_IGNORE-CONNECTED-CHECK-EBGP {
    description
      "Common node of neighbor-group-af, neighbor-af,
       vrf-neighbor-af, af-group-afCommon node of
       neighbor-group, neighbor, vrf-neighbor,
       session-group";
    leaf ignore-connected-check-ebgp {
      type string;
      description
        "TRUE to disable the connected nexthop check for
         this peer.FALSE to enable the connected nexthop
         check for this peer.";
    }
  }

  grouping ncs_template_REMOTE-AS-LIST {
    description
      "Common node of neighbor-group, neighbor,
       vrf-neighbor, session-group";
    leaf remote-as-list {
      type string;
      description
        "Remote-as-list group name";
    }
  }

  grouping ncs_template_SEND-MULTICAST-ATTR {
    description
      "Common node of neighbor-group-af, neighbor-af,
       af-group-af";
    leaf send-multicast-attr {
      type string;
      description
        "Config send multicast attribute for this
         neighbor";
    }
  }

  grouping ncs_template_ENCAPSULATION-TYPE {
    description
      "Common node of neighbor-group-af, neighbor-af,
       af-group-afCommon node of neighbor-group-af,
       neighbor-af, vrf-neighbor-af, af-group-af";
    leaf encapsulation-type {
      type string;
      description
        "Encapsulation type for this neighbor";
    }
  }

  grouping ncs_template_LOCAL-ADDRESS-SUB-NET {
    description
      "Common node of neighbor-group, neighbor,
       vrf-neighbor, session-group";
    container local-address-sub-net {
      description
        "Local Address subnet of routing updates";
      leaf local-addresss-subnet {
        type string;
        description
          "local address subnet ip address ";
      }
      leaf prefix-len {
        type string;
        description
          "prefix length";
      }
    }
  }

  grouping ncs_template_ADVERTISE-BRIDGE-DOMAIN-IMP-DISABLE-V4 {
    description
      "Common node of neighbor-group-af, neighbor-af,
       vrf-neighbor-af, af-group-af";
    container advertise-bridge-domain-imp-disable-v4 {
      description
        "Disable Advertise Of VRF EVPN Extranet Imported
         Routes";
      leaf af-name {
        type string;
        // NCS drop must statement
        description
          "Address family";
      }
      leaf adv-option {
        type string;
        // NCS drop must statement
        description
          "Advertise option";
      }
      leaf rt-type {
        type string;
        // NCS drop must statement
        description
          "RT type";
      }
    }
  }

  grouping ncs_template_OPTIMAL-ROUTE-REFLECTOR-GROUP-TABLE {
    description
      "Common node of global-af, vrf-global-af";
    container optimal-route-reflector-groups {
      description
        "Table of multiple ORR groups";
      list optimal-route-reflector-group {
        // NCS patched for predictable order
        ordered-by user;
        key "group-name";
        description
          "Optimal Route Reffelctor group. Each such group
           is equivalent to an IGP area";
        leaf group-name {
          type string;
          description
            "Name of the ORR group";
        }
        leaf primary-root-address {
          type string;
          description
            "Primary Root for the ORR group";
        }
        leaf secondary-root-address {
          type string;
          description
            "Secondary Root for the ORR group";
        }
        leaf tertiary-root-address {
          type string;
          description
            "Tertiary Root for the ORR group";
        }
      }
    }
  }

  grouping ncs_template_ADVERTISE-BRIDGE-DOMAIN-IMP-DISABLE-V6 {
    description
      "Common node of global-af, vrf-global-afCommon
       node of neighbor-group-af, neighbor-af,
       vrf-neighbor-af, af-group-af";
    container advertise-bridge-domain-imp-disable-v6 {
      description
        "Disable Advertise Of VRF EVPN Extranet Imported
         Routes";
      leaf af-name {
        type string;
        // NCS drop must statement
        description
          "Address family";
      }
      leaf adv-option {
        type string;
        // NCS drop must statement
        description
          "Advertise option";
      }
      leaf rt-type {
        type string;
        // NCS drop must statement
        description
          "RT type";
      }
    }
  }

  grouping ncs_template_ADVERTISE-PERMANENT-NETWORK {
    description
      "Common node of neighbor-group-af, neighbor-af,
       vrf-neighbor-af, af-group-af";
    leaf advertise-permanent-network {
      type empty;
      description
        "Advertise Permanent Networks to the peer";
    }
  }

  grouping ncs_template_BEST-PATH-COST-COMMUNITY {
    description
      "Common node of global, vrf-global";
    leaf best-path-cost-community {
      type empty;
      description
        "Change default route selection criteria to
         ignore cost community comparison";
    }
  }

  grouping ncs_template_RPKI-BESTPATH-ORIGIN-AS-ALLOW-INVALID {
    description
      "Common node of neighbor-group-af, neighbor-af,
       vrf-neighbor-af, af-group-af";
    leaf rpki-bestpath-origin-as-allow-invalid {
      type empty;
      description
        "RPKI bestpath origin-AS allow invalid";
    }
  }

  grouping ncs_template_BGP-CFG-RPKI-BESTPATH-ORIGIN-AS-ALLOW-INVALID {
    description
      "Common node of neighbor-group-af, neighbor-af,
       vrf-neighbor-af, af-group-afCommon node of
       neighbor-group, neighbor, vrf-neighbor,
       session-group";
    leaf rpki-bestpath-origin-as-allow-invalid {
      type empty;
      description
        "RPKI bestpath origin-AS allow invalid";
    }
  }

  grouping ncs_template_BGP-CFG-RPKI-BESTPATH-ORIGIN-AS-ALLOW-INVALID-MP {
    description
      "Common node of neighbor-group-af, neighbor-af,
       vrf-neighbor-af, af-group-afCommon node of
       neighbor-group, neighbor, vrf-neighbor,
       session-groupCommon node of global-af,
       vrf-global-af";
    leaf rpki-bestpath-origin-as-allow-invalid {
      type empty;
      description
        "RPKI bestpath origin-AS allow invalid";
    }
  }

  grouping ncs_template_NEIGHBOR-GRACEFUL-RESTART-TIME {
    description
      "Common node of neighbor-group, neighbor,
       vrf-neighbor, session-group";
    leaf neighbor-graceful-restart-time {
      type string;
      units "second";
      // NCS drop default statement
      description
        "Restart time advertised to neighbor";
    }
  }

  grouping ncs_template_TOS {
    description
      "Common node of neighbor-group, neighbor,
       vrf-neighbor, session-group";
    container tos {
      description
        "TOS (Type Of Service)";
      leaf type {
        type string;
        description
          "Set type of service";
      }
      leaf value {
        type string;
        description
          "TOS value to set";
      }
    }
  }

  grouping ncs_template_NEIGHBOR-CLUSTER-ID {
    description
      "Common node of neighbor-group, neighbor,
       vrf-neighbor, session-group";
    container neighbor-cluster-id {
      description
        "Neighbor Cluster-id";
      leaf cluster-id-number {
        type string;
        description
          "Route-Reflector Cluster ID as 32 bit quantity";
      }
      leaf cluster-id-address {
        type string;
        description
          "Route-Reflector Cluster ID in IPV4 address
           format";
      }
    }
  }

  grouping ncs_template_ACTIVATE {
    description
      "Common node of neighbor-af, vrf-neighbor-af,
       neighbor-group-af";
    leaf activate {
      type empty;
      description
        "Activate an address family for this neighbor.
         Deletion of this object causes deletion of all
         the objects under
         NeighborAF/VRFNeighborAF/NeighborGroupAF
         associated with this object.";
    }
  }

  grouping ncs_template_NEXT-HOP-SELF {
    description
      "Common node of neighbor-group-af, neighbor-af,
       vrf-neighbor-af, af-group-af";
    leaf next-hop-self {
      type string;
      description
        "Disable the next hop calculation and  insert
         your own address in the nexthop field of
         advertised routes you learned from the neighbor.";
    }
  }

  grouping ncs_template_ALLOW-AS-IN {
    description
      "Common node of neighbor-group-af, neighbor-af,
       vrf-neighbor-af, af-group-af";
    leaf allow-as-in {
      type string;
      // NCS drop default statement
      description
        "Allow as-path with my AS present in it";
    }
  }

  grouping ncs_template_ADVERTISE-LOCAL-V4 {
    description
      "Common node of neighbor-group-af, neighbor-af,
       vrf-neighbor-af, af-group-af";
    container advertise-local-v4 {
      description
        "Advertise Of Local Routes to the peer with
         different RT";
      leaf af-name {
        type string;
        description
          "Address family";
      }
      leaf reorg-option {
        type string;
        description
          "Reorigination option";
      }
      leaf rt-type {
        type string;
        description
          "RT type";
      }
    }
  }

  grouping ncs_template_ADVERTISE-LOCAL-V6 {
    description
      "Common node of neighbor-group-af, neighbor-af,
       vrf-neighbor-af, af-group-af";
    container advertise-local-v6 {
      description
        "Advertise Of Local Routes to the peer with
         different RT";
      leaf af-name {
        type string;
        description
          "Address family";
      }
      leaf reorg-option {
        type string;
        description
          "Reorigination option";
      }
      leaf rt-type {
        type string;
        description
          "RT type";
      }
    }
  }

  grouping ncs_template_BEST-EXTERNAL {
    description
      "Common node of global-af, vrf-global-af";
    leaf best-external {
      type string;
      description
        "TRUE to enable BE FALSE to disable BE
         inheritance from a parent";
    }
  }

  grouping ncs_template_ATTRIBUTE-DOWNLOAD {
    description
      "Common node of global-af, vrf-global-af";
    leaf attribute-download {
      type empty;
      description
        "Attribute download configuration";
    }
  }

  grouping ncs_template_AO-KEYCHAIN {
    description
      "Common node of neighbor-group, neighbor,
       vrf-neighbor, session-group";
    container ao-keychain {
      description
        "Set or disable AO based authentication";
      leaf ao-keychain-disable {
        type string;
        description
          "TRUE to prevent this entity from having AO
           keychain based authentication even if the
           parent has one.FALSE to enable AO keychain
           based authentication";
      }
      leaf ao-keychain-name {
        // NCS drop when statement
        type string;
        description
          "Name of the AO keychain associated with this
           neighbor";
      }
      leaf ao-include-tcp-options {
        // NCS drop when statement
        type string;
        description
          "Include TCP options header with AO";
      }
      leaf ao-accept-mismatch-connection {
        // NCS drop when statement
        type string;
        description
          "Accept new connections even though AO
           mismatched";
      }
    }
  }

  grouping ncs_template_ADDITIONAL-PATHS-SELECTION {
    description
      "Common node of global-af, vrf-global-af";
    container additional-paths-selection {
      description
        "Configure additional paths selection";
      leaf selection {
        type string;
        description
          "Enable/disable selection ";
      }
      leaf route-policy-name {
        type string;
        description
          "Route policy for selection";
      }
    }
  }

  grouping ncs_template_NEIGHBOR-AF-LONG-LIVED-GRACEFUL-RESTART-CAPABLE {
    description
      "Common node of neighbor-group-af, neighbor-af,
       vrf-neighbor-af, af-group-af";
    leaf neighbor-af-long-lived-graceful-restart-capable {
      type string;
      // NCS drop default statement
      description
        "TRUE to treat neighbor as Long-lived
         Graceful-restart capable. FALSE to rely on
         capability negotiation.";
    }
  }

  grouping ncs_template_BEST-PATH-AS-MULTIPATH-RELAX {
    description
      "Common node of global, vrf-global";
    leaf best-path-as-multipath-relax {
      type empty;
      description
        "Change default multi-route selection criteria to
         relax as-path checking - only require same
         aspath length";
    }
  }

  grouping ncs_template_UNSAFE-EBGP-POLICY {
    description
      "Common node of global, vrf-global";
    leaf unsafe-ebgp-policy {
      type empty;
      description
        "If eBGP neighbor is configured without a
         route-policy,the routes from that neighbor are
         not accepted by default.This knob overrides the
         default behavior. When configured,routes from
         the eBGP neighbors with no policy are accepted.";
    }
  }

  grouping ncs_template_GLOBAL-TIMERS {
    description
      "Common node of global, vrf-global";
    container global-timers {
      description
        "Adjust routing timers.";
      leaf keepalive {
        type string;
        units "second";
        // NCS drop default statement
        description
          "Keepalive interval (seconds)";
      }
      leaf hold-time {
        type string;
        units "second";
        // NCS drop default statement
        description
          "Hold time (seconds).  Specify 0 to disable
           keepalives/hold time";
      }
      leaf min-accept-hold-time {
        type string;
        units "second";
        // NCS drop default statement
        description
          "Minimum acceptable hold time (seconds). Specify
           0 to disable keepalives/hold time";
      }
    }
  }

  grouping ncs_template_NEIGHBOR-GROUP-ADD-MEMBER {
    description
      "Common node of neighbor, vrf-neighbor";
    leaf neighbor-group-add-member {
      type string;
      description
        "Inherit configuration from a neighbor-group";
    }
  }

  grouping ncs_template_MOBILE-ROUTES {
    description
      "Common node of global-af, vrf-global-af";
    container mobile-routes {
      presence "enable mobile-routes";
      description
        "Redistribute mobile routes";
      leaf default-metric {
        type string;
        description
          "Default metric";
      }
      leaf route-policy-name {
        type string;
        description
          "Route policy name";
      }
      leaf not-used {
        type string;
        description
          "Not used";
      }
    }
  }

  grouping ncs_template_LOCAL-PREFERENCE {
    description
      "Common node of global, vrf-global";
    leaf local-preference {
      type string;
      // NCS drop default statement
      description
        "Configure default local preference";
    }
  }

  grouping ncs_template_CREATE {
    description
      "Common node of neighbor-group, session-group";
    leaf create {
      type empty;
      description
        "Create this group. Deletion of this object
         causes deletion of all the objects under
         NeighborGroup/SessionGroup associated with this
         object.";
    }
  }

  grouping ncs_template_EBGP-SEND-DMZ-ENABLE-MODES {
    description
      "Common node of neighbor-group, neighbor,
       vrf-neighbor, session-group";
    leaf ebgp-send-dmz-enable-modes {
      type string;
      description
        "Default mode, Cumulative mode or Disable to
         prevent inheritance from a parent";
    }
  }

  grouping ncs_template_SEND-SOCKET-BUFFER-SIZES {
    description
      "Common node of global, vrf-global";
    container send-socket-buffer-sizes {
      description
        "set socket parameters";
      leaf socket-send-size {
        type string;
        units "byte";
        // NCS drop default statement
        description
          "Send socket buffer size in bytes";
      }
      leaf bgp-send-size {
        type string;
        units "byte";
        // NCS drop default statement
        description
          "BGP Write buffer size in bytes";
      }
    }
  }

  grouping ncs_template_RECEIVE-SOCKET-BUFFER-SIZES {
    description
      "Common node of global, vrf-globalCommon node of
       global, vrf-global";
    container receive-socket-buffer-sizes {
      description
        "Set socket and BGP receive buffer sizes";
      leaf socket-receive-size {
        type string;
        units "byte";
        // NCS drop default statement
        description
          "Receive socket buffer size in bytes";
      }
      leaf bgp-receive-size {
        type string;
        units "byte";
        // NCS drop default statement
        description
          "BGP Read buffer size in bytes";
      }
    }
  }

  grouping ncs_template_BFD-ENABLE-MODES {
    description
      "Common node of neighbor-group, neighbor,
       vrf-neighbor, session-group";
    leaf bfd-enable-modes {
      type string;
      description
        "Strict mode, Default mode or Disable to prevent
         inheritance from a parent";
    }
  }

  grouping ncs_template_RESET-WEIGHT-ON-IMPORT {
    description
      "Common node of global-af, vrf-global-af";
    leaf reset-weight-on-import {
      type string;
      description
        "TRUE to reset weight on import. FALSE to not
         reset and to prevent inheritance from a parent";
    }
  }

  grouping ncs_template_AGGREGATE-ADDRESS-TABLE {
    description
      "Common node of global-af, vrf-global-af";
    container aggregate-addresses {
      description
        "Configure BGP aggregate entries";
      list aggregate-address {
        // NCS patched for predictable order
        ordered-by user;
        key "aggregate-addr aggregate-prefix";
        description
          "Aggregate address configuration";
        leaf aggregate-addr {
          type string;
          description
            "Aggregate in prefix/length format (address
             part)";
        }
        leaf aggregate-prefix {
          type string;
          description
            "Aggregate in prefix/length format (prefix
             part)";
        }
        leaf generate-set-info {
          type string;
          description
            "TRUE to generate AS set path information,
             FALSE otherwise";
        }
        leaf generate-confederation-set-info {
          type string;
          description
            "TRUE to generate AS confederation set path
             information, FALSE otherwise";
        }
        leaf summary-only {
          type string;
          description
            "TRUE to filter more specific routes from
             updates, FALSEotherwise";
        }
        leaf route-policy-name {
          type string;
          description
            "Route policy on which to condition
             advertisement, suppression, and attributes";
        }
      }
    }
  }

  grouping ncs_template_EBGP-MULTIHOP {
    description
      "Common node of neighbor-group, neighbor,
       vrf-neighbor, session-group";
    container ebgp-multihop {
      description
        "Allow EBGP neighbors not on directly connected
         networks";
      leaf max-hop-count {
        type string;
        // NCS drop default statement
        description
          "Maximum hop count";
      }
      leaf mpls-deactivation {
        type string;
        // NCS drop default statement
        description
          "TRUE to not enable MPLS and NULL rewrite.";
      }
    }
  }

  grouping ncs_template_MERGE-SAFI1-AND4-INBOUND-UPDATES {
    description
      "Common node of neighbor-group, neighbor,
       vrf-neighbor, session-group";
    leaf merge-safi1-and4-inbound-updates {
      type string;
      description
        "TRUE to merge updates FALSE to not merge updates
         and to prevent inheritance from a parent";
    }
  }

  grouping ncs_template_NEIGHBOR-GRACEFUL-RESTART-STALEPATH-TIME {
    description
      "Common node of neighbor-group, neighbor,
       vrf-neighbor, session-group";
    leaf neighbor-graceful-restart-stalepath-time {
      type string;
      units "second";
      // NCS drop default statement
      description
        "Maximum time to wait for restart of GR capable
         peer";
    }
  }

  grouping ncs_template_NEXT-HOP-RES-ALLOW-DEFAULT {
    description
      "Common node of neighbor-group, neighbor,
       vrf-neighbor, session-groupCommon node of global,
       vrf-global";
    leaf next-hop-res-allow-default {
      type empty;
      description
        "Enable path resolution for nexthops using
         default route";
    }
  }

  grouping ncs_template_BEST-PATH-AIGP-IGNORE {
    description
      "Common node of global, vrf-global";
    leaf best-path-aigp-ignore {
      type empty;
      description
        "Change default route selection criteria to
         ignore AIGP unless both paths whichare compared
         have AIGP attribute";
    }
  }

  grouping ncs_template_SESSION-GROUP-ADD-MEMBER {
    description
      "Common node of neighbor-group, neighbor,
       vrf-neighbor";
    leaf session-group-add-member {
      type string;
      description
        "Inherit address-family independent config from a
         session-group";
    }
  }

  grouping ncs_template_BFD-MULTIPLIER {
    description
      "Common node of neighbor-group, neighbor,
       vrf-neighbor, session-group";
    leaf bfd-multiplier {
      type string;
      description
        "Detection multiplier for BFD sessions created by
         BGP";
    }
  }

  grouping ncs_template_FLOWSPEC-VALIDATION {
    description
      "Common node of neighbor-group-af, neighbor-af,
       vrf-neighbor-af, af-group-af";
    leaf flowspec-validation {
      type string;
      description
        "Config Flowspec validation for this neighbor";
    }
  }

  grouping ncs_template_TTL-SECURITY {
    description
      "Common node of neighbor-group, neighbor,
       vrf-neighbor, session-group";
    leaf ttl-security {
      type string;
      description
        "TRUE to enable BGP TTL Security.  FALSE to not
         enable it and to prevent inheritance from a
         parent";
    }
  }

  grouping ncs_template_BEST-PATH-MED-ALWAYS {
    description
      "Common node of global, vrf-global";
    leaf best-path-med-always {
      type empty;
      description
        "Change default route selection criteria and
         allow comparing of MED from different neighbors";
    }
  }

  grouping ncs_template_MAX-PEERS {
    description
      "Common node of neighbor-group, neighbor,
       vrf-neighbor, session-group";
    leaf max-peers {
      type string;
      description
        "Set Maximum Peers in Dynamic Range";
    }
  }

  grouping ncs_template_SEND-COMMUNITY-EBGP-GRACEFUL-SHUTDOWN {
    description
      "Common node of neighbor-group-af, neighbor-af,
       vrf-neighbor-af, af-group-af";
    leaf send-community-ebgp-graceful-shutdown {
      type string;
      description
        "TRUE to send communities to the external
         neighbor/neighbor-group/af-group.  FALSE not to
         send and to prevent inheritance from a parent";
    }
  }

  grouping ncs_template_DISABLE-MSG-LOG {
    description
      "Common node of global, vrf-global";
    leaf disable-msg-log {
      type empty;
      description
        "Disable inbound and outbound messagelogging for
         all neighbors under the vrf";
    }
  }

  grouping ncs_template_LOCAL-AS {
    description
      "Common node of neighbor-group, neighbor,
       vrf-neighbor, session-group";
    container local-as {
      description
        "Specify a local-as number";
      leaf as-xx {
        type string;
        // NCS drop must statement
        description
          "xx of AS number xx.yy";
      }
      leaf as-yy {
        type string;
        // NCS drop must statement
        description
          "yy of AS number xx.yy";
      }
      leaf no-prepend {
        type empty;
        // NCS drop must statement
        description
          "Do not prepend Local AS to announcements from
           this neighbor";
      }
      leaf disable {
        type empty;
        // NCS drop must statement
        description
          "Disable Local AS and prevent it from being
           inherited from a parent";
      }
      leaf replace-as {
        type empty;
        // NCS drop must statement
        description
          "Prepend only Local AS to announcements from
           this neighbor";
      }
      leaf dual-as {
        type empty;
        // NCS drop must statement
        description
          "Dual-AS mode";
      }
    }
  }

  grouping ncs_template_LISP-ROUTES {
    description
      "Common node of global-af, vrf-global-af";
    container lisp-routes {
      presence "enable lisp-routes";
      description
        "Redistribute lisp routes";
      leaf default-metric {
        type string;
        description
          "Default metric";
      }
      leaf route-policy-name {
        type string;
        description
          "Route policy name";
      }
    }
  }

  grouping ncs_template_ADDITIONAL-PATHS-SEND-CAPABILITY {
    description
      "Common node of neighbor-group, neighbor,
       vrf-neighbor, session-group";
    leaf additional-paths-send-capability {
      type string;
      description
        "Advertise additional paths Send capability";
    }
  }

  grouping ncs_template_BEST-PATH-IGP-METRIC-IGNORE {
    description
      "Common node of global, vrf-global";
    leaf best-path-igp-metric-ignore {
      type empty;
      description
        "Change default route selection criteria to
         ignore IGP Metric ";
    }
  }

  grouping ncs_template_L2VPN-SIGNALLING {
    description
      "Common node of neighbor-group-af, neighbor-af,
       af-group-af";
    leaf l2vpn-signalling {
      type string;
      description
        "Disable signalling type on the peer";
    }
  }

  grouping ncs_template_DAMPENING {
    description
      "Common node of global-af, vrf-global-af";
    container dampening {
      presence "enable dampening";
      description
        "Enable route-flap dampening";
      leaf half-life {
        type string;
        units "minute";
        description
          "Half-life time for the penalty (minutes).";
      }
      leaf reuse-threshold {
        type string;
        description
          "Value to start reusing a route.";
      }
      leaf suppress-threshold {
        type string;
        description
          "Value to start suppressing a route.";
      }
      leaf suppress-time {
        type string;
        units "second";
        description
          "Maximum duration to suppress a stable route
           (seconds).";
      }
      leaf route-policy-name {
        type string;
        description
          "Route policy to specify criteria for dampening.
           This cannot be specified if any other
           parameters are specified.";
      }
    }
  }

  grouping ncs_template_ADVERTISE-LOCAL-LABELED-ROUTE-SAFI-UNICAST {
    description
      "Common node of global-af, vrf-global-af";
    leaf advertise-local-labeled-route-safi-unicast {
      type string;
      description
        "Enable/disable advertisement of routes with
         local-label via Unicast SAFI";
    }
  }

  grouping ncs_template_SUBSCRIBER-ROUTES {
    description
      "Common node of global-af, vrf-global-af";
    container subscriber-routes {
      presence "enable subscriber-routes";
      description
        "Redistribute subscriber routes";
      leaf default-metric {
        type string;
        description
          "Default metric";
      }
      leaf route-policy-name {
        type string;
        description
          "Route policy name";
      }
      leaf not-used {
        type string;
        description
          "Not used";
      }
    }
  }

  grouping ncs_template_INTERNAL-VPN-CLIENT-IBGP-CE {
    description
      "Common node of neighbor-group, neighbor,
       vrf-neighbor, session-group";
    leaf internal-vpn-client-ibgp-ce {
      type string;
      description
        "TRUE to preserve the CE path attributes.FALSE to
         override CE path attributes.";
    }
  }

  grouping ncs_template_ACCEPT-ROUTE-LEGACY-RT {
    description
      "Common node of neighbor-group-af, neighbor-af,
       vrf-neighbor-af, af-group-af";
    leaf accept-route-legacy-rt {
      type string;
      description
        "TRUE to configure as a accept-route-legacy-RT.
         FALSE to prevent accept-route-legacy-RT from
         being inherited.";
    }
  }

  grouping ncs_template_PERMANENT-NETWORK {
    description
      "Common node of global-af, vrf-global-af";
    leaf permanent-network {
      type string;
      description
        "Route policy for permanent networks";
    }
  }

  grouping ncs_template_ENABLE {
    description
      "Common node of global-af, vrf-global-af";
    leaf enable {
      type empty;
      description
        "Enable the address family. Deletion of this
         object causes deletion of all the objects under
         GlobalAF/VRFGlobalAF associated with this object
         .";
    }
  }

  grouping ncs_template_EBGP-RECV-DMZ {
    description
      "Common node of neighbor-group, neighbor,
       vrf-neighbor, session-group";
    leaf ebgp-recv-dmz {
      type string;
      description
        "TRUE to receive DMZ link bandwidth from ebgp
         peer. FALSE to not receive from ebgp peer and to
         prevent inheritance from a parent";
    }
  }

  grouping ncs_template_ADVERTISEMENT-INTERVAL {
    description
      "Common node of neighbor-group, neighbor,
       vrf-neighbor, session-group";
    container advertisement-interval {
      presence "Indicates a advertisement-interval node is configured.";
      description
        "Minimum interval between sending BGP routing
         updates";
      leaf minimum-interval {
        type string;
        units "second";
        // NCS drop mandatory statement
        description
          "Minimum advertisement interval time, secs part";
      }
      leaf minimum-interval-msecs {
        type string;
        units "millisecond";
        description
          "Minimum advertisement interval time, msecs part";
      }
    }
  }

  grouping ncs_template_RPKI-ORIGIN-AS-VALIDITY-SIGNAL-IBGP {
    description
      "Common node of global-af, vrf-global-af";
    leaf rpki-origin-as-validity-signal-ibgp {
      type empty;
      description
        "RPKI origin-AS validity signal ibgp";
    }
  }

  grouping ncs_template_BGP-CFG-RPKI-ORIGIN-AS-VALIDITY-SIGNAL-IBGP {
    description
      "Common node of global-af, vrf-global-afCommon
       node of global, vrf-global";
    leaf rpki-origin-as-validity-signal-ibgp {
      type empty;
      description
        "RPKI origin-AS validity signal ibgp";
    }
  }

  grouping ncs_template_IMPORT {
    description
      "Common node of neighbor-group-af, neighbor-af,
       vrf-neighbor-af, af-group-af";
    container import {
      description
        "Import Reorigination options for Routes from the
         peer";
      leaf import-stitching {
        type string;
        description
          "TRUE to Import with Stitching RTs, FALSE to
           Import with normal RTs";
      }
      leaf import-reoriginate {
        type string;
        description
          "TRUE to Reoriginate imported routes, FALSE to
           not Reoriginate imported routes - not supported";
      }
      leaf import-reoriginate-stitching {
        type string;
        description
          "TRUE to Reoriginate imported routes with
           Stitching RTs, FALSE to Reoriginate imported
           routes with normal RTs";
      }
    }
  }

  grouping ncs_template_ACCEPT-OWN {
    description
      "Common node of neighbor-group-af, neighbor-af,
       vrf-neighbor-af, af-group-af";
    leaf accept-own {
      type string;
      description
        "Handle self-originated routes with Accept-Own
         community. Valid for following neighbor
         address-families: VPNv4Unicast, VPNv6Unicast.";
    }
  }

  grouping ncs_template_ADDITIONAL-PATHS-RECEIVE {
    description
      "Common node of global-af, vrf-global-af";
    leaf additional-paths-receive {
      type string;
      description
        "Advertise additional paths Receive capability";
    }
  }

  grouping ncs_template_MPLS-ACTIVATED-INTERFACE-TABLE {
    description
      "Common node of global, vrf-global";
    container mpls-activated-interfaces {
      description
        "Configure list of MPLS activated interfaces";
      list mpls-activated-interface {
        // NCS patched for predictable order
        ordered-by user;
        key "interface-name";
        description
          "Configure a MPLS activated interface";
        leaf interface-name {
          type string;
          description
            "Interface Name";
        }
      }
    }
  }

  grouping ncs_template_MULTIPATH {
    description
      "Common node of neighbor-group-af, neighbor-af,
       vrf-neighbor-af, af-group-af";
    leaf multipath {
      type empty;
      description
        "Allow paths from this neighbor to be eligible
         for selective multipath";
    }
  }

  grouping ncs_template_EIGRP-ROUTE-TABLE {
    description
      "Common node of global-af, vrf-global-af";
    container eigrp-routes {
      description
        "Redistribute information for EIGRP routes.";
      list eigrp-route {
        // NCS patched for predictable order
        ordered-by user;
        key "instance-name";
        description
          "Redistribute EIGRP routes";
        leaf instance-name {
          type string;
          description
            "EIGRP router tag";
        }
        leaf default-metric {
          type string;
          description
            "Default metric";
        }
        leaf route-policy-name {
          type string;
          description
            "Route policy name";
        }
        leaf redist-type {
          type string;
          description
            "Redistribution type: 01 for internal routes,
             02 for external routes, Logical combinations
             permitted.";
        }
      }
    }
  }

  grouping ncs_template_OPTIMAL-ROUTE-REFLECTION-GROUP {
    description
      "Common node of global-af, vrf-global-afCommon
       node of neighbor-group-af, neighbor-af,
       vrf-neighbor-af, af-group-af";
    leaf optimal-route-reflection-group {
      type string;
      description
        "Name of the ORR group this neighbor is going to
         be part of";
    }
  }

  grouping ncs_template_ROUTE-REFLECTOR-CLIENT {
    description
      "Common node of neighbor-group-af, neighbor-af,
       vrf-neighbor-af, af-group-af";
    leaf route-reflector-client {
      type string;
      description
        "TRUE to configure as a route-reflector-client.
         FALSE to prevent route-reflector-client from
         being inherited.";
    }
  }

  grouping ncs_template_ADVERTISE-LOCAL-LABELED-ROUTE {
    description
      "Common node of neighbor-group-af, neighbor-af,
       vrf-neighbor-af, af-group-af";
    leaf advertise-local-labeled-route {
      type string;
      description
        "Enable/disable advertisement of routes with
         local-label";
    }
  }

  grouping ncs_template_SESSION-OPEN-MODE {
    description
      "Common node of neighbor-group, neighbor,
       vrf-neighbor, session-group";
    leaf session-open-mode {
      type string;
      // NCS drop default statement
      description
        "TCP mode to be used to establish BGP session";
    }
  }

  grouping ncs_template_RPKI-ORIGIN-AS-VALIDATION-ENABLE {
    description
      "Common node of global-af, vrf-global-af";
    leaf rpki-origin-as-validation-enable {
      type empty;
      description
        "RPKI origin-AS validation enable";
    }
  }

  grouping ncs_template_UPDATE-OUT-ORIG-LOOP-CHK-DISABLE {
    description
      "Common node of neighbor-group-af, neighbor-af,
       vrf-neighbor-af, af-group-af";
    leaf update-out-orig-loop-chk-disable {
      type empty;
      description
        "Enable/disable Originator loop check for this
         neighbor-group/af-group";
    }
  }

  grouping ncs_template_STATIC-ROUTES {
    description
      "Common node of global-af, vrf-global-af";
    container static-routes {
      presence "enable static-routes";
      description
        "Redistribute static routes";
      leaf default-metric {
        type string;
        description
          "Default metric";
      }
      leaf route-policy-name {
        type string;
        description
          "Route policy name";
      }
      leaf not-used {
        type string;
        description
          "Not used";
      }
    }
  }

  grouping ncs_template_PASSWORD {
    description
      "Common node of neighbor-group, neighbor,
       vrf-neighbor, session-group";
    container password {
      description
        "Set or disable a password";
      leaf password-disable {
        type string;
        description
          "TRUE to prevent this entity from having a
           password even if the parent has one.  FALSEto
           specify a password";
      }
      leaf password {
        // NCS drop when statement
        type string;
        description
          "The neighbor password.  Leave unspecified when
           disabling the password.";
      }
    }
  }

  grouping ncs_template_NEXT-HOP-UNCHANGED-MULTIPATH {
    description
      "Common node of neighbor-group, neighbor,
       vrf-neighbor, session-groupCommon node of
       neighbor-group-af, neighbor-af, vrf-neighbor-af,
       af-group-af";
    leaf next-hop-unchanged-multipath {
      type string;
      description
        "TRUE to disable overwriting of next hop for
         multipaths. FALSE to prevent next-hop-unchanged
         for multipaths.";
    }
  }

  grouping ncs_template_NEXT-HOP-RESOLUTION-PREFIX-LENGTH-MINIMUM {
    description
      "Common node of global-af, vrf-global-af";
    leaf next-hop-resolution-prefix-length-minimum {
      type string;
      // NCS drop default statement
      description
        "Minimum prefix-length for nexthop resolution";
    }
  }

  grouping ncs_template_BEST-PATH-AS-PATH-LENGTH {
    description
      "Common node of global, vrf-global";
    leaf best-path-as-path-length {
      type empty;
      description
        "Change default route selection criteria to
         ignore AS path length";
    }
  }

  grouping ncs_template_MSG-LOG-OUT {
    description
      "Common node of global, vrf-globalCommon node of
       neighbor-group, neighbor, vrf-neighbor,
       session-group";
    container msg-log-out {
      description
        "Message log outbound";
      leaf msg-buf-count {
        type string;
        description
          "Outbound message log buffer size";
      }
      leaf msg-log-disable {
        type string;
        description
          "Disable inbound message logging";
      }
      leaf msg-log-inherit-disable {
        type string;
        description
          "TRUE, to prevent this entity from having a
           outbound message logging if parent has one";
      }
    }
  }

  grouping ncs_template_ENFORCE-MULTIPLE-LABELS {
    description
      "Common node of neighbor-group-af, neighbor-af,
       vrf-neighbor-af, af-group-af";
    leaf enforce-multiple-labels {
      type string;
      description
        "TRUE to enforce multiple labels support.";
    }
  }

  grouping ncs_template_PREFIX-ORF-POLICY {
    description
      "Common node of neighbor-group-af, neighbor-af,
       vrf-neighbor-af, af-group-afCommon node of
       neighbor-group-af, neighbor-af, vrf-neighbor-af,
       af-group-af";
    leaf prefix-orf-policy {
      type string;
      description
        "Prefix ORF policy name for incoming updates";
    }
  }

  grouping ncs_template_SOURCED-NETWORK-TABLE {
    description
      "Common node of global-af, vrf-global-af";
    container sourced-networks {
      description
        "Specify a network to announce via BGP";
      list sourced-network {
        // NCS patched for predictable order
        ordered-by user;
        key "network-addr network-prefix";
        description
          "Sourced network configuration";
        leaf network-addr {
          type string;
          description
            "Network in prefix/length format (address part)";
        }
        leaf network-prefix {
          type string;
          description
            "Network in prefix/length format (prefix part)";
        }
        leaf backdoor {
          type string;
          description
            "Specify a BGP backdoor route, default is FALSE";
        }
        leaf route-policy-name {
          type string;
          description
            "Route policy name";
        }
      }
    }
  }

  grouping ncs_template_REMOVE-PRIVATE-AS-ENTIRE-AS-PATH {
    description
      "Common node of neighbor-group-af, neighbor-af,
       vrf-neighbor-af, af-group-af";
    container remove-private-as-entire-as-path {
      presence "Indicates a remove-private-as-entire-as-path node is configured.";
      description
        "Remove private AS number from outbound updates";
      leaf enable {
        type string;
        // NCS drop mandatory statement
        description
          "TRUE to remove private AS from outbound updates
           .  FALSE to prevent remove-private-AS from
           being inherited.";
      }
      leaf entire {
        type string;
        description
          "TRUE to remove private AS from outbound updates
           if all ASes in aspath areprivate. FALSE to
           prevent remove-private-ASfrom being inherited.";
      }
    }
  }

  grouping ncs_template_GRACEFUL-MAINTENANCE {
    description
      "Common node of neighbor-group, neighbor,
       vrf-neighbor, session-group";
    container graceful-maintenance {
      description
        "Graceful Maintenance mode";
      container graceful-maintenance-local-preference {
        description
          "Set Local Preference to advertise routes with";
        leaf gshut-loc-pref-disable {
          type string;
          description
            "TRUE, to prevent inheritance of Local Pref
             value from its parents.FALSE, otherwise";
        }
        leaf local-preference {
          type string;
          description
            "Local Preference Value";
        }
      }
      container graceful-maintenance-as-prepends {
        description
          "Number of times to prepend local AS number to
           the AS path";
        leaf gshut-prepends-disable {
          type string;
          description
            "TRUE, to prevent inheritance of AS Prepends
             value from its parents.FALSE, otherwise";
        }
        leaf as-prepends {
          type string;
          description
            "number of times AS prepends";
        }
      }
      leaf enable {
        type empty;
        description
          "Enter Graceful Maintenance mode to configure
           parametrs";
      }
      leaf graceful-maintenance-activate {
        type string;
        description
          "Initiate the graceful shutdown procedure";
      }
    }
  }

  grouping ncs_template_NEIGHBOR-AF-LONG-LIVED-GRACEFUL-RESTART-STALE-TIME {
    description
      "Common node of neighbor-group-af, neighbor-af,
       vrf-neighbor-af, af-group-af";
    container neighbor-af-long-lived-graceful-restart-stale-time {
      description
        "Maximum time to wait before purging long lived
         routes";
      leaf stale-time-send {
        type string;
        units "second";
        // NCS drop default statement
        description
          "Max time (seconds)";
      }
      leaf stale-time-accept {
        type string;
        units "second";
        // NCS drop default statement
        description
          "Max time (seconds)";
      }
    }
  }

  grouping ncs_template_BFD {
    description
      "Common node of global, vrf-global";
    container bfd {
      description
        "BFD configuration";
      leaf detection-multiplier {
        type string;
        description
          "Detection multiplier for BFD sessions created
           by BGP";
      }
      leaf interval {
        type string;
        units "millisecond";
        description
          "Hello interval for BFD sessions created by BGP";
      }
    }
  }

  grouping ncs_template_ALLOCATE-LABEL {
    description
      "Common node of global-af, vrf-global-af";
    container allocate-label {
      presence "enable allocate-label";
      description
        "Label allocation policy";
      leaf all {
        type string;
        description
          "Whether all nets should be labeled, default is
           FALSE";
      }
      leaf route-policy-name {
        type string;
        description
          "Route policy name";
      }
      leaf un-labeled-path {
        type string;
        // NCS drop must statement
        description
          "Allocate label for unlabeled paths too";
      }
    }
  }

  grouping ncs_template_SEND-BUFFER-SIZE {
    description
      "Common node of neighbor-group, neighbor,
       vrf-neighbor, session-group";
    container send-buffer-size {
      description
        "Set socket send buffer size and BGP write buffer
         size";
      leaf socket-send-size {
        type string;
        units "byte";
        // NCS drop default statement
        description
          "Send socket buffer size in bytes";
      }
      leaf bgp-send-size {
        type string;
        units "byte";
        // NCS drop default statement
        description
          "BGP write buffer size in bytes";
      }
    }
  }

  grouping ncs_template_BEST-PATH-MED-MISSING {
    description
      "Common node of neighbor-group, neighbor,
       vrf-neighbor, session-groupCommon node of global,
       vrf-global";
    leaf best-path-med-missing {
      type empty;
      description
        "Treat missing MED as the least preferred one";
    }
  }

  grouping ncs_template_SUPPRESS-ALL-CAPABILITIES {
    description
      "Common node of neighbor-group, neighbor,
       vrf-neighbor, session-group";
    leaf suppress-all-capabilities {
      type string;
      description
        "TRUE to suppress all capabilities. FALSE to not
         suppress and to prevent inheritance from a
         parent";
    }
  }

  grouping ncs_template_DEFAULT-WEIGHT {
    description
      "Common node of neighbor-group, neighbor,
       vrf-neighbor, session-groupCommon node of
       neighbor-group-af, neighbor-af, vrf-neighbor-af,
       af-group-af";
    leaf default-weight {
      type string;
      description
        "Set default weight for routes from this
         neighbor/neighbor-group/af-group";
    }
  }

  grouping ncs_template_SUPPRESS-FOUR-BYTE-AS-CAPABILITY {
    description
      "Common node of neighbor-group, neighbor,
       vrf-neighbor, session-group";
    leaf suppress-four-byte-as-capability {
      type string;
      description
        "TRUE to suppress BGP 4-byte-as capability.
         FALSE to not suppress it and to prevent
         inheritance from a parent";
    }
  }

  grouping ncs_template_ADVERTISE-LOCAL-L2VPN-EVPN {
    description
      "Common node of neighbor-group-af, neighbor-af,
       vrf-neighbor-af, af-group-af";
    container advertise-local-l2vpn-evpn {
      description
        "Advertise Of Local Routes to the peer with
         different RT";
      leaf af-name {
        type string;
        description
          "Address family";
      }
      leaf reorg-option {
        type string;
        description
          "Reorigination option";
      }
      leaf rt-type {
        type string;
        description
          "RT type";
      }
    }
  }

  grouping ncs_template_EGRESS-PEER-ENGINEERING {
    description
      "Common node of neighbor-group, neighbor,
       vrf-neighbor, session-group";
    leaf egress-peer-engineering {
      type string;
      description
        "TRUE to enable egress peer engineering FALSE to
         disable egress peer engineering and to prevent
         inheritance from a parent";
    }
  }

  grouping ncs_template_BEST-PATH-CONFEDERATION-PATHS {
    description
      "Common node of global, vrf-global";
    leaf best-path-confederation-paths {
      type empty;
      description
        "Change default route selection criteria and
         allow the comparing of MED among confederation
         paths";
    }
  }

  grouping ncs_template_DYNAMIC-MED-INTERVAL {
    description
      "Common node of global-af, vrf-global-af";
    leaf dynamic-med-interval {
      type string;
      units "minute";
      // NCS drop default statement
      description
        "Update generation delay (in minutes) after a MED
         change";
    }
  }

  grouping ncs_template_REMOVE-PRIVATE-AS-ENTIRE-AS-PATH-INBOUND {
    description
      "Common node of neighbor-group-af, neighbor-af,
       vrf-neighbor-af, af-group-af";
    container remove-private-as-entire-as-path-inbound {
      presence "Indicates a remove-private-as-entire-as-path-inbound node is configured.";
      description
        "Remove private AS number from inbound updates";
      leaf enable {
        type string;
        // NCS drop mandatory statement
        description
          "TRUE to remove private AS from inbound updates.
           FALSE to prevent remove-private-AS from being
           inherited.";
      }
      leaf entire {
        type string;
        description
          "TRUE to remove private AS from inbound updates
           if all ASes in aspath areprivate. FALSE to
           prevent remove-private-ASfrom being inherited.";
      }
    }
  }

  grouping ncs_template_RPKI-BESTPATH-USE-ORIGIN-AS-VALIDITY {
    description
      "Common node of global-af, vrf-global-af";
    leaf rpki-bestpath-use-origin-as-validity {
      type empty;
      description
        "RPKI bestpath use origin-AS validity";
    }
  }

  grouping ncs_template_BGP-CFG-RPKI-BESTPATH-USE-ORIGIN-AS-VALIDITY {
    description
      "Common node of global-af, vrf-global-afCommon
       node of global, vrf-global";
    leaf rpki-bestpath-use-origin-as-validity {
      type empty;
      description
        "RPKI bestpath use origin-AS validity";
    }
  }

  grouping ncs_template_CONNECTED-ROUTES {
    description
      "Common node of global-af, vrf-global-af";
    container connected-routes {
      presence "enable connected-routes";
      description
        "Redistribute connected routes";
      leaf default-metric {
        type string;
        description
          "Default metric";
      }
      leaf route-policy-name {
        type string;
        description
          "Route policy name";
      }
      leaf not-used {
        type string;
        description
          "Not used";
      }
    }
  }

  grouping ncs_template_IGP-REDIST-INTERNAL {
    description
      "Common node of global, vrf-global";
    leaf igp-redist-internal {
      type empty;
      description
        "Allow redistribution of iBGP into IGPs
         (dangerous)";
    }
  }

  grouping ncs_template_AIGP-SEND-MED {
    description
      "Common node of neighbor-group-af, neighbor-af,
       vrf-neighbor-af, af-group-af";
    leaf aigp-send-med {
      type string;
      description
        "Enable/Disable sending AIGP in MED ";
    }
  }

  grouping ncs_template_AIGP {
    description
      "Common node of neighbor-group-af, neighbor-af,
       vrf-neighbor-af, af-group-af";
    leaf aigp {
      type string;
      description
        "Enable Accumulated IGP Metric for this neighbor.";
    }
  }

  grouping ncs_template_ADVERTISE-ORF {
    description
      "Common node of neighbor-group-af, neighbor-af,
       vrf-neighbor-af, af-group-af";
    leaf advertise-orf {
      type string;
      // NCS drop default statement
      description
        "Advertise ORF capability to the peer";
    }
  }

  grouping ncs_template_BFD-MINIMUM-INTERVAL {
    description
      "Common node of neighbor-group, neighbor,
       vrf-neighbor, session-group";
    leaf bfd-minimum-interval {
      type string;
      units "millisecond";
      description
        "Hello interval for BFD sessions created by BGP";
    }
  }

  grouping ncs_template_AIGP-COST-COMMUNITY {
    description
      "Common node of neighbor-group-af, neighbor-af,
       vrf-neighbor-af, af-group-af";
    container aigp-cost-community {
      description
        "Send AIGP value in Cost Community. ";
      leaf enable {
        type string;
        description
          "TRUE to enable sending cost community, FALSE
           otherwise ";
      }
      leaf cost-community-id {
        // NCS drop when statement
        type string;
        description
          "Cost Community ID";
      }
      leaf transitive {
        // NCS drop when statement
        type string;
        description
          "True to send transitive cost community FALSE
           otherwise";
      }
      leaf cost-community-poi-type {
        // NCS drop when statement
        type string;
        description
          "Cost Community POI";
      }
    }
  }

  grouping ncs_template_DISABLE-AS-PATH-LOOP-CHECK {
    description
      "Common node of global-af, vrf-global-af";
    leaf disable-as-path-loop-check {
      type empty;
      description
        "Disable outbound AS Path loop check";
    }
  }

  grouping ncs_template_BEST-PATH-ROUTER-ID {
    description
      "Common node of global, vrf-global";
    leaf best-path-router-id {
      type empty;
      description
        "Change default route selection criteria and
         compare router-id for identical EBGP paths";
    }
  }

  grouping ncs_template_RIP-ROUTES {
    description
      "Common node of global-af, vrf-global-af";
    container rip-routes {
      presence "enable rip-routes";
      description
        "Redistribute RIP routes";
      leaf default-metric {
        type string;
        description
          "Default metric";
      }
      leaf route-policy-name {
        type string;
        description
          "Route policy name";
      }
      leaf not-used {
        type string;
        description
          "Not used";
      }
    }
  }

  grouping ncs_template_DESCRIPTION {
    description
      "Common node of neighbor-group, neighbor,
       vrf-neighbor, session-group";
    leaf description {
      type string;
      description
        "Up to 80 characters describing this neighbor";
    }
  }

  grouping ncs_template_ADVERTISE-L2VPN-EVPN {
    description
      "Common node of neighbor-group-af, neighbor-af,
       vrf-neighbor-af, af-group-af";
    container advertise-l2vpn-evpn {
      description
        "Advertise Translated Routes to the peer";
      leaf af-name {
        type string;
        description
          "Address family";
      }
      leaf reorg-option {
        type string;
        description
          "Reorigination option";
      }
      leaf rt-type {
        type string;
        description
          "RT type";
      }
    }
  }

  grouping ncs_template_KEYCHAIN {
    description
      "Common node of neighbor-group, neighbor,
       vrf-neighbor, session-group";
    container keychain {
      description
        "Set or disable keychain based authentication";
      leaf keychain-disable {
        type string;
        description
          "TRUE to prevent this entity from having a
           keychain based authentication even if the
           parent has one.FALSE to specify a keychain name";
      }
      leaf keychain-name {
        // NCS drop when statement
        type string;
        description
          "Name of the keychain associated with neighbor";
      }
    }
  }

  grouping ncs_template_RECEIVE-BUFFER-SIZE {
    description
      "Common node of neighbor-group, neighbor,
       vrf-neighbor, session-group";
    container receive-buffer-size {
      description
        "Set socket receive buffer size and BGP read
         buffer size";
      leaf socket-receive-size {
        type string;
        units "byte";
        // NCS drop default statement
        description
          "Receive socket buffer size in bytes";
      }
      leaf bgp-receive-size {
        type string;
        units "byte";
        // NCS drop default statement
        description
          "BGP read buffer size in bytes";
      }
    }
  }

  grouping ncs_template_NEXT-HOP-UNCHANGED {
    description
      "Common node of neighbor-group-af, neighbor-af,
       vrf-neighbor-af, af-group-af";
    leaf next-hop-unchanged {
      type string;
      description
        "TRUE to disable overwriting of next hop before
         advertising to eBGP peers. FALSE to prevent
         next-hop-unchanged from being inherited.";
    }
  }

  grouping ncs_template_OSPF-ROUTE-TABLE {
    description
      "Common node of global-af, vrf-global-af";
    container ospf-routes {
      description
        "Redistribute information for OSPF routes.";
      list ospf-route {
        // NCS patched for predictable order
        ordered-by user;
        key "instance-name";
        description
          "Redistribute OSPF routes";
        leaf instance-name {
          type string;
          description
            "OSPF router tag";
        }
        leaf default-metric {
          type string;
          description
            "Default metric";
        }
        leaf route-policy-name {
          type string;
          description
            "Route policy name";
        }
        leaf redist-type {
          type string;
          description
            "Redistribution type: 01 for internal routes,
             02 for external routes of type 1, 04 for
             external routes of type 2, 08 for NSSA
             external routes of type 1, 10 for NSSA
             external routes of type 2, 20 for external
             routes, 40 for NSSA external routes.  Logical
             combinations permitted.";
        }
      }
    }
  }

  grouping ncs_template_ROUTER-ID {
    description
      "Common node of global, vrf-global";
    leaf router-id {
      type string;
      // NCS drop default statement
      description
        "Configure Router-id";
    }
  }

  grouping ncs_template_DEFAULT-METRIC {
    description
      "Common node of global, vrf-global";
    leaf default-metric {
      type string;
      description
        "Default redistributed metric";
    }
  }

  grouping ncs_template_RPKI-ORIGIN-AS-VALIDATION-DISABLE {
    description
      "Common node of neighbor-group-af, neighbor-af,
       vrf-neighbor-af, af-group-af";
    leaf rpki-origin-as-validation-disable {
      type empty;
      description
        "RPKI origin-AS validation disable";
    }
  }

  grouping ncs_template_BGP-CFG-RPKI-ORIGIN-AS-VALIDATION-DISABLE {
    description
      "Common node of neighbor-group-af, neighbor-af,
       vrf-neighbor-af, af-group-afCommon node of
       neighbor-group, neighbor, vrf-neighbor,
       session-group";
    leaf rpki-origin-as-validation-disable {
      type empty;
      description
        "RPKI origin-AS validation disable";
    }
  }

  grouping ncs_template_DISABLE-NEIGHBOR-LOGGING {
    description
      "Common node of global, vrf-global";
    leaf disable-neighbor-logging {
      type empty;
      description
        "Disable neighbor change logging";
    }
  }

  grouping ncs_template_TCPMSS {
    description
      "Common node of neighbor-group, neighbor,
       vrf-neighbor, session-group";
    container tcpmss {
      description
        "TCP Maximum segment size";
      leaf tcpmss-disable {
        type string;
        description
          "TRUE, to prevent inheritance ofTCP MSS
           valuefrom its parents.FALSE, otherwise";
      }
      leaf mss {
        type string;
        description
          "Maximum Segment Size";
      }
    }
  }

  grouping ncs_rpc_notif_ADVERTISE-DISABLE {
    description
      "Common node of neighbor-group-af, neighbor-af,
       vrf-neighbor-af, af-group-af";
    container advertise-disable {
      description
        "Disable Advertise Of Routes to the peer";
      leaf af-name {
        type dt1:Bgp-address-family;
        description
          "Address family";
      }
      leaf reorg-option {
        type Bgp-reorg-opt;
        description
          "Reorigination option";
      }
      leaf rt-type {
        type Bgp-adv-rt;
        description
          "RT type";
      }
    }
  }

  grouping ncs_rpc_notif_TABLE-POLICY {
    description
      "Common node of global-af, vrf-global-af";
    leaf table-policy {
      type string;
      description
        "Configure policy for installation of routes to
         RIB";
    }
  }

  grouping ncs_rpc_notif_MAXIMUM-PREFIXES {
    description
      "Common node of global-af, vrf-global-afCommon
       node of neighbor-group-af, neighbor-af,
       vrf-neighbor-af, af-group-af";
    container maximum-prefixes {
      presence "Indicates a maximum-prefixes node is configured.";
      description
        "Maximum number of prefixes to accept from this
         peer";
      leaf prefix-limit {
        type uint32 {
          range "1..4294967295";
        }
        mandatory true;
        description
          "Maximum prefixes limit";
      }
      leaf warning-percentage {
        type uint32 {
          range "1..100";
        }
        default "75";
        description
          "Threshold value (%) at which to generate a
           warning message.";
      }
      leaf warning-only {
        type boolean;
        default "false";
        description
          "TRUE to only give a warning message when limit
           is exceeded.  FALSE to accept max prefix limit
           only.";
      }
      leaf restart-time {
        type uint32 {
          range "0..65535";
        }
        default "0";
        description
          "Restart interval";
      }
      leaf discard-extra-paths {
        type boolean;
        default "false";
        description
          "Discard extra paths when limit is exceeded";
      }
    }
  }

  grouping ncs_rpc_notif_DISTANCE {
    description
      "Common node of global-af, vrf-global-af";
    container distance {
      presence "Indicates a distance node is configured.";
      description
        "Define an administrative distance";
      leaf external-routes {
        type uint32 {
          range "1..255";
        }
        mandatory true;
        description
          "Distance for routes external to the AS";
      }
      leaf internal-routes {
        type uint32 {
          range "1..255";
        }
        mandatory true;
        description
          "Distance for routes internal to the AS";
      }
      leaf local-routes {
        type uint32 {
          range "1..255";
        }
        mandatory true;
        description
          "Distance for local routes";
      }
    }
  }

  grouping ncs_rpc_notif_UPDATE-SOURCE-INTERFACE {
    description
      "Common node of neighbor-group, neighbor,
       vrf-neighbor, session-group";
    leaf update-source-interface {
      type xr:Interface-name;
      description
        "Select an interface to configure";
    }
  }

  grouping ncs_rpc_notif_MULTI-PATH-AS-PATH-IGNORE-ONWARDS {
    description
      "Common node of global, vrf-global";
    leaf multi-path-as-path-ignore-onwards {
      type empty;
      description
        "Change default multi-route selection criteria to
         ignore everything onwards as-path check";
    }
  }

  grouping ncs_rpc_notif_PROPAGATE-DMZ-LINK-BANDWIDTH {
    description
      "Common node of neighbor-group, neighbor,
       vrf-neighbor, session-group";
    leaf propagate-dmz-link-bandwidth {
      type boolean;
      description
        "TRUE to propagate DMZ link bandwidth.  FALSE to
         not propagate and to prevent inheritance from a
         parent";
    }
  }

  grouping ncs_rpc_notif_DISABLE-AUTO-SOFT-RESET {
    description
      "Common node of global, vrf-global";
    leaf disable-auto-soft-reset {
      type empty;
      description
        "Disable automatic soft peer reset on policy
         reconfiguration";
    }
  }

  grouping ncs_rpc_notif_MSG-LOG-IN {
    description
      "Common node of neighbor-group, neighbor,
       vrf-neighbor, session-group";
    container msg-log-in {
      description
        "Message log inbound";
      leaf msg-buf-count {
        type uint32 {
          range "1..100";
        }
        description
          "Inbound message log buffer size";
      }
      leaf msg-log-disable {
        type boolean;
        description
          "Disable inbound message logging";
      }
      leaf msg-log-inherit-disable {
        type boolean;
        description
          "TRUE, to prevent this entity from having a
           inbound message logging if parent has one";
      }
    }
  }

  grouping ncs_rpc_notif_DISABLE-ENFORCE-FIRST-AS {
    description
      "Common node of global, vrf-global";
    leaf disable-enforce-first-as {
      type empty;
      description
        "Disable enforce the first AS for EBGP routes";
    }
  }

  grouping ncs_rpc_notif_ROUTE-TARGET-TABLE {
    description
      "Common node of import-route-targets,
       export-route-targets";
    container route-targets {
      description
        "Route target table";
      list route-target {
        must 'as-or-four-byte-as or ipv4-address' {
          tailf:xpath-root 3;
          description
            "AS-or-FourByteAS or IPV4Address must be
             present.";
        }
        key "type";
        description
          "Route target";
        leaf type {
          type Bgp-vrf-route-target;
          description
            "Type of RT";
        }
        list as-or-four-byte-as {
          when "../type = 'as' or ../type = 'four-byte-as'" {
            tailf:xpath-root 3;
            description
              "../Type = AS or ../Type = FourByteAS";
          }
          key "as-xx as as-index stitching-rt";
          description
            "as or four byte as";
          leaf as-xx {
            type uint32 {
              range "0";
            }
            description
              "AS number";
          }
          leaf as {
            type uint32 {
              range "1..4294967295";
            }
            description
              "AS number";
          }
          leaf as-index {
            type Route-target-as-index;
            description
              "AS number Index";
          }
          leaf stitching-rt {
            type uint32 {
              range "0..1";
            }
            description
              "Stitching RT";
          }
        }
        list ipv4-address {
          when "../type = 'ipv4-address'" {
            tailf:xpath-root 3;
            description
              "../Type = IPV4Address";
          }
          key "address address-index stitching-rt";
          description
            "ipv4 address";
          leaf address {
            type inet:ipv4-address-no-zone;
            description
              "IP address";
          }
          leaf address-index {
            type Route-target-addr-index;
            description
              "IP address Index";
          }
          leaf stitching-rt {
            type uint32 {
              range "0..1";
            }
            description
              "Stitching RT";
          }
        }
      }
    }
  }

  grouping ncs_rpc_notif_REMOTE-AS {
    description
      "Common node of neighbor-group, neighbor,
       vrf-neighbor, session-group";
    container remote-as {
      description
        "Set remote AS";
      leaf as-xx {
        type dt1:Bgp-as-range;
        description
          "xx of AS number xx.yy";
      }
      leaf as-yy {
        type dt1:Bgp-as-range;
        description
          "yy of AS number xx.yy";
      }
    }
  }

  grouping ncs_rpc_notif_ADDITIONAL-PATHS-SEND {
    description
      "Common node of global-af, vrf-global-af";
    leaf additional-paths-send {
      type dt1:Bgp-af-additional-paths-cfg;
      description
        "Advertise additional paths Send capability";
    }
  }

  grouping ncs_rpc_notif_UPDATE-IN-FILTERING {
    description
      "Common node of neighbor-group, neighbor,
       vrf-neighbor, session-group";
    container update-in-filtering {
      description
        "Inbound update filtering";
      container update-in-filtering-message-buffers {
        presence "Indicates a update-in-filtering-message-buffers node is configured.";
        description
          "Message buffers to store filtered updates";
        leaf number-of-buffers {
          type uint32 {
            range "0..25";
          }
          mandatory true;
          description
            "Number of message buffers";
        }
        leaf non-circular-buffer {
          type boolean;
          mandatory true;
          description
            "TRUE to configure non-circular buffer";
        }
      }
      leaf enable {
        type empty;
        description
          "Configure inbound update filtering";
      }
      leaf update-in-filtering-attribute-filter-group {
        type string;
        description
          "Attribute-filter group name for update
           filtering";
      }
      leaf update-in-filtering-syslog-disable {
        type empty;
        description
          "Disable inbound update filtering syslog
           messages";
      }
    }
  }

  grouping ncs_rpc_notif_SHUTDOWN {
    description
      "Common node of neighbor-group, neighbor,
       vrf-neighbor, session-group";
    leaf shutdown {
      type boolean;
      description
        "TRUE to shutdown this entity, FALSE to prevent
         this entity from being shutdown even if the
         parent is.";
    }
  }

  grouping ncs_rpc_notif_BMP-ACTIVATE-TABLE {
    description
      "Common node of neighbor-group, neighbor,
       vrf-neighbor, session-group";
    container bmp-activates {
      description
        "Enable BMP logging for this neighbor";
      list bmp-activate {
        key "server-id";
        description
          "Enable BMP logging for this particular server";
        leaf server-id {
          type uint32 {
            range "1..8";
          }
          description
            "BMP Server ID";
        }
      }
    }
  }

  grouping ncs_rpc_notif_ADVERTISE-VRF-IMP-DISABLE-V4 {
    description
      "Common node of neighbor-group-af, neighbor-af,
       vrf-neighbor-af, af-group-af";
    container advertise-vrf-imp-disable-v4 {
      description
        "Disable Advertise Of VRF ReImported Routes";
      leaf af-name {
        type dt1:Bgp-address-family;
        description
          "Address family";
      }
      leaf adv-option {
        type Bgp-reorg-opt;
        description
          "Advertise option";
      }
      leaf rt-type {
        type Bgp-adv-rt;
        description
          "RT type";
      }
    }
  }

  grouping ncs_rpc_notif_ADVERTISE-VRF-IMP-DISABLE-V6 {
    description
      "Common node of neighbor-group-af, neighbor-af,
       vrf-neighbor-af, af-group-af";
    container advertise-vrf-imp-disable-v6 {
      description
        "Disable Advertise Of VRF ReImported Routes";
      leaf af-name {
        type dt1:Bgp-address-family;
        description
          "Address family";
      }
      leaf adv-option {
        type Bgp-reorg-opt;
        description
          "Advertise option";
      }
      leaf rt-type {
        type Bgp-adv-rt;
        description
          "RT type";
      }
    }
  }

  grouping ncs_rpc_notif_SITE-OF-ORIGIN {
    description
      "Common node of neighbor-group-af, vrf-neighbor-af
       , af-group-af";
    container site-of-origin {
      description
        "Site-of-Origin extended community associated
         with the neighbor";
      leaf type {
        type Bgp-site-of-origin;
        description
          "Type of Extended community";
      }
      leaf as-xx {
        when "../type = 'as' or ../type = 'four-byte-as'" {
          tailf:xpath-root 3;
          description
            "../Type = AS or ../Type = FourByteAS";
        }
        type dt1:Bgp-as-range;
        description
          "AS number";
      }
      leaf as {
        when "../type = 'as' or ../type = 'four-byte-as'" {
          tailf:xpath-root 3;
          description
            "../Type = AS or ../Type = FourByteAS";
        }
        type dt1:Bgp-as-range;
        description
          "AS number";
      }
      leaf as-index {
        when "../type = 'as' or ../type = 'four-byte-as'" {
          tailf:xpath-root 3;
          description
            "../Type = AS or ../Type = FourByteAS";
        }
        type dt1:Bgp-extcomm-asn-index;
        description
          "AS number Index";
      }
      leaf address {
        when "../type = 'ipv4-address'" {
          tailf:xpath-root 3;
          description
            "../Type = IPV4Address";
        }
        type inet:ipv4-address-no-zone;
        description
          "IP address";
      }
      leaf address-index {
        when "../type = 'ipv4-address'" {
          tailf:xpath-root 3;
          description
            "../Type = IPV4Address";
        }
        type dt1:Bgp-extcomm-v4-addr-index;
        description
          "IP address Index";
      }
    }
  }

  grouping ncs_rpc_notif_ROUTE-POLICY-OUT {
    description
      "Common node of neighbor-group-af, neighbor-af,
       vrf-neighbor-af, af-group-af";
    leaf route-policy-out {
      type string;
      description
        "Route policy name to apply to outbound routes";
    }
  }

  grouping ncs_rpc_notif_SEGMENT-ROUTING {
    description
      "Common node of global-af, vrf-global-af";
    container segment-routing {
      description
        "Segment-routing Configurations";
      container srv6 {
        description
          "SRv6 Configurations";
        leaf enable {
          type empty;
          description
            "Enable SRv6 configuration submode";
        }
        leaf srv6sid-allocation-mode {
          type string;
          description
            "SID allocation mode: per-ce  Set per CE SID
             mode,per-vrf Set per VRF SID mode";
        }
        leaf locator-name {
          type string;
          description
            "Configure Locator name for SID allocation";
        }
      }
    }
  }

  grouping ncs_rpc_notif_ADVERTISE-V4 {
    description
      "Common node of neighbor-group-af, neighbor-af,
       vrf-neighbor-af, af-group-af";
    container advertise-v4 {
      description
        "Advertise Translated Routes to the peer";
      leaf af-name {
        type dt1:Bgp-address-family;
        description
          "Address family";
      }
      leaf reorg-option {
        type Bgp-reorg-opt;
        description
          "Reorigination option";
      }
      leaf rt-type {
        type Bgp-adv-rt;
        description
          "RT type";
      }
    }
  }

  grouping ncs_rpc_notif_ADVERTISE-V6 {
    description
      "Common node of neighbor-group-af, neighbor-af,
       vrf-neighbor-af, af-group-af";
    container advertise-v6 {
      description
        "Advertise Translated Routes to the peer";
      leaf af-name {
        type dt1:Bgp-address-family;
        description
          "Address family";
      }
      leaf reorg-option {
        type Bgp-reorg-opt;
        description
          "Reorigination option";
      }
      leaf rt-type {
        type Bgp-adv-rt;
        description
          "RT type";
      }
    }
  }

  grouping ncs_rpc_notif_DEFAULT-ORIGINATE {
    description
      "Common node of neighbor-group-af, neighbor-af,
       vrf-neighbor-af, af-group-af";
    container default-originate {
      description
        "Originate default route to this neighbor";
      leaf enable {
        type boolean;
        default "false";
        description
          "FALSE to prevent default-originate from, being
           inherited from a parent. TRUE otherwise.";
      }
      leaf route-policy-name {
        type string;
        description
          "Route policy name to specify criteria to
           originate default.";
      }
    }
  }

  grouping ncs_rpc_notif_IDLE-WATCH-TIME {
    description
      "Common node of neighbor-group, neighbor,
       vrf-neighbor, session-group";
    leaf idle-watch-time {
      type uint32 {
        range "30..1800";
      }
      units "second";
      description
        "Time to wait for deleteing IDLE state Dynamic
         peer";
    }
  }

  grouping ncs_rpc_notif_TIMERS {
    description
      "Common node of neighbor-group, neighbor,
       vrf-neighbor, session-group";
    container timers {
      description
        "BGP per neighbor timers.";
      leaf keepalive-interval {
        type uint32 {
          range "0..65535";
        }
        default "60";
        description
          "Keepalive interval";
      }
      leaf hold-time {
        type uint32 {
          range "0..65535";
        }
        default "180";
        description
          "Hold time.  Specify 0 to disable
           keepalives/hold time";
      }
      leaf min-accept-hold-time {
        type uint32 {
          range "0..65535";
        }
        default "3";
        description
          "Minimum acceptable hold time.  Specify 0 to
           disable keepalives/hold time";
      }
    }
  }

  grouping ncs_rpc_notif_NEXT-HOP-MPLS-FWD-IBGP {
    description
      "Common node of global, vrf-global";
    leaf next-hop-mpls-fwd-ibgp {
      type empty;
      description
        "Enable mpls forwarding path for ibgp learnt
         nexthops";
    }
  }

  grouping ncs_rpc_notif_DISABLE-FAST-EXTERNAL-FALLOVER {
    description
      "Common node of global, vrf-global";
    leaf disable-fast-external-fallover {
      type empty;
      description
        "Disable immediate reset session if a link to a
         directly connected external peer goes down";
    }
  }

  grouping ncs_rpc_notif_SEND-COMMUNITY-EBGP {
    description
      "Common node of neighbor-group-af, neighbor-af,
       vrf-neighbor-af, af-group-af";
    leaf send-community-ebgp {
      type boolean;
      description
        "TRUE to send communities to the external
         neighbor/neighbor-group/af-group.  FALSE not to
         send and to prevent inheritance from a parent";
    }
  }

  grouping ncs_rpc_notif_ADDITIONAL-PATHS-RECEIVE-CAPABILITY {
    description
      "Common node of neighbor-group, neighbor,
       vrf-neighbor, session-group";
    leaf additional-paths-receive-capability {
      type dt1:Bgp-nbr-cap-additional-paths-cfg;
      description
        "Advertise additional paths Receive capability";
    }
  }

  grouping ncs_rpc_notif_SEND-EXT-COMMUNITY-EBGP {
    description
      "Common node of neighbor-group-af, neighbor-af,
       vrf-neighbor-af, af-group-af";
    leaf send-ext-community-ebgp {
      type boolean;
      description
        "TRUE to send extended communities to the
         external neighbor/neighbor-group/af-group.
         FALSE not to send and to prevent inheritance
         from a parent";
    }
  }

  grouping ncs_rpc_notif_AF-GROUP {
    description
      "Common node of neighbor-group-af, neighbor-af,
       vrf-neighbor-af";
    leaf af-group {
      type string;
      description
        "Inherit configuration for this address-family
         from an AF-group";
    }
  }

  grouping ncs_rpc_notif_ROUTE-POLICY-IN {
    description
      "Common node of neighbor-group-af, neighbor-af,
       vrf-neighbor-af, af-group-af";
    leaf route-policy-in {
      type string;
      description
        "Route policy name to apply to inbound routes";
    }
  }

  grouping ncs_rpc_notif_LABEL-MODE {
    description
      "Common node of global-af, vrf-global-af";
    container label-mode {
      presence "enable label-mode";
      description
        "BGP 6PE/MPLS-VPN label allocation mode";
      leaf label-allocation-mode {
        type string;
        description
          "Label allocation mode: per-ce  Set per CE label
           mode, per-vrf Set per VRF label mode,
           per-prefix Set per Prefix label mode (for
           MPLS-VPN only)";
      }
      leaf route-policy-name {
        type string;
        description
          "Label mode route policy name";
      }
    }
  }

  grouping ncs_rpc_notif_APP-ROUTE-TABLE {
    description
      "Common node of global-af, vrf-global-af";
    container application-routes {
      description
        "Redistribute information for Application routes.";
      list application-route {
        key "instance-name";
        description
          "Redistribute application routes";
        leaf instance-name {
          type xr:Cisco-ios-xr-string;
          description
            "OnePK application name";
        }
        leaf default-metric {
          type Bgp-default-metric-range;
          description
            "Default metric";
        }
        leaf route-policy-name {
          type string;
          description
            "Route policy name";
        }
        leaf not-used {
          type uint32 {
            range "0..127";
          }
          description
            "Not used";
        }
      }
    }
  }

  grouping ncs_rpc_notif_DEFAULT-INFO-ORIGINATE {
    description
      "Common node of global, vrf-global";
    leaf default-info-originate {
      type empty;
      description
        "Control distribution of default information";
    }
  }

  grouping ncs_rpc_notif_ENFORCE-FIRST-AS {
    description
      "Common node of neighbor-group, neighbor,
       vrf-neighbor, session-group";
    leaf enforce-first-as {
      type boolean;
      description
        "TRUE to enforce first AS; FALSE to not enforce
         first AS.";
    }
  }

  grouping ncs_rpc_notif_SOFT-RECONFIGURATION {
    description
      "Common node of neighbor-group-af, neighbor-af,
       vrf-neighbor-af, af-group-af";
    container soft-reconfiguration {
      description
        "Enable/disable inbound soft reconfiguration for
         this neighbor/neighbor-group/af-group";
      leaf inbound-soft {
        type boolean;
        default "false";
        description
          "FALSE to prohibit inbound soft reconfiguration.
           TRUE otherwise.";
      }
      leaf soft-always {
        type boolean;
        default "false";
        description
          "TRUE to always use soft reconfig, even if route
           refresh is supported.  FALSE otherwise.";
      }
    }
  }

  grouping ncs_rpc_notif_NEIGHBOR-GRACEFUL-RESTART {
    description
      "Common node of neighbor-group, neighbor,
       vrf-neighbor, session-group";
    leaf neighbor-graceful-restart {
      type Bgp-nbrgr;
      description
        "TRUE to Enable graceful restart supportfor
         neighbor.  FALSE to disable graceful restart
         support for neighbor.";
    }
  }

  grouping ncs_rpc_notif_ADVERTISE-DEF-IMP-DISABLE-V4 {
    description
      "Common node of neighbor-group-af, neighbor-af,
       vrf-neighbor-af, af-group-af";
    container advertise-def-imp-disable-v4 {
      description
        "Disable Advertise Of Default VRF Imported Routes";
      leaf af-name {
        type dt1:Bgp-address-family;
        description
          "Address family";
      }
      leaf adv-option {
        type Bgp-reorg-opt;
        description
          "Advertise option";
      }
      leaf rt-type {
        type Bgp-adv-rt;
        description
          "RT type";
      }
    }
  }

  grouping ncs_rpc_notif_ADVERTISE-DEF-IMP-DISABLE-V6 {
    description
      "Common node of neighbor-group-af, neighbor-af,
       vrf-neighbor-af, af-group-af";
    container advertise-def-imp-disable-v6 {
      description
        "Disable Advertise Of Default VRF Imported Routes";
      leaf af-name {
        type dt1:Bgp-address-family;
        description
          "Address family";
      }
      leaf adv-option {
        type Bgp-reorg-opt;
        description
          "Advertise option";
      }
      leaf rt-type {
        type Bgp-adv-rt;
        description
          "RT type";
      }
    }
  }

  grouping ncs_rpc_notif_LOCAL-ADDRESS {
    description
      "Common node of neighbor-group, neighbor,
       vrf-neighbor, session-group";
    container local-address {
      description
        "Local ip address";
      leaf local-address-disable {
        type boolean;
        description
          "TRUE to prevent this entity from having a local
           address if the parent has one.FALSE to specify
           local ip address";
      }
      leaf local-ip-address {
        when "../local-address-disable = 'false'" {
          tailf:xpath-root 3;
          description
            "../LocalAddressDisable = false";
        }
        type inet:ip-address-no-zone;
        description
          "Local ip address for neighbor";
      }
    }
  }

  grouping ncs_rpc_notif_AS-OVERRIDE {
    description
      "Common node of neighbor-group-af, neighbor-af,
       vrf-neighbor-af, af-group-af";
    leaf as-override {
      type boolean;
      default "true";
      description
        "TRUE to override matching AS-number while
         sending update. FALSE to prevent as-override
         from being inherited from the parent";
    }
  }

  grouping ncs_rpc_notif_IGNORE-CONNECTED-CHECK-EBGP {
    description
      "Common node of neighbor-group-af, neighbor-af,
       vrf-neighbor-af, af-group-afCommon node of
       neighbor-group, neighbor, vrf-neighbor,
       session-group";
    leaf ignore-connected-check-ebgp {
      type boolean;
      description
        "TRUE to disable the connected nexthop check for
         this peer.FALSE to enable the connected nexthop
         check for this peer.";
    }
  }

  grouping ncs_rpc_notif_REMOTE-AS-LIST {
    description
      "Common node of neighbor-group, neighbor,
       vrf-neighbor, session-group";
    leaf remote-as-list {
      type string;
      description
        "Remote-as-list group name";
    }
  }

  grouping ncs_rpc_notif_SEND-MULTICAST-ATTR {
    description
      "Common node of neighbor-group-af, neighbor-af,
       af-group-af";
    leaf send-multicast-attr {
      type Bgp-send-mcast-attr-cfg;
      description
        "Config send multicast attribute for this
         neighbor";
    }
  }

  grouping ncs_rpc_notif_ENCAPSULATION-TYPE {
    description
      "Common node of neighbor-group-af, neighbor-af,
       af-group-afCommon node of neighbor-group-af,
       neighbor-af, vrf-neighbor-af, af-group-af";
    leaf encapsulation-type {
      type Bgp-af-encapsulation;
      description
        "Encapsulation type for this neighbor";
    }
  }

  grouping ncs_rpc_notif_LOCAL-ADDRESS-SUB-NET {
    description
      "Common node of neighbor-group, neighbor,
       vrf-neighbor, session-group";
    container local-address-sub-net {
      description
        "Local Address subnet of routing updates";
      leaf local-addresss-subnet {
        type inet:ip-address-no-zone;
        description
          "local address subnet ip address ";
      }
      leaf prefix-len {
        type uint32 {
          range "0..128";
        }
        description
          "prefix length";
      }
    }
  }

  grouping ncs_rpc_notif_ADVERTISE-BRIDGE-DOMAIN-IMP-DISABLE-V4 {
    description
      "Common node of neighbor-group-af, neighbor-af,
       vrf-neighbor-af, af-group-af";
    container advertise-bridge-domain-imp-disable-v4 {
      description
        "Disable Advertise Of VRF EVPN Extranet Imported
         Routes";
      leaf af-name {
        type dt1:Bgp-address-family;
        must '../adv-option and ../rt-type' {
          tailf:xpath-root 3;
        }
        description
          "Address family";
      }
      leaf adv-option {
        type Bgp-reorg-opt;
        must '../af-name and ../rt-type' {
          tailf:xpath-root 3;
        }
        description
          "Advertise option";
      }
      leaf rt-type {
        type Bgp-adv-rt;
        must '../af-name and ../adv-option' {
          tailf:xpath-root 3;
        }
        description
          "RT type";
      }
    }
  }

  grouping ncs_rpc_notif_OPTIMAL-ROUTE-REFLECTOR-GROUP-TABLE {
    description
      "Common node of global-af, vrf-global-af";
    container optimal-route-reflector-groups {
      description
        "Table of multiple ORR groups";
      list optimal-route-reflector-group {
        key "group-name";
        description
          "Optimal Route Reffelctor group. Each such group
           is equivalent to an IGP area";
        leaf group-name {
          type xr:Cisco-ios-xr-string;
          description
            "Name of the ORR group";
        }
        leaf primary-root-address {
          type inet:ip-address-no-zone;
          description
            "Primary Root for the ORR group";
        }
        leaf secondary-root-address {
          type inet:ip-address-no-zone;
          description
            "Secondary Root for the ORR group";
        }
        leaf tertiary-root-address {
          type inet:ip-address-no-zone;
          description
            "Tertiary Root for the ORR group";
        }
      }
    }
  }

  grouping ncs_rpc_notif_ADVERTISE-BRIDGE-DOMAIN-IMP-DISABLE-V6 {
    description
      "Common node of global-af, vrf-global-afCommon
       node of neighbor-group-af, neighbor-af,
       vrf-neighbor-af, af-group-af";
    container advertise-bridge-domain-imp-disable-v6 {
      description
        "Disable Advertise Of VRF EVPN Extranet Imported
         Routes";
      leaf af-name {
        type dt1:Bgp-address-family;
        must '../adv-option and ../rt-type' {
          tailf:xpath-root 3;
        }
        description
          "Address family";
      }
      leaf adv-option {
        type Bgp-reorg-opt;
        must '../af-name and ../rt-type' {
          tailf:xpath-root 3;
        }
        description
          "Advertise option";
      }
      leaf rt-type {
        type Bgp-adv-rt;
        must '../af-name and ../adv-option' {
          tailf:xpath-root 3;
        }
        description
          "RT type";
      }
    }
  }

  grouping ncs_rpc_notif_ADVERTISE-PERMANENT-NETWORK {
    description
      "Common node of neighbor-group-af, neighbor-af,
       vrf-neighbor-af, af-group-af";
    leaf advertise-permanent-network {
      type empty;
      description
        "Advertise Permanent Networks to the peer";
    }
  }

  grouping ncs_rpc_notif_BEST-PATH-COST-COMMUNITY {
    description
      "Common node of global, vrf-global";
    leaf best-path-cost-community {
      type empty;
      description
        "Change default route selection criteria to
         ignore cost community comparison";
    }
  }

  grouping ncs_rpc_notif_RPKI-BESTPATH-ORIGIN-AS-ALLOW-INVALID {
    description
      "Common node of neighbor-group-af, neighbor-af,
       vrf-neighbor-af, af-group-af";
    leaf rpki-bestpath-origin-as-allow-invalid {
      type empty;
      description
        "RPKI bestpath origin-AS allow invalid";
    }
  }

  grouping ncs_rpc_notif_BGP-CFG-RPKI-BESTPATH-ORIGIN-AS-ALLOW-INVALID {
    description
      "Common node of neighbor-group-af, neighbor-af,
       vrf-neighbor-af, af-group-afCommon node of
       neighbor-group, neighbor, vrf-neighbor,
       session-group";
    leaf rpki-bestpath-origin-as-allow-invalid {
      type empty;
      description
        "RPKI bestpath origin-AS allow invalid";
    }
  }

  grouping ncs_rpc_notif_BGP-CFG-RPKI-BESTPATH-ORIGIN-AS-ALLOW-INVALID-MP {
    description
      "Common node of neighbor-group-af, neighbor-af,
       vrf-neighbor-af, af-group-afCommon node of
       neighbor-group, neighbor, vrf-neighbor,
       session-groupCommon node of global-af,
       vrf-global-af";
    leaf rpki-bestpath-origin-as-allow-invalid {
      type empty;
      description
        "RPKI bestpath origin-AS allow invalid";
    }
  }

  grouping ncs_rpc_notif_NEIGHBOR-GRACEFUL-RESTART-TIME {
    description
      "Common node of neighbor-group, neighbor,
       vrf-neighbor, session-group";
    leaf neighbor-graceful-restart-time {
      type uint32 {
        range "1..4095";
      }
      units "second";
      default "120";
      description
        "Restart time advertised to neighbor";
    }
  }

  grouping ncs_rpc_notif_TOS {
    description
      "Common node of neighbor-group, neighbor,
       vrf-neighbor, session-group";
    container tos {
      description
        "TOS (Type Of Service)";
      leaf type {
        type dt1:Bgp-tos;
        description
          "Set type of service";
      }
      leaf value {
        type dt1:Bgp-precedence-dscp;
        description
          "TOS value to set";
      }
    }
  }

  grouping ncs_rpc_notif_NEIGHBOR-CLUSTER-ID {
    description
      "Common node of neighbor-group, neighbor,
       vrf-neighbor, session-group";
    container neighbor-cluster-id {
      description
        "Neighbor Cluster-id";
      leaf cluster-id-number {
        type uint32 {
          range "1..4294967295";
        }
        description
          "Route-Reflector Cluster ID as 32 bit quantity";
      }
      leaf cluster-id-address {
        type inet:ipv4-address-no-zone;
        description
          "Route-Reflector Cluster ID in IPV4 address
           format";
      }
    }
  }

  grouping ncs_rpc_notif_ACTIVATE {
    description
      "Common node of neighbor-af, vrf-neighbor-af,
       neighbor-group-af";
    leaf activate {
      type empty;
      description
        "Activate an address family for this neighbor.
         Deletion of this object causes deletion of all
         the objects under
         NeighborAF/VRFNeighborAF/NeighborGroupAF
         associated with this object.";
    }
  }

  grouping ncs_rpc_notif_NEXT-HOP-SELF {
    description
      "Common node of neighbor-group-af, neighbor-af,
       vrf-neighbor-af, af-group-af";
    leaf next-hop-self {
      type boolean;
      description
        "Disable the next hop calculation and  insert
         your own address in the nexthop field of
         advertised routes you learned from the neighbor.";
    }
  }

  grouping ncs_rpc_notif_ALLOW-AS-IN {
    description
      "Common node of neighbor-group-af, neighbor-af,
       vrf-neighbor-af, af-group-af";
    leaf allow-as-in {
      type uint32 {
        range "1..10";
      }
      default "3";
      description
        "Allow as-path with my AS present in it";
    }
  }

  grouping ncs_rpc_notif_ADVERTISE-LOCAL-V4 {
    description
      "Common node of neighbor-group-af, neighbor-af,
       vrf-neighbor-af, af-group-af";
    container advertise-local-v4 {
      description
        "Advertise Of Local Routes to the peer with
         different RT";
      leaf af-name {
        type dt1:Bgp-address-family;
        description
          "Address family";
      }
      leaf reorg-option {
        type Bgp-reorg-opt;
        description
          "Reorigination option";
      }
      leaf rt-type {
        type Bgp-adv-rt;
        description
          "RT type";
      }
    }
  }

  grouping ncs_rpc_notif_ADVERTISE-LOCAL-V6 {
    description
      "Common node of neighbor-group-af, neighbor-af,
       vrf-neighbor-af, af-group-af";
    container advertise-local-v6 {
      description
        "Advertise Of Local Routes to the peer with
         different RT";
      leaf af-name {
        type dt1:Bgp-address-family;
        description
          "Address family";
      }
      leaf reorg-option {
        type Bgp-reorg-opt;
        description
          "Reorigination option";
      }
      leaf rt-type {
        type Bgp-adv-rt;
        description
          "RT type";
      }
    }
  }

  grouping ncs_rpc_notif_BEST-EXTERNAL {
    description
      "Common node of global-af, vrf-global-af";
    leaf best-external {
      type boolean;
      description
        "TRUE to enable BE FALSE to disable BE
         inheritance from a parent";
    }
  }

  grouping ncs_rpc_notif_ATTRIBUTE-DOWNLOAD {
    description
      "Common node of global-af, vrf-global-af";
    leaf attribute-download {
      type empty;
      description
        "Attribute download configuration";
    }
  }

  grouping ncs_rpc_notif_AO-KEYCHAIN {
    description
      "Common node of neighbor-group, neighbor,
       vrf-neighbor, session-group";
    container ao-keychain {
      description
        "Set or disable AO based authentication";
      leaf ao-keychain-disable {
        type boolean;
        description
          "TRUE to prevent this entity from having AO
           keychain based authentication even if the
           parent has one.FALSE to enable AO keychain
           based authentication";
      }
      leaf ao-keychain-name {
        when "../ao-keychain-disable = 'false'" {
          tailf:xpath-root 3;
          description
            "../AOKeychainDisable = false";
        }
        type string;
        description
          "Name of the AO keychain associated with this
           neighbor";
      }
      leaf ao-include-tcp-options {
        when "../ao-keychain-disable = 'false'" {
          tailf:xpath-root 3;
          description
            "../AOKeychainDisable = false";
        }
        type boolean;
        description
          "Include TCP options header with AO";
      }
      leaf ao-accept-mismatch-connection {
        when "../ao-keychain-disable = 'false'" {
          tailf:xpath-root 3;
          description
            "../AOKeychainDisable = false";
        }
        type boolean;
        description
          "Accept new connections even though AO
           mismatched";
      }
    }
  }

  grouping ncs_rpc_notif_ADDITIONAL-PATHS-SELECTION {
    description
      "Common node of global-af, vrf-global-af";
    container additional-paths-selection {
      description
        "Configure additional paths selection";
      leaf selection {
        type dt1:Bgp-af-additional-paths-cfg;
        description
          "Enable/disable selection ";
      }
      leaf route-policy-name {
        type string;
        description
          "Route policy for selection";
      }
    }
  }

  grouping ncs_rpc_notif_NEIGHBOR-AF-LONG-LIVED-GRACEFUL-RESTART-CAPABLE {
    description
      "Common node of neighbor-group-af, neighbor-af,
       vrf-neighbor-af, af-group-af";
    leaf neighbor-af-long-lived-graceful-restart-capable {
      type boolean;
      default "false";
      description
        "TRUE to treat neighbor as Long-lived
         Graceful-restart capable. FALSE to rely on
         capability negotiation.";
    }
  }

  grouping ncs_rpc_notif_BEST-PATH-AS-MULTIPATH-RELAX {
    description
      "Common node of global, vrf-global";
    leaf best-path-as-multipath-relax {
      type empty;
      description
        "Change default multi-route selection criteria to
         relax as-path checking - only require same
         aspath length";
    }
  }

  grouping ncs_rpc_notif_UNSAFE-EBGP-POLICY {
    description
      "Common node of global, vrf-global";
    leaf unsafe-ebgp-policy {
      type empty;
      description
        "If eBGP neighbor is configured without a
         route-policy,the routes from that neighbor are
         not accepted by default.This knob overrides the
         default behavior. When configured,routes from
         the eBGP neighbors with no policy are accepted.";
    }
  }

  grouping ncs_rpc_notif_GLOBAL-TIMERS {
    description
      "Common node of global, vrf-global";
    container global-timers {
      description
        "Adjust routing timers.";
      leaf keepalive {
        type uint32 {
          range "0..65535";
        }
        units "second";
        default "60";
        description
          "Keepalive interval (seconds)";
      }
      leaf hold-time {
        type uint32 {
          range "0..65535";
        }
        units "second";
        default "180";
        description
          "Hold time (seconds).  Specify 0 to disable
           keepalives/hold time";
      }
      leaf min-accept-hold-time {
        type uint32 {
          range "0..65535";
        }
        units "second";
        default "3";
        description
          "Minimum acceptable hold time (seconds). Specify
           0 to disable keepalives/hold time";
      }
    }
  }

  grouping ncs_rpc_notif_NEIGHBOR-GROUP-ADD-MEMBER {
    description
      "Common node of neighbor, vrf-neighbor";
    leaf neighbor-group-add-member {
      type string;
      description
        "Inherit configuration from a neighbor-group";
    }
  }

  grouping ncs_rpc_notif_MOBILE-ROUTES {
    description
      "Common node of global-af, vrf-global-af";
    container mobile-routes {
      presence "enable mobile-routes";
      description
        "Redistribute mobile routes";
      leaf default-metric {
        type Bgp-default-metric-range;
        description
          "Default metric";
      }
      leaf route-policy-name {
        type string;
        description
          "Route policy name";
      }
      leaf not-used {
        type uint32 {
          range "0..127";
        }
        description
          "Not used";
      }
    }
  }

  grouping ncs_rpc_notif_LOCAL-PREFERENCE {
    description
      "Common node of global, vrf-global";
    leaf local-preference {
      type uint32 {
        range "0..4294967295";
      }
      default "100";
      description
        "Configure default local preference";
    }
  }

  grouping ncs_rpc_notif_CREATE {
    description
      "Common node of neighbor-group, session-group";
    leaf create {
      type empty;
      description
        "Create this group. Deletion of this object
         causes deletion of all the objects under
         NeighborGroup/SessionGroup associated with this
         object.";
    }
  }

  grouping ncs_rpc_notif_EBGP-SEND-DMZ-ENABLE-MODES {
    description
      "Common node of neighbor-group, neighbor,
       vrf-neighbor, session-group";
    leaf ebgp-send-dmz-enable-modes {
      type Bgp-ebgp-send-dmz-enable-mode;
      description
        "Default mode, Cumulative mode or Disable to
         prevent inheritance from a parent";
    }
  }

  grouping ncs_rpc_notif_SEND-SOCKET-BUFFER-SIZES {
    description
      "Common node of global, vrf-global";
    container send-socket-buffer-sizes {
      description
        "set socket parameters";
      leaf socket-send-size {
        type uint32 {
          range "4096..131072";
        }
        units "byte";
        default "24576";
        description
          "Send socket buffer size in bytes";
      }
      leaf bgp-send-size {
        type uint32 {
          range "4096..131072";
        }
        units "byte";
        default "4096";
        description
          "BGP Write buffer size in bytes";
      }
    }
  }

  grouping ncs_rpc_notif_RECEIVE-SOCKET-BUFFER-SIZES {
    description
      "Common node of global, vrf-globalCommon node of
       global, vrf-global";
    container receive-socket-buffer-sizes {
      description
        "Set socket and BGP receive buffer sizes";
      leaf socket-receive-size {
        type uint32 {
          range "512..131072";
        }
        units "byte";
        default "32768";
        description
          "Receive socket buffer size in bytes";
      }
      leaf bgp-receive-size {
        type uint32 {
          range "512..131072";
        }
        units "byte";
        default "4096";
        description
          "BGP Read buffer size in bytes";
      }
    }
  }

  grouping ncs_rpc_notif_BFD-ENABLE-MODES {
    description
      "Common node of neighbor-group, neighbor,
       vrf-neighbor, session-group";
    leaf bfd-enable-modes {
      type Bgp-bfd-enable-mode;
      description
        "Strict mode, Default mode or Disable to prevent
         inheritance from a parent";
    }
  }

  grouping ncs_rpc_notif_RESET-WEIGHT-ON-IMPORT {
    description
      "Common node of global-af, vrf-global-af";
    leaf reset-weight-on-import {
      type boolean;
      description
        "TRUE to reset weight on import. FALSE to not
         reset and to prevent inheritance from a parent";
    }
  }

  grouping ncs_rpc_notif_AGGREGATE-ADDRESS-TABLE {
    description
      "Common node of global-af, vrf-global-af";
    container aggregate-addresses {
      description
        "Configure BGP aggregate entries";
      list aggregate-address {
        key "aggregate-addr aggregate-prefix";
        description
          "Aggregate address configuration";
        leaf aggregate-addr {
          type inet:ip-address;
          description
            "Aggregate in prefix/length format (address
             part)";
        }
        leaf aggregate-prefix {
          type uint16 {
            range "0..128";
          }
          description
            "Aggregate in prefix/length format (prefix
             part)";
        }
        leaf generate-set-info {
          type boolean;
          description
            "TRUE to generate AS set path information,
             FALSE otherwise";
        }
        leaf generate-confederation-set-info {
          type boolean;
          description
            "TRUE to generate AS confederation set path
             information, FALSE otherwise";
        }
        leaf summary-only {
          type boolean;
          description
            "TRUE to filter more specific routes from
             updates, FALSEotherwise";
        }
        leaf route-policy-name {
          type string;
          description
            "Route policy on which to condition
             advertisement, suppression, and attributes";
        }
      }
    }
  }

  grouping ncs_rpc_notif_EBGP-MULTIHOP {
    description
      "Common node of neighbor-group, neighbor,
       vrf-neighbor, session-group";
    container ebgp-multihop {
      description
        "Allow EBGP neighbors not on directly connected
         networks";
      leaf max-hop-count {
        type uint32 {
          range "1..255";
        }
        default "255";
        description
          "Maximum hop count";
      }
      leaf mpls-deactivation {
        type boolean;
        default "false";
        description
          "TRUE to not enable MPLS and NULL rewrite.";
      }
    }
  }

  grouping ncs_rpc_notif_MERGE-SAFI1-AND4-INBOUND-UPDATES {
    description
      "Common node of neighbor-group, neighbor,
       vrf-neighbor, session-group";
    leaf merge-safi1-and4-inbound-updates {
      type boolean;
      description
        "TRUE to merge updates FALSE to not merge updates
         and to prevent inheritance from a parent";
    }
  }

  grouping ncs_rpc_notif_NEIGHBOR-GRACEFUL-RESTART-STALEPATH-TIME {
    description
      "Common node of neighbor-group, neighbor,
       vrf-neighbor, session-group";
    leaf neighbor-graceful-restart-stalepath-time {
      type uint32 {
        range "1..4095";
      }
      units "second";
      default "360";
      description
        "Maximum time to wait for restart of GR capable
         peer";
    }
  }

  grouping ncs_rpc_notif_NEXT-HOP-RES-ALLOW-DEFAULT {
    description
      "Common node of neighbor-group, neighbor,
       vrf-neighbor, session-groupCommon node of global,
       vrf-global";
    leaf next-hop-res-allow-default {
      type empty;
      description
        "Enable path resolution for nexthops using
         default route";
    }
  }

  grouping ncs_rpc_notif_BEST-PATH-AIGP-IGNORE {
    description
      "Common node of global, vrf-global";
    leaf best-path-aigp-ignore {
      type empty;
      description
        "Change default route selection criteria to
         ignore AIGP unless both paths whichare compared
         have AIGP attribute";
    }
  }

  grouping ncs_rpc_notif_SESSION-GROUP-ADD-MEMBER {
    description
      "Common node of neighbor-group, neighbor,
       vrf-neighbor";
    leaf session-group-add-member {
      type string;
      description
        "Inherit address-family independent config from a
         session-group";
    }
  }

  grouping ncs_rpc_notif_BFD-MULTIPLIER {
    description
      "Common node of neighbor-group, neighbor,
       vrf-neighbor, session-group";
    leaf bfd-multiplier {
      type uint32 {
        range "2..16";
      }
      description
        "Detection multiplier for BFD sessions created by
         BGP";
    }
  }

  grouping ncs_rpc_notif_FLOWSPEC-VALIDATION {
    description
      "Common node of neighbor-group-af, neighbor-af,
       vrf-neighbor-af, af-group-af";
    leaf flowspec-validation {
      type Bgp-flowspec-validation-cfg;
      description
        "Config Flowspec validation for this neighbor";
    }
  }

  grouping ncs_rpc_notif_TTL-SECURITY {
    description
      "Common node of neighbor-group, neighbor,
       vrf-neighbor, session-group";
    leaf ttl-security {
      type boolean;
      description
        "TRUE to enable BGP TTL Security.  FALSE to not
         enable it and to prevent inheritance from a
         parent";
    }
  }

  grouping ncs_rpc_notif_BEST-PATH-MED-ALWAYS {
    description
      "Common node of global, vrf-global";
    leaf best-path-med-always {
      type empty;
      description
        "Change default route selection criteria and
         allow comparing of MED from different neighbors";
    }
  }

  grouping ncs_rpc_notif_MAX-PEERS {
    description
      "Common node of neighbor-group, neighbor,
       vrf-neighbor, session-group";
    leaf max-peers {
      type uint32 {
        range "1..4096";
      }
      description
        "Set Maximum Peers in Dynamic Range";
    }
  }

  grouping ncs_rpc_notif_SEND-COMMUNITY-EBGP-GRACEFUL-SHUTDOWN {
    description
      "Common node of neighbor-group-af, neighbor-af,
       vrf-neighbor-af, af-group-af";
    leaf send-community-ebgp-graceful-shutdown {
      type boolean;
      description
        "TRUE to send communities to the external
         neighbor/neighbor-group/af-group.  FALSE not to
         send and to prevent inheritance from a parent";
    }
  }

  grouping ncs_rpc_notif_DISABLE-MSG-LOG {
    description
      "Common node of global, vrf-global";
    leaf disable-msg-log {
      type empty;
      description
        "Disable inbound and outbound messagelogging for
         all neighbors under the vrf";
    }
  }

  grouping ncs_rpc_notif_LOCAL-AS {
    description
      "Common node of neighbor-group, neighbor,
       vrf-neighbor, session-group";
    container local-as {
      description
        "Specify a local-as number";
      leaf as-xx {
        type dt1:Bgp-as-range;
        must '../as-yy and not(../disable)' {
          tailf:xpath-root 3;
        }
        description
          "xx of AS number xx.yy";
      }
      leaf as-yy {
        type dt1:Bgp-as-range;
        must '../as-xx and not(../disable)' {
          tailf:xpath-root 3;
        }
        description
          "yy of AS number xx.yy";
      }
      leaf no-prepend {
        type empty;
        must '../as-xx and ../as-yy and not(../disable)' {
          tailf:xpath-root 3;
        }
        description
          "Do not prepend Local AS to announcements from
           this neighbor";
      }
      leaf disable {
        type empty;
        must 'not(../as-xx or ../as-yy or ../no-prepend or ../replace-as or ../dual-as)' {
          tailf:xpath-root 3;
        }
        description
          "Disable Local AS and prevent it from being
           inherited from a parent";
      }
      leaf replace-as {
        type empty;
        must '../as-xx and ../as-yy and ../no-prepend and not(../disable)' {
          tailf:xpath-root 3;
        }
        description
          "Prepend only Local AS to announcements from
           this neighbor";
      }
      leaf dual-as {
        type empty;
        must '../as-xx and ../as-yy and ../no-prepend and ../replace-as and not(../disable)' {
          tailf:xpath-root 3;
        }
        description
          "Dual-AS mode";
      }
    }
  }

  grouping ncs_rpc_notif_LISP-ROUTES {
    description
      "Common node of global-af, vrf-global-af";
    container lisp-routes {
      presence "enable lisp-routes";
      description
        "Redistribute lisp routes";
      leaf default-metric {
        type Bgp-default-metric-range;
        description
          "Default metric";
      }
      leaf route-policy-name {
        type string;
        description
          "Route policy name";
      }
    }
  }

  grouping ncs_rpc_notif_ADDITIONAL-PATHS-SEND-CAPABILITY {
    description
      "Common node of neighbor-group, neighbor,
       vrf-neighbor, session-group";
    leaf additional-paths-send-capability {
      type dt1:Bgp-nbr-cap-additional-paths-cfg;
      description
        "Advertise additional paths Send capability";
    }
  }

  grouping ncs_rpc_notif_BEST-PATH-IGP-METRIC-IGNORE {
    description
      "Common node of global, vrf-global";
    leaf best-path-igp-metric-ignore {
      type empty;
      description
        "Change default route selection criteria to
         ignore IGP Metric ";
    }
  }

  grouping ncs_rpc_notif_L2VPN-SIGNALLING {
    description
      "Common node of neighbor-group-af, neighbor-af,
       af-group-af";
    leaf l2vpn-signalling {
      type Bgp-signal;
      description
        "Disable signalling type on the peer";
    }
  }

  grouping ncs_rpc_notif_DAMPENING {
    description
      "Common node of global-af, vrf-global-af";
    container dampening {
      presence "enable dampening";
      description
        "Enable route-flap dampening";
      leaf half-life {
        type uint32 {
          range "1..45";
        }
        units "minute";
        description
          "Half-life time for the penalty (minutes).";
      }
      leaf reuse-threshold {
        type uint32 {
          range "1..20000";
        }
        description
          "Value to start reusing a route.";
      }
      leaf suppress-threshold {
        type uint32 {
          range "1..20000";
        }
        description
          "Value to start suppressing a route.";
      }
      leaf suppress-time {
        type uint32 {
          range "1..255";
        }
        units "second";
        description
          "Maximum duration to suppress a stable route
           (seconds).";
      }
      leaf route-policy-name {
        type string;
        description
          "Route policy to specify criteria for dampening.
           This cannot be specified if any other
           parameters are specified.";
      }
    }
  }

  grouping ncs_rpc_notif_ADVERTISE-LOCAL-LABELED-ROUTE-SAFI-UNICAST {
    description
      "Common node of global-af, vrf-global-af";
    leaf advertise-local-labeled-route-safi-unicast {
      type dt1:Bgp-advertise-local-labeled-route-cfg;
      description
        "Enable/disable advertisement of routes with
         local-label via Unicast SAFI";
    }
  }

  grouping ncs_rpc_notif_SUBSCRIBER-ROUTES {
    description
      "Common node of global-af, vrf-global-af";
    container subscriber-routes {
      presence "enable subscriber-routes";
      description
        "Redistribute subscriber routes";
      leaf default-metric {
        type Bgp-default-metric-range;
        description
          "Default metric";
      }
      leaf route-policy-name {
        type string;
        description
          "Route policy name";
      }
      leaf not-used {
        type uint32 {
          range "0..127";
        }
        description
          "Not used";
      }
    }
  }

  grouping ncs_rpc_notif_INTERNAL-VPN-CLIENT-IBGP-CE {
    description
      "Common node of neighbor-group, neighbor,
       vrf-neighbor, session-group";
    leaf internal-vpn-client-ibgp-ce {
      type boolean;
      description
        "TRUE to preserve the CE path attributes.FALSE to
         override CE path attributes.";
    }
  }

  grouping ncs_rpc_notif_ACCEPT-ROUTE-LEGACY-RT {
    description
      "Common node of neighbor-group-af, neighbor-af,
       vrf-neighbor-af, af-group-af";
    leaf accept-route-legacy-rt {
      type boolean;
      description
        "TRUE to configure as a accept-route-legacy-RT.
         FALSE to prevent accept-route-legacy-RT from
         being inherited.";
    }
  }

  grouping ncs_rpc_notif_PERMANENT-NETWORK {
    description
      "Common node of global-af, vrf-global-af";
    leaf permanent-network {
      type string;
      description
        "Route policy for permanent networks";
    }
  }

  grouping ncs_rpc_notif_ENABLE {
    description
      "Common node of global-af, vrf-global-af";
    leaf enable {
      type empty;
      description
        "Enable the address family. Deletion of this
         object causes deletion of all the objects under
         GlobalAF/VRFGlobalAF associated with this object
         .";
    }
  }

  grouping ncs_rpc_notif_EBGP-RECV-DMZ {
    description
      "Common node of neighbor-group, neighbor,
       vrf-neighbor, session-group";
    leaf ebgp-recv-dmz {
      type boolean;
      description
        "TRUE to receive DMZ link bandwidth from ebgp
         peer. FALSE to not receive from ebgp peer and to
         prevent inheritance from a parent";
    }
  }

  grouping ncs_rpc_notif_ADVERTISEMENT-INTERVAL {
    description
      "Common node of neighbor-group, neighbor,
       vrf-neighbor, session-group";
    container advertisement-interval {
      presence "Indicates a advertisement-interval node is configured.";
      description
        "Minimum interval between sending BGP routing
         updates";
      leaf minimum-interval {
        type uint32 {
          range "0..600";
        }
        units "second";
        mandatory true;
        description
          "Minimum advertisement interval time, secs part";
      }
      leaf minimum-interval-msecs {
        type uint32 {
          range "0..999";
        }
        units "millisecond";
        description
          "Minimum advertisement interval time, msecs part";
      }
    }
  }

  grouping ncs_rpc_notif_RPKI-ORIGIN-AS-VALIDITY-SIGNAL-IBGP {
    description
      "Common node of global-af, vrf-global-af";
    leaf rpki-origin-as-validity-signal-ibgp {
      type empty;
      description
        "RPKI origin-AS validity signal ibgp";
    }
  }

  grouping ncs_rpc_notif_BGP-CFG-RPKI-ORIGIN-AS-VALIDITY-SIGNAL-IBGP {
    description
      "Common node of global-af, vrf-global-afCommon
       node of global, vrf-global";
    leaf rpki-origin-as-validity-signal-ibgp {
      type empty;
      description
        "RPKI origin-AS validity signal ibgp";
    }
  }

  grouping ncs_rpc_notif_IMPORT {
    description
      "Common node of neighbor-group-af, neighbor-af,
       vrf-neighbor-af, af-group-af";
    container import {
      description
        "Import Reorigination options for Routes from the
         peer";
      leaf import-stitching {
        type boolean;
        description
          "TRUE to Import with Stitching RTs, FALSE to
           Import with normal RTs";
      }
      leaf import-reoriginate {
        type boolean;
        description
          "TRUE to Reoriginate imported routes, FALSE to
           not Reoriginate imported routes - not supported";
      }
      leaf import-reoriginate-stitching {
        type boolean;
        description
          "TRUE to Reoriginate imported routes with
           Stitching RTs, FALSE to Reoriginate imported
           routes with normal RTs";
      }
    }
  }

  grouping ncs_rpc_notif_ACCEPT-OWN {
    description
      "Common node of neighbor-group-af, neighbor-af,
       vrf-neighbor-af, af-group-af";
    leaf accept-own {
      type boolean;
      description
        "Handle self-originated routes with Accept-Own
         community. Valid for following neighbor
         address-families: VPNv4Unicast, VPNv6Unicast.";
    }
  }

  grouping ncs_rpc_notif_ADDITIONAL-PATHS-RECEIVE {
    description
      "Common node of global-af, vrf-global-af";
    leaf additional-paths-receive {
      type dt1:Bgp-af-additional-paths-cfg;
      description
        "Advertise additional paths Receive capability";
    }
  }

  grouping ncs_rpc_notif_MPLS-ACTIVATED-INTERFACE-TABLE {
    description
      "Common node of global, vrf-global";
    container mpls-activated-interfaces {
      description
        "Configure list of MPLS activated interfaces";
      list mpls-activated-interface {
        key "interface-name";
        description
          "Configure a MPLS activated interface";
        leaf interface-name {
          type xr:Interface-name;
          description
            "Interface Name";
        }
      }
    }
  }

  grouping ncs_rpc_notif_MULTIPATH {
    description
      "Common node of neighbor-group-af, neighbor-af,
       vrf-neighbor-af, af-group-af";
    leaf multipath {
      type empty;
      description
        "Allow paths from this neighbor to be eligible
         for selective multipath";
    }
  }

  grouping ncs_rpc_notif_EIGRP-ROUTE-TABLE {
    description
      "Common node of global-af, vrf-global-af";
    container eigrp-routes {
      description
        "Redistribute information for EIGRP routes.";
      list eigrp-route {
        key "instance-name";
        description
          "Redistribute EIGRP routes";
        leaf instance-name {
          type xr:Cisco-ios-xr-string;
          description
            "EIGRP router tag";
        }
        leaf default-metric {
          type Bgp-default-metric-range;
          description
            "Default metric";
        }
        leaf route-policy-name {
          type string;
          description
            "Route policy name";
        }
        leaf redist-type {
          type xr:Hex-integer;
          description
            "Redistribution type: 01 for internal routes,
             02 for external routes, Logical combinations
             permitted.";
        }
      }
    }
  }

  grouping ncs_rpc_notif_OPTIMAL-ROUTE-REFLECTION-GROUP {
    description
      "Common node of global-af, vrf-global-afCommon
       node of neighbor-group-af, neighbor-af,
       vrf-neighbor-af, af-group-af";
    leaf optimal-route-reflection-group {
      type string;
      description
        "Name of the ORR group this neighbor is going to
         be part of";
    }
  }

  grouping ncs_rpc_notif_ROUTE-REFLECTOR-CLIENT {
    description
      "Common node of neighbor-group-af, neighbor-af,
       vrf-neighbor-af, af-group-af";
    leaf route-reflector-client {
      type boolean;
      description
        "TRUE to configure as a route-reflector-client.
         FALSE to prevent route-reflector-client from
         being inherited.";
    }
  }

  grouping ncs_rpc_notif_ADVERTISE-LOCAL-LABELED-ROUTE {
    description
      "Common node of neighbor-group-af, neighbor-af,
       vrf-neighbor-af, af-group-af";
    leaf advertise-local-labeled-route {
      type dt1:Bgp-advertise-local-labeled-route-cfg;
      description
        "Enable/disable advertisement of routes with
         local-label";
    }
  }

  grouping ncs_rpc_notif_SESSION-OPEN-MODE {
    description
      "Common node of neighbor-group, neighbor,
       vrf-neighbor, session-group";
    leaf session-open-mode {
      type Bgp-tcp-mode;
      default "either";
      description
        "TCP mode to be used to establish BGP session";
    }
  }

  grouping ncs_rpc_notif_RPKI-ORIGIN-AS-VALIDATION-ENABLE {
    description
      "Common node of global-af, vrf-global-af";
    leaf rpki-origin-as-validation-enable {
      type empty;
      description
        "RPKI origin-AS validation enable";
    }
  }

  grouping ncs_rpc_notif_UPDATE-OUT-ORIG-LOOP-CHK-DISABLE {
    description
      "Common node of neighbor-group-af, neighbor-af,
       vrf-neighbor-af, af-group-af";
    leaf update-out-orig-loop-chk-disable {
      type empty;
      description
        "Enable/disable Originator loop check for this
         neighbor-group/af-group";
    }
  }

  grouping ncs_rpc_notif_STATIC-ROUTES {
    description
      "Common node of global-af, vrf-global-af";
    container static-routes {
      presence "enable static-routes";
      description
        "Redistribute static routes";
      leaf default-metric {
        type Bgp-default-metric-range;
        description
          "Default metric";
      }
      leaf route-policy-name {
        type string;
        description
          "Route policy name";
      }
      leaf not-used {
        type uint32 {
          range "0..127";
        }
        description
          "Not used";
      }
    }
  }

  grouping ncs_rpc_notif_PASSWORD {
    description
      "Common node of neighbor-group, neighbor,
       vrf-neighbor, session-group";
    container password {
      description
        "Set or disable a password";
      leaf password-disable {
        type boolean;
        description
          "TRUE to prevent this entity from having a
           password even if the parent has one.  FALSEto
           specify a password";
      }
      leaf password {
        when "../password-disable = 'false'" {
          tailf:xpath-root 3;
          description
            "../PasswordDisable = false";
        }
        type xr:Proprietary-password;
        description
          "The neighbor password.  Leave unspecified when
           disabling the password.";
      }
    }
  }

  grouping ncs_rpc_notif_NEXT-HOP-UNCHANGED-MULTIPATH {
    description
      "Common node of neighbor-group, neighbor,
       vrf-neighbor, session-groupCommon node of
       neighbor-group-af, neighbor-af, vrf-neighbor-af,
       af-group-af";
    leaf next-hop-unchanged-multipath {
      type boolean;
      description
        "TRUE to disable overwriting of next hop for
         multipaths. FALSE to prevent next-hop-unchanged
         for multipaths.";
    }
  }

  grouping ncs_rpc_notif_NEXT-HOP-RESOLUTION-PREFIX-LENGTH-MINIMUM {
    description
      "Common node of global-af, vrf-global-af";
    leaf next-hop-resolution-prefix-length-minimum {
      type uint32 {
        range "0..128";
      }
      default "0";
      description
        "Minimum prefix-length for nexthop resolution";
    }
  }

  grouping ncs_rpc_notif_BEST-PATH-AS-PATH-LENGTH {
    description
      "Common node of global, vrf-global";
    leaf best-path-as-path-length {
      type empty;
      description
        "Change default route selection criteria to
         ignore AS path length";
    }
  }

  grouping ncs_rpc_notif_MSG-LOG-OUT {
    description
      "Common node of global, vrf-globalCommon node of
       neighbor-group, neighbor, vrf-neighbor,
       session-group";
    container msg-log-out {
      description
        "Message log outbound";
      leaf msg-buf-count {
        type uint32 {
          range "1..100";
        }
        description
          "Outbound message log buffer size";
      }
      leaf msg-log-disable {
        type boolean;
        description
          "Disable inbound message logging";
      }
      leaf msg-log-inherit-disable {
        type boolean;
        description
          "TRUE, to prevent this entity from having a
           outbound message logging if parent has one";
      }
    }
  }

  grouping ncs_rpc_notif_ENFORCE-MULTIPLE-LABELS {
    description
      "Common node of neighbor-group-af, neighbor-af,
       vrf-neighbor-af, af-group-af";
    leaf enforce-multiple-labels {
      type boolean;
      description
        "TRUE to enforce multiple labels support.";
    }
  }

  grouping ncs_rpc_notif_PREFIX-ORF-POLICY {
    description
      "Common node of neighbor-group-af, neighbor-af,
       vrf-neighbor-af, af-group-afCommon node of
       neighbor-group-af, neighbor-af, vrf-neighbor-af,
       af-group-af";
    leaf prefix-orf-policy {
      type string;
      description
        "Prefix ORF policy name for incoming updates";
    }
  }

  grouping ncs_rpc_notif_SOURCED-NETWORK-TABLE {
    description
      "Common node of global-af, vrf-global-af";
    container sourced-networks {
      description
        "Specify a network to announce via BGP";
      list sourced-network {
        key "network-addr network-prefix";
        description
          "Sourced network configuration";
        leaf network-addr {
          type inet:ip-address;
          description
            "Network in prefix/length format (address part)";
        }
        leaf network-prefix {
          type uint16 {
            range "0..128";
          }
          description
            "Network in prefix/length format (prefix part)";
        }
        leaf backdoor {
          type boolean;
          description
            "Specify a BGP backdoor route, default is FALSE";
        }
        leaf route-policy-name {
          type string;
          description
            "Route policy name";
        }
      }
    }
  }

  grouping ncs_rpc_notif_REMOVE-PRIVATE-AS-ENTIRE-AS-PATH {
    description
      "Common node of neighbor-group-af, neighbor-af,
       vrf-neighbor-af, af-group-af";
    container remove-private-as-entire-as-path {
      presence "Indicates a remove-private-as-entire-as-path node is configured.";
      description
        "Remove private AS number from outbound updates";
      leaf enable {
        type boolean;
        mandatory true;
        description
          "TRUE to remove private AS from outbound updates
           .  FALSE to prevent remove-private-AS from
           being inherited.";
      }
      leaf entire {
        type boolean;
        description
          "TRUE to remove private AS from outbound updates
           if all ASes in aspath areprivate. FALSE to
           prevent remove-private-ASfrom being inherited.";
      }
    }
  }

  grouping ncs_rpc_notif_GRACEFUL-MAINTENANCE {
    description
      "Common node of neighbor-group, neighbor,
       vrf-neighbor, session-group";
    container graceful-maintenance {
      description
        "Graceful Maintenance mode";
      container graceful-maintenance-local-preference {
        description
          "Set Local Preference to advertise routes with";
        leaf gshut-loc-pref-disable {
          type boolean;
          description
            "TRUE, to prevent inheritance of Local Pref
             value from its parents.FALSE, otherwise";
        }
        leaf local-preference {
          type uint32 {
            range "0..4294967295";
          }
          description
            "Local Preference Value";
        }
      }
      container graceful-maintenance-as-prepends {
        description
          "Number of times to prepend local AS number to
           the AS path";
        leaf gshut-prepends-disable {
          type boolean;
          description
            "TRUE, to prevent inheritance of AS Prepends
             value from its parents.FALSE, otherwise";
        }
        leaf as-prepends {
          type uint32 {
            range "0..6";
          }
          description
            "number of times AS prepends";
        }
      }
      leaf enable {
        type empty;
        description
          "Enter Graceful Maintenance mode to configure
           parametrs";
      }
      leaf graceful-maintenance-activate {
        type boolean;
        description
          "Initiate the graceful shutdown procedure";
      }
    }
  }

  grouping ncs_rpc_notif_NEIGHBOR-AF-LONG-LIVED-GRACEFUL-RESTART-STALE-TIME {
    description
      "Common node of neighbor-group-af, neighbor-af,
       vrf-neighbor-af, af-group-af";
    container neighbor-af-long-lived-graceful-restart-stale-time {
      description
        "Maximum time to wait before purging long lived
         routes";
      leaf stale-time-send {
        type uint32 {
          range "0..16777215";
        }
        units "second";
        default "0";
        description
          "Max time (seconds)";
      }
      leaf stale-time-accept {
        type uint32 {
          range "0..16777215";
        }
        units "second";
        default "0";
        description
          "Max time (seconds)";
      }
    }
  }

  grouping ncs_rpc_notif_BFD {
    description
      "Common node of global, vrf-global";
    container bfd {
      description
        "BFD configuration";
      leaf detection-multiplier {
        type uint32 {
          range "2..16";
        }
        description
          "Detection multiplier for BFD sessions created
           by BGP";
      }
      leaf interval {
        type uint32 {
          range "3..30000";
        }
        units "millisecond";
        description
          "Hello interval for BFD sessions created by BGP";
      }
    }
  }

  grouping ncs_rpc_notif_ALLOCATE-LABEL {
    description
      "Common node of global-af, vrf-global-af";
    container allocate-label {
      presence "enable allocate-label";
      description
        "Label allocation policy";
      leaf all {
        type boolean;
        description
          "Whether all nets should be labeled, default is
           FALSE";
      }
      leaf route-policy-name {
        type string;
        description
          "Route policy name";
      }
      leaf un-labeled-path {
        type boolean;
        must '../all or ../route-policy-name' {
          tailf:xpath-root 3;
        }
        description
          "Allocate label for unlabeled paths too";
      }
    }
  }

  grouping ncs_rpc_notif_SEND-BUFFER-SIZE {
    description
      "Common node of neighbor-group, neighbor,
       vrf-neighbor, session-group";
    container send-buffer-size {
      description
        "Set socket send buffer size and BGP write buffer
         size";
      leaf socket-send-size {
        type uint32 {
          range "4096..131072";
        }
        units "byte";
        default "24576";
        description
          "Send socket buffer size in bytes";
      }
      leaf bgp-send-size {
        type uint32 {
          range "4096..131072";
        }
        units "byte";
        default "4096";
        description
          "BGP write buffer size in bytes";
      }
    }
  }

  grouping ncs_rpc_notif_BEST-PATH-MED-MISSING {
    description
      "Common node of neighbor-group, neighbor,
       vrf-neighbor, session-groupCommon node of global,
       vrf-global";
    leaf best-path-med-missing {
      type empty;
      description
        "Treat missing MED as the least preferred one";
    }
  }

  grouping ncs_rpc_notif_SUPPRESS-ALL-CAPABILITIES {
    description
      "Common node of neighbor-group, neighbor,
       vrf-neighbor, session-group";
    leaf suppress-all-capabilities {
      type boolean;
      description
        "TRUE to suppress all capabilities. FALSE to not
         suppress and to prevent inheritance from a
         parent";
    }
  }

  grouping ncs_rpc_notif_DEFAULT-WEIGHT {
    description
      "Common node of neighbor-group, neighbor,
       vrf-neighbor, session-groupCommon node of
       neighbor-group-af, neighbor-af, vrf-neighbor-af,
       af-group-af";
    leaf default-weight {
      type uint32 {
        range "0..65535";
      }
      description
        "Set default weight for routes from this
         neighbor/neighbor-group/af-group";
    }
  }

  grouping ncs_rpc_notif_SUPPRESS-FOUR-BYTE-AS-CAPABILITY {
    description
      "Common node of neighbor-group, neighbor,
       vrf-neighbor, session-group";
    leaf suppress-four-byte-as-capability {
      type boolean;
      description
        "TRUE to suppress BGP 4-byte-as capability.
         FALSE to not suppress it and to prevent
         inheritance from a parent";
    }
  }

  grouping ncs_rpc_notif_ADVERTISE-LOCAL-L2VPN-EVPN {
    description
      "Common node of neighbor-group-af, neighbor-af,
       vrf-neighbor-af, af-group-af";
    container advertise-local-l2vpn-evpn {
      description
        "Advertise Of Local Routes to the peer with
         different RT";
      leaf af-name {
        type dt1:Bgp-address-family;
        description
          "Address family";
      }
      leaf reorg-option {
        type Bgp-reorg-opt;
        description
          "Reorigination option";
      }
      leaf rt-type {
        type Bgp-adv-rt;
        description
          "RT type";
      }
    }
  }

  grouping ncs_rpc_notif_EGRESS-PEER-ENGINEERING {
    description
      "Common node of neighbor-group, neighbor,
       vrf-neighbor, session-group";
    leaf egress-peer-engineering {
      type boolean;
      description
        "TRUE to enable egress peer engineering FALSE to
         disable egress peer engineering and to prevent
         inheritance from a parent";
    }
  }

  grouping ncs_rpc_notif_BEST-PATH-CONFEDERATION-PATHS {
    description
      "Common node of global, vrf-global";
    leaf best-path-confederation-paths {
      type empty;
      description
        "Change default route selection criteria and
         allow the comparing of MED among confederation
         paths";
    }
  }

  grouping ncs_rpc_notif_DYNAMIC-MED-INTERVAL {
    description
      "Common node of global-af, vrf-global-af";
    leaf dynamic-med-interval {
      type uint32 {
        range "0..10";
      }
      units "minute";
      default "10";
      description
        "Update generation delay (in minutes) after a MED
         change";
    }
  }

  grouping ncs_rpc_notif_REMOVE-PRIVATE-AS-ENTIRE-AS-PATH-INBOUND {
    description
      "Common node of neighbor-group-af, neighbor-af,
       vrf-neighbor-af, af-group-af";
    container remove-private-as-entire-as-path-inbound {
      presence "Indicates a remove-private-as-entire-as-path-inbound node is configured.";
      description
        "Remove private AS number from inbound updates";
      leaf enable {
        type boolean;
        mandatory true;
        description
          "TRUE to remove private AS from inbound updates.
           FALSE to prevent remove-private-AS from being
           inherited.";
      }
      leaf entire {
        type boolean;
        description
          "TRUE to remove private AS from inbound updates
           if all ASes in aspath areprivate. FALSE to
           prevent remove-private-ASfrom being inherited.";
      }
    }
  }

  grouping ncs_rpc_notif_RPKI-BESTPATH-USE-ORIGIN-AS-VALIDITY {
    description
      "Common node of global-af, vrf-global-af";
    leaf rpki-bestpath-use-origin-as-validity {
      type empty;
      description
        "RPKI bestpath use origin-AS validity";
    }
  }

  grouping ncs_rpc_notif_BGP-CFG-RPKI-BESTPATH-USE-ORIGIN-AS-VALIDITY {
    description
      "Common node of global-af, vrf-global-afCommon
       node of global, vrf-global";
    leaf rpki-bestpath-use-origin-as-validity {
      type empty;
      description
        "RPKI bestpath use origin-AS validity";
    }
  }

  grouping ncs_rpc_notif_CONNECTED-ROUTES {
    description
      "Common node of global-af, vrf-global-af";
    container connected-routes {
      presence "enable connected-routes";
      description
        "Redistribute connected routes";
      leaf default-metric {
        type Bgp-default-metric-range;
        description
          "Default metric";
      }
      leaf route-policy-name {
        type string;
        description
          "Route policy name";
      }
      leaf not-used {
        type uint32 {
          range "0..127";
        }
        description
          "Not used";
      }
    }
  }

  grouping ncs_rpc_notif_IGP-REDIST-INTERNAL {
    description
      "Common node of global, vrf-global";
    leaf igp-redist-internal {
      type empty;
      description
        "Allow redistribution of iBGP into IGPs
         (dangerous)";
    }
  }

  grouping ncs_rpc_notif_AIGP-SEND-MED {
    description
      "Common node of neighbor-group-af, neighbor-af,
       vrf-neighbor-af, af-group-af";
    leaf aigp-send-med {
      type Bgp-aigp-cfg;
      description
        "Enable/Disable sending AIGP in MED ";
    }
  }

  grouping ncs_rpc_notif_AIGP {
    description
      "Common node of neighbor-group-af, neighbor-af,
       vrf-neighbor-af, af-group-af";
    leaf aigp {
      type Bgp-aigp-cfg;
      description
        "Enable Accumulated IGP Metric for this neighbor.";
    }
  }

  grouping ncs_rpc_notif_ADVERTISE-ORF {
    description
      "Common node of neighbor-group-af, neighbor-af,
       vrf-neighbor-af, af-group-af";
    leaf advertise-orf {
      type Bgp-orf;
      default "none";
      description
        "Advertise ORF capability to the peer";
    }
  }

  grouping ncs_rpc_notif_BFD-MINIMUM-INTERVAL {
    description
      "Common node of neighbor-group, neighbor,
       vrf-neighbor, session-group";
    leaf bfd-minimum-interval {
      type uint32 {
        range "3..30000";
      }
      units "millisecond";
      description
        "Hello interval for BFD sessions created by BGP";
    }
  }

  grouping ncs_rpc_notif_AIGP-COST-COMMUNITY {
    description
      "Common node of neighbor-group-af, neighbor-af,
       vrf-neighbor-af, af-group-af";
    container aigp-cost-community {
      description
        "Send AIGP value in Cost Community. ";
      leaf enable {
        type boolean;
        description
          "TRUE to enable sending cost community, FALSE
           otherwise ";
      }
      leaf cost-community-id {
        when "../enable = 'true'" {
          tailf:xpath-root 3;
          description
            "../Enable = 'true'";
        }
        type uint32 {
          range "0..255";
        }
        description
          "Cost Community ID";
      }
      leaf transitive {
        when "../enable = 'true'" {
          tailf:xpath-root 3;
          description
            "../Enable = 'true'";
        }
        type boolean;
        description
          "True to send transitive cost community FALSE
           otherwise";
      }
      leaf cost-community-poi-type {
        when "../enable = 'true'" {
          tailf:xpath-root 3;
          description
            "../Enable = 'true'";
        }
        type Bgp-aigp-cfg-poi;
        description
          "Cost Community POI";
      }
    }
  }

  grouping ncs_rpc_notif_DISABLE-AS-PATH-LOOP-CHECK {
    description
      "Common node of global-af, vrf-global-af";
    leaf disable-as-path-loop-check {
      type empty;
      description
        "Disable outbound AS Path loop check";
    }
  }

  grouping ncs_rpc_notif_BEST-PATH-ROUTER-ID {
    description
      "Common node of global, vrf-global";
    leaf best-path-router-id {
      type empty;
      description
        "Change default route selection criteria and
         compare router-id for identical EBGP paths";
    }
  }

  grouping ncs_rpc_notif_RIP-ROUTES {
    description
      "Common node of global-af, vrf-global-af";
    container rip-routes {
      presence "enable rip-routes";
      description
        "Redistribute RIP routes";
      leaf default-metric {
        type Bgp-default-metric-range;
        description
          "Default metric";
      }
      leaf route-policy-name {
        type string;
        description
          "Route policy name";
      }
      leaf not-used {
        type uint32 {
          range "0..127";
        }
        description
          "Not used";
      }
    }
  }

  grouping ncs_rpc_notif_DESCRIPTION {
    description
      "Common node of neighbor-group, neighbor,
       vrf-neighbor, session-group";
    leaf description {
      type string;
      description
        "Up to 80 characters describing this neighbor";
    }
  }

  grouping ncs_rpc_notif_ADVERTISE-L2VPN-EVPN {
    description
      "Common node of neighbor-group-af, neighbor-af,
       vrf-neighbor-af, af-group-af";
    container advertise-l2vpn-evpn {
      description
        "Advertise Translated Routes to the peer";
      leaf af-name {
        type dt1:Bgp-address-family;
        description
          "Address family";
      }
      leaf reorg-option {
        type Bgp-reorg-opt;
        description
          "Reorigination option";
      }
      leaf rt-type {
        type Bgp-adv-rt;
        description
          "RT type";
      }
    }
  }

  grouping ncs_rpc_notif_KEYCHAIN {
    description
      "Common node of neighbor-group, neighbor,
       vrf-neighbor, session-group";
    container keychain {
      description
        "Set or disable keychain based authentication";
      leaf keychain-disable {
        type boolean;
        description
          "TRUE to prevent this entity from having a
           keychain based authentication even if the
           parent has one.FALSE to specify a keychain name";
      }
      leaf keychain-name {
        when "../keychain-disable = 'false'" {
          tailf:xpath-root 3;
          description
            "../KeychainDisable = false";
        }
        type string;
        description
          "Name of the keychain associated with neighbor";
      }
    }
  }

  grouping ncs_rpc_notif_RECEIVE-BUFFER-SIZE {
    description
      "Common node of neighbor-group, neighbor,
       vrf-neighbor, session-group";
    container receive-buffer-size {
      description
        "Set socket receive buffer size and BGP read
         buffer size";
      leaf socket-receive-size {
        type uint32 {
          range "512..131072";
        }
        units "byte";
        default "32768";
        description
          "Receive socket buffer size in bytes";
      }
      leaf bgp-receive-size {
        type uint32 {
          range "512..131072";
        }
        units "byte";
        default "4096";
        description
          "BGP read buffer size in bytes";
      }
    }
  }

  grouping ncs_rpc_notif_NEXT-HOP-UNCHANGED {
    description
      "Common node of neighbor-group-af, neighbor-af,
       vrf-neighbor-af, af-group-af";
    leaf next-hop-unchanged {
      type boolean;
      description
        "TRUE to disable overwriting of next hop before
         advertising to eBGP peers. FALSE to prevent
         next-hop-unchanged from being inherited.";
    }
  }

  grouping ncs_rpc_notif_OSPF-ROUTE-TABLE {
    description
      "Common node of global-af, vrf-global-af";
    container ospf-routes {
      description
        "Redistribute information for OSPF routes.";
      list ospf-route {
        key "instance-name";
        description
          "Redistribute OSPF routes";
        leaf instance-name {
          type xr:Cisco-ios-xr-string;
          description
            "OSPF router tag";
        }
        leaf default-metric {
          type Bgp-default-metric-range;
          description
            "Default metric";
        }
        leaf route-policy-name {
          type string;
          description
            "Route policy name";
        }
        leaf redist-type {
          type xr:Hex-integer;
          description
            "Redistribution type: 01 for internal routes,
             02 for external routes of type 1, 04 for
             external routes of type 2, 08 for NSSA
             external routes of type 1, 10 for NSSA
             external routes of type 2, 20 for external
             routes, 40 for NSSA external routes.  Logical
             combinations permitted.";
        }
      }
    }
  }

  grouping ncs_rpc_notif_ROUTER-ID {
    description
      "Common node of global, vrf-global";
    leaf router-id {
      type inet:ipv4-address-no-zone;
      default "0.0.0.0";
      description
        "Configure Router-id";
    }
  }

  grouping ncs_rpc_notif_DEFAULT-METRIC {
    description
      "Common node of global, vrf-global";
    leaf default-metric {
      type uint32 {
        range "1..4294967295";
      }
      description
        "Default redistributed metric";
    }
  }

  grouping ncs_rpc_notif_RPKI-ORIGIN-AS-VALIDATION-DISABLE {
    description
      "Common node of neighbor-group-af, neighbor-af,
       vrf-neighbor-af, af-group-af";
    leaf rpki-origin-as-validation-disable {
      type empty;
      description
        "RPKI origin-AS validation disable";
    }
  }

  grouping ncs_rpc_notif_BGP-CFG-RPKI-ORIGIN-AS-VALIDATION-DISABLE {
    description
      "Common node of neighbor-group-af, neighbor-af,
       vrf-neighbor-af, af-group-afCommon node of
       neighbor-group, neighbor, vrf-neighbor,
       session-group";
    leaf rpki-origin-as-validation-disable {
      type empty;
      description
        "RPKI origin-AS validation disable";
    }
  }

  grouping ncs_rpc_notif_DISABLE-NEIGHBOR-LOGGING {
    description
      "Common node of global, vrf-global";
    leaf disable-neighbor-logging {
      type empty;
      description
        "Disable neighbor change logging";
    }
  }

  grouping ncs_rpc_notif_TCPMSS {
    description
      "Common node of neighbor-group, neighbor,
       vrf-neighbor, session-group";
    container tcpmss {
      description
        "TCP Maximum segment size";
      leaf tcpmss-disable {
        type boolean;
        description
          "TRUE, to prevent inheritance ofTCP MSS
           valuefrom its parents.FALSE, otherwise";
      }
      leaf mss {
        type uint32 {
          range "68..10000";
        }
        description
          "Maximum Segment Size";
      }
    }
  }

  grouping live_ncs_ADVERTISE-DISABLE {
    description
      "Common node of neighbor-group-af, neighbor-af,
       vrf-neighbor-af, af-group-af";
    container advertise-disable {
      description
        "Disable Advertise Of Routes to the peer";
      leaf af-name {
        type dt1:Bgp-address-family;
        description
          "Address family";
      }
      leaf reorg-option {
        type Bgp-reorg-opt;
        description
          "Reorigination option";
      }
      leaf rt-type {
        type Bgp-adv-rt;
        description
          "RT type";
      }
    }
  }

  grouping live_ncs_TABLE-POLICY {
    description
      "Common node of global-af, vrf-global-af";
    leaf table-policy {
      type string;
      description
        "Configure policy for installation of routes to
         RIB";
    }
  }

  grouping live_ncs_MAXIMUM-PREFIXES {
    description
      "Common node of global-af, vrf-global-afCommon
       node of neighbor-group-af, neighbor-af,
       vrf-neighbor-af, af-group-af";
    container maximum-prefixes {
      presence "Indicates a maximum-prefixes node is configured.";
      description
        "Maximum number of prefixes to accept from this
         peer";
      leaf prefix-limit {
        type uint32 {
          range "1..4294967295";
        }
        // NCS drop mandatory statement
        description
          "Maximum prefixes limit";
      }
      leaf warning-percentage {
        type uint32 {
          range "1..100";
        }
        // NCS drop default statement
        description
          "Threshold value (%) at which to generate a
           warning message.";
      }
      leaf warning-only {
        type boolean;
        // NCS drop default statement
        description
          "TRUE to only give a warning message when limit
           is exceeded.  FALSE to accept max prefix limit
           only.";
      }
      leaf restart-time {
        type uint32 {
          range "0..65535";
        }
        // NCS drop default statement
        description
          "Restart interval";
      }
      leaf discard-extra-paths {
        type boolean;
        // NCS drop default statement
        description
          "Discard extra paths when limit is exceeded";
      }
    }
  }

  grouping live_ncs_DISTANCE {
    description
      "Common node of global-af, vrf-global-af";
    container distance {
      presence "Indicates a distance node is configured.";
      description
        "Define an administrative distance";
      leaf external-routes {
        type uint32 {
          range "1..255";
        }
        // NCS drop mandatory statement
        description
          "Distance for routes external to the AS";
      }
      leaf internal-routes {
        type uint32 {
          range "1..255";
        }
        // NCS drop mandatory statement
        description
          "Distance for routes internal to the AS";
      }
      leaf local-routes {
        type uint32 {
          range "1..255";
        }
        // NCS drop mandatory statement
        description
          "Distance for local routes";
      }
    }
  }

  grouping live_ncs_UPDATE-SOURCE-INTERFACE {
    description
      "Common node of neighbor-group, neighbor,
       vrf-neighbor, session-group";
    leaf update-source-interface {
      type xr:Interface-name;
      description
        "Select an interface to configure";
    }
  }

  grouping live_ncs_MULTI-PATH-AS-PATH-IGNORE-ONWARDS {
    description
      "Common node of global, vrf-global";
    leaf multi-path-as-path-ignore-onwards {
      type empty;
      description
        "Change default multi-route selection criteria to
         ignore everything onwards as-path check";
    }
  }

  grouping live_ncs_PROPAGATE-DMZ-LINK-BANDWIDTH {
    description
      "Common node of neighbor-group, neighbor,
       vrf-neighbor, session-group";
    leaf propagate-dmz-link-bandwidth {
      type boolean;
      description
        "TRUE to propagate DMZ link bandwidth.  FALSE to
         not propagate and to prevent inheritance from a
         parent";
    }
  }

  grouping live_ncs_DISABLE-AUTO-SOFT-RESET {
    description
      "Common node of global, vrf-global";
    leaf disable-auto-soft-reset {
      type empty;
      description
        "Disable automatic soft peer reset on policy
         reconfiguration";
    }
  }

  grouping live_ncs_MSG-LOG-IN {
    description
      "Common node of neighbor-group, neighbor,
       vrf-neighbor, session-group";
    container msg-log-in {
      description
        "Message log inbound";
      leaf msg-buf-count {
        type uint32 {
          range "1..100";
        }
        description
          "Inbound message log buffer size";
      }
      leaf msg-log-disable {
        type boolean;
        description
          "Disable inbound message logging";
      }
      leaf msg-log-inherit-disable {
        type boolean;
        description
          "TRUE, to prevent this entity from having a
           inbound message logging if parent has one";
      }
    }
  }

  grouping live_ncs_DISABLE-ENFORCE-FIRST-AS {
    description
      "Common node of global, vrf-global";
    leaf disable-enforce-first-as {
      type empty;
      description
        "Disable enforce the first AS for EBGP routes";
    }
  }

  grouping live_ncs_ROUTE-TARGET-TABLE {
    description
      "Common node of import-route-targets,
       export-route-targets";
    container route-targets {
      description
        "Route target table";
      list route-target {
        // NCS drop must statement
        key "type";
        description
          "Route target";
        leaf type {
          type Bgp-vrf-route-target;
          description
            "Type of RT";
        }
        list as-or-four-byte-as {
          // NCS drop when statement
          key "as-xx as as-index stitching-rt";
          description
            "as or four byte as";
          leaf as-xx {
            type uint32 {
              range "0";
            }
            description
              "AS number";
          }
          leaf as {
            type uint32 {
              range "1..4294967295";
            }
            description
              "AS number";
          }
          leaf as-index {
            type Route-target-as-index;
            description
              "AS number Index";
          }
          leaf stitching-rt {
            type uint32 {
              range "0..1";
            }
            description
              "Stitching RT";
          }
        }
        list ipv4-address {
          // NCS drop when statement
          key "address address-index stitching-rt";
          description
            "ipv4 address";
          leaf address {
            type inet:ipv4-address-no-zone;
            description
              "IP address";
          }
          leaf address-index {
            type Route-target-addr-index;
            description
              "IP address Index";
          }
          leaf stitching-rt {
            type uint32 {
              range "0..1";
            }
            description
              "Stitching RT";
          }
        }
      }
    }
  }

  grouping live_ncs_REMOTE-AS {
    description
      "Common node of neighbor-group, neighbor,
       vrf-neighbor, session-group";
    container remote-as {
      description
        "Set remote AS";
      leaf as-xx {
        type dt1:Bgp-as-range;
        description
          "xx of AS number xx.yy";
      }
      leaf as-yy {
        type dt1:Bgp-as-range;
        description
          "yy of AS number xx.yy";
      }
    }
  }

  grouping live_ncs_ADDITIONAL-PATHS-SEND {
    description
      "Common node of global-af, vrf-global-af";
    leaf additional-paths-send {
      type dt1:Bgp-af-additional-paths-cfg;
      description
        "Advertise additional paths Send capability";
    }
  }

  grouping live_ncs_UPDATE-IN-FILTERING {
    description
      "Common node of neighbor-group, neighbor,
       vrf-neighbor, session-group";
    container update-in-filtering {
      description
        "Inbound update filtering";
      container update-in-filtering-message-buffers {
        presence "Indicates a update-in-filtering-message-buffers node is configured.";
        description
          "Message buffers to store filtered updates";
        leaf number-of-buffers {
          type uint32 {
            range "0..25";
          }
          // NCS drop mandatory statement
          description
            "Number of message buffers";
        }
        leaf non-circular-buffer {
          type boolean;
          // NCS drop mandatory statement
          description
            "TRUE to configure non-circular buffer";
        }
      }
      leaf enable {
        type empty;
        description
          "Configure inbound update filtering";
      }
      leaf update-in-filtering-attribute-filter-group {
        type string;
        description
          "Attribute-filter group name for update
           filtering";
      }
      leaf update-in-filtering-syslog-disable {
        type empty;
        description
          "Disable inbound update filtering syslog
           messages";
      }
    }
  }

  grouping live_ncs_SHUTDOWN {
    description
      "Common node of neighbor-group, neighbor,
       vrf-neighbor, session-group";
    leaf shutdown {
      type boolean;
      description
        "TRUE to shutdown this entity, FALSE to prevent
         this entity from being shutdown even if the
         parent is.";
    }
  }

  grouping live_ncs_BMP-ACTIVATE-TABLE {
    description
      "Common node of neighbor-group, neighbor,
       vrf-neighbor, session-group";
    container bmp-activates {
      description
        "Enable BMP logging for this neighbor";
      list bmp-activate {
        key "server-id";
        description
          "Enable BMP logging for this particular server";
        leaf server-id {
          type uint32 {
            range "1..8";
          }
          description
            "BMP Server ID";
        }
      }
    }
  }

  grouping live_ncs_ADVERTISE-VRF-IMP-DISABLE-V4 {
    description
      "Common node of neighbor-group-af, neighbor-af,
       vrf-neighbor-af, af-group-af";
    container advertise-vrf-imp-disable-v4 {
      description
        "Disable Advertise Of VRF ReImported Routes";
      leaf af-name {
        type dt1:Bgp-address-family;
        description
          "Address family";
      }
      leaf adv-option {
        type Bgp-reorg-opt;
        description
          "Advertise option";
      }
      leaf rt-type {
        type Bgp-adv-rt;
        description
          "RT type";
      }
    }
  }

  grouping live_ncs_ADVERTISE-VRF-IMP-DISABLE-V6 {
    description
      "Common node of neighbor-group-af, neighbor-af,
       vrf-neighbor-af, af-group-af";
    container advertise-vrf-imp-disable-v6 {
      description
        "Disable Advertise Of VRF ReImported Routes";
      leaf af-name {
        type dt1:Bgp-address-family;
        description
          "Address family";
      }
      leaf adv-option {
        type Bgp-reorg-opt;
        description
          "Advertise option";
      }
      leaf rt-type {
        type Bgp-adv-rt;
        description
          "RT type";
      }
    }
  }

  grouping live_ncs_SITE-OF-ORIGIN {
    description
      "Common node of neighbor-group-af, vrf-neighbor-af
       , af-group-af";
    container site-of-origin {
      description
        "Site-of-Origin extended community associated
         with the neighbor";
      leaf type {
        type Bgp-site-of-origin;
        description
          "Type of Extended community";
      }
      leaf as-xx {
        // NCS drop when statement
        type dt1:Bgp-as-range;
        description
          "AS number";
      }
      leaf as {
        // NCS drop when statement
        type dt1:Bgp-as-range;
        description
          "AS number";
      }
      leaf as-index {
        // NCS drop when statement
        type dt1:Bgp-extcomm-asn-index;
        description
          "AS number Index";
      }
      leaf address {
        // NCS drop when statement
        type inet:ipv4-address-no-zone;
        description
          "IP address";
      }
      leaf address-index {
        // NCS drop when statement
        type dt1:Bgp-extcomm-v4-addr-index;
        description
          "IP address Index";
      }
    }
  }

  grouping live_ncs_ROUTE-POLICY-OUT {
    description
      "Common node of neighbor-group-af, neighbor-af,
       vrf-neighbor-af, af-group-af";
    leaf route-policy-out {
      type string;
      description
        "Route policy name to apply to outbound routes";
    }
  }

  grouping live_ncs_SEGMENT-ROUTING {
    description
      "Common node of global-af, vrf-global-af";
    container segment-routing {
      description
        "Segment-routing Configurations";
      container srv6 {
        description
          "SRv6 Configurations";
        leaf enable {
          type empty;
          description
            "Enable SRv6 configuration submode";
        }
        leaf srv6sid-allocation-mode {
          type string;
          description
            "SID allocation mode: per-ce  Set per CE SID
             mode,per-vrf Set per VRF SID mode";
        }
        leaf locator-name {
          type string;
          description
            "Configure Locator name for SID allocation";
        }
      }
    }
  }

  grouping live_ncs_ADVERTISE-V4 {
    description
      "Common node of neighbor-group-af, neighbor-af,
       vrf-neighbor-af, af-group-af";
    container advertise-v4 {
      description
        "Advertise Translated Routes to the peer";
      leaf af-name {
        type dt1:Bgp-address-family;
        description
          "Address family";
      }
      leaf reorg-option {
        type Bgp-reorg-opt;
        description
          "Reorigination option";
      }
      leaf rt-type {
        type Bgp-adv-rt;
        description
          "RT type";
      }
    }
  }

  grouping live_ncs_ADVERTISE-V6 {
    description
      "Common node of neighbor-group-af, neighbor-af,
       vrf-neighbor-af, af-group-af";
    container advertise-v6 {
      description
        "Advertise Translated Routes to the peer";
      leaf af-name {
        type dt1:Bgp-address-family;
        description
          "Address family";
      }
      leaf reorg-option {
        type Bgp-reorg-opt;
        description
          "Reorigination option";
      }
      leaf rt-type {
        type Bgp-adv-rt;
        description
          "RT type";
      }
    }
  }

  grouping live_ncs_DEFAULT-ORIGINATE {
    description
      "Common node of neighbor-group-af, neighbor-af,
       vrf-neighbor-af, af-group-af";
    container default-originate {
      description
        "Originate default route to this neighbor";
      leaf enable {
        type boolean;
        // NCS drop default statement
        description
          "FALSE to prevent default-originate from, being
           inherited from a parent. TRUE otherwise.";
      }
      leaf route-policy-name {
        type string;
        description
          "Route policy name to specify criteria to
           originate default.";
      }
    }
  }

  grouping live_ncs_IDLE-WATCH-TIME {
    description
      "Common node of neighbor-group, neighbor,
       vrf-neighbor, session-group";
    leaf idle-watch-time {
      type uint32 {
        range "30..1800";
      }
      units "second";
      description
        "Time to wait for deleteing IDLE state Dynamic
         peer";
    }
  }

  grouping live_ncs_TIMERS {
    description
      "Common node of neighbor-group, neighbor,
       vrf-neighbor, session-group";
    container timers {
      description
        "BGP per neighbor timers.";
      leaf keepalive-interval {
        type uint32 {
          range "0..65535";
        }
        // NCS drop default statement
        description
          "Keepalive interval";
      }
      leaf hold-time {
        type uint32 {
          range "0..65535";
        }
        // NCS drop default statement
        description
          "Hold time.  Specify 0 to disable
           keepalives/hold time";
      }
      leaf min-accept-hold-time {
        type uint32 {
          range "0..65535";
        }
        // NCS drop default statement
        description
          "Minimum acceptable hold time.  Specify 0 to
           disable keepalives/hold time";
      }
    }
  }

  grouping live_ncs_NEXT-HOP-MPLS-FWD-IBGP {
    description
      "Common node of global, vrf-global";
    leaf next-hop-mpls-fwd-ibgp {
      type empty;
      description
        "Enable mpls forwarding path for ibgp learnt
         nexthops";
    }
  }

  grouping live_ncs_DISABLE-FAST-EXTERNAL-FALLOVER {
    description
      "Common node of global, vrf-global";
    leaf disable-fast-external-fallover {
      type empty;
      description
        "Disable immediate reset session if a link to a
         directly connected external peer goes down";
    }
  }

  grouping live_ncs_SEND-COMMUNITY-EBGP {
    description
      "Common node of neighbor-group-af, neighbor-af,
       vrf-neighbor-af, af-group-af";
    leaf send-community-ebgp {
      type boolean;
      description
        "TRUE to send communities to the external
         neighbor/neighbor-group/af-group.  FALSE not to
         send and to prevent inheritance from a parent";
    }
  }

  grouping live_ncs_ADDITIONAL-PATHS-RECEIVE-CAPABILITY {
    description
      "Common node of neighbor-group, neighbor,
       vrf-neighbor, session-group";
    leaf additional-paths-receive-capability {
      type dt1:Bgp-nbr-cap-additional-paths-cfg;
      description
        "Advertise additional paths Receive capability";
    }
  }

  grouping live_ncs_SEND-EXT-COMMUNITY-EBGP {
    description
      "Common node of neighbor-group-af, neighbor-af,
       vrf-neighbor-af, af-group-af";
    leaf send-ext-community-ebgp {
      type boolean;
      description
        "TRUE to send extended communities to the
         external neighbor/neighbor-group/af-group.
         FALSE not to send and to prevent inheritance
         from a parent";
    }
  }

  grouping live_ncs_AF-GROUP {
    description
      "Common node of neighbor-group-af, neighbor-af,
       vrf-neighbor-af";
    leaf af-group {
      type string;
      description
        "Inherit configuration for this address-family
         from an AF-group";
    }
  }

  grouping live_ncs_ROUTE-POLICY-IN {
    description
      "Common node of neighbor-group-af, neighbor-af,
       vrf-neighbor-af, af-group-af";
    leaf route-policy-in {
      type string;
      description
        "Route policy name to apply to inbound routes";
    }
  }

  grouping live_ncs_LABEL-MODE {
    description
      "Common node of global-af, vrf-global-af";
    container label-mode {
      presence "enable label-mode";
      description
        "BGP 6PE/MPLS-VPN label allocation mode";
      leaf label-allocation-mode {
        type string;
        description
          "Label allocation mode: per-ce  Set per CE label
           mode, per-vrf Set per VRF label mode,
           per-prefix Set per Prefix label mode (for
           MPLS-VPN only)";
      }
      leaf route-policy-name {
        type string;
        description
          "Label mode route policy name";
      }
    }
  }

  grouping live_ncs_APP-ROUTE-TABLE {
    description
      "Common node of global-af, vrf-global-af";
    container application-routes {
      description
        "Redistribute information for Application routes.";
      list application-route {
        key "instance-name";
        description
          "Redistribute application routes";
        leaf instance-name {
          type xr:Cisco-ios-xr-string;
          description
            "OnePK application name";
        }
        leaf default-metric {
          type Bgp-default-metric-range;
          description
            "Default metric";
        }
        leaf route-policy-name {
          type string;
          description
            "Route policy name";
        }
        leaf not-used {
          type uint32 {
            range "0..127";
          }
          description
            "Not used";
        }
      }
    }
  }

  grouping live_ncs_DEFAULT-INFO-ORIGINATE {
    description
      "Common node of global, vrf-global";
    leaf default-info-originate {
      type empty;
      description
        "Control distribution of default information";
    }
  }

  grouping live_ncs_ENFORCE-FIRST-AS {
    description
      "Common node of neighbor-group, neighbor,
       vrf-neighbor, session-group";
    leaf enforce-first-as {
      type boolean;
      description
        "TRUE to enforce first AS; FALSE to not enforce
         first AS.";
    }
  }

  grouping live_ncs_SOFT-RECONFIGURATION {
    description
      "Common node of neighbor-group-af, neighbor-af,
       vrf-neighbor-af, af-group-af";
    container soft-reconfiguration {
      description
        "Enable/disable inbound soft reconfiguration for
         this neighbor/neighbor-group/af-group";
      leaf inbound-soft {
        type boolean;
        // NCS drop default statement
        description
          "FALSE to prohibit inbound soft reconfiguration.
           TRUE otherwise.";
      }
      leaf soft-always {
        type boolean;
        // NCS drop default statement
        description
          "TRUE to always use soft reconfig, even if route
           refresh is supported.  FALSE otherwise.";
      }
    }
  }

  grouping live_ncs_NEIGHBOR-GRACEFUL-RESTART {
    description
      "Common node of neighbor-group, neighbor,
       vrf-neighbor, session-group";
    leaf neighbor-graceful-restart {
      type Bgp-nbrgr;
      description
        "TRUE to Enable graceful restart supportfor
         neighbor.  FALSE to disable graceful restart
         support for neighbor.";
    }
  }

  grouping live_ncs_ADVERTISE-DEF-IMP-DISABLE-V4 {
    description
      "Common node of neighbor-group-af, neighbor-af,
       vrf-neighbor-af, af-group-af";
    container advertise-def-imp-disable-v4 {
      description
        "Disable Advertise Of Default VRF Imported Routes";
      leaf af-name {
        type dt1:Bgp-address-family;
        description
          "Address family";
      }
      leaf adv-option {
        type Bgp-reorg-opt;
        description
          "Advertise option";
      }
      leaf rt-type {
        type Bgp-adv-rt;
        description
          "RT type";
      }
    }
  }

  grouping live_ncs_ADVERTISE-DEF-IMP-DISABLE-V6 {
    description
      "Common node of neighbor-group-af, neighbor-af,
       vrf-neighbor-af, af-group-af";
    container advertise-def-imp-disable-v6 {
      description
        "Disable Advertise Of Default VRF Imported Routes";
      leaf af-name {
        type dt1:Bgp-address-family;
        description
          "Address family";
      }
      leaf adv-option {
        type Bgp-reorg-opt;
        description
          "Advertise option";
      }
      leaf rt-type {
        type Bgp-adv-rt;
        description
          "RT type";
      }
    }
  }

  grouping live_ncs_LOCAL-ADDRESS {
    description
      "Common node of neighbor-group, neighbor,
       vrf-neighbor, session-group";
    container local-address {
      description
        "Local ip address";
      leaf local-address-disable {
        type boolean;
        description
          "TRUE to prevent this entity from having a local
           address if the parent has one.FALSE to specify
           local ip address";
      }
      leaf local-ip-address {
        // NCS drop when statement
        type inet:ip-address-no-zone;
        description
          "Local ip address for neighbor";
      }
    }
  }

  grouping live_ncs_AS-OVERRIDE {
    description
      "Common node of neighbor-group-af, neighbor-af,
       vrf-neighbor-af, af-group-af";
    leaf as-override {
      type boolean;
      // NCS drop default statement
      description
        "TRUE to override matching AS-number while
         sending update. FALSE to prevent as-override
         from being inherited from the parent";
    }
  }

  grouping live_ncs_IGNORE-CONNECTED-CHECK-EBGP {
    description
      "Common node of neighbor-group-af, neighbor-af,
       vrf-neighbor-af, af-group-afCommon node of
       neighbor-group, neighbor, vrf-neighbor,
       session-group";
    leaf ignore-connected-check-ebgp {
      type boolean;
      description
        "TRUE to disable the connected nexthop check for
         this peer.FALSE to enable the connected nexthop
         check for this peer.";
    }
  }

  grouping live_ncs_REMOTE-AS-LIST {
    description
      "Common node of neighbor-group, neighbor,
       vrf-neighbor, session-group";
    leaf remote-as-list {
      type string;
      description
        "Remote-as-list group name";
    }
  }

  grouping live_ncs_SEND-MULTICAST-ATTR {
    description
      "Common node of neighbor-group-af, neighbor-af,
       af-group-af";
    leaf send-multicast-attr {
      type Bgp-send-mcast-attr-cfg;
      description
        "Config send multicast attribute for this
         neighbor";
    }
  }

  grouping live_ncs_ENCAPSULATION-TYPE {
    description
      "Common node of neighbor-group-af, neighbor-af,
       af-group-afCommon node of neighbor-group-af,
       neighbor-af, vrf-neighbor-af, af-group-af";
    leaf encapsulation-type {
      type Bgp-af-encapsulation;
      description
        "Encapsulation type for this neighbor";
    }
  }

  grouping live_ncs_LOCAL-ADDRESS-SUB-NET {
    description
      "Common node of neighbor-group, neighbor,
       vrf-neighbor, session-group";
    container local-address-sub-net {
      description
        "Local Address subnet of routing updates";
      leaf local-addresss-subnet {
        type inet:ip-address-no-zone;
        description
          "local address subnet ip address ";
      }
      leaf prefix-len {
        type uint32 {
          range "0..128";
        }
        description
          "prefix length";
      }
    }
  }

  grouping live_ncs_ADVERTISE-BRIDGE-DOMAIN-IMP-DISABLE-V4 {
    description
      "Common node of neighbor-group-af, neighbor-af,
       vrf-neighbor-af, af-group-af";
    container advertise-bridge-domain-imp-disable-v4 {
      description
        "Disable Advertise Of VRF EVPN Extranet Imported
         Routes";
      leaf af-name {
        type dt1:Bgp-address-family;
        // NCS drop must statement
        description
          "Address family";
      }
      leaf adv-option {
        type Bgp-reorg-opt;
        // NCS drop must statement
        description
          "Advertise option";
      }
      leaf rt-type {
        type Bgp-adv-rt;
        // NCS drop must statement
        description
          "RT type";
      }
    }
  }

  grouping live_ncs_OPTIMAL-ROUTE-REFLECTOR-GROUP-TABLE {
    description
      "Common node of global-af, vrf-global-af";
    container optimal-route-reflector-groups {
      description
        "Table of multiple ORR groups";
      list optimal-route-reflector-group {
        key "group-name";
        description
          "Optimal Route Reffelctor group. Each such group
           is equivalent to an IGP area";
        leaf group-name {
          type xr:Cisco-ios-xr-string;
          description
            "Name of the ORR group";
        }
        leaf primary-root-address {
          type inet:ip-address-no-zone;
          description
            "Primary Root for the ORR group";
        }
        leaf secondary-root-address {
          type inet:ip-address-no-zone;
          description
            "Secondary Root for the ORR group";
        }
        leaf tertiary-root-address {
          type inet:ip-address-no-zone;
          description
            "Tertiary Root for the ORR group";
        }
      }
    }
  }

  grouping live_ncs_ADVERTISE-BRIDGE-DOMAIN-IMP-DISABLE-V6 {
    description
      "Common node of global-af, vrf-global-afCommon
       node of neighbor-group-af, neighbor-af,
       vrf-neighbor-af, af-group-af";
    container advertise-bridge-domain-imp-disable-v6 {
      description
        "Disable Advertise Of VRF EVPN Extranet Imported
         Routes";
      leaf af-name {
        type dt1:Bgp-address-family;
        // NCS drop must statement
        description
          "Address family";
      }
      leaf adv-option {
        type Bgp-reorg-opt;
        // NCS drop must statement
        description
          "Advertise option";
      }
      leaf rt-type {
        type Bgp-adv-rt;
        // NCS drop must statement
        description
          "RT type";
      }
    }
  }

  grouping live_ncs_ADVERTISE-PERMANENT-NETWORK {
    description
      "Common node of neighbor-group-af, neighbor-af,
       vrf-neighbor-af, af-group-af";
    leaf advertise-permanent-network {
      type empty;
      description
        "Advertise Permanent Networks to the peer";
    }
  }

  grouping live_ncs_BEST-PATH-COST-COMMUNITY {
    description
      "Common node of global, vrf-global";
    leaf best-path-cost-community {
      type empty;
      description
        "Change default route selection criteria to
         ignore cost community comparison";
    }
  }

  grouping live_ncs_RPKI-BESTPATH-ORIGIN-AS-ALLOW-INVALID {
    description
      "Common node of neighbor-group-af, neighbor-af,
       vrf-neighbor-af, af-group-af";
    leaf rpki-bestpath-origin-as-allow-invalid {
      type empty;
      description
        "RPKI bestpath origin-AS allow invalid";
    }
  }

  grouping live_ncs_BGP-CFG-RPKI-BESTPATH-ORIGIN-AS-ALLOW-INVALID {
    description
      "Common node of neighbor-group-af, neighbor-af,
       vrf-neighbor-af, af-group-afCommon node of
       neighbor-group, neighbor, vrf-neighbor,
       session-group";
    leaf rpki-bestpath-origin-as-allow-invalid {
      type empty;
      description
        "RPKI bestpath origin-AS allow invalid";
    }
  }

  grouping live_ncs_BGP-CFG-RPKI-BESTPATH-ORIGIN-AS-ALLOW-INVALID-MP {
    description
      "Common node of neighbor-group-af, neighbor-af,
       vrf-neighbor-af, af-group-afCommon node of
       neighbor-group, neighbor, vrf-neighbor,
       session-groupCommon node of global-af,
       vrf-global-af";
    leaf rpki-bestpath-origin-as-allow-invalid {
      type empty;
      description
        "RPKI bestpath origin-AS allow invalid";
    }
  }

  grouping live_ncs_NEIGHBOR-GRACEFUL-RESTART-TIME {
    description
      "Common node of neighbor-group, neighbor,
       vrf-neighbor, session-group";
    leaf neighbor-graceful-restart-time {
      type uint32 {
        range "1..4095";
      }
      units "second";
      // NCS drop default statement
      description
        "Restart time advertised to neighbor";
    }
  }

  grouping live_ncs_TOS {
    description
      "Common node of neighbor-group, neighbor,
       vrf-neighbor, session-group";
    container tos {
      description
        "TOS (Type Of Service)";
      leaf type {
        type dt1:Bgp-tos;
        description
          "Set type of service";
      }
      leaf value {
        type dt1:Bgp-precedence-dscp;
        description
          "TOS value to set";
      }
    }
  }

  grouping live_ncs_NEIGHBOR-CLUSTER-ID {
    description
      "Common node of neighbor-group, neighbor,
       vrf-neighbor, session-group";
    container neighbor-cluster-id {
      description
        "Neighbor Cluster-id";
      leaf cluster-id-number {
        type uint32 {
          range "1..4294967295";
        }
        description
          "Route-Reflector Cluster ID as 32 bit quantity";
      }
      leaf cluster-id-address {
        type inet:ipv4-address-no-zone;
        description
          "Route-Reflector Cluster ID in IPV4 address
           format";
      }
    }
  }

  grouping live_ncs_ACTIVATE {
    description
      "Common node of neighbor-af, vrf-neighbor-af,
       neighbor-group-af";
    leaf activate {
      type empty;
      description
        "Activate an address family for this neighbor.
         Deletion of this object causes deletion of all
         the objects under
         NeighborAF/VRFNeighborAF/NeighborGroupAF
         associated with this object.";
    }
  }

  grouping live_ncs_NEXT-HOP-SELF {
    description
      "Common node of neighbor-group-af, neighbor-af,
       vrf-neighbor-af, af-group-af";
    leaf next-hop-self {
      type boolean;
      description
        "Disable the next hop calculation and  insert
         your own address in the nexthop field of
         advertised routes you learned from the neighbor.";
    }
  }

  grouping live_ncs_ALLOW-AS-IN {
    description
      "Common node of neighbor-group-af, neighbor-af,
       vrf-neighbor-af, af-group-af";
    leaf allow-as-in {
      type uint32 {
        range "1..10";
      }
      // NCS drop default statement
      description
        "Allow as-path with my AS present in it";
    }
  }

  grouping live_ncs_ADVERTISE-LOCAL-V4 {
    description
      "Common node of neighbor-group-af, neighbor-af,
       vrf-neighbor-af, af-group-af";
    container advertise-local-v4 {
      description
        "Advertise Of Local Routes to the peer with
         different RT";
      leaf af-name {
        type dt1:Bgp-address-family;
        description
          "Address family";
      }
      leaf reorg-option {
        type Bgp-reorg-opt;
        description
          "Reorigination option";
      }
      leaf rt-type {
        type Bgp-adv-rt;
        description
          "RT type";
      }
    }
  }

  grouping live_ncs_ADVERTISE-LOCAL-V6 {
    description
      "Common node of neighbor-group-af, neighbor-af,
       vrf-neighbor-af, af-group-af";
    container advertise-local-v6 {
      description
        "Advertise Of Local Routes to the peer with
         different RT";
      leaf af-name {
        type dt1:Bgp-address-family;
        description
          "Address family";
      }
      leaf reorg-option {
        type Bgp-reorg-opt;
        description
          "Reorigination option";
      }
      leaf rt-type {
        type Bgp-adv-rt;
        description
          "RT type";
      }
    }
  }

  grouping live_ncs_BEST-EXTERNAL {
    description
      "Common node of global-af, vrf-global-af";
    leaf best-external {
      type boolean;
      description
        "TRUE to enable BE FALSE to disable BE
         inheritance from a parent";
    }
  }

  grouping live_ncs_ATTRIBUTE-DOWNLOAD {
    description
      "Common node of global-af, vrf-global-af";
    leaf attribute-download {
      type empty;
      description
        "Attribute download configuration";
    }
  }

  grouping live_ncs_AO-KEYCHAIN {
    description
      "Common node of neighbor-group, neighbor,
       vrf-neighbor, session-group";
    container ao-keychain {
      description
        "Set or disable AO based authentication";
      leaf ao-keychain-disable {
        type boolean;
        description
          "TRUE to prevent this entity from having AO
           keychain based authentication even if the
           parent has one.FALSE to enable AO keychain
           based authentication";
      }
      leaf ao-keychain-name {
        // NCS drop when statement
        type string;
        description
          "Name of the AO keychain associated with this
           neighbor";
      }
      leaf ao-include-tcp-options {
        // NCS drop when statement
        type boolean;
        description
          "Include TCP options header with AO";
      }
      leaf ao-accept-mismatch-connection {
        // NCS drop when statement
        type boolean;
        description
          "Accept new connections even though AO
           mismatched";
      }
    }
  }

  grouping live_ncs_ADDITIONAL-PATHS-SELECTION {
    description
      "Common node of global-af, vrf-global-af";
    container additional-paths-selection {
      description
        "Configure additional paths selection";
      leaf selection {
        type dt1:Bgp-af-additional-paths-cfg;
        description
          "Enable/disable selection ";
      }
      leaf route-policy-name {
        type string;
        description
          "Route policy for selection";
      }
    }
  }

  grouping live_ncs_NEIGHBOR-AF-LONG-LIVED-GRACEFUL-RESTART-CAPABLE {
    description
      "Common node of neighbor-group-af, neighbor-af,
       vrf-neighbor-af, af-group-af";
    leaf neighbor-af-long-lived-graceful-restart-capable {
      type boolean;
      // NCS drop default statement
      description
        "TRUE to treat neighbor as Long-lived
         Graceful-restart capable. FALSE to rely on
         capability negotiation.";
    }
  }

  grouping live_ncs_BEST-PATH-AS-MULTIPATH-RELAX {
    description
      "Common node of global, vrf-global";
    leaf best-path-as-multipath-relax {
      type empty;
      description
        "Change default multi-route selection criteria to
         relax as-path checking - only require same
         aspath length";
    }
  }

  grouping live_ncs_UNSAFE-EBGP-POLICY {
    description
      "Common node of global, vrf-global";
    leaf unsafe-ebgp-policy {
      type empty;
      description
        "If eBGP neighbor is configured without a
         route-policy,the routes from that neighbor are
         not accepted by default.This knob overrides the
         default behavior. When configured,routes from
         the eBGP neighbors with no policy are accepted.";
    }
  }

  grouping live_ncs_GLOBAL-TIMERS {
    description
      "Common node of global, vrf-global";
    container global-timers {
      description
        "Adjust routing timers.";
      leaf keepalive {
        type uint32 {
          range "0..65535";
        }
        units "second";
        // NCS drop default statement
        description
          "Keepalive interval (seconds)";
      }
      leaf hold-time {
        type uint32 {
          range "0..65535";
        }
        units "second";
        // NCS drop default statement
        description
          "Hold time (seconds).  Specify 0 to disable
           keepalives/hold time";
      }
      leaf min-accept-hold-time {
        type uint32 {
          range "0..65535";
        }
        units "second";
        // NCS drop default statement
        description
          "Minimum acceptable hold time (seconds). Specify
           0 to disable keepalives/hold time";
      }
    }
  }

  grouping live_ncs_NEIGHBOR-GROUP-ADD-MEMBER {
    description
      "Common node of neighbor, vrf-neighbor";
    leaf neighbor-group-add-member {
      type string;
      description
        "Inherit configuration from a neighbor-group";
    }
  }

  grouping live_ncs_MOBILE-ROUTES {
    description
      "Common node of global-af, vrf-global-af";
    container mobile-routes {
      presence "enable mobile-routes";
      description
        "Redistribute mobile routes";
      leaf default-metric {
        type Bgp-default-metric-range;
        description
          "Default metric";
      }
      leaf route-policy-name {
        type string;
        description
          "Route policy name";
      }
      leaf not-used {
        type uint32 {
          range "0..127";
        }
        description
          "Not used";
      }
    }
  }

  grouping live_ncs_LOCAL-PREFERENCE {
    description
      "Common node of global, vrf-global";
    leaf local-preference {
      type uint32 {
        range "0..4294967295";
      }
      // NCS drop default statement
      description
        "Configure default local preference";
    }
  }

  grouping live_ncs_CREATE {
    description
      "Common node of neighbor-group, session-group";
    leaf create {
      type empty;
      description
        "Create this group. Deletion of this object
         causes deletion of all the objects under
         NeighborGroup/SessionGroup associated with this
         object.";
    }
  }

  grouping live_ncs_EBGP-SEND-DMZ-ENABLE-MODES {
    description
      "Common node of neighbor-group, neighbor,
       vrf-neighbor, session-group";
    leaf ebgp-send-dmz-enable-modes {
      type Bgp-ebgp-send-dmz-enable-mode;
      description
        "Default mode, Cumulative mode or Disable to
         prevent inheritance from a parent";
    }
  }

  grouping live_ncs_SEND-SOCKET-BUFFER-SIZES {
    description
      "Common node of global, vrf-global";
    container send-socket-buffer-sizes {
      description
        "set socket parameters";
      leaf socket-send-size {
        type uint32 {
          range "4096..131072";
        }
        units "byte";
        // NCS drop default statement
        description
          "Send socket buffer size in bytes";
      }
      leaf bgp-send-size {
        type uint32 {
          range "4096..131072";
        }
        units "byte";
        // NCS drop default statement
        description
          "BGP Write buffer size in bytes";
      }
    }
  }

  grouping live_ncs_RECEIVE-SOCKET-BUFFER-SIZES {
    description
      "Common node of global, vrf-globalCommon node of
       global, vrf-global";
    container receive-socket-buffer-sizes {
      description
        "Set socket and BGP receive buffer sizes";
      leaf socket-receive-size {
        type uint32 {
          range "512..131072";
        }
        units "byte";
        // NCS drop default statement
        description
          "Receive socket buffer size in bytes";
      }
      leaf bgp-receive-size {
        type uint32 {
          range "512..131072";
        }
        units "byte";
        // NCS drop default statement
        description
          "BGP Read buffer size in bytes";
      }
    }
  }

  grouping live_ncs_BFD-ENABLE-MODES {
    description
      "Common node of neighbor-group, neighbor,
       vrf-neighbor, session-group";
    leaf bfd-enable-modes {
      type Bgp-bfd-enable-mode;
      description
        "Strict mode, Default mode or Disable to prevent
         inheritance from a parent";
    }
  }

  grouping live_ncs_RESET-WEIGHT-ON-IMPORT {
    description
      "Common node of global-af, vrf-global-af";
    leaf reset-weight-on-import {
      type boolean;
      description
        "TRUE to reset weight on import. FALSE to not
         reset and to prevent inheritance from a parent";
    }
  }

  grouping live_ncs_AGGREGATE-ADDRESS-TABLE {
    description
      "Common node of global-af, vrf-global-af";
    container aggregate-addresses {
      description
        "Configure BGP aggregate entries";
      list aggregate-address {
        key "aggregate-addr aggregate-prefix";
        description
          "Aggregate address configuration";
        leaf aggregate-addr {
          type inet:ip-address;
          description
            "Aggregate in prefix/length format (address
             part)";
        }
        leaf aggregate-prefix {
          type uint16 {
            range "0..128";
          }
          description
            "Aggregate in prefix/length format (prefix
             part)";
        }
        leaf generate-set-info {
          type boolean;
          description
            "TRUE to generate AS set path information,
             FALSE otherwise";
        }
        leaf generate-confederation-set-info {
          type boolean;
          description
            "TRUE to generate AS confederation set path
             information, FALSE otherwise";
        }
        leaf summary-only {
          type boolean;
          description
            "TRUE to filter more specific routes from
             updates, FALSEotherwise";
        }
        leaf route-policy-name {
          type string;
          description
            "Route policy on which to condition
             advertisement, suppression, and attributes";
        }
      }
    }
  }

  grouping live_ncs_EBGP-MULTIHOP {
    description
      "Common node of neighbor-group, neighbor,
       vrf-neighbor, session-group";
    container ebgp-multihop {
      description
        "Allow EBGP neighbors not on directly connected
         networks";
      leaf max-hop-count {
        type uint32 {
          range "1..255";
        }
        // NCS drop default statement
        description
          "Maximum hop count";
      }
      leaf mpls-deactivation {
        type boolean;
        // NCS drop default statement
        description
          "TRUE to not enable MPLS and NULL rewrite.";
      }
    }
  }

  grouping live_ncs_MERGE-SAFI1-AND4-INBOUND-UPDATES {
    description
      "Common node of neighbor-group, neighbor,
       vrf-neighbor, session-group";
    leaf merge-safi1-and4-inbound-updates {
      type boolean;
      description
        "TRUE to merge updates FALSE to not merge updates
         and to prevent inheritance from a parent";
    }
  }

  grouping live_ncs_NEIGHBOR-GRACEFUL-RESTART-STALEPATH-TIME {
    description
      "Common node of neighbor-group, neighbor,
       vrf-neighbor, session-group";
    leaf neighbor-graceful-restart-stalepath-time {
      type uint32 {
        range "1..4095";
      }
      units "second";
      // NCS drop default statement
      description
        "Maximum time to wait for restart of GR capable
         peer";
    }
  }

  grouping live_ncs_NEXT-HOP-RES-ALLOW-DEFAULT {
    description
      "Common node of neighbor-group, neighbor,
       vrf-neighbor, session-groupCommon node of global,
       vrf-global";
    leaf next-hop-res-allow-default {
      type empty;
      description
        "Enable path resolution for nexthops using
         default route";
    }
  }

  grouping live_ncs_BEST-PATH-AIGP-IGNORE {
    description
      "Common node of global, vrf-global";
    leaf best-path-aigp-ignore {
      type empty;
      description
        "Change default route selection criteria to
         ignore AIGP unless both paths whichare compared
         have AIGP attribute";
    }
  }

  grouping live_ncs_SESSION-GROUP-ADD-MEMBER {
    description
      "Common node of neighbor-group, neighbor,
       vrf-neighbor";
    leaf session-group-add-member {
      type string;
      description
        "Inherit address-family independent config from a
         session-group";
    }
  }

  grouping live_ncs_BFD-MULTIPLIER {
    description
      "Common node of neighbor-group, neighbor,
       vrf-neighbor, session-group";
    leaf bfd-multiplier {
      type uint32 {
        range "2..16";
      }
      description
        "Detection multiplier for BFD sessions created by
         BGP";
    }
  }

  grouping live_ncs_FLOWSPEC-VALIDATION {
    description
      "Common node of neighbor-group-af, neighbor-af,
       vrf-neighbor-af, af-group-af";
    leaf flowspec-validation {
      type Bgp-flowspec-validation-cfg;
      description
        "Config Flowspec validation for this neighbor";
    }
  }

  grouping live_ncs_TTL-SECURITY {
    description
      "Common node of neighbor-group, neighbor,
       vrf-neighbor, session-group";
    leaf ttl-security {
      type boolean;
      description
        "TRUE to enable BGP TTL Security.  FALSE to not
         enable it and to prevent inheritance from a
         parent";
    }
  }

  grouping live_ncs_BEST-PATH-MED-ALWAYS {
    description
      "Common node of global, vrf-global";
    leaf best-path-med-always {
      type empty;
      description
        "Change default route selection criteria and
         allow comparing of MED from different neighbors";
    }
  }

  grouping live_ncs_MAX-PEERS {
    description
      "Common node of neighbor-group, neighbor,
       vrf-neighbor, session-group";
    leaf max-peers {
      type uint32 {
        range "1..4096";
      }
      description
        "Set Maximum Peers in Dynamic Range";
    }
  }

  grouping live_ncs_SEND-COMMUNITY-EBGP-GRACEFUL-SHUTDOWN {
    description
      "Common node of neighbor-group-af, neighbor-af,
       vrf-neighbor-af, af-group-af";
    leaf send-community-ebgp-graceful-shutdown {
      type boolean;
      description
        "TRUE to send communities to the external
         neighbor/neighbor-group/af-group.  FALSE not to
         send and to prevent inheritance from a parent";
    }
  }

  grouping live_ncs_DISABLE-MSG-LOG {
    description
      "Common node of global, vrf-global";
    leaf disable-msg-log {
      type empty;
      description
        "Disable inbound and outbound messagelogging for
         all neighbors under the vrf";
    }
  }

  grouping live_ncs_LOCAL-AS {
    description
      "Common node of neighbor-group, neighbor,
       vrf-neighbor, session-group";
    container local-as {
      description
        "Specify a local-as number";
      leaf as-xx {
        type dt1:Bgp-as-range;
        // NCS drop must statement
        description
          "xx of AS number xx.yy";
      }
      leaf as-yy {
        type dt1:Bgp-as-range;
        // NCS drop must statement
        description
          "yy of AS number xx.yy";
      }
      leaf no-prepend {
        type empty;
        // NCS drop must statement
        description
          "Do not prepend Local AS to announcements from
           this neighbor";
      }
      leaf disable {
        type empty;
        // NCS drop must statement
        description
          "Disable Local AS and prevent it from being
           inherited from a parent";
      }
      leaf replace-as {
        type empty;
        // NCS drop must statement
        description
          "Prepend only Local AS to announcements from
           this neighbor";
      }
      leaf dual-as {
        type empty;
        // NCS drop must statement
        description
          "Dual-AS mode";
      }
    }
  }

  grouping live_ncs_LISP-ROUTES {
    description
      "Common node of global-af, vrf-global-af";
    container lisp-routes {
      presence "enable lisp-routes";
      description
        "Redistribute lisp routes";
      leaf default-metric {
        type Bgp-default-metric-range;
        description
          "Default metric";
      }
      leaf route-policy-name {
        type string;
        description
          "Route policy name";
      }
    }
  }

  grouping live_ncs_ADDITIONAL-PATHS-SEND-CAPABILITY {
    description
      "Common node of neighbor-group, neighbor,
       vrf-neighbor, session-group";
    leaf additional-paths-send-capability {
      type dt1:Bgp-nbr-cap-additional-paths-cfg;
      description
        "Advertise additional paths Send capability";
    }
  }

  grouping live_ncs_BEST-PATH-IGP-METRIC-IGNORE {
    description
      "Common node of global, vrf-global";
    leaf best-path-igp-metric-ignore {
      type empty;
      description
        "Change default route selection criteria to
         ignore IGP Metric ";
    }
  }

  grouping live_ncs_L2VPN-SIGNALLING {
    description
      "Common node of neighbor-group-af, neighbor-af,
       af-group-af";
    leaf l2vpn-signalling {
      type Bgp-signal;
      description
        "Disable signalling type on the peer";
    }
  }

  grouping live_ncs_DAMPENING {
    description
      "Common node of global-af, vrf-global-af";
    container dampening {
      presence "enable dampening";
      description
        "Enable route-flap dampening";
      leaf half-life {
        type uint32 {
          range "1..45";
        }
        units "minute";
        description
          "Half-life time for the penalty (minutes).";
      }
      leaf reuse-threshold {
        type uint32 {
          range "1..20000";
        }
        description
          "Value to start reusing a route.";
      }
      leaf suppress-threshold {
        type uint32 {
          range "1..20000";
        }
        description
          "Value to start suppressing a route.";
      }
      leaf suppress-time {
        type uint32 {
          range "1..255";
        }
        units "second";
        description
          "Maximum duration to suppress a stable route
           (seconds).";
      }
      leaf route-policy-name {
        type string;
        description
          "Route policy to specify criteria for dampening.
           This cannot be specified if any other
           parameters are specified.";
      }
    }
  }

  grouping live_ncs_ADVERTISE-LOCAL-LABELED-ROUTE-SAFI-UNICAST {
    description
      "Common node of global-af, vrf-global-af";
    leaf advertise-local-labeled-route-safi-unicast {
      type dt1:Bgp-advertise-local-labeled-route-cfg;
      description
        "Enable/disable advertisement of routes with
         local-label via Unicast SAFI";
    }
  }

  grouping live_ncs_SUBSCRIBER-ROUTES {
    description
      "Common node of global-af, vrf-global-af";
    container subscriber-routes {
      presence "enable subscriber-routes";
      description
        "Redistribute subscriber routes";
      leaf default-metric {
        type Bgp-default-metric-range;
        description
          "Default metric";
      }
      leaf route-policy-name {
        type string;
        description
          "Route policy name";
      }
      leaf not-used {
        type uint32 {
          range "0..127";
        }
        description
          "Not used";
      }
    }
  }

  grouping live_ncs_INTERNAL-VPN-CLIENT-IBGP-CE {
    description
      "Common node of neighbor-group, neighbor,
       vrf-neighbor, session-group";
    leaf internal-vpn-client-ibgp-ce {
      type boolean;
      description
        "TRUE to preserve the CE path attributes.FALSE to
         override CE path attributes.";
    }
  }

  grouping live_ncs_ACCEPT-ROUTE-LEGACY-RT {
    description
      "Common node of neighbor-group-af, neighbor-af,
       vrf-neighbor-af, af-group-af";
    leaf accept-route-legacy-rt {
      type boolean;
      description
        "TRUE to configure as a accept-route-legacy-RT.
         FALSE to prevent accept-route-legacy-RT from
         being inherited.";
    }
  }

  grouping live_ncs_PERMANENT-NETWORK {
    description
      "Common node of global-af, vrf-global-af";
    leaf permanent-network {
      type string;
      description
        "Route policy for permanent networks";
    }
  }

  grouping live_ncs_ENABLE {
    description
      "Common node of global-af, vrf-global-af";
    leaf enable {
      type empty;
      description
        "Enable the address family. Deletion of this
         object causes deletion of all the objects under
         GlobalAF/VRFGlobalAF associated with this object
         .";
    }
  }

  grouping live_ncs_EBGP-RECV-DMZ {
    description
      "Common node of neighbor-group, neighbor,
       vrf-neighbor, session-group";
    leaf ebgp-recv-dmz {
      type boolean;
      description
        "TRUE to receive DMZ link bandwidth from ebgp
         peer. FALSE to not receive from ebgp peer and to
         prevent inheritance from a parent";
    }
  }

  grouping live_ncs_ADVERTISEMENT-INTERVAL {
    description
      "Common node of neighbor-group, neighbor,
       vrf-neighbor, session-group";
    container advertisement-interval {
      presence "Indicates a advertisement-interval node is configured.";
      description
        "Minimum interval between sending BGP routing
         updates";
      leaf minimum-interval {
        type uint32 {
          range "0..600";
        }
        units "second";
        // NCS drop mandatory statement
        description
          "Minimum advertisement interval time, secs part";
      }
      leaf minimum-interval-msecs {
        type uint32 {
          range "0..999";
        }
        units "millisecond";
        description
          "Minimum advertisement interval time, msecs part";
      }
    }
  }

  grouping live_ncs_RPKI-ORIGIN-AS-VALIDITY-SIGNAL-IBGP {
    description
      "Common node of global-af, vrf-global-af";
    leaf rpki-origin-as-validity-signal-ibgp {
      type empty;
      description
        "RPKI origin-AS validity signal ibgp";
    }
  }

  grouping live_ncs_BGP-CFG-RPKI-ORIGIN-AS-VALIDITY-SIGNAL-IBGP {
    description
      "Common node of global-af, vrf-global-afCommon
       node of global, vrf-global";
    leaf rpki-origin-as-validity-signal-ibgp {
      type empty;
      description
        "RPKI origin-AS validity signal ibgp";
    }
  }

  grouping live_ncs_IMPORT {
    description
      "Common node of neighbor-group-af, neighbor-af,
       vrf-neighbor-af, af-group-af";
    container import {
      description
        "Import Reorigination options for Routes from the
         peer";
      leaf import-stitching {
        type boolean;
        description
          "TRUE to Import with Stitching RTs, FALSE to
           Import with normal RTs";
      }
      leaf import-reoriginate {
        type boolean;
        description
          "TRUE to Reoriginate imported routes, FALSE to
           not Reoriginate imported routes - not supported";
      }
      leaf import-reoriginate-stitching {
        type boolean;
        description
          "TRUE to Reoriginate imported routes with
           Stitching RTs, FALSE to Reoriginate imported
           routes with normal RTs";
      }
    }
  }

  grouping live_ncs_ACCEPT-OWN {
    description
      "Common node of neighbor-group-af, neighbor-af,
       vrf-neighbor-af, af-group-af";
    leaf accept-own {
      type boolean;
      description
        "Handle self-originated routes with Accept-Own
         community. Valid for following neighbor
         address-families: VPNv4Unicast, VPNv6Unicast.";
    }
  }

  grouping live_ncs_ADDITIONAL-PATHS-RECEIVE {
    description
      "Common node of global-af, vrf-global-af";
    leaf additional-paths-receive {
      type dt1:Bgp-af-additional-paths-cfg;
      description
        "Advertise additional paths Receive capability";
    }
  }

  grouping live_ncs_MPLS-ACTIVATED-INTERFACE-TABLE {
    description
      "Common node of global, vrf-global";
    container mpls-activated-interfaces {
      description
        "Configure list of MPLS activated interfaces";
      list mpls-activated-interface {
        key "interface-name";
        description
          "Configure a MPLS activated interface";
        leaf interface-name {
          type xr:Interface-name;
          description
            "Interface Name";
        }
      }
    }
  }

  grouping live_ncs_MULTIPATH {
    description
      "Common node of neighbor-group-af, neighbor-af,
       vrf-neighbor-af, af-group-af";
    leaf multipath {
      type empty;
      description
        "Allow paths from this neighbor to be eligible
         for selective multipath";
    }
  }

  grouping live_ncs_EIGRP-ROUTE-TABLE {
    description
      "Common node of global-af, vrf-global-af";
    container eigrp-routes {
      description
        "Redistribute information for EIGRP routes.";
      list eigrp-route {
        key "instance-name";
        description
          "Redistribute EIGRP routes";
        leaf instance-name {
          type xr:Cisco-ios-xr-string;
          description
            "EIGRP router tag";
        }
        leaf default-metric {
          type Bgp-default-metric-range;
          description
            "Default metric";
        }
        leaf route-policy-name {
          type string;
          description
            "Route policy name";
        }
        leaf redist-type {
          type xr:Hex-integer;
          description
            "Redistribution type: 01 for internal routes,
             02 for external routes, Logical combinations
             permitted.";
        }
      }
    }
  }

  grouping live_ncs_OPTIMAL-ROUTE-REFLECTION-GROUP {
    description
      "Common node of global-af, vrf-global-afCommon
       node of neighbor-group-af, neighbor-af,
       vrf-neighbor-af, af-group-af";
    leaf optimal-route-reflection-group {
      type string;
      description
        "Name of the ORR group this neighbor is going to
         be part of";
    }
  }

  grouping live_ncs_ROUTE-REFLECTOR-CLIENT {
    description
      "Common node of neighbor-group-af, neighbor-af,
       vrf-neighbor-af, af-group-af";
    leaf route-reflector-client {
      type boolean;
      description
        "TRUE to configure as a route-reflector-client.
         FALSE to prevent route-reflector-client from
         being inherited.";
    }
  }

  grouping live_ncs_ADVERTISE-LOCAL-LABELED-ROUTE {
    description
      "Common node of neighbor-group-af, neighbor-af,
       vrf-neighbor-af, af-group-af";
    leaf advertise-local-labeled-route {
      type dt1:Bgp-advertise-local-labeled-route-cfg;
      description
        "Enable/disable advertisement of routes with
         local-label";
    }
  }

  grouping live_ncs_SESSION-OPEN-MODE {
    description
      "Common node of neighbor-group, neighbor,
       vrf-neighbor, session-group";
    leaf session-open-mode {
      type Bgp-tcp-mode;
      // NCS drop default statement
      description
        "TCP mode to be used to establish BGP session";
    }
  }

  grouping live_ncs_RPKI-ORIGIN-AS-VALIDATION-ENABLE {
    description
      "Common node of global-af, vrf-global-af";
    leaf rpki-origin-as-validation-enable {
      type empty;
      description
        "RPKI origin-AS validation enable";
    }
  }

  grouping live_ncs_UPDATE-OUT-ORIG-LOOP-CHK-DISABLE {
    description
      "Common node of neighbor-group-af, neighbor-af,
       vrf-neighbor-af, af-group-af";
    leaf update-out-orig-loop-chk-disable {
      type empty;
      description
        "Enable/disable Originator loop check for this
         neighbor-group/af-group";
    }
  }

  grouping live_ncs_STATIC-ROUTES {
    description
      "Common node of global-af, vrf-global-af";
    container static-routes {
      presence "enable static-routes";
      description
        "Redistribute static routes";
      leaf default-metric {
        type Bgp-default-metric-range;
        description
          "Default metric";
      }
      leaf route-policy-name {
        type string;
        description
          "Route policy name";
      }
      leaf not-used {
        type uint32 {
          range "0..127";
        }
        description
          "Not used";
      }
    }
  }

  grouping live_ncs_PASSWORD {
    description
      "Common node of neighbor-group, neighbor,
       vrf-neighbor, session-group";
    container password {
      description
        "Set or disable a password";
      leaf password-disable {
        type boolean;
        description
          "TRUE to prevent this entity from having a
           password even if the parent has one.  FALSEto
           specify a password";
      }
      leaf password {
        // NCS drop when statement
        type xr:Proprietary-password;
        description
          "The neighbor password.  Leave unspecified when
           disabling the password.";
      }
    }
  }

  grouping live_ncs_NEXT-HOP-UNCHANGED-MULTIPATH {
    description
      "Common node of neighbor-group, neighbor,
       vrf-neighbor, session-groupCommon node of
       neighbor-group-af, neighbor-af, vrf-neighbor-af,
       af-group-af";
    leaf next-hop-unchanged-multipath {
      type boolean;
      description
        "TRUE to disable overwriting of next hop for
         multipaths. FALSE to prevent next-hop-unchanged
         for multipaths.";
    }
  }

  grouping live_ncs_NEXT-HOP-RESOLUTION-PREFIX-LENGTH-MINIMUM {
    description
      "Common node of global-af, vrf-global-af";
    leaf next-hop-resolution-prefix-length-minimum {
      type uint32 {
        range "0..128";
      }
      // NCS drop default statement
      description
        "Minimum prefix-length for nexthop resolution";
    }
  }

  grouping live_ncs_BEST-PATH-AS-PATH-LENGTH {
    description
      "Common node of global, vrf-global";
    leaf best-path-as-path-length {
      type empty;
      description
        "Change default route selection criteria to
         ignore AS path length";
    }
  }

  grouping live_ncs_MSG-LOG-OUT {
    description
      "Common node of global, vrf-globalCommon node of
       neighbor-group, neighbor, vrf-neighbor,
       session-group";
    container msg-log-out {
      description
        "Message log outbound";
      leaf msg-buf-count {
        type uint32 {
          range "1..100";
        }
        description
          "Outbound message log buffer size";
      }
      leaf msg-log-disable {
        type boolean;
        description
          "Disable inbound message logging";
      }
      leaf msg-log-inherit-disable {
        type boolean;
        description
          "TRUE, to prevent this entity from having a
           outbound message logging if parent has one";
      }
    }
  }

  grouping live_ncs_ENFORCE-MULTIPLE-LABELS {
    description
      "Common node of neighbor-group-af, neighbor-af,
       vrf-neighbor-af, af-group-af";
    leaf enforce-multiple-labels {
      type boolean;
      description
        "TRUE to enforce multiple labels support.";
    }
  }

  grouping live_ncs_PREFIX-ORF-POLICY {
    description
      "Common node of neighbor-group-af, neighbor-af,
       vrf-neighbor-af, af-group-afCommon node of
       neighbor-group-af, neighbor-af, vrf-neighbor-af,
       af-group-af";
    leaf prefix-orf-policy {
      type string;
      description
        "Prefix ORF policy name for incoming updates";
    }
  }

  grouping live_ncs_SOURCED-NETWORK-TABLE {
    description
      "Common node of global-af, vrf-global-af";
    container sourced-networks {
      description
        "Specify a network to announce via BGP";
      list sourced-network {
        key "network-addr network-prefix";
        description
          "Sourced network configuration";
        leaf network-addr {
          type inet:ip-address;
          description
            "Network in prefix/length format (address part)";
        }
        leaf network-prefix {
          type uint16 {
            range "0..128";
          }
          description
            "Network in prefix/length format (prefix part)";
        }
        leaf backdoor {
          type boolean;
          description
            "Specify a BGP backdoor route, default is FALSE";
        }
        leaf route-policy-name {
          type string;
          description
            "Route policy name";
        }
      }
    }
  }

  grouping live_ncs_REMOVE-PRIVATE-AS-ENTIRE-AS-PATH {
    description
      "Common node of neighbor-group-af, neighbor-af,
       vrf-neighbor-af, af-group-af";
    container remove-private-as-entire-as-path {
      presence "Indicates a remove-private-as-entire-as-path node is configured.";
      description
        "Remove private AS number from outbound updates";
      leaf enable {
        type boolean;
        // NCS drop mandatory statement
        description
          "TRUE to remove private AS from outbound updates
           .  FALSE to prevent remove-private-AS from
           being inherited.";
      }
      leaf entire {
        type boolean;
        description
          "TRUE to remove private AS from outbound updates
           if all ASes in aspath areprivate. FALSE to
           prevent remove-private-ASfrom being inherited.";
      }
    }
  }

  grouping live_ncs_GRACEFUL-MAINTENANCE {
    description
      "Common node of neighbor-group, neighbor,
       vrf-neighbor, session-group";
    container graceful-maintenance {
      description
        "Graceful Maintenance mode";
      container graceful-maintenance-local-preference {
        description
          "Set Local Preference to advertise routes with";
        leaf gshut-loc-pref-disable {
          type boolean;
          description
            "TRUE, to prevent inheritance of Local Pref
             value from its parents.FALSE, otherwise";
        }
        leaf local-preference {
          type uint32 {
            range "0..4294967295";
          }
          description
            "Local Preference Value";
        }
      }
      container graceful-maintenance-as-prepends {
        description
          "Number of times to prepend local AS number to
           the AS path";
        leaf gshut-prepends-disable {
          type boolean;
          description
            "TRUE, to prevent inheritance of AS Prepends
             value from its parents.FALSE, otherwise";
        }
        leaf as-prepends {
          type uint32 {
            range "0..6";
          }
          description
            "number of times AS prepends";
        }
      }
      leaf enable {
        type empty;
        description
          "Enter Graceful Maintenance mode to configure
           parametrs";
      }
      leaf graceful-maintenance-activate {
        type boolean;
        description
          "Initiate the graceful shutdown procedure";
      }
    }
  }

  grouping live_ncs_NEIGHBOR-AF-LONG-LIVED-GRACEFUL-RESTART-STALE-TIME {
    description
      "Common node of neighbor-group-af, neighbor-af,
       vrf-neighbor-af, af-group-af";
    container neighbor-af-long-lived-graceful-restart-stale-time {
      description
        "Maximum time to wait before purging long lived
         routes";
      leaf stale-time-send {
        type uint32 {
          range "0..16777215";
        }
        units "second";
        // NCS drop default statement
        description
          "Max time (seconds)";
      }
      leaf stale-time-accept {
        type uint32 {
          range "0..16777215";
        }
        units "second";
        // NCS drop default statement
        description
          "Max time (seconds)";
      }
    }
  }

  grouping live_ncs_BFD {
    description
      "Common node of global, vrf-global";
    container bfd {
      description
        "BFD configuration";
      leaf detection-multiplier {
        type uint32 {
          range "2..16";
        }
        description
          "Detection multiplier for BFD sessions created
           by BGP";
      }
      leaf interval {
        type uint32 {
          range "3..30000";
        }
        units "millisecond";
        description
          "Hello interval for BFD sessions created by BGP";
      }
    }
  }

  grouping live_ncs_ALLOCATE-LABEL {
    description
      "Common node of global-af, vrf-global-af";
    container allocate-label {
      presence "enable allocate-label";
      description
        "Label allocation policy";
      leaf all {
        type boolean;
        description
          "Whether all nets should be labeled, default is
           FALSE";
      }
      leaf route-policy-name {
        type string;
        description
          "Route policy name";
      }
      leaf un-labeled-path {
        type boolean;
        // NCS drop must statement
        description
          "Allocate label for unlabeled paths too";
      }
    }
  }

  grouping live_ncs_SEND-BUFFER-SIZE {
    description
      "Common node of neighbor-group, neighbor,
       vrf-neighbor, session-group";
    container send-buffer-size {
      description
        "Set socket send buffer size and BGP write buffer
         size";
      leaf socket-send-size {
        type uint32 {
          range "4096..131072";
        }
        units "byte";
        // NCS drop default statement
        description
          "Send socket buffer size in bytes";
      }
      leaf bgp-send-size {
        type uint32 {
          range "4096..131072";
        }
        units "byte";
        // NCS drop default statement
        description
          "BGP write buffer size in bytes";
      }
    }
  }

  grouping live_ncs_BEST-PATH-MED-MISSING {
    description
      "Common node of neighbor-group, neighbor,
       vrf-neighbor, session-groupCommon node of global,
       vrf-global";
    leaf best-path-med-missing {
      type empty;
      description
        "Treat missing MED as the least preferred one";
    }
  }

  grouping live_ncs_SUPPRESS-ALL-CAPABILITIES {
    description
      "Common node of neighbor-group, neighbor,
       vrf-neighbor, session-group";
    leaf suppress-all-capabilities {
      type boolean;
      description
        "TRUE to suppress all capabilities. FALSE to not
         suppress and to prevent inheritance from a
         parent";
    }
  }

  grouping live_ncs_DEFAULT-WEIGHT {
    description
      "Common node of neighbor-group, neighbor,
       vrf-neighbor, session-groupCommon node of
       neighbor-group-af, neighbor-af, vrf-neighbor-af,
       af-group-af";
    leaf default-weight {
      type uint32 {
        range "0..65535";
      }
      description
        "Set default weight for routes from this
         neighbor/neighbor-group/af-group";
    }
  }

  grouping live_ncs_SUPPRESS-FOUR-BYTE-AS-CAPABILITY {
    description
      "Common node of neighbor-group, neighbor,
       vrf-neighbor, session-group";
    leaf suppress-four-byte-as-capability {
      type boolean;
      description
        "TRUE to suppress BGP 4-byte-as capability.
         FALSE to not suppress it and to prevent
         inheritance from a parent";
    }
  }

  grouping live_ncs_ADVERTISE-LOCAL-L2VPN-EVPN {
    description
      "Common node of neighbor-group-af, neighbor-af,
       vrf-neighbor-af, af-group-af";
    container advertise-local-l2vpn-evpn {
      description
        "Advertise Of Local Routes to the peer with
         different RT";
      leaf af-name {
        type dt1:Bgp-address-family;
        description
          "Address family";
      }
      leaf reorg-option {
        type Bgp-reorg-opt;
        description
          "Reorigination option";
      }
      leaf rt-type {
        type Bgp-adv-rt;
        description
          "RT type";
      }
    }
  }

  grouping live_ncs_EGRESS-PEER-ENGINEERING {
    description
      "Common node of neighbor-group, neighbor,
       vrf-neighbor, session-group";
    leaf egress-peer-engineering {
      type boolean;
      description
        "TRUE to enable egress peer engineering FALSE to
         disable egress peer engineering and to prevent
         inheritance from a parent";
    }
  }

  grouping live_ncs_BEST-PATH-CONFEDERATION-PATHS {
    description
      "Common node of global, vrf-global";
    leaf best-path-confederation-paths {
      type empty;
      description
        "Change default route selection criteria and
         allow the comparing of MED among confederation
         paths";
    }
  }

  grouping live_ncs_DYNAMIC-MED-INTERVAL {
    description
      "Common node of global-af, vrf-global-af";
    leaf dynamic-med-interval {
      type uint32 {
        range "0..10";
      }
      units "minute";
      // NCS drop default statement
      description
        "Update generation delay (in minutes) after a MED
         change";
    }
  }

  grouping live_ncs_REMOVE-PRIVATE-AS-ENTIRE-AS-PATH-INBOUND {
    description
      "Common node of neighbor-group-af, neighbor-af,
       vrf-neighbor-af, af-group-af";
    container remove-private-as-entire-as-path-inbound {
      presence "Indicates a remove-private-as-entire-as-path-inbound node is configured.";
      description
        "Remove private AS number from inbound updates";
      leaf enable {
        type boolean;
        // NCS drop mandatory statement
        description
          "TRUE to remove private AS from inbound updates.
           FALSE to prevent remove-private-AS from being
           inherited.";
      }
      leaf entire {
        type boolean;
        description
          "TRUE to remove private AS from inbound updates
           if all ASes in aspath areprivate. FALSE to
           prevent remove-private-ASfrom being inherited.";
      }
    }
  }

  grouping live_ncs_RPKI-BESTPATH-USE-ORIGIN-AS-VALIDITY {
    description
      "Common node of global-af, vrf-global-af";
    leaf rpki-bestpath-use-origin-as-validity {
      type empty;
      description
        "RPKI bestpath use origin-AS validity";
    }
  }

  grouping live_ncs_BGP-CFG-RPKI-BESTPATH-USE-ORIGIN-AS-VALIDITY {
    description
      "Common node of global-af, vrf-global-afCommon
       node of global, vrf-global";
    leaf rpki-bestpath-use-origin-as-validity {
      type empty;
      description
        "RPKI bestpath use origin-AS validity";
    }
  }

  grouping live_ncs_CONNECTED-ROUTES {
    description
      "Common node of global-af, vrf-global-af";
    container connected-routes {
      presence "enable connected-routes";
      description
        "Redistribute connected routes";
      leaf default-metric {
        type Bgp-default-metric-range;
        description
          "Default metric";
      }
      leaf route-policy-name {
        type string;
        description
          "Route policy name";
      }
      leaf not-used {
        type uint32 {
          range "0..127";
        }
        description
          "Not used";
      }
    }
  }

  grouping live_ncs_IGP-REDIST-INTERNAL {
    description
      "Common node of global, vrf-global";
    leaf igp-redist-internal {
      type empty;
      description
        "Allow redistribution of iBGP into IGPs
         (dangerous)";
    }
  }

  grouping live_ncs_AIGP-SEND-MED {
    description
      "Common node of neighbor-group-af, neighbor-af,
       vrf-neighbor-af, af-group-af";
    leaf aigp-send-med {
      type Bgp-aigp-cfg;
      description
        "Enable/Disable sending AIGP in MED ";
    }
  }

  grouping live_ncs_AIGP {
    description
      "Common node of neighbor-group-af, neighbor-af,
       vrf-neighbor-af, af-group-af";
    leaf aigp {
      type Bgp-aigp-cfg;
      description
        "Enable Accumulated IGP Metric for this neighbor.";
    }
  }

  grouping live_ncs_ADVERTISE-ORF {
    description
      "Common node of neighbor-group-af, neighbor-af,
       vrf-neighbor-af, af-group-af";
    leaf advertise-orf {
      type Bgp-orf;
      // NCS drop default statement
      description
        "Advertise ORF capability to the peer";
    }
  }

  grouping live_ncs_BFD-MINIMUM-INTERVAL {
    description
      "Common node of neighbor-group, neighbor,
       vrf-neighbor, session-group";
    leaf bfd-minimum-interval {
      type uint32 {
        range "3..30000";
      }
      units "millisecond";
      description
        "Hello interval for BFD sessions created by BGP";
    }
  }

  grouping live_ncs_AIGP-COST-COMMUNITY {
    description
      "Common node of neighbor-group-af, neighbor-af,
       vrf-neighbor-af, af-group-af";
    container aigp-cost-community {
      description
        "Send AIGP value in Cost Community. ";
      leaf enable {
        type boolean;
        description
          "TRUE to enable sending cost community, FALSE
           otherwise ";
      }
      leaf cost-community-id {
        // NCS drop when statement
        type uint32 {
          range "0..255";
        }
        description
          "Cost Community ID";
      }
      leaf transitive {
        // NCS drop when statement
        type boolean;
        description
          "True to send transitive cost community FALSE
           otherwise";
      }
      leaf cost-community-poi-type {
        // NCS drop when statement
        type Bgp-aigp-cfg-poi;
        description
          "Cost Community POI";
      }
    }
  }

  grouping live_ncs_DISABLE-AS-PATH-LOOP-CHECK {
    description
      "Common node of global-af, vrf-global-af";
    leaf disable-as-path-loop-check {
      type empty;
      description
        "Disable outbound AS Path loop check";
    }
  }

  grouping live_ncs_BEST-PATH-ROUTER-ID {
    description
      "Common node of global, vrf-global";
    leaf best-path-router-id {
      type empty;
      description
        "Change default route selection criteria and
         compare router-id for identical EBGP paths";
    }
  }

  grouping live_ncs_RIP-ROUTES {
    description
      "Common node of global-af, vrf-global-af";
    container rip-routes {
      presence "enable rip-routes";
      description
        "Redistribute RIP routes";
      leaf default-metric {
        type Bgp-default-metric-range;
        description
          "Default metric";
      }
      leaf route-policy-name {
        type string;
        description
          "Route policy name";
      }
      leaf not-used {
        type uint32 {
          range "0..127";
        }
        description
          "Not used";
      }
    }
  }

  grouping live_ncs_DESCRIPTION {
    description
      "Common node of neighbor-group, neighbor,
       vrf-neighbor, session-group";
    leaf description {
      type string;
      description
        "Up to 80 characters describing this neighbor";
    }
  }

  grouping live_ncs_ADVERTISE-L2VPN-EVPN {
    description
      "Common node of neighbor-group-af, neighbor-af,
       vrf-neighbor-af, af-group-af";
    container advertise-l2vpn-evpn {
      description
        "Advertise Translated Routes to the peer";
      leaf af-name {
        type dt1:Bgp-address-family;
        description
          "Address family";
      }
      leaf reorg-option {
        type Bgp-reorg-opt;
        description
          "Reorigination option";
      }
      leaf rt-type {
        type Bgp-adv-rt;
        description
          "RT type";
      }
    }
  }

  grouping live_ncs_KEYCHAIN {
    description
      "Common node of neighbor-group, neighbor,
       vrf-neighbor, session-group";
    container keychain {
      description
        "Set or disable keychain based authentication";
      leaf keychain-disable {
        type boolean;
        description
          "TRUE to prevent this entity from having a
           keychain based authentication even if the
           parent has one.FALSE to specify a keychain name";
      }
      leaf keychain-name {
        // NCS drop when statement
        type string;
        description
          "Name of the keychain associated with neighbor";
      }
    }
  }

  grouping live_ncs_RECEIVE-BUFFER-SIZE {
    description
      "Common node of neighbor-group, neighbor,
       vrf-neighbor, session-group";
    container receive-buffer-size {
      description
        "Set socket receive buffer size and BGP read
         buffer size";
      leaf socket-receive-size {
        type uint32 {
          range "512..131072";
        }
        units "byte";
        // NCS drop default statement
        description
          "Receive socket buffer size in bytes";
      }
      leaf bgp-receive-size {
        type uint32 {
          range "512..131072";
        }
        units "byte";
        // NCS drop default statement
        description
          "BGP read buffer size in bytes";
      }
    }
  }

  grouping live_ncs_NEXT-HOP-UNCHANGED {
    description
      "Common node of neighbor-group-af, neighbor-af,
       vrf-neighbor-af, af-group-af";
    leaf next-hop-unchanged {
      type boolean;
      description
        "TRUE to disable overwriting of next hop before
         advertising to eBGP peers. FALSE to prevent
         next-hop-unchanged from being inherited.";
    }
  }

  grouping live_ncs_OSPF-ROUTE-TABLE {
    description
      "Common node of global-af, vrf-global-af";
    container ospf-routes {
      description
        "Redistribute information for OSPF routes.";
      list ospf-route {
        key "instance-name";
        description
          "Redistribute OSPF routes";
        leaf instance-name {
          type xr:Cisco-ios-xr-string;
          description
            "OSPF router tag";
        }
        leaf default-metric {
          type Bgp-default-metric-range;
          description
            "Default metric";
        }
        leaf route-policy-name {
          type string;
          description
            "Route policy name";
        }
        leaf redist-type {
          type xr:Hex-integer;
          description
            "Redistribution type: 01 for internal routes,
             02 for external routes of type 1, 04 for
             external routes of type 2, 08 for NSSA
             external routes of type 1, 10 for NSSA
             external routes of type 2, 20 for external
             routes, 40 for NSSA external routes.  Logical
             combinations permitted.";
        }
      }
    }
  }

  grouping live_ncs_ROUTER-ID {
    description
      "Common node of global, vrf-global";
    leaf router-id {
      type inet:ipv4-address-no-zone;
      // NCS drop default statement
      description
        "Configure Router-id";
    }
  }

  grouping live_ncs_DEFAULT-METRIC {
    description
      "Common node of global, vrf-global";
    leaf default-metric {
      type uint32 {
        range "1..4294967295";
      }
      description
        "Default redistributed metric";
    }
  }

  grouping live_ncs_RPKI-ORIGIN-AS-VALIDATION-DISABLE {
    description
      "Common node of neighbor-group-af, neighbor-af,
       vrf-neighbor-af, af-group-af";
    leaf rpki-origin-as-validation-disable {
      type empty;
      description
        "RPKI origin-AS validation disable";
    }
  }

  grouping live_ncs_BGP-CFG-RPKI-ORIGIN-AS-VALIDATION-DISABLE {
    description
      "Common node of neighbor-group-af, neighbor-af,
       vrf-neighbor-af, af-group-afCommon node of
       neighbor-group, neighbor, vrf-neighbor,
       session-group";
    leaf rpki-origin-as-validation-disable {
      type empty;
      description
        "RPKI origin-AS validation disable";
    }
  }

  grouping live_ncs_DISABLE-NEIGHBOR-LOGGING {
    description
      "Common node of global, vrf-global";
    leaf disable-neighbor-logging {
      type empty;
      description
        "Disable neighbor change logging";
    }
  }

  grouping live_ncs_TCPMSS {
    description
      "Common node of neighbor-group, neighbor,
       vrf-neighbor, session-group";
    container tcpmss {
      description
        "TCP Maximum segment size";
      leaf tcpmss-disable {
        type boolean;
        description
          "TRUE, to prevent inheritance ofTCP MSS
           valuefrom its parents.FALSE, otherwise";
      }
      leaf mss {
        type uint32 {
          range "68..10000";
        }
        description
          "Maximum Segment Size";
      }
    }
  }

  grouping ADVERTISE-DISABLE {
    description
      "Common node of neighbor-group-af, neighbor-af,
       vrf-neighbor-af, af-group-af";
    container advertise-disable {
      description
        "Disable Advertise Of Routes to the peer";
      leaf af-name {
        type dt1:Bgp-address-family;
        description
          "Address family";
      }
      leaf reorg-option {
        type Bgp-reorg-opt;
        description
          "Reorigination option";
      }
      leaf rt-type {
        type Bgp-adv-rt;
        description
          "RT type";
      }
    }
  }

  grouping TABLE-POLICY {
    description
      "Common node of global-af, vrf-global-af";
    leaf table-policy {
      type string;
      description
        "Configure policy for installation of routes to
         RIB";
    }
  }

  grouping MAXIMUM-PREFIXES {
    description
      "Common node of global-af, vrf-global-afCommon
       node of neighbor-group-af, neighbor-af,
       vrf-neighbor-af, af-group-af";
    container maximum-prefixes {
      presence "Indicates a maximum-prefixes node is configured.";
      description
        "Maximum number of prefixes to accept from this
         peer";
      leaf prefix-limit {
        type uint32 {
          range "1..4294967295";
        }
        mandatory true;
        description
          "Maximum prefixes limit";
      }
      leaf warning-percentage {
        type uint32 {
          range "1..100";
        }
        default "75";
        description
          "Threshold value (%) at which to generate a
           warning message.";
      }
      leaf warning-only {
        type boolean;
        default "false";
        description
          "TRUE to only give a warning message when limit
           is exceeded.  FALSE to accept max prefix limit
           only.";
      }
      leaf restart-time {
        type uint32 {
          range "0..65535";
        }
        default "0";
        description
          "Restart interval";
      }
      leaf discard-extra-paths {
        type boolean;
        default "false";
        description
          "Discard extra paths when limit is exceeded";
      }
    }
  }

  grouping DISTANCE {
    description
      "Common node of global-af, vrf-global-af";
    container distance {
      presence "Indicates a distance node is configured.";
      description
        "Define an administrative distance";
      leaf external-routes {
        type uint32 {
          range "1..255";
        }
        mandatory true;
        description
          "Distance for routes external to the AS";
      }
      leaf internal-routes {
        type uint32 {
          range "1..255";
        }
        mandatory true;
        description
          "Distance for routes internal to the AS";
      }
      leaf local-routes {
        type uint32 {
          range "1..255";
        }
        mandatory true;
        description
          "Distance for local routes";
      }
    }
  }

  grouping UPDATE-SOURCE-INTERFACE {
    description
      "Common node of neighbor-group, neighbor,
       vrf-neighbor, session-group";
    leaf update-source-interface {
      type xr:Interface-name;
      description
        "Select an interface to configure";
    }
  }

  grouping MULTI-PATH-AS-PATH-IGNORE-ONWARDS {
    description
      "Common node of global, vrf-global";
    leaf multi-path-as-path-ignore-onwards {
      type empty;
      description
        "Change default multi-route selection criteria to
         ignore everything onwards as-path check";
    }
  }

  grouping PROPAGATE-DMZ-LINK-BANDWIDTH {
    description
      "Common node of neighbor-group, neighbor,
       vrf-neighbor, session-group";
    leaf propagate-dmz-link-bandwidth {
      type boolean;
      description
        "TRUE to propagate DMZ link bandwidth.  FALSE to
         not propagate and to prevent inheritance from a
         parent";
    }
  }

  grouping DISABLE-AUTO-SOFT-RESET {
    description
      "Common node of global, vrf-global";
    leaf disable-auto-soft-reset {
      type empty;
      description
        "Disable automatic soft peer reset on policy
         reconfiguration";
    }
  }

  grouping MSG-LOG-IN {
    description
      "Common node of neighbor-group, neighbor,
       vrf-neighbor, session-group";
    container msg-log-in {
      description
        "Message log inbound";
      leaf msg-buf-count {
        type uint32 {
          range "1..100";
        }
        description
          "Inbound message log buffer size";
      }
      leaf msg-log-disable {
        type boolean;
        description
          "Disable inbound message logging";
      }
      leaf msg-log-inherit-disable {
        type boolean;
        description
          "TRUE, to prevent this entity from having a
           inbound message logging if parent has one";
      }
    }
  }

  grouping DISABLE-ENFORCE-FIRST-AS {
    description
      "Common node of global, vrf-global";
    leaf disable-enforce-first-as {
      type empty;
      description
        "Disable enforce the first AS for EBGP routes";
    }
  }

  grouping ROUTE-TARGET-TABLE {
    description
      "Common node of import-route-targets,
       export-route-targets";
    container route-targets {
      description
        "Route target table";
      list route-target {
        must 'as-or-four-byte-as or ipv4-address' {
          tailf:xpath-root 3;
          description
            "AS-or-FourByteAS or IPV4Address must be
             present.";
        }
        key "type";
        description
          "Route target";
        leaf type {
          type Bgp-vrf-route-target;
          description
            "Type of RT";
        }
        list as-or-four-byte-as {
          when "../type = 'as' or ../type = 'four-byte-as'" {
            tailf:xpath-root 3;
            description
              "../Type = AS or ../Type = FourByteAS";
          }
          key "as-xx as as-index stitching-rt";
          description
            "as or four byte as";
          leaf as-xx {
            type uint32 {
              range "0";
            }
            description
              "AS number";
          }
          leaf as {
            type uint32 {
              range "1..4294967295";
            }
            description
              "AS number";
          }
          leaf as-index {
            type Route-target-as-index;
            description
              "AS number Index";
          }
          leaf stitching-rt {
            type uint32 {
              range "0..1";
            }
            description
              "Stitching RT";
          }
        }
        list ipv4-address {
          when "../type = 'ipv4-address'" {
            tailf:xpath-root 3;
            description
              "../Type = IPV4Address";
          }
          key "address address-index stitching-rt";
          description
            "ipv4 address";
          leaf address {
            type inet:ipv4-address-no-zone;
            description
              "IP address";
          }
          leaf address-index {
            type Route-target-addr-index;
            description
              "IP address Index";
          }
          leaf stitching-rt {
            type uint32 {
              range "0..1";
            }
            description
              "Stitching RT";
          }
        }
      }
    }
  }

  grouping REMOTE-AS {
    description
      "Common node of neighbor-group, neighbor,
       vrf-neighbor, session-group";
    container remote-as {
      description
        "Set remote AS";
      leaf as-xx {
        type dt1:Bgp-as-range;
        description
          "xx of AS number xx.yy";
      }
      leaf as-yy {
        type dt1:Bgp-as-range;
        description
          "yy of AS number xx.yy";
      }
    }
  }

  grouping ADDITIONAL-PATHS-SEND {
    description
      "Common node of global-af, vrf-global-af";
    leaf additional-paths-send {
      type dt1:Bgp-af-additional-paths-cfg;
      description
        "Advertise additional paths Send capability";
    }
  }

  grouping UPDATE-IN-FILTERING {
    description
      "Common node of neighbor-group, neighbor,
       vrf-neighbor, session-group";
    container update-in-filtering {
      description
        "Inbound update filtering";
      container update-in-filtering-message-buffers {
        presence "Indicates a update-in-filtering-message-buffers node is configured.";
        description
          "Message buffers to store filtered updates";
        leaf number-of-buffers {
          type uint32 {
            range "0..25";
          }
          mandatory true;
          description
            "Number of message buffers";
        }
        leaf non-circular-buffer {
          type boolean;
          mandatory true;
          description
            "TRUE to configure non-circular buffer";
        }
      }
      leaf enable {
        type empty;
        description
          "Configure inbound update filtering";
      }
      leaf update-in-filtering-attribute-filter-group {
        type string;
        description
          "Attribute-filter group name for update
           filtering";
      }
      leaf update-in-filtering-syslog-disable {
        type empty;
        description
          "Disable inbound update filtering syslog
           messages";
      }
    }
  }

  grouping SHUTDOWN {
    description
      "Common node of neighbor-group, neighbor,
       vrf-neighbor, session-group";
    leaf shutdown {
      type boolean;
      description
        "TRUE to shutdown this entity, FALSE to prevent
         this entity from being shutdown even if the
         parent is.";
    }
  }

  grouping BMP-ACTIVATE-TABLE {
    description
      "Common node of neighbor-group, neighbor,
       vrf-neighbor, session-group";
    container bmp-activates {
      description
        "Enable BMP logging for this neighbor";
      list bmp-activate {
        key "server-id";
        description
          "Enable BMP logging for this particular server";
        leaf server-id {
          type uint32 {
            range "1..8";
          }
          description
            "BMP Server ID";
        }
      }
    }
  }

  grouping ADVERTISE-VRF-IMP-DISABLE-V4 {
    description
      "Common node of neighbor-group-af, neighbor-af,
       vrf-neighbor-af, af-group-af";
    container advertise-vrf-imp-disable-v4 {
      description
        "Disable Advertise Of VRF ReImported Routes";
      leaf af-name {
        type dt1:Bgp-address-family;
        description
          "Address family";
      }
      leaf adv-option {
        type Bgp-reorg-opt;
        description
          "Advertise option";
      }
      leaf rt-type {
        type Bgp-adv-rt;
        description
          "RT type";
      }
    }
  }

  grouping ADVERTISE-VRF-IMP-DISABLE-V6 {
    description
      "Common node of neighbor-group-af, neighbor-af,
       vrf-neighbor-af, af-group-af";
    container advertise-vrf-imp-disable-v6 {
      description
        "Disable Advertise Of VRF ReImported Routes";
      leaf af-name {
        type dt1:Bgp-address-family;
        description
          "Address family";
      }
      leaf adv-option {
        type Bgp-reorg-opt;
        description
          "Advertise option";
      }
      leaf rt-type {
        type Bgp-adv-rt;
        description
          "RT type";
      }
    }
  }

  grouping SITE-OF-ORIGIN {
    description
      "Common node of neighbor-group-af, vrf-neighbor-af
       , af-group-af";
    container site-of-origin {
      description
        "Site-of-Origin extended community associated
         with the neighbor";
      leaf type {
        type Bgp-site-of-origin;
        description
          "Type of Extended community";
      }
      leaf as-xx {
        when "../type = 'as' or ../type = 'four-byte-as'" {
          tailf:xpath-root 3;
          description
            "../Type = AS or ../Type = FourByteAS";
        }
        type dt1:Bgp-as-range;
        description
          "AS number";
      }
      leaf as {
        when "../type = 'as' or ../type = 'four-byte-as'" {
          tailf:xpath-root 3;
          description
            "../Type = AS or ../Type = FourByteAS";
        }
        type dt1:Bgp-as-range;
        description
          "AS number";
      }
      leaf as-index {
        when "../type = 'as' or ../type = 'four-byte-as'" {
          tailf:xpath-root 3;
          description
            "../Type = AS or ../Type = FourByteAS";
        }
        type dt1:Bgp-extcomm-asn-index;
        description
          "AS number Index";
      }
      leaf address {
        when "../type = 'ipv4-address'" {
          tailf:xpath-root 3;
          description
            "../Type = IPV4Address";
        }
        type inet:ipv4-address-no-zone;
        description
          "IP address";
      }
      leaf address-index {
        when "../type = 'ipv4-address'" {
          tailf:xpath-root 3;
          description
            "../Type = IPV4Address";
        }
        type dt1:Bgp-extcomm-v4-addr-index;
        description
          "IP address Index";
      }
    }
  }

  grouping ROUTE-POLICY-OUT {
    description
      "Common node of neighbor-group-af, neighbor-af,
       vrf-neighbor-af, af-group-af";
    leaf route-policy-out {
      type string;
      description
        "Route policy name to apply to outbound routes";
    }
  }

  grouping SEGMENT-ROUTING {
    description
      "Common node of global-af, vrf-global-af";
    container segment-routing {
      description
        "Segment-routing Configurations";
      container srv6 {
        description
          "SRv6 Configurations";
        leaf enable {
          type empty;
          description
            "Enable SRv6 configuration submode";
        }
        leaf srv6sid-allocation-mode {
          type string;
          description
            "SID allocation mode: per-ce  Set per CE SID
             mode,per-vrf Set per VRF SID mode";
        }
        leaf locator-name {
          type string;
          description
            "Configure Locator name for SID allocation";
        }
      }
    }
  }

  grouping ADVERTISE-V4 {
    description
      "Common node of neighbor-group-af, neighbor-af,
       vrf-neighbor-af, af-group-af";
    container advertise-v4 {
      description
        "Advertise Translated Routes to the peer";
      leaf af-name {
        type dt1:Bgp-address-family;
        description
          "Address family";
      }
      leaf reorg-option {
        type Bgp-reorg-opt;
        description
          "Reorigination option";
      }
      leaf rt-type {
        type Bgp-adv-rt;
        description
          "RT type";
      }
    }
  }

  grouping ADVERTISE-V6 {
    description
      "Common node of neighbor-group-af, neighbor-af,
       vrf-neighbor-af, af-group-af";
    container advertise-v6 {
      description
        "Advertise Translated Routes to the peer";
      leaf af-name {
        type dt1:Bgp-address-family;
        description
          "Address family";
      }
      leaf reorg-option {
        type Bgp-reorg-opt;
        description
          "Reorigination option";
      }
      leaf rt-type {
        type Bgp-adv-rt;
        description
          "RT type";
      }
    }
  }

  grouping DEFAULT-ORIGINATE {
    description
      "Common node of neighbor-group-af, neighbor-af,
       vrf-neighbor-af, af-group-af";
    container default-originate {
      description
        "Originate default route to this neighbor";
      leaf enable {
        type boolean;
        default "false";
        description
          "FALSE to prevent default-originate from, being
           inherited from a parent. TRUE otherwise.";
      }
      leaf route-policy-name {
        type string;
        description
          "Route policy name to specify criteria to
           originate default.";
      }
    }
  }

  grouping IDLE-WATCH-TIME {
    description
      "Common node of neighbor-group, neighbor,
       vrf-neighbor, session-group";
    leaf idle-watch-time {
      type uint32 {
        range "30..1800";
      }
      units "second";
      description
        "Time to wait for deleteing IDLE state Dynamic
         peer";
    }
  }

  grouping TIMERS {
    description
      "Common node of neighbor-group, neighbor,
       vrf-neighbor, session-group";
    container timers {
      description
        "BGP per neighbor timers.";
      leaf keepalive-interval {
        type uint32 {
          range "0..65535";
        }
        default "60";
        description
          "Keepalive interval";
      }
      leaf hold-time {
        type uint32 {
          range "0..65535";
        }
        default "180";
        description
          "Hold time.  Specify 0 to disable
           keepalives/hold time";
      }
      leaf min-accept-hold-time {
        type uint32 {
          range "0..65535";
        }
        default "3";
        description
          "Minimum acceptable hold time.  Specify 0 to
           disable keepalives/hold time";
      }
    }
  }

  grouping NEXT-HOP-MPLS-FWD-IBGP {
    description
      "Common node of global, vrf-global";
    leaf next-hop-mpls-fwd-ibgp {
      type empty;
      description
        "Enable mpls forwarding path for ibgp learnt
         nexthops";
    }
  }

  grouping DISABLE-FAST-EXTERNAL-FALLOVER {
    description
      "Common node of global, vrf-global";
    leaf disable-fast-external-fallover {
      type empty;
      description
        "Disable immediate reset session if a link to a
         directly connected external peer goes down";
    }
  }

  grouping SEND-COMMUNITY-EBGP {
    description
      "Common node of neighbor-group-af, neighbor-af,
       vrf-neighbor-af, af-group-af";
    leaf send-community-ebgp {
      type boolean;
      description
        "TRUE to send communities to the external
         neighbor/neighbor-group/af-group.  FALSE not to
         send and to prevent inheritance from a parent";
    }
  }

  grouping ADDITIONAL-PATHS-RECEIVE-CAPABILITY {
    description
      "Common node of neighbor-group, neighbor,
       vrf-neighbor, session-group";
    leaf additional-paths-receive-capability {
      type dt1:Bgp-nbr-cap-additional-paths-cfg;
      description
        "Advertise additional paths Receive capability";
    }
  }

  grouping SEND-EXT-COMMUNITY-EBGP {
    description
      "Common node of neighbor-group-af, neighbor-af,
       vrf-neighbor-af, af-group-af";
    leaf send-ext-community-ebgp {
      type boolean;
      description
        "TRUE to send extended communities to the
         external neighbor/neighbor-group/af-group.
         FALSE not to send and to prevent inheritance
         from a parent";
    }
  }

  grouping AF-GROUP {
    description
      "Common node of neighbor-group-af, neighbor-af,
       vrf-neighbor-af";
    leaf af-group {
      type string;
      description
        "Inherit configuration for this address-family
         from an AF-group";
    }
  }

  grouping ROUTE-POLICY-IN {
    description
      "Common node of neighbor-group-af, neighbor-af,
       vrf-neighbor-af, af-group-af";
    leaf route-policy-in {
      type string;
      description
        "Route policy name to apply to inbound routes";
    }
  }

  grouping LABEL-MODE {
    description
      "Common node of global-af, vrf-global-af";
    container label-mode {
      presence "enable label-mode";
      description
        "BGP 6PE/MPLS-VPN label allocation mode";
      leaf label-allocation-mode {
        type string;
        description
          "Label allocation mode: per-ce  Set per CE label
           mode, per-vrf Set per VRF label mode,
           per-prefix Set per Prefix label mode (for
           MPLS-VPN only)";
      }
      leaf route-policy-name {
        type string;
        description
          "Label mode route policy name";
      }
    }
  }

  grouping APP-ROUTE-TABLE {
    description
      "Common node of global-af, vrf-global-af";
    container application-routes {
      description
        "Redistribute information for Application routes.";
      list application-route {
        key "instance-name";
        description
          "Redistribute application routes";
        leaf instance-name {
          type xr:Cisco-ios-xr-string;
          description
            "OnePK application name";
        }
        leaf default-metric {
          type Bgp-default-metric-range;
          description
            "Default metric";
        }
        leaf route-policy-name {
          type string;
          description
            "Route policy name";
        }
        leaf not-used {
          type uint32 {
            range "0..127";
          }
          description
            "Not used";
        }
      }
    }
  }

  grouping DEFAULT-INFO-ORIGINATE {
    description
      "Common node of global, vrf-global";
    leaf default-info-originate {
      type empty;
      description
        "Control distribution of default information";
    }
  }

  grouping ENFORCE-FIRST-AS {
    description
      "Common node of neighbor-group, neighbor,
       vrf-neighbor, session-group";
    leaf enforce-first-as {
      type boolean;
      description
        "TRUE to enforce first AS; FALSE to not enforce
         first AS.";
    }
  }

  grouping SOFT-RECONFIGURATION {
    description
      "Common node of neighbor-group-af, neighbor-af,
       vrf-neighbor-af, af-group-af";
    container soft-reconfiguration {
      description
        "Enable/disable inbound soft reconfiguration for
         this neighbor/neighbor-group/af-group";
      leaf inbound-soft {
        type boolean;
        default "false";
        description
          "FALSE to prohibit inbound soft reconfiguration.
           TRUE otherwise.";
      }
      leaf soft-always {
        type boolean;
        default "false";
        description
          "TRUE to always use soft reconfig, even if route
           refresh is supported.  FALSE otherwise.";
      }
    }
  }

  grouping NEIGHBOR-GRACEFUL-RESTART {
    description
      "Common node of neighbor-group, neighbor,
       vrf-neighbor, session-group";
    leaf neighbor-graceful-restart {
      type Bgp-nbrgr;
      description
        "TRUE to Enable graceful restart supportfor
         neighbor.  FALSE to disable graceful restart
         support for neighbor.";
    }
  }

  grouping ADVERTISE-DEF-IMP-DISABLE-V4 {
    description
      "Common node of neighbor-group-af, neighbor-af,
       vrf-neighbor-af, af-group-af";
    container advertise-def-imp-disable-v4 {
      description
        "Disable Advertise Of Default VRF Imported Routes";
      leaf af-name {
        type dt1:Bgp-address-family;
        description
          "Address family";
      }
      leaf adv-option {
        type Bgp-reorg-opt;
        description
          "Advertise option";
      }
      leaf rt-type {
        type Bgp-adv-rt;
        description
          "RT type";
      }
    }
  }

  grouping ADVERTISE-DEF-IMP-DISABLE-V6 {
    description
      "Common node of neighbor-group-af, neighbor-af,
       vrf-neighbor-af, af-group-af";
    container advertise-def-imp-disable-v6 {
      description
        "Disable Advertise Of Default VRF Imported Routes";
      leaf af-name {
        type dt1:Bgp-address-family;
        description
          "Address family";
      }
      leaf adv-option {
        type Bgp-reorg-opt;
        description
          "Advertise option";
      }
      leaf rt-type {
        type Bgp-adv-rt;
        description
          "RT type";
      }
    }
  }

  grouping LOCAL-ADDRESS {
    description
      "Common node of neighbor-group, neighbor,
       vrf-neighbor, session-group";
    container local-address {
      description
        "Local ip address";
      leaf local-address-disable {
        type boolean;
        description
          "TRUE to prevent this entity from having a local
           address if the parent has one.FALSE to specify
           local ip address";
      }
      leaf local-ip-address {
        when "../local-address-disable = 'false'" {
          tailf:xpath-root 3;
          description
            "../LocalAddressDisable = false";
        }
        type inet:ip-address-no-zone;
        description
          "Local ip address for neighbor";
      }
    }
  }

  grouping AS-OVERRIDE {
    description
      "Common node of neighbor-group-af, neighbor-af,
       vrf-neighbor-af, af-group-af";
    leaf as-override {
      type boolean;
      default "true";
      description
        "TRUE to override matching AS-number while
         sending update. FALSE to prevent as-override
         from being inherited from the parent";
    }
  }

  grouping IGNORE-CONNECTED-CHECK-EBGP {
    description
      "Common node of neighbor-group-af, neighbor-af,
       vrf-neighbor-af, af-group-afCommon node of
       neighbor-group, neighbor, vrf-neighbor,
       session-group";
    leaf ignore-connected-check-ebgp {
      type boolean;
      description
        "TRUE to disable the connected nexthop check for
         this peer.FALSE to enable the connected nexthop
         check for this peer.";
    }
  }

  grouping REMOTE-AS-LIST {
    description
      "Common node of neighbor-group, neighbor,
       vrf-neighbor, session-group";
    leaf remote-as-list {
      type string;
      description
        "Remote-as-list group name";
    }
  }

  grouping SEND-MULTICAST-ATTR {
    description
      "Common node of neighbor-group-af, neighbor-af,
       af-group-af";
    leaf send-multicast-attr {
      type Bgp-send-mcast-attr-cfg;
      description
        "Config send multicast attribute for this
         neighbor";
    }
  }

  grouping ENCAPSULATION-TYPE {
    description
      "Common node of neighbor-group-af, neighbor-af,
       af-group-afCommon node of neighbor-group-af,
       neighbor-af, vrf-neighbor-af, af-group-af";
    leaf encapsulation-type {
      type Bgp-af-encapsulation;
      description
        "Encapsulation type for this neighbor";
    }
  }

  grouping LOCAL-ADDRESS-SUB-NET {
    description
      "Common node of neighbor-group, neighbor,
       vrf-neighbor, session-group";
    container local-address-sub-net {
      description
        "Local Address subnet of routing updates";
      leaf local-addresss-subnet {
        type inet:ip-address-no-zone;
        description
          "local address subnet ip address ";
      }
      leaf prefix-len {
        type uint32 {
          range "0..128";
        }
        description
          "prefix length";
      }
    }
  }

  grouping ADVERTISE-BRIDGE-DOMAIN-IMP-DISABLE-V4 {
    description
      "Common node of neighbor-group-af, neighbor-af,
       vrf-neighbor-af, af-group-af";
    container advertise-bridge-domain-imp-disable-v4 {
      description
        "Disable Advertise Of VRF EVPN Extranet Imported
         Routes";
      leaf af-name {
        type dt1:Bgp-address-family;
        must '../adv-option and ../rt-type' {
          tailf:xpath-root 3;
        }
        description
          "Address family";
      }
      leaf adv-option {
        type Bgp-reorg-opt;
        must '../af-name and ../rt-type' {
          tailf:xpath-root 3;
        }
        description
          "Advertise option";
      }
      leaf rt-type {
        type Bgp-adv-rt;
        must '../af-name and ../adv-option' {
          tailf:xpath-root 3;
        }
        description
          "RT type";
      }
    }
  }

  grouping OPTIMAL-ROUTE-REFLECTOR-GROUP-TABLE {
    description
      "Common node of global-af, vrf-global-af";
    container optimal-route-reflector-groups {
      description
        "Table of multiple ORR groups";
      list optimal-route-reflector-group {
        key "group-name";
        description
          "Optimal Route Reffelctor group. Each such group
           is equivalent to an IGP area";
        leaf group-name {
          type xr:Cisco-ios-xr-string;
          description
            "Name of the ORR group";
        }
        leaf primary-root-address {
          type inet:ip-address-no-zone;
          description
            "Primary Root for the ORR group";
        }
        leaf secondary-root-address {
          type inet:ip-address-no-zone;
          description
            "Secondary Root for the ORR group";
        }
        leaf tertiary-root-address {
          type inet:ip-address-no-zone;
          description
            "Tertiary Root for the ORR group";
        }
      }
    }
  }

  grouping ADVERTISE-BRIDGE-DOMAIN-IMP-DISABLE-V6 {
    description
      "Common node of global-af, vrf-global-afCommon
       node of neighbor-group-af, neighbor-af,
       vrf-neighbor-af, af-group-af";
    container advertise-bridge-domain-imp-disable-v6 {
      description
        "Disable Advertise Of VRF EVPN Extranet Imported
         Routes";
      leaf af-name {
        type dt1:Bgp-address-family;
        must '../adv-option and ../rt-type' {
          tailf:xpath-root 3;
        }
        description
          "Address family";
      }
      leaf adv-option {
        type Bgp-reorg-opt;
        must '../af-name and ../rt-type' {
          tailf:xpath-root 3;
        }
        description
          "Advertise option";
      }
      leaf rt-type {
        type Bgp-adv-rt;
        must '../af-name and ../adv-option' {
          tailf:xpath-root 3;
        }
        description
          "RT type";
      }
    }
  }

  grouping ADVERTISE-PERMANENT-NETWORK {
    description
      "Common node of neighbor-group-af, neighbor-af,
       vrf-neighbor-af, af-group-af";
    leaf advertise-permanent-network {
      type empty;
      description
        "Advertise Permanent Networks to the peer";
    }
  }

  grouping BEST-PATH-COST-COMMUNITY {
    description
      "Common node of global, vrf-global";
    leaf best-path-cost-community {
      type empty;
      description
        "Change default route selection criteria to
         ignore cost community comparison";
    }
  }

  grouping RPKI-BESTPATH-ORIGIN-AS-ALLOW-INVALID {
    description
      "Common node of neighbor-group-af, neighbor-af,
       vrf-neighbor-af, af-group-af";
    leaf rpki-bestpath-origin-as-allow-invalid {
      type empty;
      description
        "RPKI bestpath origin-AS allow invalid";
    }
  }

  grouping BGP-CFG-RPKI-BESTPATH-ORIGIN-AS-ALLOW-INVALID {
    description
      "Common node of neighbor-group-af, neighbor-af,
       vrf-neighbor-af, af-group-afCommon node of
       neighbor-group, neighbor, vrf-neighbor,
       session-group";
    leaf rpki-bestpath-origin-as-allow-invalid {
      type empty;
      description
        "RPKI bestpath origin-AS allow invalid";
    }
  }

  grouping BGP-CFG-RPKI-BESTPATH-ORIGIN-AS-ALLOW-INVALID-MP {
    description
      "Common node of neighbor-group-af, neighbor-af,
       vrf-neighbor-af, af-group-afCommon node of
       neighbor-group, neighbor, vrf-neighbor,
       session-groupCommon node of global-af,
       vrf-global-af";
    leaf rpki-bestpath-origin-as-allow-invalid {
      type empty;
      description
        "RPKI bestpath origin-AS allow invalid";
    }
  }

  grouping NEIGHBOR-GRACEFUL-RESTART-TIME {
    description
      "Common node of neighbor-group, neighbor,
       vrf-neighbor, session-group";
    leaf neighbor-graceful-restart-time {
      type uint32 {
        range "1..4095";
      }
      units "second";
      default "120";
      description
        "Restart time advertised to neighbor";
    }
  }

  grouping TOS {
    description
      "Common node of neighbor-group, neighbor,
       vrf-neighbor, session-group";
    container tos {
      description
        "TOS (Type Of Service)";
      leaf type {
        type dt1:Bgp-tos;
        description
          "Set type of service";
      }
      leaf value {
        type dt1:Bgp-precedence-dscp;
        description
          "TOS value to set";
      }
    }
  }

  grouping NEIGHBOR-CLUSTER-ID {
    description
      "Common node of neighbor-group, neighbor,
       vrf-neighbor, session-group";
    container neighbor-cluster-id {
      description
        "Neighbor Cluster-id";
      leaf cluster-id-number {
        type uint32 {
          range "1..4294967295";
        }
        description
          "Route-Reflector Cluster ID as 32 bit quantity";
      }
      leaf cluster-id-address {
        type inet:ipv4-address-no-zone;
        description
          "Route-Reflector Cluster ID in IPV4 address
           format";
      }
    }
  }

  grouping ACTIVATE {
    description
      "Common node of neighbor-af, vrf-neighbor-af,
       neighbor-group-af";
    leaf activate {
      type empty;
      description
        "Activate an address family for this neighbor.
         Deletion of this object causes deletion of all
         the objects under
         NeighborAF/VRFNeighborAF/NeighborGroupAF
         associated with this object.";
    }
  }

  grouping NEXT-HOP-SELF {
    description
      "Common node of neighbor-group-af, neighbor-af,
       vrf-neighbor-af, af-group-af";
    leaf next-hop-self {
      type boolean;
      description
        "Disable the next hop calculation and  insert
         your own address in the nexthop field of
         advertised routes you learned from the neighbor.";
    }
  }

  grouping ALLOW-AS-IN {
    description
      "Common node of neighbor-group-af, neighbor-af,
       vrf-neighbor-af, af-group-af";
    leaf allow-as-in {
      type uint32 {
        range "1..10";
      }
      default "3";
      description
        "Allow as-path with my AS present in it";
    }
  }

  grouping ADVERTISE-LOCAL-V4 {
    description
      "Common node of neighbor-group-af, neighbor-af,
       vrf-neighbor-af, af-group-af";
    container advertise-local-v4 {
      description
        "Advertise Of Local Routes to the peer with
         different RT";
      leaf af-name {
        type dt1:Bgp-address-family;
        description
          "Address family";
      }
      leaf reorg-option {
        type Bgp-reorg-opt;
        description
          "Reorigination option";
      }
      leaf rt-type {
        type Bgp-adv-rt;
        description
          "RT type";
      }
    }
  }

  grouping ADVERTISE-LOCAL-V6 {
    description
      "Common node of neighbor-group-af, neighbor-af,
       vrf-neighbor-af, af-group-af";
    container advertise-local-v6 {
      description
        "Advertise Of Local Routes to the peer with
         different RT";
      leaf af-name {
        type dt1:Bgp-address-family;
        description
          "Address family";
      }
      leaf reorg-option {
        type Bgp-reorg-opt;
        description
          "Reorigination option";
      }
      leaf rt-type {
        type Bgp-adv-rt;
        description
          "RT type";
      }
    }
  }

  grouping BEST-EXTERNAL {
    description
      "Common node of global-af, vrf-global-af";
    leaf best-external {
      type boolean;
      description
        "TRUE to enable BE FALSE to disable BE
         inheritance from a parent";
    }
  }

  grouping ATTRIBUTE-DOWNLOAD {
    description
      "Common node of global-af, vrf-global-af";
    leaf attribute-download {
      type empty;
      description
        "Attribute download configuration";
    }
  }

  grouping AO-KEYCHAIN {
    description
      "Common node of neighbor-group, neighbor,
       vrf-neighbor, session-group";
    container ao-keychain {
      description
        "Set or disable AO based authentication";
      leaf ao-keychain-disable {
        type boolean;
        description
          "TRUE to prevent this entity from having AO
           keychain based authentication even if the
           parent has one.FALSE to enable AO keychain
           based authentication";
      }
      leaf ao-keychain-name {
        when "../ao-keychain-disable = 'false'" {
          tailf:xpath-root 3;
          description
            "../AOKeychainDisable = false";
        }
        type string;
        description
          "Name of the AO keychain associated with this
           neighbor";
      }
      leaf ao-include-tcp-options {
        when "../ao-keychain-disable = 'false'" {
          tailf:xpath-root 3;
          description
            "../AOKeychainDisable = false";
        }
        type boolean;
        description
          "Include TCP options header with AO";
      }
      leaf ao-accept-mismatch-connection {
        when "../ao-keychain-disable = 'false'" {
          tailf:xpath-root 3;
          description
            "../AOKeychainDisable = false";
        }
        type boolean;
        description
          "Accept new connections even though AO
           mismatched";
      }
    }
  }

  grouping ADDITIONAL-PATHS-SELECTION {
    description
      "Common node of global-af, vrf-global-af";
    container additional-paths-selection {
      description
        "Configure additional paths selection";
      leaf selection {
        type dt1:Bgp-af-additional-paths-cfg;
        description
          "Enable/disable selection ";
      }
      leaf route-policy-name {
        type string;
        description
          "Route policy for selection";
      }
    }
  }

  grouping NEIGHBOR-AF-LONG-LIVED-GRACEFUL-RESTART-CAPABLE {
    description
      "Common node of neighbor-group-af, neighbor-af,
       vrf-neighbor-af, af-group-af";
    leaf neighbor-af-long-lived-graceful-restart-capable {
      type boolean;
      default "false";
      description
        "TRUE to treat neighbor as Long-lived
         Graceful-restart capable. FALSE to rely on
         capability negotiation.";
    }
  }

  grouping BEST-PATH-AS-MULTIPATH-RELAX {
    description
      "Common node of global, vrf-global";
    leaf best-path-as-multipath-relax {
      type empty;
      description
        "Change default multi-route selection criteria to
         relax as-path checking - only require same
         aspath length";
    }
  }

  grouping UNSAFE-EBGP-POLICY {
    description
      "Common node of global, vrf-global";
    leaf unsafe-ebgp-policy {
      type empty;
      description
        "If eBGP neighbor is configured without a
         route-policy,the routes from that neighbor are
         not accepted by default.This knob overrides the
         default behavior. When configured,routes from
         the eBGP neighbors with no policy are accepted.";
    }
  }

  grouping GLOBAL-TIMERS {
    description
      "Common node of global, vrf-global";
    container global-timers {
      description
        "Adjust routing timers.";
      leaf keepalive {
        type uint32 {
          range "0..65535";
        }
        units "second";
        default "60";
        description
          "Keepalive interval (seconds)";
      }
      leaf hold-time {
        type uint32 {
          range "0..65535";
        }
        units "second";
        default "180";
        description
          "Hold time (seconds).  Specify 0 to disable
           keepalives/hold time";
      }
      leaf min-accept-hold-time {
        type uint32 {
          range "0..65535";
        }
        units "second";
        default "3";
        description
          "Minimum acceptable hold time (seconds). Specify
           0 to disable keepalives/hold time";
      }
    }
  }

  grouping NEIGHBOR-GROUP-ADD-MEMBER {
    description
      "Common node of neighbor, vrf-neighbor";
    leaf neighbor-group-add-member {
      type string;
      description
        "Inherit configuration from a neighbor-group";
    }
  }

  grouping MOBILE-ROUTES {
    description
      "Common node of global-af, vrf-global-af";
    container mobile-routes {
      presence "enable mobile-routes";
      description
        "Redistribute mobile routes";
      leaf default-metric {
        type Bgp-default-metric-range;
        description
          "Default metric";
      }
      leaf route-policy-name {
        type string;
        description
          "Route policy name";
      }
      leaf not-used {
        type uint32 {
          range "0..127";
        }
        description
          "Not used";
      }
    }
  }

  grouping LOCAL-PREFERENCE {
    description
      "Common node of global, vrf-global";
    leaf local-preference {
      type uint32 {
        range "0..4294967295";
      }
      default "100";
      description
        "Configure default local preference";
    }
  }

  grouping CREATE {
    description
      "Common node of neighbor-group, session-group";
    leaf create {
      type empty;
      description
        "Create this group. Deletion of this object
         causes deletion of all the objects under
         NeighborGroup/SessionGroup associated with this
         object.";
    }
  }

  grouping EBGP-SEND-DMZ-ENABLE-MODES {
    description
      "Common node of neighbor-group, neighbor,
       vrf-neighbor, session-group";
    leaf ebgp-send-dmz-enable-modes {
      type Bgp-ebgp-send-dmz-enable-mode;
      description
        "Default mode, Cumulative mode or Disable to
         prevent inheritance from a parent";
    }
  }

  grouping SEND-SOCKET-BUFFER-SIZES {
    description
      "Common node of global, vrf-global";
    container send-socket-buffer-sizes {
      description
        "set socket parameters";
      leaf socket-send-size {
        type uint32 {
          range "4096..131072";
        }
        units "byte";
        default "24576";
        description
          "Send socket buffer size in bytes";
      }
      leaf bgp-send-size {
        type uint32 {
          range "4096..131072";
        }
        units "byte";
        default "4096";
        description
          "BGP Write buffer size in bytes";
      }
    }
  }

  grouping RECEIVE-SOCKET-BUFFER-SIZES {
    description
      "Common node of global, vrf-globalCommon node of
       global, vrf-global";
    container receive-socket-buffer-sizes {
      description
        "Set socket and BGP receive buffer sizes";
      leaf socket-receive-size {
        type uint32 {
          range "512..131072";
        }
        units "byte";
        default "32768";
        description
          "Receive socket buffer size in bytes";
      }
      leaf bgp-receive-size {
        type uint32 {
          range "512..131072";
        }
        units "byte";
        default "4096";
        description
          "BGP Read buffer size in bytes";
      }
    }
  }

  grouping BFD-ENABLE-MODES {
    description
      "Common node of neighbor-group, neighbor,
       vrf-neighbor, session-group";
    leaf bfd-enable-modes {
      type Bgp-bfd-enable-mode;
      description
        "Strict mode, Default mode or Disable to prevent
         inheritance from a parent";
    }
  }

  grouping RESET-WEIGHT-ON-IMPORT {
    description
      "Common node of global-af, vrf-global-af";
    leaf reset-weight-on-import {
      type boolean;
      description
        "TRUE to reset weight on import. FALSE to not
         reset and to prevent inheritance from a parent";
    }
  }

  grouping AGGREGATE-ADDRESS-TABLE {
    description
      "Common node of global-af, vrf-global-af";
    container aggregate-addresses {
      description
        "Configure BGP aggregate entries";
      list aggregate-address {
        key "aggregate-addr aggregate-prefix";
        description
          "Aggregate address configuration";
        leaf aggregate-addr {
          type inet:ip-address;
          description
            "Aggregate in prefix/length format (address
             part)";
        }
        leaf aggregate-prefix {
          type uint16 {
            range "0..128";
          }
          description
            "Aggregate in prefix/length format (prefix
             part)";
        }
        leaf generate-set-info {
          type boolean;
          description
            "TRUE to generate AS set path information,
             FALSE otherwise";
        }
        leaf generate-confederation-set-info {
          type boolean;
          description
            "TRUE to generate AS confederation set path
             information, FALSE otherwise";
        }
        leaf summary-only {
          type boolean;
          description
            "TRUE to filter more specific routes from
             updates, FALSEotherwise";
        }
        leaf route-policy-name {
          type string;
          description
            "Route policy on which to condition
             advertisement, suppression, and attributes";
        }
      }
    }
  }

  grouping EBGP-MULTIHOP {
    description
      "Common node of neighbor-group, neighbor,
       vrf-neighbor, session-group";
    container ebgp-multihop {
      description
        "Allow EBGP neighbors not on directly connected
         networks";
      leaf max-hop-count {
        type uint32 {
          range "1..255";
        }
        default "255";
        description
          "Maximum hop count";
      }
      leaf mpls-deactivation {
        type boolean;
        default "false";
        description
          "TRUE to not enable MPLS and NULL rewrite.";
      }
    }
  }

  grouping MERGE-SAFI1-AND4-INBOUND-UPDATES {
    description
      "Common node of neighbor-group, neighbor,
       vrf-neighbor, session-group";
    leaf merge-safi1-and4-inbound-updates {
      type boolean;
      description
        "TRUE to merge updates FALSE to not merge updates
         and to prevent inheritance from a parent";
    }
  }

  grouping NEIGHBOR-GRACEFUL-RESTART-STALEPATH-TIME {
    description
      "Common node of neighbor-group, neighbor,
       vrf-neighbor, session-group";
    leaf neighbor-graceful-restart-stalepath-time {
      type uint32 {
        range "1..4095";
      }
      units "second";
      default "360";
      description
        "Maximum time to wait for restart of GR capable
         peer";
    }
  }

  grouping NEXT-HOP-RES-ALLOW-DEFAULT {
    description
      "Common node of neighbor-group, neighbor,
       vrf-neighbor, session-groupCommon node of global,
       vrf-global";
    leaf next-hop-res-allow-default {
      type empty;
      description
        "Enable path resolution for nexthops using
         default route";
    }
  }

  grouping BEST-PATH-AIGP-IGNORE {
    description
      "Common node of global, vrf-global";
    leaf best-path-aigp-ignore {
      type empty;
      description
        "Change default route selection criteria to
         ignore AIGP unless both paths whichare compared
         have AIGP attribute";
    }
  }

  grouping SESSION-GROUP-ADD-MEMBER {
    description
      "Common node of neighbor-group, neighbor,
       vrf-neighbor";
    leaf session-group-add-member {
      type string;
      description
        "Inherit address-family independent config from a
         session-group";
    }
  }

  grouping BFD-MULTIPLIER {
    description
      "Common node of neighbor-group, neighbor,
       vrf-neighbor, session-group";
    leaf bfd-multiplier {
      type uint32 {
        range "2..16";
      }
      description
        "Detection multiplier for BFD sessions created by
         BGP";
    }
  }

  grouping FLOWSPEC-VALIDATION {
    description
      "Common node of neighbor-group-af, neighbor-af,
       vrf-neighbor-af, af-group-af";
    leaf flowspec-validation {
      type Bgp-flowspec-validation-cfg;
      description
        "Config Flowspec validation for this neighbor";
    }
  }

  grouping TTL-SECURITY {
    description
      "Common node of neighbor-group, neighbor,
       vrf-neighbor, session-group";
    leaf ttl-security {
      type boolean;
      description
        "TRUE to enable BGP TTL Security.  FALSE to not
         enable it and to prevent inheritance from a
         parent";
    }
  }

  grouping BEST-PATH-MED-ALWAYS {
    description
      "Common node of global, vrf-global";
    leaf best-path-med-always {
      type empty;
      description
        "Change default route selection criteria and
         allow comparing of MED from different neighbors";
    }
  }

  grouping MAX-PEERS {
    description
      "Common node of neighbor-group, neighbor,
       vrf-neighbor, session-group";
    leaf max-peers {
      type uint32 {
        range "1..4096";
      }
      description
        "Set Maximum Peers in Dynamic Range";
    }
  }

  grouping SEND-COMMUNITY-EBGP-GRACEFUL-SHUTDOWN {
    description
      "Common node of neighbor-group-af, neighbor-af,
       vrf-neighbor-af, af-group-af";
    leaf send-community-ebgp-graceful-shutdown {
      type boolean;
      description
        "TRUE to send communities to the external
         neighbor/neighbor-group/af-group.  FALSE not to
         send and to prevent inheritance from a parent";
    }
  }

  grouping DISABLE-MSG-LOG {
    description
      "Common node of global, vrf-global";
    leaf disable-msg-log {
      type empty;
      description
        "Disable inbound and outbound messagelogging for
         all neighbors under the vrf";
    }
  }

  grouping LOCAL-AS {
    description
      "Common node of neighbor-group, neighbor,
       vrf-neighbor, session-group";
    container local-as {
      description
        "Specify a local-as number";
      leaf as-xx {
        type dt1:Bgp-as-range;
        must '../as-yy and not(../disable)' {
          tailf:xpath-root 3;
        }
        description
          "xx of AS number xx.yy";
      }
      leaf as-yy {
        type dt1:Bgp-as-range;
        must '../as-xx and not(../disable)' {
          tailf:xpath-root 3;
        }
        description
          "yy of AS number xx.yy";
      }
      leaf no-prepend {
        type empty;
        must '../as-xx and ../as-yy and not(../disable)' {
          tailf:xpath-root 3;
        }
        description
          "Do not prepend Local AS to announcements from
           this neighbor";
      }
      leaf disable {
        type empty;
        must 'not(../as-xx or ../as-yy or ../no-prepend or ../replace-as or ../dual-as)' {
          tailf:xpath-root 3;
        }
        description
          "Disable Local AS and prevent it from being
           inherited from a parent";
      }
      leaf replace-as {
        type empty;
        must '../as-xx and ../as-yy and ../no-prepend and not(../disable)' {
          tailf:xpath-root 3;
        }
        description
          "Prepend only Local AS to announcements from
           this neighbor";
      }
      leaf dual-as {
        type empty;
        must '../as-xx and ../as-yy and ../no-prepend and ../replace-as and not(../disable)' {
          tailf:xpath-root 3;
        }
        description
          "Dual-AS mode";
      }
    }
  }

  grouping LISP-ROUTES {
    description
      "Common node of global-af, vrf-global-af";
    container lisp-routes {
      presence "enable lisp-routes";
      description
        "Redistribute lisp routes";
      leaf default-metric {
        type Bgp-default-metric-range;
        description
          "Default metric";
      }
      leaf route-policy-name {
        type string;
        description
          "Route policy name";
      }
    }
  }

  grouping ADDITIONAL-PATHS-SEND-CAPABILITY {
    description
      "Common node of neighbor-group, neighbor,
       vrf-neighbor, session-group";
    leaf additional-paths-send-capability {
      type dt1:Bgp-nbr-cap-additional-paths-cfg;
      description
        "Advertise additional paths Send capability";
    }
  }

  grouping BEST-PATH-IGP-METRIC-IGNORE {
    description
      "Common node of global, vrf-global";
    leaf best-path-igp-metric-ignore {
      type empty;
      description
        "Change default route selection criteria to
         ignore IGP Metric ";
    }
  }

  grouping L2VPN-SIGNALLING {
    description
      "Common node of neighbor-group-af, neighbor-af,
       af-group-af";
    leaf l2vpn-signalling {
      type Bgp-signal;
      description
        "Disable signalling type on the peer";
    }
  }

  grouping DAMPENING {
    description
      "Common node of global-af, vrf-global-af";
    container dampening {
      presence "enable dampening";
      description
        "Enable route-flap dampening";
      leaf half-life {
        type uint32 {
          range "1..45";
        }
        units "minute";
        description
          "Half-life time for the penalty (minutes).";
      }
      leaf reuse-threshold {
        type uint32 {
          range "1..20000";
        }
        description
          "Value to start reusing a route.";
      }
      leaf suppress-threshold {
        type uint32 {
          range "1..20000";
        }
        description
          "Value to start suppressing a route.";
      }
      leaf suppress-time {
        type uint32 {
          range "1..255";
        }
        units "second";
        description
          "Maximum duration to suppress a stable route
           (seconds).";
      }
      leaf route-policy-name {
        type string;
        description
          "Route policy to specify criteria for dampening.
           This cannot be specified if any other
           parameters are specified.";
      }
    }
  }

  grouping ADVERTISE-LOCAL-LABELED-ROUTE-SAFI-UNICAST {
    description
      "Common node of global-af, vrf-global-af";
    leaf advertise-local-labeled-route-safi-unicast {
      type dt1:Bgp-advertise-local-labeled-route-cfg;
      description
        "Enable/disable advertisement of routes with
         local-label via Unicast SAFI";
    }
  }

  grouping SUBSCRIBER-ROUTES {
    description
      "Common node of global-af, vrf-global-af";
    container subscriber-routes {
      presence "enable subscriber-routes";
      description
        "Redistribute subscriber routes";
      leaf default-metric {
        type Bgp-default-metric-range;
        description
          "Default metric";
      }
      leaf route-policy-name {
        type string;
        description
          "Route policy name";
      }
      leaf not-used {
        type uint32 {
          range "0..127";
        }
        description
          "Not used";
      }
    }
  }

  grouping INTERNAL-VPN-CLIENT-IBGP-CE {
    description
      "Common node of neighbor-group, neighbor,
       vrf-neighbor, session-group";
    leaf internal-vpn-client-ibgp-ce {
      type boolean;
      description
        "TRUE to preserve the CE path attributes.FALSE to
         override CE path attributes.";
    }
  }

  grouping ACCEPT-ROUTE-LEGACY-RT {
    description
      "Common node of neighbor-group-af, neighbor-af,
       vrf-neighbor-af, af-group-af";
    leaf accept-route-legacy-rt {
      type boolean;
      description
        "TRUE to configure as a accept-route-legacy-RT.
         FALSE to prevent accept-route-legacy-RT from
         being inherited.";
    }
  }

  grouping PERMANENT-NETWORK {
    description
      "Common node of global-af, vrf-global-af";
    leaf permanent-network {
      type string;
      description
        "Route policy for permanent networks";
    }
  }

  grouping ENABLE {
    description
      "Common node of global-af, vrf-global-af";
    leaf enable {
      type empty;
      description
        "Enable the address family. Deletion of this
         object causes deletion of all the objects under
         GlobalAF/VRFGlobalAF associated with this object
         .";
    }
  }

  grouping EBGP-RECV-DMZ {
    description
      "Common node of neighbor-group, neighbor,
       vrf-neighbor, session-group";
    leaf ebgp-recv-dmz {
      type boolean;
      description
        "TRUE to receive DMZ link bandwidth from ebgp
         peer. FALSE to not receive from ebgp peer and to
         prevent inheritance from a parent";
    }
  }

  grouping ADVERTISEMENT-INTERVAL {
    description
      "Common node of neighbor-group, neighbor,
       vrf-neighbor, session-group";
    container advertisement-interval {
      presence "Indicates a advertisement-interval node is configured.";
      description
        "Minimum interval between sending BGP routing
         updates";
      leaf minimum-interval {
        type uint32 {
          range "0..600";
        }
        units "second";
        mandatory true;
        description
          "Minimum advertisement interval time, secs part";
      }
      leaf minimum-interval-msecs {
        type uint32 {
          range "0..999";
        }
        units "millisecond";
        description
          "Minimum advertisement interval time, msecs part";
      }
    }
  }

  grouping RPKI-ORIGIN-AS-VALIDITY-SIGNAL-IBGP {
    description
      "Common node of global-af, vrf-global-af";
    leaf rpki-origin-as-validity-signal-ibgp {
      type empty;
      description
        "RPKI origin-AS validity signal ibgp";
    }
  }

  grouping BGP-CFG-RPKI-ORIGIN-AS-VALIDITY-SIGNAL-IBGP {
    description
      "Common node of global-af, vrf-global-afCommon
       node of global, vrf-global";
    leaf rpki-origin-as-validity-signal-ibgp {
      type empty;
      description
        "RPKI origin-AS validity signal ibgp";
    }
  }

  grouping IMPORT {
    description
      "Common node of neighbor-group-af, neighbor-af,
       vrf-neighbor-af, af-group-af";
    container import {
      description
        "Import Reorigination options for Routes from the
         peer";
      leaf import-stitching {
        type boolean;
        description
          "TRUE to Import with Stitching RTs, FALSE to
           Import with normal RTs";
      }
      leaf import-reoriginate {
        type boolean;
        description
          "TRUE to Reoriginate imported routes, FALSE to
           not Reoriginate imported routes - not supported";
      }
      leaf import-reoriginate-stitching {
        type boolean;
        description
          "TRUE to Reoriginate imported routes with
           Stitching RTs, FALSE to Reoriginate imported
           routes with normal RTs";
      }
    }
  }

  grouping ACCEPT-OWN {
    description
      "Common node of neighbor-group-af, neighbor-af,
       vrf-neighbor-af, af-group-af";
    leaf accept-own {
      type boolean;
      description
        "Handle self-originated routes with Accept-Own
         community. Valid for following neighbor
         address-families: VPNv4Unicast, VPNv6Unicast.";
    }
  }

  grouping ADDITIONAL-PATHS-RECEIVE {
    description
      "Common node of global-af, vrf-global-af";
    leaf additional-paths-receive {
      type dt1:Bgp-af-additional-paths-cfg;
      description
        "Advertise additional paths Receive capability";
    }
  }

  grouping MPLS-ACTIVATED-INTERFACE-TABLE {
    description
      "Common node of global, vrf-global";
    container mpls-activated-interfaces {
      description
        "Configure list of MPLS activated interfaces";
      list mpls-activated-interface {
        key "interface-name";
        description
          "Configure a MPLS activated interface";
        leaf interface-name {
          type xr:Interface-name;
          description
            "Interface Name";
        }
      }
    }
  }

  grouping MULTIPATH {
    description
      "Common node of neighbor-group-af, neighbor-af,
       vrf-neighbor-af, af-group-af";
    leaf multipath {
      type empty;
      description
        "Allow paths from this neighbor to be eligible
         for selective multipath";
    }
  }

  grouping EIGRP-ROUTE-TABLE {
    description
      "Common node of global-af, vrf-global-af";
    container eigrp-routes {
      description
        "Redistribute information for EIGRP routes.";
      list eigrp-route {
        key "instance-name";
        description
          "Redistribute EIGRP routes";
        leaf instance-name {
          type xr:Cisco-ios-xr-string;
          description
            "EIGRP router tag";
        }
        leaf default-metric {
          type Bgp-default-metric-range;
          description
            "Default metric";
        }
        leaf route-policy-name {
          type string;
          description
            "Route policy name";
        }
        leaf redist-type {
          type xr:Hex-integer;
          description
            "Redistribution type: 01 for internal routes,
             02 for external routes, Logical combinations
             permitted.";
        }
      }
    }
  }

  grouping OPTIMAL-ROUTE-REFLECTION-GROUP {
    description
      "Common node of global-af, vrf-global-afCommon
       node of neighbor-group-af, neighbor-af,
       vrf-neighbor-af, af-group-af";
    leaf optimal-route-reflection-group {
      type string;
      description
        "Name of the ORR group this neighbor is going to
         be part of";
    }
  }

  grouping ROUTE-REFLECTOR-CLIENT {
    description
      "Common node of neighbor-group-af, neighbor-af,
       vrf-neighbor-af, af-group-af";
    leaf route-reflector-client {
      type boolean;
      description
        "TRUE to configure as a route-reflector-client.
         FALSE to prevent route-reflector-client from
         being inherited.";
    }
  }

  grouping ADVERTISE-LOCAL-LABELED-ROUTE {
    description
      "Common node of neighbor-group-af, neighbor-af,
       vrf-neighbor-af, af-group-af";
    leaf advertise-local-labeled-route {
      type dt1:Bgp-advertise-local-labeled-route-cfg;
      description
        "Enable/disable advertisement of routes with
         local-label";
    }
  }

  grouping SESSION-OPEN-MODE {
    description
      "Common node of neighbor-group, neighbor,
       vrf-neighbor, session-group";
    leaf session-open-mode {
      type Bgp-tcp-mode;
      default "either";
      description
        "TCP mode to be used to establish BGP session";
    }
  }

  grouping RPKI-ORIGIN-AS-VALIDATION-ENABLE {
    description
      "Common node of global-af, vrf-global-af";
    leaf rpki-origin-as-validation-enable {
      type empty;
      description
        "RPKI origin-AS validation enable";
    }
  }

  grouping UPDATE-OUT-ORIG-LOOP-CHK-DISABLE {
    description
      "Common node of neighbor-group-af, neighbor-af,
       vrf-neighbor-af, af-group-af";
    leaf update-out-orig-loop-chk-disable {
      type empty;
      description
        "Enable/disable Originator loop check for this
         neighbor-group/af-group";
    }
  }

  grouping STATIC-ROUTES {
    description
      "Common node of global-af, vrf-global-af";
    container static-routes {
      presence "enable static-routes";
      description
        "Redistribute static routes";
      leaf default-metric {
        type Bgp-default-metric-range;
        description
          "Default metric";
      }
      leaf route-policy-name {
        type string;
        description
          "Route policy name";
      }
      leaf not-used {
        type uint32 {
          range "0..127";
        }
        description
          "Not used";
      }
    }
  }

  grouping PASSWORD {
    description
      "Common node of neighbor-group, neighbor,
       vrf-neighbor, session-group";
    container password {
      description
        "Set or disable a password";
      leaf password-disable {
        type boolean;
        description
          "TRUE to prevent this entity from having a
           password even if the parent has one.  FALSEto
           specify a password";
      }
      leaf password {
        when "../password-disable = 'false'" {
          tailf:xpath-root 3;
          description
            "../PasswordDisable = false";
        }
        type xr:Proprietary-password;
        description
          "The neighbor password.  Leave unspecified when
           disabling the password.";
      }
    }
  }

  grouping NEXT-HOP-UNCHANGED-MULTIPATH {
    description
      "Common node of neighbor-group, neighbor,
       vrf-neighbor, session-groupCommon node of
       neighbor-group-af, neighbor-af, vrf-neighbor-af,
       af-group-af";
    leaf next-hop-unchanged-multipath {
      type boolean;
      description
        "TRUE to disable overwriting of next hop for
         multipaths. FALSE to prevent next-hop-unchanged
         for multipaths.";
    }
  }

  grouping NEXT-HOP-RESOLUTION-PREFIX-LENGTH-MINIMUM {
    description
      "Common node of global-af, vrf-global-af";
    leaf next-hop-resolution-prefix-length-minimum {
      type uint32 {
        range "0..128";
      }
      default "0";
      description
        "Minimum prefix-length for nexthop resolution";
    }
  }

  grouping BEST-PATH-AS-PATH-LENGTH {
    description
      "Common node of global, vrf-global";
    leaf best-path-as-path-length {
      type empty;
      description
        "Change default route selection criteria to
         ignore AS path length";
    }
  }

  grouping MSG-LOG-OUT {
    description
      "Common node of global, vrf-globalCommon node of
       neighbor-group, neighbor, vrf-neighbor,
       session-group";
    container msg-log-out {
      description
        "Message log outbound";
      leaf msg-buf-count {
        type uint32 {
          range "1..100";
        }
        description
          "Outbound message log buffer size";
      }
      leaf msg-log-disable {
        type boolean;
        description
          "Disable inbound message logging";
      }
      leaf msg-log-inherit-disable {
        type boolean;
        description
          "TRUE, to prevent this entity from having a
           outbound message logging if parent has one";
      }
    }
  }

  grouping ENFORCE-MULTIPLE-LABELS {
    description
      "Common node of neighbor-group-af, neighbor-af,
       vrf-neighbor-af, af-group-af";
    leaf enforce-multiple-labels {
      type boolean;
      description
        "TRUE to enforce multiple labels support.";
    }
  }

  grouping PREFIX-ORF-POLICY {
    description
      "Common node of neighbor-group-af, neighbor-af,
       vrf-neighbor-af, af-group-afCommon node of
       neighbor-group-af, neighbor-af, vrf-neighbor-af,
       af-group-af";
    leaf prefix-orf-policy {
      type string;
      description
        "Prefix ORF policy name for incoming updates";
    }
  }

  grouping SOURCED-NETWORK-TABLE {
    description
      "Common node of global-af, vrf-global-af";
    container sourced-networks {
      description
        "Specify a network to announce via BGP";
      list sourced-network {
        key "network-addr network-prefix";
        description
          "Sourced network configuration";
        leaf network-addr {
          type inet:ip-address;
          description
            "Network in prefix/length format (address part)";
        }
        leaf network-prefix {
          type uint16 {
            range "0..128";
          }
          description
            "Network in prefix/length format (prefix part)";
        }
        leaf backdoor {
          type boolean;
          description
            "Specify a BGP backdoor route, default is FALSE";
        }
        leaf route-policy-name {
          type string;
          description
            "Route policy name";
        }
      }
    }
  }

  grouping REMOVE-PRIVATE-AS-ENTIRE-AS-PATH {
    description
      "Common node of neighbor-group-af, neighbor-af,
       vrf-neighbor-af, af-group-af";
    container remove-private-as-entire-as-path {
      presence "Indicates a remove-private-as-entire-as-path node is configured.";
      description
        "Remove private AS number from outbound updates";
      leaf enable {
        type boolean;
        mandatory true;
        description
          "TRUE to remove private AS from outbound updates
           .  FALSE to prevent remove-private-AS from
           being inherited.";
      }
      leaf entire {
        type boolean;
        description
          "TRUE to remove private AS from outbound updates
           if all ASes in aspath areprivate. FALSE to
           prevent remove-private-ASfrom being inherited.";
      }
    }
  }

  grouping GRACEFUL-MAINTENANCE {
    description
      "Common node of neighbor-group, neighbor,
       vrf-neighbor, session-group";
    container graceful-maintenance {
      description
        "Graceful Maintenance mode";
      container graceful-maintenance-local-preference {
        description
          "Set Local Preference to advertise routes with";
        leaf gshut-loc-pref-disable {
          type boolean;
          description
            "TRUE, to prevent inheritance of Local Pref
             value from its parents.FALSE, otherwise";
        }
        leaf local-preference {
          type uint32 {
            range "0..4294967295";
          }
          description
            "Local Preference Value";
        }
      }
      container graceful-maintenance-as-prepends {
        description
          "Number of times to prepend local AS number to
           the AS path";
        leaf gshut-prepends-disable {
          type boolean;
          description
            "TRUE, to prevent inheritance of AS Prepends
             value from its parents.FALSE, otherwise";
        }
        leaf as-prepends {
          type uint32 {
            range "0..6";
          }
          description
            "number of times AS prepends";
        }
      }
      leaf enable {
        type empty;
        description
          "Enter Graceful Maintenance mode to configure
           parametrs";
      }
      leaf graceful-maintenance-activate {
        type boolean;
        description
          "Initiate the graceful shutdown procedure";
      }
    }
  }

  grouping NEIGHBOR-AF-LONG-LIVED-GRACEFUL-RESTART-STALE-TIME {
    description
      "Common node of neighbor-group-af, neighbor-af,
       vrf-neighbor-af, af-group-af";
    container neighbor-af-long-lived-graceful-restart-stale-time {
      description
        "Maximum time to wait before purging long lived
         routes";
      leaf stale-time-send {
        type uint32 {
          range "0..16777215";
        }
        units "second";
        default "0";
        description
          "Max time (seconds)";
      }
      leaf stale-time-accept {
        type uint32 {
          range "0..16777215";
        }
        units "second";
        default "0";
        description
          "Max time (seconds)";
      }
    }
  }

  grouping BFD {
    description
      "Common node of global, vrf-global";
    container bfd {
      description
        "BFD configuration";
      leaf detection-multiplier {
        type uint32 {
          range "2..16";
        }
        description
          "Detection multiplier for BFD sessions created
           by BGP";
      }
      leaf interval {
        type uint32 {
          range "3..30000";
        }
        units "millisecond";
        description
          "Hello interval for BFD sessions created by BGP";
      }
    }
  }

  grouping ALLOCATE-LABEL {
    description
      "Common node of global-af, vrf-global-af";
    container allocate-label {
      presence "enable allocate-label";
      description
        "Label allocation policy";
      leaf all {
        type boolean;
        description
          "Whether all nets should be labeled, default is
           FALSE";
      }
      leaf route-policy-name {
        type string;
        description
          "Route policy name";
      }
      leaf un-labeled-path {
        type boolean;
        must '../all or ../route-policy-name' {
          tailf:xpath-root 3;
        }
        description
          "Allocate label for unlabeled paths too";
      }
    }
  }

  grouping SEND-BUFFER-SIZE {
    description
      "Common node of neighbor-group, neighbor,
       vrf-neighbor, session-group";
    container send-buffer-size {
      description
        "Set socket send buffer size and BGP write buffer
         size";
      leaf socket-send-size {
        type uint32 {
          range "4096..131072";
        }
        units "byte";
        default "24576";
        description
          "Send socket buffer size in bytes";
      }
      leaf bgp-send-size {
        type uint32 {
          range "4096..131072";
        }
        units "byte";
        default "4096";
        description
          "BGP write buffer size in bytes";
      }
    }
  }

  grouping BEST-PATH-MED-MISSING {
    description
      "Common node of neighbor-group, neighbor,
       vrf-neighbor, session-groupCommon node of global,
       vrf-global";
    leaf best-path-med-missing {
      type empty;
      description
        "Treat missing MED as the least preferred one";
    }
  }

  grouping SUPPRESS-ALL-CAPABILITIES {
    description
      "Common node of neighbor-group, neighbor,
       vrf-neighbor, session-group";
    leaf suppress-all-capabilities {
      type boolean;
      description
        "TRUE to suppress all capabilities. FALSE to not
         suppress and to prevent inheritance from a
         parent";
    }
  }

  grouping DEFAULT-WEIGHT {
    description
      "Common node of neighbor-group, neighbor,
       vrf-neighbor, session-groupCommon node of
       neighbor-group-af, neighbor-af, vrf-neighbor-af,
       af-group-af";
    leaf default-weight {
      type uint32 {
        range "0..65535";
      }
      description
        "Set default weight for routes from this
         neighbor/neighbor-group/af-group";
    }
  }

  grouping SUPPRESS-FOUR-BYTE-AS-CAPABILITY {
    description
      "Common node of neighbor-group, neighbor,
       vrf-neighbor, session-group";
    leaf suppress-four-byte-as-capability {
      type boolean;
      description
        "TRUE to suppress BGP 4-byte-as capability.
         FALSE to not suppress it and to prevent
         inheritance from a parent";
    }
  }

  grouping ADVERTISE-LOCAL-L2VPN-EVPN {
    description
      "Common node of neighbor-group-af, neighbor-af,
       vrf-neighbor-af, af-group-af";
    container advertise-local-l2vpn-evpn {
      description
        "Advertise Of Local Routes to the peer with
         different RT";
      leaf af-name {
        type dt1:Bgp-address-family;
        description
          "Address family";
      }
      leaf reorg-option {
        type Bgp-reorg-opt;
        description
          "Reorigination option";
      }
      leaf rt-type {
        type Bgp-adv-rt;
        description
          "RT type";
      }
    }
  }

  grouping EGRESS-PEER-ENGINEERING {
    description
      "Common node of neighbor-group, neighbor,
       vrf-neighbor, session-group";
    leaf egress-peer-engineering {
      type boolean;
      description
        "TRUE to enable egress peer engineering FALSE to
         disable egress peer engineering and to prevent
         inheritance from a parent";
    }
  }

  grouping BEST-PATH-CONFEDERATION-PATHS {
    description
      "Common node of global, vrf-global";
    leaf best-path-confederation-paths {
      type empty;
      description
        "Change default route selection criteria and
         allow the comparing of MED among confederation
         paths";
    }
  }

  grouping DYNAMIC-MED-INTERVAL {
    description
      "Common node of global-af, vrf-global-af";
    leaf dynamic-med-interval {
      type uint32 {
        range "0..10";
      }
      units "minute";
      default "10";
      description
        "Update generation delay (in minutes) after a MED
         change";
    }
  }

  grouping REMOVE-PRIVATE-AS-ENTIRE-AS-PATH-INBOUND {
    description
      "Common node of neighbor-group-af, neighbor-af,
       vrf-neighbor-af, af-group-af";
    container remove-private-as-entire-as-path-inbound {
      presence "Indicates a remove-private-as-entire-as-path-inbound node is configured.";
      description
        "Remove private AS number from inbound updates";
      leaf enable {
        type boolean;
        mandatory true;
        description
          "TRUE to remove private AS from inbound updates.
           FALSE to prevent remove-private-AS from being
           inherited.";
      }
      leaf entire {
        type boolean;
        description
          "TRUE to remove private AS from inbound updates
           if all ASes in aspath areprivate. FALSE to
           prevent remove-private-ASfrom being inherited.";
      }
    }
  }

  grouping RPKI-BESTPATH-USE-ORIGIN-AS-VALIDITY {
    description
      "Common node of global-af, vrf-global-af";
    leaf rpki-bestpath-use-origin-as-validity {
      type empty;
      description
        "RPKI bestpath use origin-AS validity";
    }
  }

  grouping BGP-CFG-RPKI-BESTPATH-USE-ORIGIN-AS-VALIDITY {
    description
      "Common node of global-af, vrf-global-afCommon
       node of global, vrf-global";
    leaf rpki-bestpath-use-origin-as-validity {
      type empty;
      description
        "RPKI bestpath use origin-AS validity";
    }
  }

  grouping CONNECTED-ROUTES {
    description
      "Common node of global-af, vrf-global-af";
    container connected-routes {
      presence "enable connected-routes";
      description
        "Redistribute connected routes";
      leaf default-metric {
        type Bgp-default-metric-range;
        description
          "Default metric";
      }
      leaf route-policy-name {
        type string;
        description
          "Route policy name";
      }
      leaf not-used {
        type uint32 {
          range "0..127";
        }
        description
          "Not used";
      }
    }
  }

  grouping IGP-REDIST-INTERNAL {
    description
      "Common node of global, vrf-global";
    leaf igp-redist-internal {
      type empty;
      description
        "Allow redistribution of iBGP into IGPs
         (dangerous)";
    }
  }

  grouping AIGP-SEND-MED {
    description
      "Common node of neighbor-group-af, neighbor-af,
       vrf-neighbor-af, af-group-af";
    leaf aigp-send-med {
      type Bgp-aigp-cfg;
      description
        "Enable/Disable sending AIGP in MED ";
    }
  }

  grouping AIGP {
    description
      "Common node of neighbor-group-af, neighbor-af,
       vrf-neighbor-af, af-group-af";
    leaf aigp {
      type Bgp-aigp-cfg;
      description
        "Enable Accumulated IGP Metric for this neighbor.";
    }
  }

  grouping ADVERTISE-ORF {
    description
      "Common node of neighbor-group-af, neighbor-af,
       vrf-neighbor-af, af-group-af";
    leaf advertise-orf {
      type Bgp-orf;
      default "none";
      description
        "Advertise ORF capability to the peer";
    }
  }

  grouping BFD-MINIMUM-INTERVAL {
    description
      "Common node of neighbor-group, neighbor,
       vrf-neighbor, session-group";
    leaf bfd-minimum-interval {
      type uint32 {
        range "3..30000";
      }
      units "millisecond";
      description
        "Hello interval for BFD sessions created by BGP";
    }
  }

  grouping AIGP-COST-COMMUNITY {
    description
      "Common node of neighbor-group-af, neighbor-af,
       vrf-neighbor-af, af-group-af";
    container aigp-cost-community {
      description
        "Send AIGP value in Cost Community. ";
      leaf enable {
        type boolean;
        description
          "TRUE to enable sending cost community, FALSE
           otherwise ";
      }
      leaf cost-community-id {
        when "../enable = 'true'" {
          tailf:xpath-root 3;
          description
            "../Enable = 'true'";
        }
        type uint32 {
          range "0..255";
        }
        description
          "Cost Community ID";
      }
      leaf transitive {
        when "../enable = 'true'" {
          tailf:xpath-root 3;
          description
            "../Enable = 'true'";
        }
        type boolean;
        description
          "True to send transitive cost community FALSE
           otherwise";
      }
      leaf cost-community-poi-type {
        when "../enable = 'true'" {
          tailf:xpath-root 3;
          description
            "../Enable = 'true'";
        }
        type Bgp-aigp-cfg-poi;
        description
          "Cost Community POI";
      }
    }
  }

  grouping DISABLE-AS-PATH-LOOP-CHECK {
    description
      "Common node of global-af, vrf-global-af";
    leaf disable-as-path-loop-check {
      type empty;
      description
        "Disable outbound AS Path loop check";
    }
  }

  grouping BEST-PATH-ROUTER-ID {
    description
      "Common node of global, vrf-global";
    leaf best-path-router-id {
      type empty;
      description
        "Change default route selection criteria and
         compare router-id for identical EBGP paths";
    }
  }

  grouping RIP-ROUTES {
    description
      "Common node of global-af, vrf-global-af";
    container rip-routes {
      presence "enable rip-routes";
      description
        "Redistribute RIP routes";
      leaf default-metric {
        type Bgp-default-metric-range;
        description
          "Default metric";
      }
      leaf route-policy-name {
        type string;
        description
          "Route policy name";
      }
      leaf not-used {
        type uint32 {
          range "0..127";
        }
        description
          "Not used";
      }
    }
  }

  grouping DESCRIPTION {
    description
      "Common node of neighbor-group, neighbor,
       vrf-neighbor, session-group";
    leaf description {
      type string;
      description
        "Up to 80 characters describing this neighbor";
    }
  }

  grouping ADVERTISE-L2VPN-EVPN {
    description
      "Common node of neighbor-group-af, neighbor-af,
       vrf-neighbor-af, af-group-af";
    container advertise-l2vpn-evpn {
      description
        "Advertise Translated Routes to the peer";
      leaf af-name {
        type dt1:Bgp-address-family;
        description
          "Address family";
      }
      leaf reorg-option {
        type Bgp-reorg-opt;
        description
          "Reorigination option";
      }
      leaf rt-type {
        type Bgp-adv-rt;
        description
          "RT type";
      }
    }
  }

  grouping KEYCHAIN {
    description
      "Common node of neighbor-group, neighbor,
       vrf-neighbor, session-group";
    container keychain {
      description
        "Set or disable keychain based authentication";
      leaf keychain-disable {
        type boolean;
        description
          "TRUE to prevent this entity from having a
           keychain based authentication even if the
           parent has one.FALSE to specify a keychain name";
      }
      leaf keychain-name {
        when "../keychain-disable = 'false'" {
          tailf:xpath-root 3;
          description
            "../KeychainDisable = false";
        }
        type string;
        description
          "Name of the keychain associated with neighbor";
      }
    }
  }

  grouping RECEIVE-BUFFER-SIZE {
    description
      "Common node of neighbor-group, neighbor,
       vrf-neighbor, session-group";
    container receive-buffer-size {
      description
        "Set socket receive buffer size and BGP read
         buffer size";
      leaf socket-receive-size {
        type uint32 {
          range "512..131072";
        }
        units "byte";
        default "32768";
        description
          "Receive socket buffer size in bytes";
      }
      leaf bgp-receive-size {
        type uint32 {
          range "512..131072";
        }
        units "byte";
        default "4096";
        description
          "BGP read buffer size in bytes";
      }
    }
  }

  grouping NEXT-HOP-UNCHANGED {
    description
      "Common node of neighbor-group-af, neighbor-af,
       vrf-neighbor-af, af-group-af";
    leaf next-hop-unchanged {
      type boolean;
      description
        "TRUE to disable overwriting of next hop before
         advertising to eBGP peers. FALSE to prevent
         next-hop-unchanged from being inherited.";
    }
  }

  grouping OSPF-ROUTE-TABLE {
    description
      "Common node of global-af, vrf-global-af";
    container ospf-routes {
      description
        "Redistribute information for OSPF routes.";
      list ospf-route {
        key "instance-name";
        description
          "Redistribute OSPF routes";
        leaf instance-name {
          type xr:Cisco-ios-xr-string;
          description
            "OSPF router tag";
        }
        leaf default-metric {
          type Bgp-default-metric-range;
          description
            "Default metric";
        }
        leaf route-policy-name {
          type string;
          description
            "Route policy name";
        }
        leaf redist-type {
          type xr:Hex-integer;
          description
            "Redistribution type: 01 for internal routes,
             02 for external routes of type 1, 04 for
             external routes of type 2, 08 for NSSA
             external routes of type 1, 10 for NSSA
             external routes of type 2, 20 for external
             routes, 40 for NSSA external routes.  Logical
             combinations permitted.";
        }
      }
    }
  }

  grouping ROUTER-ID {
    description
      "Common node of global, vrf-global";
    leaf router-id {
      type inet:ipv4-address-no-zone;
      default "0.0.0.0";
      description
        "Configure Router-id";
    }
  }

  grouping DEFAULT-METRIC {
    description
      "Common node of global, vrf-global";
    leaf default-metric {
      type uint32 {
        range "1..4294967295";
      }
      description
        "Default redistributed metric";
    }
  }

  grouping RPKI-ORIGIN-AS-VALIDATION-DISABLE {
    description
      "Common node of neighbor-group-af, neighbor-af,
       vrf-neighbor-af, af-group-af";
    leaf rpki-origin-as-validation-disable {
      type empty;
      description
        "RPKI origin-AS validation disable";
    }
  }

  grouping BGP-CFG-RPKI-ORIGIN-AS-VALIDATION-DISABLE {
    description
      "Common node of neighbor-group-af, neighbor-af,
       vrf-neighbor-af, af-group-afCommon node of
       neighbor-group, neighbor, vrf-neighbor,
       session-group";
    leaf rpki-origin-as-validation-disable {
      type empty;
      description
        "RPKI origin-AS validation disable";
    }
  }

  grouping DISABLE-NEIGHBOR-LOGGING {
    description
      "Common node of global, vrf-global";
    leaf disable-neighbor-logging {
      type empty;
      description
        "Disable neighbor change logging";
    }
  }

  grouping TCPMSS {
    description
      "Common node of neighbor-group, neighbor,
       vrf-neighbor, session-group";
    container tcpmss {
      description
        "TCP Maximum segment size";
      leaf tcpmss-disable {
        type boolean;
        description
          "TRUE, to prevent inheritance ofTCP MSS
           valuefrom its parents.FALSE, otherwise";
      }
      leaf mss {
        type uint32 {
          range "68..10000";
        }
        description
          "Maximum Segment Size";
      }
    }
  }

  augment "/ncs:devices/ncs:device/ncs:config" {
    leaf asn-format {
      tailf:ncs-device-type "netconf";
      tailf:display-when "not(../../ncs:module) or ../../ncs:module[ncs:name='Cisco-IOS-XR-ipv4-bgp-cfg']";
      type Bgp-asn;
      default "as-plain";
      description
        "Autonomous system number format";
    }
    container bgp {
      tailf:ncs-device-type "netconf";
      tailf:display-when "not(../../ncs:module) or ../../ncs:module[ncs:name='Cisco-IOS-XR-ipv4-bgp-cfg']";
      description
        "bgp";
      list instance {
        must 'instance-as' {
          tailf:xpath-root 3;
          description
            "must be set.";
        }
        key "instance-name";
        description
          "BGP instance configuration commands";
        leaf instance-name {
          type xr:Cisco-ios-xr-string;
          description
            "Instance Name. For Default instance use -
             default";
        }
        list instance-as {
          must 'four-byte-as' {
            tailf:xpath-root 3;
            description
              "must be set.";
          }
          key "as";
          description
            "Autonomous system";
          leaf as {
            type dt1:Bgp-as-range;
            description
              "Higher 16 bits of 4-byte Autonomous system
               number";
          }
          list four-byte-as {
            key "as";
            description
              "4-byte Autonomous system";
            container vrfs {
              description
                "VRF config";
              list vrf {
                key "vrf-name";
                description
                  "VRF config";
                container vrf-global {
                  description
                    "VRF attribute config";
                  container route-distinguisher {
                    description
                      "Route distinguisher";
                    leaf type {
                      type Bgp-route-distinguisher;
                      description
                        "Type of RD";
                    }
                    leaf as-xx {
                      when "../type = 'as' or ../type = 'four-byte-as'" {
                        tailf:xpath-root 3;
                        description
                          "../Type = AS or ../Type = FourByteAS";
                      }
                      type dt1:Bgp-as-range;
                      description
                        "AS number";
                    }
                    leaf as {
                      when "../type = 'as' or ../type = 'four-byte-as'" {
                        tailf:xpath-root 3;
                        description
                          "../Type = AS or ../Type = FourByteAS";
                      }
                      type dt1:Bgp-as-range;
                      description
                        "AS number";
                    }
                    leaf as-index {
                      when "../type = 'as' or ../type = 'four-byte-as'" {
                        tailf:xpath-root 3;
                        description
                          "../Type = AS or ../Type = FourByteAS";
                      }
                      type dt1:Bgp-extcomm-asn-index;
                      description
                        "ASN Index";
                    }
                    leaf address {
                      when "../type = 'ipv4-address'" {
                        tailf:xpath-root 3;
                        description
                          "../Type = IPV4Address";
                      }
                      type inet:ipv4-address-no-zone;
                      description
                        "IP address";
                    }
                    leaf address-index {
                      when "../type = 'ipv4-address'" {
                        tailf:xpath-root 3;
                        description
                          "../Type = IPV4Address";
                      }
                      type dt1:Bgp-extcomm-v4-addr-index;
                      description
                        "IP address index";
                    }
                  }
                  container vrf-global-afs {
                    description
                      "Global VRF-specific configuration";
                    list vrf-global-af {
                      key "af-name";
                      description
                        "Global VRF AF-specific configuration";
                      container mvpn {
                        description
                          "MVPN configurations";
                        leaf single-forwarder-selection {
                          type Bgp-mvpn-sfs-select;
                          description
                            "Select MVPN single forwarder selection";
                        }
                      }
                      container ebgp {
                        presence "Indicates a ebgp node is configured.";
                        description
                          "Use eBGP multipaths";
                        leaf paths-value {
                          type uint32 {
                            range "2..32";
                          }
                          mandatory true;
                          description
                            "Number of paths";
                        }
                        leaf unequal-cost {
                          type boolean;
                          default "false";
                          description
                            "UNUSED";
                        }
                        leaf selective {
                          type boolean;
                          default "false";
                          description
                            "Allow multipaths only from marked
                             neighbors";
                        }
                        leaf order-by-igp-metric {
                          type boolean;
                          default "false";
                          description
                            "Order candidate multipaths by IGP
                             metric";
                        }
                      }
                      container eibgp {
                        presence "Indicates a eibgp node is configured.";
                        description
                          "Use eiBGP multipaths";
                        leaf paths-value {
                          type uint32 {
                            range "2..32";
                          }
                          mandatory true;
                          description
                            "Number of paths";
                        }
                        leaf unequal-cost {
                          type boolean;
                          default "false";
                          description
                            "UNUSED";
                        }
                        leaf selective {
                          type boolean;
                          default "false";
                          description
                            "Allow multipaths only from marked
                             neighbors";
                        }
                        leaf order-by-igp-metric {
                          type boolean;
                          default "false";
                          description
                            "Order candidate multipaths by IGP
                             metric";
                        }
                      }
                      container ibgp {
                        presence "Indicates a ibgp node is configured.";
                        description
                          "Use iBGP multipaths";
                        leaf paths-value {
                          type uint32 {
                            range "2..32";
                          }
                          mandatory true;
                          description
                            "Number of paths";
                        }
                        leaf unequal-cost {
                          type boolean;
                          default "false";
                          description
                            "Allow multipaths to have different IGP
                             metrics";
                        }
                        leaf selective {
                          type boolean;
                          default "false";
                          description
                            "Allow multipaths only from marked
                             neighbors";
                        }
                        leaf order-by-igp-metric {
                          type boolean;
                          default "false";
                          description
                            "Order candidate multipaths by IGP
                             metric";
                        }
                      }
                      leaf rt-download {
                        type empty;
                        description
                          "Route-Target download configuration";
                      }
                      leaf allow-vpn-default-originate {
                        type boolean;
                        description
                          "TRUE to send default orig route to VPN
                           neighborFALSE to not send default
                           originate route ";
                      }
                      leaf af-name {
                        type dt1:Bgp-address-family;
                        description
                          "Address family";
                      }
                      uses RPKI-ORIGIN-AS-VALIDATION-ENABLE;
                      uses AGGREGATE-ADDRESS-TABLE;
                      uses DYNAMIC-MED-INTERVAL;
                      uses OPTIMAL-ROUTE-REFLECTOR-GROUP-TABLE;
                      uses DAMPENING;
                      uses ENABLE;
                      uses RIP-ROUTES;
                      uses LISP-ROUTES;
                      uses STATIC-ROUTES;
                      uses DISTANCE;
                      uses TABLE-POLICY;
                      uses APP-ROUTE-TABLE;
                      uses ATTRIBUTE-DOWNLOAD;
                      uses LABEL-MODE;
                      uses EIGRP-ROUTE-TABLE;
                      uses BEST-EXTERNAL;
                      uses SOURCED-NETWORK-TABLE;
                      uses RPKI-ORIGIN-AS-VALIDITY-SIGNAL-IBGP;
                      uses CONNECTED-ROUTES;
                      uses ADDITIONAL-PATHS-RECEIVE;
                      uses PERMANENT-NETWORK;
                      uses RPKI-BESTPATH-USE-ORIGIN-AS-VALIDITY;
                      uses ALLOCATE-LABEL;
                      uses ADDITIONAL-PATHS-SELECTION;
                      uses BGP-CFG-RPKI-BESTPATH-ORIGIN-AS-ALLOW-INVALID-MP;
                      uses NEXT-HOP-RESOLUTION-PREFIX-LENGTH-MINIMUM;
                      uses RESET-WEIGHT-ON-IMPORT;
                      uses OSPF-ROUTE-TABLE;
                      uses ADDITIONAL-PATHS-SEND;
                      uses ADVERTISE-LOCAL-LABELED-ROUTE-SAFI-UNICAST;
                      uses MOBILE-ROUTES;
                      uses DISABLE-AS-PATH-LOOP-CHECK;
                      uses SUBSCRIBER-ROUTES;
                      uses SEGMENT-ROUTING;
                    }
                  }
                  leaf exists {
                    type empty;
                    description
                      "Create this VRF. Deletion of this object
                       causes deletion of all the objects under
                       VRF associated with this object.";
                  }
                  uses ROUTER-ID;
                  uses DISABLE-ENFORCE-FIRST-AS;
                  uses BEST-PATH-COST-COMMUNITY;
                  uses BEST-PATH-AIGP-IGNORE;
                  uses BEST-PATH-AS-PATH-LENGTH;
                  uses IGP-REDIST-INTERNAL;
                  uses MULTI-PATH-AS-PATH-IGNORE-ONWARDS;
                  uses DISABLE-FAST-EXTERNAL-FALLOVER;
                  uses UNSAFE-EBGP-POLICY;
                  uses DEFAULT-METRIC;
                  uses DEFAULT-INFO-ORIGINATE;
                  uses BGP-CFG-RPKI-ORIGIN-AS-VALIDITY-SIGNAL-IBGP;
                  uses BGP-CFG-RPKI-BESTPATH-USE-ORIGIN-AS-VALIDITY;
                  uses BEST-PATH-CONFEDERATION-PATHS;
                  uses BEST-PATH-AS-MULTIPATH-RELAX;
                  uses MPLS-ACTIVATED-INTERFACE-TABLE;
                  uses DISABLE-AUTO-SOFT-RESET;
                  uses DISABLE-MSG-LOG;
                  uses GLOBAL-TIMERS;
                  uses BEST-PATH-IGP-METRIC-IGNORE;
                  uses NEXT-HOP-RES-ALLOW-DEFAULT;
                  uses NEXT-HOP-MPLS-FWD-IBGP;
                  uses BFD;
                  uses DISABLE-NEIGHBOR-LOGGING;
                  uses SEND-SOCKET-BUFFER-SIZES;
                  uses BEST-PATH-MED-ALWAYS;
                  uses RECEIVE-SOCKET-BUFFER-SIZES;
                  uses BEST-PATH-ROUTER-ID;
                  uses BEST-PATH-MED-MISSING;
                  uses LOCAL-PREFERENCE;
                }
                container vrf-neighbors {

                  grouping VRF-NEIGHBOR-CONTENT {
                    description
                      "VRF NEIGHBOR CONTENT";
                    container vrf-neighbor-afs {
                      description
                        "Address family type of a VRF neighbor";
                      list vrf-neighbor-af {
                        key "af-name";
                        description
                          "Address family type of a VRF neighbor";
                        leaf af-name {
                          type dt1:Bgp-address-family;
                          description
                            "BGP neighbor address family";
                        }
                        uses NEIGHBOR-AF-LONG-LIVED-GRACEFUL-RESTART-CAPABLE;
                        uses SEND-EXT-COMMUNITY-EBGP;
                        uses ACCEPT-ROUTE-LEGACY-RT;
                        uses AIGP-COST-COMMUNITY;
                        uses SEND-COMMUNITY-EBGP;
                        uses ADVERTISE-DEF-IMP-DISABLE-V6;
                        uses ADVERTISE-DISABLE;
                        uses MAXIMUM-PREFIXES;
                        uses ADVERTISE-BRIDGE-DOMAIN-IMP-DISABLE-V6;
                        uses REMOVE-PRIVATE-AS-ENTIRE-AS-PATH-INBOUND;
                        uses NEXT-HOP-UNCHANGED;
                        uses ADVERTISE-LOCAL-LABELED-ROUTE;
                        uses ADVERTISE-DEF-IMP-DISABLE-V4;
                        uses RPKI-ORIGIN-AS-VALIDATION-DISABLE;
                        uses ADVERTISE-BRIDGE-DOMAIN-IMP-DISABLE-V4;
                        uses FLOWSPEC-VALIDATION;
                        uses ADVERTISE-L2VPN-EVPN;
                        uses ADVERTISE-LOCAL-L2VPN-EVPN;
                        uses ENCAPSULATION-TYPE;
                        uses RPKI-BESTPATH-ORIGIN-AS-ALLOW-INVALID;
                        uses ENFORCE-MULTIPLE-LABELS;
                        uses AS-OVERRIDE;
                        uses MULTIPATH;
                        uses SEND-COMMUNITY-EBGP-GRACEFUL-SHUTDOWN;
                        uses ACTIVATE;
                        uses PREFIX-ORF-POLICY;
                        uses NEIGHBOR-AF-LONG-LIVED-GRACEFUL-RESTART-STALE-TIME;
                        uses SITE-OF-ORIGIN;
                        uses UPDATE-OUT-ORIG-LOOP-CHK-DISABLE;
                        uses AIGP;
                        uses AIGP-SEND-MED;
                        uses ADVERTISE-V6;
                        uses ALLOW-AS-IN;
                        uses ADVERTISE-ORF;
                        uses ROUTE-REFLECTOR-CLIENT;
                        uses NEXT-HOP-SELF;
                        uses ADVERTISE-LOCAL-V6;
                        uses ROUTE-POLICY-IN;
                        uses IMPORT;
                        uses DEFAULT-ORIGINATE;
                        uses SOFT-RECONFIGURATION;
                        uses ADVERTISE-VRF-IMP-DISABLE-V6;
                        uses DEFAULT-WEIGHT;
                        uses AF-GROUP;
                        uses ADVERTISE-V4;
                        uses NEXT-HOP-UNCHANGED-MULTIPATH;
                        uses OPTIMAL-ROUTE-REFLECTION-GROUP;
                        uses ACCEPT-OWN;
                        uses ROUTE-POLICY-OUT;
                        uses ADVERTISE-LOCAL-V4;
                        uses ADVERTISE-PERMANENT-NETWORK;
                        uses REMOVE-PRIVATE-AS-ENTIRE-AS-PATH;
                        uses ADVERTISE-VRF-IMP-DISABLE-V4;
                      }
                    }
                    uses LOCAL-ADDRESS-SUB-NET;
                    uses INTERNAL-VPN-CLIENT-IBGP-CE;
                    uses LOCAL-ADDRESS;
                    uses BMP-ACTIVATE-TABLE;
                    uses EBGP-MULTIHOP;
                    uses SESSION-GROUP-ADD-MEMBER;
                    uses EGRESS-PEER-ENGINEERING;
                    uses REMOTE-AS;
                    uses MERGE-SAFI1-AND4-INBOUND-UPDATES;
                    uses LOCAL-AS;
                    uses NEIGHBOR-GRACEFUL-RESTART-STALEPATH-TIME;
                    uses SHUTDOWN;
                    uses DESCRIPTION;
                    uses NEIGHBOR-GROUP-ADD-MEMBER;
                    uses PASSWORD;
                    uses EBGP-RECV-DMZ;
                    uses ADVERTISEMENT-INTERVAL;
                    uses NEIGHBOR-CLUSTER-ID;
                    uses NEIGHBOR-GRACEFUL-RESTART;
                    uses ENFORCE-FIRST-AS;
                    uses IDLE-WATCH-TIME;
                    uses TCPMSS;
                    uses SESSION-OPEN-MODE;
                    uses BGP-CFG-RPKI-ORIGIN-AS-VALIDATION-DISABLE;
                    uses TOS;
                    uses UPDATE-IN-FILTERING;
                    uses EBGP-SEND-DMZ-ENABLE-MODES;
                    uses MSG-LOG-OUT;
                    uses SUPPRESS-ALL-CAPABILITIES;
                    uses MAX-PEERS;
                    uses AO-KEYCHAIN;
                    uses BGP-CFG-RPKI-BESTPATH-ORIGIN-AS-ALLOW-INVALID;
                    uses RECEIVE-BUFFER-SIZE;
                    uses MSG-LOG-IN;
                    uses ADDITIONAL-PATHS-SEND-CAPABILITY;
                    uses PROPAGATE-DMZ-LINK-BANDWIDTH;
                    uses BFD-ENABLE-MODES;
                    uses SEND-BUFFER-SIZE;
                    uses TTL-SECURITY;
                    uses NEIGHBOR-GRACEFUL-RESTART-TIME;
                    uses TIMERS;
                    uses BFD-MULTIPLIER;
                    uses BFD-MINIMUM-INTERVAL;
                    uses REMOTE-AS-LIST;
                    uses ADDITIONAL-PATHS-RECEIVE-CAPABILITY;
                    uses KEYCHAIN;
                    uses IGNORE-CONNECTED-CHECK-EBGP;
                    uses SUPPRESS-FOUR-BYTE-AS-CAPABILITY;
                    uses UPDATE-SOURCE-INTERFACE;
                    uses GRACEFUL-MAINTENANCE;
                  }
                  list vrf-neighbor {
                    key "neighbor-address";
                    description
                      "A particular VRF peer";
                    leaf neighbor-address {
                      type inet:ip-address-no-zone;
                      description
                        "Neighbor address";
                    }
                    uses VRF-NEIGHBOR-CONTENT;
                  }
                  list vrf-neighbor-prefix-length {
                    key "prefix-length neighbor-address";
                    description
                      "A particular VRF peer";
                    leaf prefix-length {
                      type uint32 {
                        range "0..127";
                      }
                      description
                        "Prefix length";
                    }
                    leaf neighbor-address {
                      type inet:ip-address-no-zone;
                      description
                        "Neighbor address";
                    }
                    uses VRF-NEIGHBOR-CONTENT;
                  }
                  description
                    "BGP VRF peer";
                }
                leaf vrf-name {
                  type xr:Cisco-ios-xr-string;
                  description
                    "VRF name";
                }
              }
            }
            container default-vrf {
              description
                "Global default config";
              container bgp-entity {
                description
                  "Neighbor, neighbor-group, af-group and
                   session-group configuration";
                container neighbors {

                  grouping NEIGHBOR-CONTENT {
                    description
                      "NEIGHBOR CONTENT";
                    container neighbor-afs {
                      description
                        "BGP neighbor AF configuration table";
                      list neighbor-af {
                        key "af-name";
                        description
                          "Address family type of neighbor";
                        leaf af-name {
                          type dt1:Bgp-address-family;
                          description
                            "BGP neighbor address family";
                        }
                        uses NEIGHBOR-AF-LONG-LIVED-GRACEFUL-RESTART-CAPABLE;
                        uses L2VPN-SIGNALLING;
                        uses SEND-EXT-COMMUNITY-EBGP;
                        uses ACCEPT-ROUTE-LEGACY-RT;
                        uses AIGP-COST-COMMUNITY;
                        uses SEND-COMMUNITY-EBGP;
                        uses ADVERTISE-DEF-IMP-DISABLE-V6;
                        uses ADVERTISE-DISABLE;
                        uses SEND-MULTICAST-ATTR;
                        uses MAXIMUM-PREFIXES;
                        uses ADVERTISE-BRIDGE-DOMAIN-IMP-DISABLE-V6;
                        uses REMOVE-PRIVATE-AS-ENTIRE-AS-PATH-INBOUND;
                        uses NEXT-HOP-UNCHANGED;
                        uses ADVERTISE-LOCAL-LABELED-ROUTE;
                        uses ADVERTISE-DEF-IMP-DISABLE-V4;
                        uses RPKI-ORIGIN-AS-VALIDATION-DISABLE;
                        uses ADVERTISE-BRIDGE-DOMAIN-IMP-DISABLE-V4;
                        uses FLOWSPEC-VALIDATION;
                        uses ADVERTISE-L2VPN-EVPN;
                        uses ADVERTISE-LOCAL-L2VPN-EVPN;
                        uses ENCAPSULATION-TYPE;
                        uses RPKI-BESTPATH-ORIGIN-AS-ALLOW-INVALID;
                        uses ENFORCE-MULTIPLE-LABELS;
                        uses AS-OVERRIDE;
                        uses MULTIPATH;
                        uses SEND-COMMUNITY-EBGP-GRACEFUL-SHUTDOWN;
                        uses ACTIVATE;
                        uses PREFIX-ORF-POLICY;
                        uses NEIGHBOR-AF-LONG-LIVED-GRACEFUL-RESTART-STALE-TIME;
                        uses UPDATE-OUT-ORIG-LOOP-CHK-DISABLE;
                        uses AIGP;
                        uses AIGP-SEND-MED;
                        uses ADVERTISE-V6;
                        uses ALLOW-AS-IN;
                        uses ADVERTISE-ORF;
                        uses ROUTE-REFLECTOR-CLIENT;
                        uses NEXT-HOP-SELF;
                        uses ADVERTISE-LOCAL-V6;
                        uses ROUTE-POLICY-IN;
                        uses IMPORT;
                        uses DEFAULT-ORIGINATE;
                        uses SOFT-RECONFIGURATION;
                        uses ADVERTISE-VRF-IMP-DISABLE-V6;
                        uses DEFAULT-WEIGHT;
                        uses AF-GROUP;
                        uses ADVERTISE-V4;
                        uses NEXT-HOP-UNCHANGED-MULTIPATH;
                        uses OPTIMAL-ROUTE-REFLECTION-GROUP;
                        uses ACCEPT-OWN;
                        uses ROUTE-POLICY-OUT;
                        uses ADVERTISE-LOCAL-V4;
                        uses ADVERTISE-PERMANENT-NETWORK;
                        uses REMOVE-PRIVATE-AS-ENTIRE-AS-PATH;
                        uses ADVERTISE-VRF-IMP-DISABLE-V4;
                      }
                    }
                    uses LOCAL-ADDRESS-SUB-NET;
                    uses INTERNAL-VPN-CLIENT-IBGP-CE;
                    uses LOCAL-ADDRESS;
                    uses BMP-ACTIVATE-TABLE;
                    uses EBGP-MULTIHOP;
                    uses SESSION-GROUP-ADD-MEMBER;
                    uses EGRESS-PEER-ENGINEERING;
                    uses REMOTE-AS;
                    uses MERGE-SAFI1-AND4-INBOUND-UPDATES;
                    uses LOCAL-AS;
                    uses NEIGHBOR-GRACEFUL-RESTART-STALEPATH-TIME;
                    uses SHUTDOWN;
                    uses DESCRIPTION;
                    uses NEIGHBOR-GROUP-ADD-MEMBER;
                    uses PASSWORD;
                    uses EBGP-RECV-DMZ;
                    uses ADVERTISEMENT-INTERVAL;
                    uses NEIGHBOR-CLUSTER-ID;
                    uses NEIGHBOR-GRACEFUL-RESTART;
                    uses ENFORCE-FIRST-AS;
                    uses IDLE-WATCH-TIME;
                    uses TCPMSS;
                    uses SESSION-OPEN-MODE;
                    uses BGP-CFG-RPKI-ORIGIN-AS-VALIDATION-DISABLE;
                    uses TOS;
                    uses UPDATE-IN-FILTERING;
                    uses EBGP-SEND-DMZ-ENABLE-MODES;
                    uses MSG-LOG-OUT;
                    uses SUPPRESS-ALL-CAPABILITIES;
                    uses MAX-PEERS;
                    uses AO-KEYCHAIN;
                    uses BGP-CFG-RPKI-BESTPATH-ORIGIN-AS-ALLOW-INVALID;
                    uses RECEIVE-BUFFER-SIZE;
                    uses MSG-LOG-IN;
                    uses ADDITIONAL-PATHS-SEND-CAPABILITY;
                    uses PROPAGATE-DMZ-LINK-BANDWIDTH;
                    uses BFD-ENABLE-MODES;
                    uses SEND-BUFFER-SIZE;
                    uses TTL-SECURITY;
                    uses NEIGHBOR-GRACEFUL-RESTART-TIME;
                    uses TIMERS;
                    uses BFD-MULTIPLIER;
                    uses BFD-MINIMUM-INTERVAL;
                    uses REMOTE-AS-LIST;
                    uses ADDITIONAL-PATHS-RECEIVE-CAPABILITY;
                    uses KEYCHAIN;
                    uses IGNORE-CONNECTED-CHECK-EBGP;
                    uses SUPPRESS-FOUR-BYTE-AS-CAPABILITY;
                    uses UPDATE-SOURCE-INTERFACE;
                    uses GRACEFUL-MAINTENANCE;
                  }
                  list neighbor {
                    key "neighbor-address";
                    description
                      "A particular BGP peer";
                    leaf neighbor-address {
                      type inet:ip-address-no-zone;
                      description
                        "Neighbor address";
                    }
                    uses NEIGHBOR-CONTENT;
                  }
                  list neighbor-prefix-length {
                    key "prefix-length neighbor-address";
                    description
                      "A particular BGP peer";
                    leaf prefix-length {
                      type uint32 {
                        range "0..127";
                      }
                      description
                        "Prefix length";
                    }
                    leaf neighbor-address {
                      type inet:ip-address-no-zone;
                      description
                        "Neighbor address";
                    }
                    uses NEIGHBOR-CONTENT;
                  }
                  description
                    "Neighbor configuration";
                }
                container neighbor-groups {
                  description
                    "Neighbor-group configuration";
                  list neighbor-group {
                    key "neighbor-group-name";
                    description
                      "A particular BGP neighbor group";
                    container neighbor-group-afs {
                      description
                        "BGP neighbor-group AF configuration table";
                      list neighbor-group-af {
                        key "af-name";
                        description
                          "Address family type of neighbor group";
                        leaf af-name {
                          type dt1:Bgp-address-family;
                          description
                            "BGP neighbor group address family";
                        }
                        uses NEIGHBOR-AF-LONG-LIVED-GRACEFUL-RESTART-CAPABLE;
                        uses L2VPN-SIGNALLING;
                        uses SEND-EXT-COMMUNITY-EBGP;
                        uses ACCEPT-ROUTE-LEGACY-RT;
                        uses AIGP-COST-COMMUNITY;
                        uses SEND-COMMUNITY-EBGP;
                        uses ADVERTISE-DEF-IMP-DISABLE-V6;
                        uses ADVERTISE-DISABLE;
                        uses SEND-MULTICAST-ATTR;
                        uses MAXIMUM-PREFIXES;
                        uses ADVERTISE-BRIDGE-DOMAIN-IMP-DISABLE-V6;
                        uses REMOVE-PRIVATE-AS-ENTIRE-AS-PATH-INBOUND;
                        uses NEXT-HOP-UNCHANGED;
                        uses ADVERTISE-LOCAL-LABELED-ROUTE;
                        uses ADVERTISE-DEF-IMP-DISABLE-V4;
                        uses RPKI-ORIGIN-AS-VALIDATION-DISABLE;
                        uses ADVERTISE-BRIDGE-DOMAIN-IMP-DISABLE-V4;
                        uses FLOWSPEC-VALIDATION;
                        uses ADVERTISE-L2VPN-EVPN;
                        uses ADVERTISE-LOCAL-L2VPN-EVPN;
                        uses ENCAPSULATION-TYPE;
                        uses RPKI-BESTPATH-ORIGIN-AS-ALLOW-INVALID;
                        uses ENFORCE-MULTIPLE-LABELS;
                        uses AS-OVERRIDE;
                        uses MULTIPATH;
                        uses SEND-COMMUNITY-EBGP-GRACEFUL-SHUTDOWN;
                        uses ACTIVATE;
                        uses PREFIX-ORF-POLICY;
                        uses NEIGHBOR-AF-LONG-LIVED-GRACEFUL-RESTART-STALE-TIME;
                        uses SITE-OF-ORIGIN;
                        uses UPDATE-OUT-ORIG-LOOP-CHK-DISABLE;
                        uses AIGP;
                        uses AIGP-SEND-MED;
                        uses ADVERTISE-V6;
                        uses ALLOW-AS-IN;
                        uses ADVERTISE-ORF;
                        uses ROUTE-REFLECTOR-CLIENT;
                        uses NEXT-HOP-SELF;
                        uses ADVERTISE-LOCAL-V6;
                        uses ROUTE-POLICY-IN;
                        uses IMPORT;
                        uses DEFAULT-ORIGINATE;
                        uses SOFT-RECONFIGURATION;
                        uses ADVERTISE-VRF-IMP-DISABLE-V6;
                        uses DEFAULT-WEIGHT;
                        uses AF-GROUP;
                        uses ADVERTISE-V4;
                        uses NEXT-HOP-UNCHANGED-MULTIPATH;
                        uses OPTIMAL-ROUTE-REFLECTION-GROUP;
                        uses ACCEPT-OWN;
                        uses ROUTE-POLICY-OUT;
                        uses ADVERTISE-LOCAL-V4;
                        uses ADVERTISE-PERMANENT-NETWORK;
                        uses REMOVE-PRIVATE-AS-ENTIRE-AS-PATH;
                        uses ADVERTISE-VRF-IMP-DISABLE-V4;
                      }
                    }
                    leaf neighbor-group-add-member {
                      type string;
                      description
                        "Inherit configuration from a
                         neighbor-group";
                    }
                    leaf neighbor-group-name {
                      type xr:Cisco-ios-xr-string;
                      description
                        "BGP neighbor group name";
                    }
                    uses LOCAL-ADDRESS-SUB-NET;
                    uses INTERNAL-VPN-CLIENT-IBGP-CE;
                    uses LOCAL-ADDRESS;
                    uses BMP-ACTIVATE-TABLE;
                    uses EBGP-MULTIHOP;
                    uses SESSION-GROUP-ADD-MEMBER;
                    uses EGRESS-PEER-ENGINEERING;
                    uses REMOTE-AS;
                    uses MERGE-SAFI1-AND4-INBOUND-UPDATES;
                    uses LOCAL-AS;
                    uses NEIGHBOR-GRACEFUL-RESTART-STALEPATH-TIME;
                    uses SHUTDOWN;
                    uses DESCRIPTION;
                    uses PASSWORD;
                    uses EBGP-RECV-DMZ;
                    uses ADVERTISEMENT-INTERVAL;
                    uses NEIGHBOR-CLUSTER-ID;
                    uses NEIGHBOR-GRACEFUL-RESTART;
                    uses ENFORCE-FIRST-AS;
                    uses IDLE-WATCH-TIME;
                    uses TCPMSS;
                    uses SESSION-OPEN-MODE;
                    uses BGP-CFG-RPKI-ORIGIN-AS-VALIDATION-DISABLE;
                    uses TOS;
                    uses UPDATE-IN-FILTERING;
                    uses EBGP-SEND-DMZ-ENABLE-MODES;
                    uses MSG-LOG-OUT;
                    uses SUPPRESS-ALL-CAPABILITIES;
                    uses MAX-PEERS;
                    uses AO-KEYCHAIN;
                    uses BGP-CFG-RPKI-BESTPATH-ORIGIN-AS-ALLOW-INVALID;
                    uses RECEIVE-BUFFER-SIZE;
                    uses MSG-LOG-IN;
                    uses ADDITIONAL-PATHS-SEND-CAPABILITY;
                    uses PROPAGATE-DMZ-LINK-BANDWIDTH;
                    uses BFD-ENABLE-MODES;
                    uses SEND-BUFFER-SIZE;
                    uses TTL-SECURITY;
                    uses NEIGHBOR-GRACEFUL-RESTART-TIME;
                    uses TIMERS;
                    uses BFD-MULTIPLIER;
                    uses BFD-MINIMUM-INTERVAL;
                    uses REMOTE-AS-LIST;
                    uses ADDITIONAL-PATHS-RECEIVE-CAPABILITY;
                    uses KEYCHAIN;
                    uses IGNORE-CONNECTED-CHECK-EBGP;
                    uses SUPPRESS-FOUR-BYTE-AS-CAPABILITY;
                    uses UPDATE-SOURCE-INTERFACE;
                    uses CREATE;
                    uses GRACEFUL-MAINTENANCE;
                  }
                }
                container af-groups {
                  description
                    "AF-group configuration";
                  list af-group {
                    key "af-group-name";
                    description
                      "A particular BGP AF group";
                    container af-group-afs {
                      description
                        "AF group configuration table";
                      list af-group-af {
                        key "af-name";
                        description
                          "Address family type of an AF group";
                        leaf af-group {
                          type string;
                          description
                            "Inherit configuration for this
                             address-family from an AF-group";
                        }
                        leaf create {
                          type empty;
                          description
                            "Create this address family group.
                             Deletion of this object causes deletion
                             of all the objects under AFGroup
                             associated with this object.";
                        }
                        leaf af-name {
                          type dt1:Bgp-address-family;
                          description
                            "BGP AF group address family";
                        }
                        uses NEIGHBOR-AF-LONG-LIVED-GRACEFUL-RESTART-CAPABLE;
                        uses L2VPN-SIGNALLING;
                        uses SEND-EXT-COMMUNITY-EBGP;
                        uses ACCEPT-ROUTE-LEGACY-RT;
                        uses AIGP-COST-COMMUNITY;
                        uses SEND-COMMUNITY-EBGP;
                        uses ADVERTISE-DEF-IMP-DISABLE-V6;
                        uses ADVERTISE-DISABLE;
                        uses SEND-MULTICAST-ATTR;
                        uses MAXIMUM-PREFIXES;
                        uses ADVERTISE-BRIDGE-DOMAIN-IMP-DISABLE-V6;
                        uses REMOVE-PRIVATE-AS-ENTIRE-AS-PATH-INBOUND;
                        uses NEXT-HOP-UNCHANGED;
                        uses ADVERTISE-LOCAL-LABELED-ROUTE;
                        uses ADVERTISE-DEF-IMP-DISABLE-V4;
                        uses RPKI-ORIGIN-AS-VALIDATION-DISABLE;
                        uses ADVERTISE-BRIDGE-DOMAIN-IMP-DISABLE-V4;
                        uses FLOWSPEC-VALIDATION;
                        uses ADVERTISE-L2VPN-EVPN;
                        uses ADVERTISE-LOCAL-L2VPN-EVPN;
                        uses ENCAPSULATION-TYPE;
                        uses RPKI-BESTPATH-ORIGIN-AS-ALLOW-INVALID;
                        uses ENFORCE-MULTIPLE-LABELS;
                        uses AS-OVERRIDE;
                        uses MULTIPATH;
                        uses SEND-COMMUNITY-EBGP-GRACEFUL-SHUTDOWN;
                        uses PREFIX-ORF-POLICY;
                        uses NEIGHBOR-AF-LONG-LIVED-GRACEFUL-RESTART-STALE-TIME;
                        uses SITE-OF-ORIGIN;
                        uses UPDATE-OUT-ORIG-LOOP-CHK-DISABLE;
                        uses AIGP;
                        uses AIGP-SEND-MED;
                        uses ADVERTISE-V6;
                        uses ALLOW-AS-IN;
                        uses ADVERTISE-ORF;
                        uses ROUTE-REFLECTOR-CLIENT;
                        uses NEXT-HOP-SELF;
                        uses ADVERTISE-LOCAL-V6;
                        uses ROUTE-POLICY-IN;
                        uses IMPORT;
                        uses DEFAULT-ORIGINATE;
                        uses SOFT-RECONFIGURATION;
                        uses ADVERTISE-VRF-IMP-DISABLE-V6;
                        uses DEFAULT-WEIGHT;
                        uses ADVERTISE-V4;
                        uses NEXT-HOP-UNCHANGED-MULTIPATH;
                        uses OPTIMAL-ROUTE-REFLECTION-GROUP;
                        uses ACCEPT-OWN;
                        uses ROUTE-POLICY-OUT;
                        uses ADVERTISE-LOCAL-V4;
                        uses ADVERTISE-PERMANENT-NETWORK;
                        uses REMOVE-PRIVATE-AS-ENTIRE-AS-PATH;
                        uses ADVERTISE-VRF-IMP-DISABLE-V4;
                      }
                    }
                    leaf af-group-name {
                      type xr:Cisco-ios-xr-string;
                      description
                        "BGP AF group name";
                    }
                  }
                }
                container session-groups {
                  description
                    "Session group configuration";
                  list session-group {
                    key "session-group-name";
                    description
                      "A particular BGP session group";
                    leaf session-group-add-member {
                      type string;
                      description
                        "Inherit address-family independent config
                         from a session-group";
                    }
                    leaf session-group-name {
                      type xr:Cisco-ios-xr-string;
                      description
                        "BGP session group name";
                    }
                    uses LOCAL-ADDRESS-SUB-NET;
                    uses INTERNAL-VPN-CLIENT-IBGP-CE;
                    uses LOCAL-ADDRESS;
                    uses BMP-ACTIVATE-TABLE;
                    uses EBGP-MULTIHOP;
                    uses EGRESS-PEER-ENGINEERING;
                    uses REMOTE-AS;
                    uses MERGE-SAFI1-AND4-INBOUND-UPDATES;
                    uses LOCAL-AS;
                    uses NEIGHBOR-GRACEFUL-RESTART-STALEPATH-TIME;
                    uses SHUTDOWN;
                    uses DESCRIPTION;
                    uses PASSWORD;
                    uses EBGP-RECV-DMZ;
                    uses ADVERTISEMENT-INTERVAL;
                    uses NEIGHBOR-CLUSTER-ID;
                    uses NEIGHBOR-GRACEFUL-RESTART;
                    uses ENFORCE-FIRST-AS;
                    uses IDLE-WATCH-TIME;
                    uses TCPMSS;
                    uses SESSION-OPEN-MODE;
                    uses BGP-CFG-RPKI-ORIGIN-AS-VALIDATION-DISABLE;
                    uses TOS;
                    uses UPDATE-IN-FILTERING;
                    uses EBGP-SEND-DMZ-ENABLE-MODES;
                    uses MSG-LOG-OUT;
                    uses SUPPRESS-ALL-CAPABILITIES;
                    uses MAX-PEERS;
                    uses AO-KEYCHAIN;
                    uses BGP-CFG-RPKI-BESTPATH-ORIGIN-AS-ALLOW-INVALID;
                    uses RECEIVE-BUFFER-SIZE;
                    uses MSG-LOG-IN;
                    uses ADDITIONAL-PATHS-SEND-CAPABILITY;
                    uses PROPAGATE-DMZ-LINK-BANDWIDTH;
                    uses BFD-ENABLE-MODES;
                    uses SEND-BUFFER-SIZE;
                    uses TTL-SECURITY;
                    uses NEIGHBOR-GRACEFUL-RESTART-TIME;
                    uses TIMERS;
                    uses BFD-MULTIPLIER;
                    uses BFD-MINIMUM-INTERVAL;
                    uses REMOTE-AS-LIST;
                    uses ADDITIONAL-PATHS-RECEIVE-CAPABILITY;
                    uses KEYCHAIN;
                    uses IGNORE-CONNECTED-CHECK-EBGP;
                    uses SUPPRESS-FOUR-BYTE-AS-CAPABILITY;
                    uses UPDATE-SOURCE-INTERFACE;
                    uses CREATE;
                    uses GRACEFUL-MAINTENANCE;
                  }
                }
              }
              container global {
                description
                  "Global default config";
                container cluster-id {
                  description
                    "Configure Route-Reflector Cluster-id";
                  leaf cluster-id-number {
                    type uint32 {
                      range "1..4294967295";
                    }
                    description
                      "Route-Reflector Cluster ID as 32 bit
                       quantity";
                  }
                  leaf cluster-id-address {
                    type inet:ipv4-address-no-zone;
                    description
                      "Route-Reflector Cluster ID in IPV4 address
                       format";
                  }
                }
                container write-limit {
                  description
                    "Set write-queue limit for each update group";
                  leaf formatted-messages {
                    type uint32 {
                      range "500..100000000";
                    }
                    default "50000";
                    description
                      "Number of messages to be formatted per
                       update group";
                  }
                  leaf enqueued-messages {
                    type uint32 {
                      range "500..100000000";
                    }
                    default "250000";
                    description
                      "Number of messages that can be enqueued in
                       total";
                  }
                  leaf desynchronize {
                    type boolean;
                    default "false";
                    description
                      "TRUE to enable desynchronization, FALSE
                       otherwise.";
                  }
                }
                container update-delay {
                  description
                    "Set the max initial delay for sending
                     updates";
                  leaf delay {
                    type uint32 {
                      range "0..3600";
                    }
                    units "second";
                    default "120";
                    description
                      "Delay value (seconds)";
                  }
                  leaf always {
                    type boolean;
                    must '../delay' {
                      tailf:xpath-root 3;
                    }
                    default "false";
                    description
                      "Set to TRUE to disable keepalive trigger
                       bestpath and delay is enforced.";
                  }
                }
                container as-league {
                  description
                    "AS League";
                  container peers {
                    description
                      "AS League Peers";
                    list peer {
                      key "as-xx as-yy";
                      description
                        "AS League Peer AS";
                      leaf as-xx {
                        type dt1:Bgp-as-range;
                        description
                          "xx of peer AS xx.yy";
                      }
                      leaf as-yy {
                        type dt1:Bgp-as-range;
                        description
                          "yy of peer AS xx.yy";
                      }
                    }
                  }
                  leaf enable {
                    type empty;
                    description
                      "AS League creation";
                  }
                }
                container rpki-servers {
                  description
                    "RPKI server configuration";
                  list rpki-server {
                    key "server";
                    description
                      "RPKI server configuration";
                    container transport {
                      description
                        "RPKI server transport";
                      leaf transport {
                        type Bgp-rpki-transport;
                        default "ssh";
                        description
                          "RPKI server transport";
                      }
                      leaf port {
                        type xr:Cisco-ios-xr-port-number;
                        default "22";
                        description
                          "port";
                      }
                    }
                    leaf enable {
                      type empty;
                      description
                        "RPKI server configuration";
                    }
                    leaf shutdown {
                      type empty;
                      description
                        "RPKI server shutdown";
                    }
                    leaf password {
                      type string;
                      description
                        "RPKI server password";
                    }
                    leaf response-time {
                      type uint32 {
                        range "15..3600";
                      }
                      units "second";
                      description
                        "RPKI server response-time (15-3600
                         seconds)";
                    }
                    leaf username {
                      type string;
                      description
                        "RPKI server username";
                    }
                    leaf refresh-time {
                      type uint32 {
                        range "15..3600";
                      }
                      units "second";
                      description
                        "RPKI server refresh-time (15-3600
                         seconds)";
                    }
                    leaf purge-time {
                      type uint32 {
                        range "30..360";
                      }
                      units "second";
                      description
                        "RPKI server purge-time (30-360 seconds)";
                    }
                    leaf server {
                      type xr:Cisco-ios-xr-string;
                      description
                        "Server address (opaque string)";
                    }
                  }
                }
                container as-list-groups {
                  description
                    "AS-list group lists";
                  list as-list-group {
                    key "as-list-group-name";
                    description
                      "AS-List group";
                    container ases {
                      description
                        "AS list";
                      list as {
                        key "as-xx as-yy";
                        description
                          "AS-List group";
                        leaf as-xx {
                          type dt1:Bgp-as-range;
                          description
                            "xx of AS number/confed peer xx.yy";
                        }
                        leaf as-yy {
                          type dt1:Bgp-as-range;
                          description
                            "yy of AS number/confed peer xx.yy";
                        }
                      }
                    }
                    leaf enable {
                      type empty;
                      description
                        "AS-List group creation";
                    }
                    leaf as-list-group-name {
                      type xr:Cisco-ios-xr-string;
                      description
                        "Group name";
                    }
                  }
                }
                container limits {
                  description
                    "Maximum number that can be configured";
                  leaf maximum-neighbors {
                    type uint32 {
                      range "1..15000";
                    }
                    default "10000";
                    description
                      "Maximum number of neighbors that can be
                       configured";
                  }
                }
                container confederation-domain {
                  description
                    "Set routing domain confederation AS";
                  leaf as-xx {
                    type dt1:Bgp-as-range;
                    description
                      "xx of AS number xx.yy";
                  }
                  leaf as-yy {
                    type dt1:Bgp-as-range;
                    description
                      "yy of AS number xx.yy";
                  }
                }
                container confederation-peer-ases {
                  description
                    "Define peer ASes in BGP confederation";
                  list confederation-peer-as {
                    key "as-xx as-yy";
                    description
                      "Confederation peer AS";
                    leaf as-xx {
                      type dt1:Bgp-as-range;
                      description
                        "xx of AS number/confed peer xx.yy";
                    }
                    leaf as-yy {
                      type dt1:Bgp-as-range;
                      description
                        "yy of AS number/confed peer xx.yy";
                    }
                  }
                }
                container attribute-filter-groups {
                  description
                    "Attribute-filter groups list";
                  list attribute-filter-group {
                    key "attribute-filter-group-name";
                    description
                      "Attribute-filter group";
                    container attribute-filters {
                      description
                        "Attribute-filter group attributes list";
                      list attribute-filter {
                        key "attribute-start attribute-end";
                        description
                          "Attribute-filter group attribute";
                        leaf attribute-start {
                          type dt1:Bgp-attribute-range;
                          description
                            "Start of attribute range";
                        }
                        leaf attribute-end {
                          type dt1:Bgp-attribute-range;
                          description
                            "End of attribute range";
                        }
                        leaf filter-action {
                          type dt1:Bgp-update-filter-action;
                          mandatory true;
                          description
                            "Filtering action";
                        }
                      }
                    }
                    leaf enable {
                      type empty;
                      description
                        "Attribute-filter group creation";
                    }
                    leaf attribute-filter-group-name {
                      type xr:Cisco-ios-xr-string;
                      description
                        "Group name";
                    }
                  }
                }
                container global-graceful-maintenance-activate {
                  description
                    "Activate Graceful Maintenance Mode for all
                     neighbors with graceful maintenance config";
                  leaf all-neighbors {
                    type boolean;
                    description
                      "Also for neighbors without graceful
                       maintenance config";
                  }
                  leaf retain-routes {
                    type boolean;
                    description
                      "Keep routes in RIB once BGP stops";
                  }
                }
                container global-afs {
                  description
                    "Global AF-specific configuration";
                  list global-af {
                    key "af-name";
                    description
                      "Global AF-specific configuration";
                    container isis-routes {
                      description
                        "Redistribute information for IS-IS routes
                         .";
                      list isis-route {
                        key "instance-name";
                        description
                          "Redistribute IS-IS routes";
                        leaf instance-name {
                          type xr:Cisco-ios-xr-string;
                          description
                            "IS-IS instance name";
                        }
                        leaf default-metric {
                          type Bgp-default-metric-range;
                          description
                            "Default metric";
                        }
                        leaf route-policy-name {
                          type string;
                          description
                            "Route policy name";
                        }
                        leaf redist-type {
                          type xr:Hex-integer;
                          description
                            "Redistribution type: 01 for level 1
                             routes, 02 for level 2 routes, 04 for
                             level 1 inter-area routes. Logical
                             combinations permitted.";
                        }
                      }
                    }
                    container domain-distinguisher {
                      presence "Indicates a domain-distinguisher node is configured.";
                      description
                        "<ASN, router-id> tuple to use to identify
                         the link-state domain";
                      leaf as {
                        type dt1:Bgp-as-range;
                        mandatory true;
                        description
                          "AS Number";
                      }
                      leaf router-id {
                        type inet:ipv4-address-no-zone;
                        mandatory true;
                        description
                          "Router ID";
                      }
                    }
                    container vrf-all {
                      description
                        "Configurations to be inherited to all
                         vrfs";
                      container label-mode {
                        description
                          "MPLS-VPN label allocation mode";
                        leaf label-allocation-mode {
                          type string;
                          description
                            "Label allocation mode: per-ce  Set per
                             CE label mode, per-vrf Set per VRF
                             label mode";
                        }
                        leaf route-policy-name {
                          type string;
                          description
                            "Label mode route policy name";
                        }
                      }
                      leaf rnh-install-format {
                        type Bgp-rnh-install-format;
                        description
                          "RNH install format type: extcomm -
                           install rnh as opaque and extcomms,
                           extcomm-only - install rnh as extcomms
                           only";
                      }
                      leaf enable {
                        type empty;
                        description
                          "Enable vrf all configuration submode";
                      }
                      leaf table-policy {
                        type string;
                        description
                          "Configure policy for installation of
                           routes to RIB";
                      }
                      leaf source-rt-import-policy {
                        type empty;
                        description
                          "Enable sourcing of import route-targets
                           from import-policy";
                      }
                    }
                    container disable-cluster-client-to-client-rrs {
                      description
                        "Disable client-to-client reflection for a
                         cluster";
                      list disable-cluster-client-to-client-rr {
                        must 'number or ipv4-address' {
                          tailf:xpath-root 3;
                          description
                            "Number or IPV4Address must be present.";
                        }
                        key "cluster-type";
                        description
                          "Cluster ID for which reflection is to be
                           disbled";
                        leaf cluster-type {
                          type Bgp-cluster-id;
                          description
                            "Type of cluster-id";
                        }
                        list number {
                          when "../cluster-type = 'number'" {
                            tailf:xpath-root 3;
                            description
                              "../ClusterType = Number";
                          }
                          key "cluster-id-number";
                          description
                            "number";
                          leaf cluster-id-number {
                            type uint32 {
                              range "0..4294967295";
                            }
                            description
                              "Cluster ID: if configured as a number";
                          }
                        }
                        list ipv4-address {
                          when "../cluster-type = 'ipv4-address'" {
                            tailf:xpath-root 3;
                            description
                              "../ClusterType = IPV4Address";
                          }
                          key "cluster-id-address";
                          description
                            "ipv4 address";
                          leaf cluster-id-address {
                            type inet:ip-address-no-zone;
                            description
                              "Cluster ID: if configured as an IP
                               Address";
                          }
                        }
                      }
                    }
                    container label-delay {
                      presence "Indicates a label-delay node is configured.";
                      description
                        "Delay timer to batch label processing.";
                      leaf seconds {
                        type uint32 {
                          range "0..10";
                        }
                        units "second";
                        mandatory true;
                        description
                          "Delay, seconds part";
                      }
                      leaf milliseconds {
                        type uint32 {
                          range "0..999";
                        }
                        units "millisecond";
                        mandatory true;
                        description
                          "Delay, milliseconds part";
                      }
                    }
                    container ebgp {
                      presence "Indicates a ebgp node is configured.";
                      description
                        "Use eBGP multipaths";
                      leaf paths-value {
                        type uint32 {
                          range "2..64";
                        }
                        mandatory true;
                        description
                          "Number of paths";
                      }
                      leaf unequal-cost {
                        type boolean;
                        default "false";
                        description
                          "UNUSED";
                      }
                      leaf selective {
                        type boolean;
                        default "false";
                        description
                          "Allow multipaths only from marked
                           neighbors";
                      }
                      leaf order-by-igp-metric {
                        type boolean;
                        default "false";
                        description
                          "Order candidate multipaths by IGP metric";
                      }
                    }
                    container eibgp {
                      presence "Indicates a eibgp node is configured.";
                      description
                        "Use eiBGP multipaths";
                      leaf paths-value {
                        type uint32 {
                          range "2..64";
                        }
                        mandatory true;
                        description
                          "Number of paths";
                      }
                      leaf unequal-cost {
                        type boolean;
                        default "false";
                        description
                          "UNUSED";
                      }
                      leaf selective {
                        type boolean;
                        default "false";
                        description
                          "Allow multipaths only from marked
                           neighbors";
                      }
                      leaf order-by-igp-metric {
                        type boolean;
                        default "false";
                        description
                          "Order candidate multipaths by IGP metric";
                      }
                    }
                    container retain-rt {
                      description
                        "Accept received updates with the
                         specified attributes";
                      leaf all {
                        type boolean;
                        description
                          "Whether all RTs are to be retained,
                           default is FALSE";
                      }
                      leaf route-policy-name {
                        type string;
                        description
                          "Route policy name";
                      }
                    }
                    container ibgp {
                      presence "Indicates a ibgp node is configured.";
                      description
                        "Use iBGP multipaths";
                      leaf paths-value {
                        type uint32 {
                          range "2..64";
                        }
                        mandatory true;
                        description
                          "Number of paths";
                      }
                      leaf unequal-cost {
                        type boolean;
                        default "false";
                        description
                          "Allow multipaths to have different IGP
                           metrics";
                      }
                      leaf selective {
                        type boolean;
                        default "false";
                        description
                          "Allow multipaths only from marked
                           neighbors";
                      }
                      leaf order-by-igp-metric {
                        type boolean;
                        default "false";
                        description
                          "Order candidate multipaths by IGP metric";
                      }
                    }
                    container import-delay {
                      presence "Indicates a import-delay node is configured.";
                      description
                        "Delay timer to batch import processing.";
                      leaf seconds {
                        type uint32 {
                          range "0..10";
                        }
                        units "second";
                        mandatory true;
                        description
                          "Delay, seconds part";
                      }
                      leaf milliseconds {
                        type uint32 {
                          range "0..999";
                        }
                        units "millisecond";
                        mandatory true;
                        description
                          "Delay, milliseconds part";
                      }
                    }
                    leaf rnh-install-format {
                      type Bgp-rnh-install-format;
                      description
                        "RNH install format type: extcomm -
                         install rnh as opaque and extcomms,
                         extcomm-only - install rnh as extcomms
                         only";
                    }
                    leaf inter-as-install {
                      type empty;
                      description
                        "Enable install remote MVPN routes to PIM
                         in default VRF";
                    }
                    leaf segmented-mcast {
                      type empty;
                      description
                        "Enable segmented multicast";
                    }
                    leaf implicit-import {
                      type empty;
                      description
                        "Implicit import configuration";
                    }
                    leaf disable-default-martian-check {
                      type empty;
                      description
                        "Disable default Martian Check";
                    }
                    leaf next-hop-critical-trigger-delay {
                      type uint32 {
                        range "0..4294967295";
                      }
                      units "millisecond";
                      default "3000";
                      description
                        "Next hop Critical Trigger Delay";
                    }
                    leaf next-hop-non-critical-trigger-delay {
                      type uint32 {
                        range "0..4294967295";
                      }
                      units "millisecond";
                      default "10000";
                      description
                        "Next hop Non-critical Trigger Delay";
                    }
                    leaf label-security-rpf {
                      type empty;
                      description
                        "Calculate label-security RPF lists and
                         install to RIB/LSD";
                    }
                    leaf use-igpsr-label {
                      type empty;
                      description
                        "Use IGP SR label for resolution
                         configuration";
                    }
                    leaf label-retain {
                      type uint32 {
                        range "3..60";
                      }
                      units "minute";
                      description
                        "Label retention time in minutes";
                    }
                    leaf scan-time {
                      type uint32 {
                        range "5..3600";
                      }
                      units "second";
                      default "60";
                      description
                        "Configure background scanner interval for
                         this address family";
                    }
                    leaf source-route-target-policy {
                      type string;
                      description
                        "Route policy name to apply to configure
                         source route-target";
                    }
                    leaf rpki-origin-as-validation-disable {
                      type empty;
                      description
                        "RPKI origin-AS validation disable";
                    }
                    leaf update-limit-sub-group-ebgp {
                      type uint32 {
                        range "1..512";
                      }
                      units "megabyte";
                      default "32";
                      description
                        "Upper bound on update generation
                         transient memory usage for every EBGP
                         Sub-group";
                    }
                    leaf update-limit-address-family {
                      type uint32 {
                        range "4..2048";
                      }
                      units "megabyte";
                      default "256";
                      description
                        "Upper bound on update generation
                         transient memory usage for the
                         address-family";
                    }
                    leaf update-limit-sub-group-ibgp {
                      type uint32 {
                        range "1..512";
                      }
                      units "megabyte";
                      default "32";
                      description
                        "Upper bound on update generation
                         transient memory usage for every IBGP
                         Sub-group";
                    }
                    leaf disable-client-to-client-rr {
                      type empty;
                      description
                        "Disable client-to-client reflection";
                    }
                    leaf next-hop-route-policy {
                      type string;
                      description
                        "Next hop policy to filter out nexthop
                         notification";
                    }
                    leaf global-table-mcast {
                      type empty;
                      description
                        "Enable global table multicast";
                    }
                    leaf wait-rib-install {
                      type empty;
                      description
                        "Wait for route install before sending
                         updates to neighbors";
                    }
                    leaf prefix-sid-map {
                      type empty;
                      description
                        "Retrieve prefix sid mapping from SRMS";
                    }
                    leaf af-name {
                      type dt1:Bgp-address-family;
                      description
                        "Address family";
                    }
                    uses RPKI-ORIGIN-AS-VALIDATION-ENABLE;
                    uses AGGREGATE-ADDRESS-TABLE;
                    uses DYNAMIC-MED-INTERVAL;
                    uses OPTIMAL-ROUTE-REFLECTOR-GROUP-TABLE;
                    uses DAMPENING;
                    uses ENABLE;
                    uses RIP-ROUTES;
                    uses LISP-ROUTES;
                    uses STATIC-ROUTES;
                    uses DISTANCE;
                    uses TABLE-POLICY;
                    uses APP-ROUTE-TABLE;
                    uses ATTRIBUTE-DOWNLOAD;
                    uses LABEL-MODE;
                    uses EIGRP-ROUTE-TABLE;
                    uses BEST-EXTERNAL;
                    uses SOURCED-NETWORK-TABLE;
                    uses RPKI-ORIGIN-AS-VALIDITY-SIGNAL-IBGP;
                    uses CONNECTED-ROUTES;
                    uses ADDITIONAL-PATHS-RECEIVE;
                    uses PERMANENT-NETWORK;
                    uses RPKI-BESTPATH-USE-ORIGIN-AS-VALIDITY;
                    uses ALLOCATE-LABEL;
                    uses ADDITIONAL-PATHS-SELECTION;
                    uses BGP-CFG-RPKI-BESTPATH-ORIGIN-AS-ALLOW-INVALID-MP;
                    uses NEXT-HOP-RESOLUTION-PREFIX-LENGTH-MINIMUM;
                    uses RESET-WEIGHT-ON-IMPORT;
                    uses OSPF-ROUTE-TABLE;
                    uses ADDITIONAL-PATHS-SEND;
                    uses ADVERTISE-LOCAL-LABELED-ROUTE-SAFI-UNICAST;
                    uses MOBILE-ROUTES;
                    uses DISABLE-AS-PATH-LOOP-CHECK;
                    uses SUBSCRIBER-ROUTES;
                    uses SEGMENT-ROUTING;
                  }
                }
                container rpki-static-routes {
                  description
                    "RPKI static route configuration";
                  list rpki-static-route {
                    key "address minimum maximum as";
                    description
                      "RPKI static route";
                    leaf address {
                      type inet:ip-address-no-zone;
                      description
                        "Address";
                    }
                    leaf minimum {
                      type uint32 {
                        range "0..128";
                      }
                      description
                        "Minimum Prefix Length";
                    }
                    leaf maximum {
                      type uint32 {
                        range "1..128";
                      }
                      description
                        "Maximum Prefix Length";
                    }
                    leaf as {
                      type uint32 {
                        range "1..4294967295";
                      }
                      description
                        "AS Number";
                    }
                  }
                }
                leaf graceful-restart {
                  type empty;
                  description
                    "Enable graceful restart support";
                }
                leaf update-out-logging {
                  type empty;
                  description
                    "Enables logging of update generation events";
                }
                leaf install-diversion {
                  type empty;
                  description
                    "Install diversion path to RIB/CEF";
                }
                leaf next-hop-trigger-delay {
                  type uint32 {
                    range "0..300";
                  }
                  units "second";
                  default "5";
                  description
                    "Set the delay for triggering nexthop
                     recalculations";
                }
                leaf nsr {
                  type boolean;
                  description
                    "TRUE to Enable non-stop routing
                     supportFALSE to Disable non-stop routing
                     support";
                }
                leaf neighbor-logging-detail {
                  type empty;
                  description
                    "Include extra detail in neighbor change
                     messages";
                }
                leaf mvpn {
                  type empty;
                  description
                    "Connect to PIM/PIM6";
                }
                leaf rpki-origin-as-validation-disable {
                  type empty;
                  description
                    "RPKI origin-AS validation disable";
                }
                leaf global-scan-time {
                  type uint32 {
                    range "5..3600";
                  }
                  units "second";
                  default "60";
                  description
                    "Configure background scanner interval for
                     generic scanner";
                }
                leaf rpki-origin-as-validation-time {
                  type uint32 {
                    range "0..60";
                  }
                  units "second";
                  description
                    "Prefix validation time (in seconds). Range
                     : 5 - 60. Specify 0 for timer off";
                }
                leaf rpki-bestpath-origin-as-allow-invalid {
                  type empty;
                  description
                    "RPKI bestpath origin-AS allow invalid";
                }
                leaf graceful-restart-purge-time {
                  type uint32 {
                    range "1..6000";
                  }
                  units "second";
                  default "600";
                  description
                    "Time before stale routes are purged.";
                }
                leaf enforce-ibgp-out-policy {
                  type empty;
                  description
                    "Allow all attributes to be modified by
                     outbound policy for iBGP peers";
                }
                leaf update-limit-process {
                  type uint32 {
                    range "16..2048";
                  }
                  units "megabyte";
                  default "512";
                  description
                    "Upper bound on update generation transient
                     memory usage for the process";
                }
                leaf graceful-restart-time {
                  type uint32 {
                    range "1..4095";
                  }
                  units "second";
                  default "120";
                  description
                    "Restart time advertised to neighbors";
                }
                leaf update-error-handling-basic-ibgp-disable {
                  type empty;
                  description
                    "Inbound update basic error-handling for
                     IBGP neighbors";
                }
                leaf read-only {
                  type empty;
                  description
                    "Allow duplicate table config and disable
                     update generation";
                }
                leaf graceful-restart-stalepath-time {
                  type uint32 {
                    range "1..4095";
                  }
                  units "second";
                  default "360";
                  description
                    "Maximum time to wait for restart of GR
                     capable peers";
                }
                leaf update-error-handling-extended-ebgp {
                  type empty;
                  description
                    "Inbound update extended error-handling for
                     EBGP neighbors";
                }
                leaf update-error-handling-basic-ebgp-disable {
                  type empty;
                  description
                    "Inbound update basic error-handling for
                     EBGP neighbors";
                }
                leaf graceful-reset {
                  type empty;
                  description
                    "Reset gracefully if configuration change
                     forces a peer reset";
                }
                leaf igp-loop-check {
                  type empty;
                  description
                    "Enable AS-path loop checking for iBGP peers";
                }
                leaf update-error-handling-extended-ibgp {
                  type empty;
                  description
                    "Inbound update extended error-handling for
                     IBGP neighbors";
                }
                uses ROUTER-ID;
                uses DISABLE-ENFORCE-FIRST-AS;
                uses BEST-PATH-COST-COMMUNITY;
                uses BEST-PATH-AIGP-IGNORE;
                uses BEST-PATH-AS-PATH-LENGTH;
                uses IGP-REDIST-INTERNAL;
                uses MULTI-PATH-AS-PATH-IGNORE-ONWARDS;
                uses DISABLE-FAST-EXTERNAL-FALLOVER;
                uses UNSAFE-EBGP-POLICY;
                uses DEFAULT-METRIC;
                uses DEFAULT-INFO-ORIGINATE;
                uses BGP-CFG-RPKI-ORIGIN-AS-VALIDITY-SIGNAL-IBGP;
                uses BGP-CFG-RPKI-BESTPATH-USE-ORIGIN-AS-VALIDITY;
                uses BEST-PATH-CONFEDERATION-PATHS;
                uses BEST-PATH-AS-MULTIPATH-RELAX;
                uses MPLS-ACTIVATED-INTERFACE-TABLE;
                uses DISABLE-AUTO-SOFT-RESET;
                uses DISABLE-MSG-LOG;
                uses GLOBAL-TIMERS;
                uses BEST-PATH-IGP-METRIC-IGNORE;
                uses NEXT-HOP-RES-ALLOW-DEFAULT;
                uses NEXT-HOP-MPLS-FWD-IBGP;
                uses BFD;
                uses DISABLE-NEIGHBOR-LOGGING;
                uses SEND-SOCKET-BUFFER-SIZES;
                uses BEST-PATH-MED-ALWAYS;
                uses RECEIVE-SOCKET-BUFFER-SIZES;
                uses BEST-PATH-ROUTER-ID;
                uses BEST-PATH-MED-MISSING;
                uses LOCAL-PREFERENCE;
              }
            }
            leaf bgp-running {
              type empty;
              description
                "Enable BGP. Deletion of this object causes
                 deletion of all the objects under FourByteAS
                 associated with this object.";
            }
            leaf as {
              type dt1:Bgp-as-range;
              description
                "2-byte or 4-byte Autonomous system number";
            }
          }
        }
      }
    }
    container bmp-server-all {
      tailf:ncs-device-type "netconf";
      tailf:display-when "not(../../ncs:module) or ../../ncs:module[ncs:name='Cisco-IOS-XR-ipv4-bgp-cfg']";
      description
        "bmp server all";
      container route-monitoring {
        description
          "Enable Route Monitoring capability for the BMP
           servers.
           BGP update messages messages will be
           regenrated with a table walk
          ";
        leaf policy {
          type Bmp-policy-select;
          description
            "Specify if the routes packed in update messages
             should be
             before or after the application of
             route-policy";
        }
        leaf direction {
          type Bmp-route-direction;
          description
            "Specify if the routes should be picked up at
             inbound
             or outbound direction";
        }
      }
      leaf maximum-buffer-size {
        type uint32 {
          range "1..4294967295";
        }
        units "megabyte";
        description
          "Range in MegaBytes for the maximum buffer size
           of BMP message queue.
           The maximum buf-size is
           20% and default buf-size is 15% of the
           platform
           virtual memory max-limit (aka rlimit).
           Please run show bgp process
           performance-statistics
           to see the individual
           values. Unit is in Megabytes";
      }
    }
    container bmp-servers {
      tailf:ncs-device-type "netconf";
      tailf:display-when "not(../../ncs:module) or ../../ncs:module[ncs:name='Cisco-IOS-XR-ipv4-bgp-cfg']";
      description
        "bmp servers";
      list bmp-server {
        key "server-id";
        description
          "A particular BMP server";
        container initial-refresh-delay {
          description
            "Initial refresh to generate BGP updates";
          leaf delay {
            type uint32 {
              range "1..3600";
            }
            units "second";
            must 'not(../skip)' {
              tailf:xpath-root 3;
            }
            description
              "Delay in seconds before sending Refresh
               request to Peers";
          }
          leaf spread {
            type uint32 {
              range "1..3600";
            }
            must '../delay and not(../skip)' {
              tailf:xpath-root 3;
            }
            description
              "Spread over which to send initial Refresh
               request to Peers";
          }
          leaf skip {
            type empty;
            must 'not(../delay or ../spread)' {
              tailf:xpath-root 3;
            }
            description
              "Skip Route Refresh request to Peers";
          }
        }
        container host-port {
          description
            "Configure Host Name/Address and Port for BMP
             Server";
          leaf host {
            type string;
            description
              "Name of the BMP server(accepts IPv4/IPv6
               Address format too)";
          }
          leaf port {
            type xr:Cisco-ios-xr-port-number;
            description
              "Port Number of listening BMP server";
          }
        }
        container tos {
          description
            "TOS (Type Of Service)";
          leaf type {
            type dt1:Bgp-tos;
            description
              "Set type of service";
          }
          leaf value {
            type dt1:Bgp-precedence-dscp;
            description
              "TOS value to set";
          }
        }
        leaf create {
          type empty;
          description
            "BMP Server Creation";
        }
        leaf maximum-buffer-size {
          type uint32 {
            range "1..4294967295";
          }
          units "megabyte";
          description
            "Range in MegaBytes for the maximum buffer size
             of BMP message queue.
             The maximum buf-size is
             20% and default buf-size is 15% of the
             platform
             virtual memory max-limit (aka rlimit)
             . Please run show bgp process
             performance-statistics
             to see the individual
             values. Unit is in Megabytes";
        }
        leaf initial-delay {
          type uint32 {
            range "1..3600";
          }
          units "second";
          description
            "Initial connect delay in seconds in sending
             updates";
        }
        leaf flapping-delay {
          type uint32 {
            range "60..3600";
          }
          units "second";
          description
            "Delay in connecting to BMP Server after a flap
             had been detected.";
        }
        leaf status-report-interval {
          type uint32 {
            range "1..3600";
          }
          units "second";
          description
            "Stats reporting period for BMP server";
        }
        leaf description {
          type string;
          description
            "String to describe the BMP server";
        }
        leaf bmptcp-maximum-segment-size {
          type uint32 {
            range "68..10000";
          }
          units "byte";
          description
            "configure TCP maximum segment size.
             Default=16384.";
        }
        leaf bmptcp-keep-alive {
          type uint32 {
            range "0..7200";
          }
          units "second";
          description
            "configure TCP keep alives to be exchanged
             between client and server. Default=1000";
        }
        leaf vrf {
          type string;
          description
            "VRF for BMP Server";
        }
        leaf shutdown {
          type empty;
          description
            "Shutdown connection to BMP server";
        }
        leaf update-source-interface {
          type xr:Interface-name;
          description
            "Select an interface to configure";
        }
        leaf server-id {
          type uint32 {
            range "1..8";
          }
          description
            "BMP Server ID";
        }
      }
    }
  }
  augment "/ncs:devices/ncs:device/ncs:live-status" {
    leaf asn-format {
      tailf:ncs-device-type "netconf";
      tailf:display-when "not(../../ncs:module) or ../../ncs:module[ncs:name='Cisco-IOS-XR-ipv4-bgp-cfg'] or (../../ncs:live-status-protocol[not(ncs:capability)]) or (../../ncs:live-status-protocol/ncs:capability/ncs:module[.='Cisco-IOS-XR-ipv4-bgp-cfg'])";
      type Bgp-asn;
      // NCS drop default statement
      description
        "Autonomous system number format";
    }
    container bgp {
      tailf:ncs-device-type "netconf";
      tailf:display-when "not(../../ncs:module) or ../../ncs:module[ncs:name='Cisco-IOS-XR-ipv4-bgp-cfg'] or (../../ncs:live-status-protocol[not(ncs:capability)]) or (../../ncs:live-status-protocol/ncs:capability/ncs:module[.='Cisco-IOS-XR-ipv4-bgp-cfg'])";
      description
        "bgp";
      list instance {
        // NCS drop must statement
        key "instance-name";
        description
          "BGP instance configuration commands";
        leaf instance-name {
          type xr:Cisco-ios-xr-string;
          description
            "Instance Name. For Default instance use -
             default";
        }
        list instance-as {
          // NCS drop must statement
          key "as";
          description
            "Autonomous system";
          leaf as {
            type dt1:Bgp-as-range;
            description
              "Higher 16 bits of 4-byte Autonomous system
               number";
          }
          list four-byte-as {
            key "as";
            description
              "4-byte Autonomous system";
            container vrfs {
              description
                "VRF config";
              list vrf {
                key "vrf-name";
                description
                  "VRF config";
                container vrf-global {
                  description
                    "VRF attribute config";
                  container route-distinguisher {
                    description
                      "Route distinguisher";
                    leaf type {
                      type Bgp-route-distinguisher;
                      description
                        "Type of RD";
                    }
                    leaf as-xx {
                      // NCS drop when statement
                      type dt1:Bgp-as-range;
                      description
                        "AS number";
                    }
                    leaf as {
                      // NCS drop when statement
                      type dt1:Bgp-as-range;
                      description
                        "AS number";
                    }
                    leaf as-index {
                      // NCS drop when statement
                      type dt1:Bgp-extcomm-asn-index;
                      description
                        "ASN Index";
                    }
                    leaf address {
                      // NCS drop when statement
                      type inet:ipv4-address-no-zone;
                      description
                        "IP address";
                    }
                    leaf address-index {
                      // NCS drop when statement
                      type dt1:Bgp-extcomm-v4-addr-index;
                      description
                        "IP address index";
                    }
                  }
                  container vrf-global-afs {
                    description
                      "Global VRF-specific configuration";
                    list vrf-global-af {
                      key "af-name";
                      description
                        "Global VRF AF-specific configuration";
                      container mvpn {
                        description
                          "MVPN configurations";
                        leaf single-forwarder-selection {
                          type Bgp-mvpn-sfs-select;
                          description
                            "Select MVPN single forwarder selection";
                        }
                      }
                      container ebgp {
                        presence "Indicates a ebgp node is configured.";
                        description
                          "Use eBGP multipaths";
                        leaf paths-value {
                          type uint32 {
                            range "2..32";
                          }
                          // NCS drop mandatory statement
                          description
                            "Number of paths";
                        }
                        leaf unequal-cost {
                          type boolean;
                          // NCS drop default statement
                          description
                            "UNUSED";
                        }
                        leaf selective {
                          type boolean;
                          // NCS drop default statement
                          description
                            "Allow multipaths only from marked
                             neighbors";
                        }
                        leaf order-by-igp-metric {
                          type boolean;
                          // NCS drop default statement
                          description
                            "Order candidate multipaths by IGP
                             metric";
                        }
                      }
                      container eibgp {
                        presence "Indicates a eibgp node is configured.";
                        description
                          "Use eiBGP multipaths";
                        leaf paths-value {
                          type uint32 {
                            range "2..32";
                          }
                          // NCS drop mandatory statement
                          description
                            "Number of paths";
                        }
                        leaf unequal-cost {
                          type boolean;
                          // NCS drop default statement
                          description
                            "UNUSED";
                        }
                        leaf selective {
                          type boolean;
                          // NCS drop default statement
                          description
                            "Allow multipaths only from marked
                             neighbors";
                        }
                        leaf order-by-igp-metric {
                          type boolean;
                          // NCS drop default statement
                          description
                            "Order candidate multipaths by IGP
                             metric";
                        }
                      }
                      container ibgp {
                        presence "Indicates a ibgp node is configured.";
                        description
                          "Use iBGP multipaths";
                        leaf paths-value {
                          type uint32 {
                            range "2..32";
                          }
                          // NCS drop mandatory statement
                          description
                            "Number of paths";
                        }
                        leaf unequal-cost {
                          type boolean;
                          // NCS drop default statement
                          description
                            "Allow multipaths to have different IGP
                             metrics";
                        }
                        leaf selective {
                          type boolean;
                          // NCS drop default statement
                          description
                            "Allow multipaths only from marked
                             neighbors";
                        }
                        leaf order-by-igp-metric {
                          type boolean;
                          // NCS drop default statement
                          description
                            "Order candidate multipaths by IGP
                             metric";
                        }
                      }
                      leaf rt-download {
                        type empty;
                        description
                          "Route-Target download configuration";
                      }
                      leaf allow-vpn-default-originate {
                        type boolean;
                        description
                          "TRUE to send default orig route to VPN
                           neighborFALSE to not send default
                           originate route ";
                      }
                      leaf af-name {
                        type dt1:Bgp-address-family;
                        description
                          "Address family";
                      }
                      uses live_ncs_RPKI-ORIGIN-AS-VALIDATION-ENABLE;
                      uses live_ncs_AGGREGATE-ADDRESS-TABLE;
                      uses live_ncs_DYNAMIC-MED-INTERVAL;
                      uses live_ncs_OPTIMAL-ROUTE-REFLECTOR-GROUP-TABLE;
                      uses live_ncs_DAMPENING;
                      uses live_ncs_ENABLE;
                      uses live_ncs_RIP-ROUTES;
                      uses live_ncs_LISP-ROUTES;
                      uses live_ncs_STATIC-ROUTES;
                      uses live_ncs_DISTANCE;
                      uses live_ncs_TABLE-POLICY;
                      uses live_ncs_APP-ROUTE-TABLE;
                      uses live_ncs_ATTRIBUTE-DOWNLOAD;
                      uses live_ncs_LABEL-MODE;
                      uses live_ncs_EIGRP-ROUTE-TABLE;
                      uses live_ncs_BEST-EXTERNAL;
                      uses live_ncs_SOURCED-NETWORK-TABLE;
                      uses live_ncs_RPKI-ORIGIN-AS-VALIDITY-SIGNAL-IBGP;
                      uses live_ncs_CONNECTED-ROUTES;
                      uses live_ncs_ADDITIONAL-PATHS-RECEIVE;
                      uses live_ncs_PERMANENT-NETWORK;
                      uses live_ncs_RPKI-BESTPATH-USE-ORIGIN-AS-VALIDITY;
                      uses live_ncs_ALLOCATE-LABEL;
                      uses live_ncs_ADDITIONAL-PATHS-SELECTION;
                      uses live_ncs_BGP-CFG-RPKI-BESTPATH-ORIGIN-AS-ALLOW-INVALID-MP;
                      uses live_ncs_NEXT-HOP-RESOLUTION-PREFIX-LENGTH-MINIMUM;
                      uses live_ncs_RESET-WEIGHT-ON-IMPORT;
                      uses live_ncs_OSPF-ROUTE-TABLE;
                      uses live_ncs_ADDITIONAL-PATHS-SEND;
                      uses live_ncs_ADVERTISE-LOCAL-LABELED-ROUTE-SAFI-UNICAST;
                      uses live_ncs_MOBILE-ROUTES;
                      uses live_ncs_DISABLE-AS-PATH-LOOP-CHECK;
                      uses live_ncs_SUBSCRIBER-ROUTES;
                      uses live_ncs_SEGMENT-ROUTING;
                    }
                  }
                  leaf exists {
                    type empty;
                    description
                      "Create this VRF. Deletion of this object
                       causes deletion of all the objects under
                       VRF associated with this object.";
                  }
                  uses live_ncs_ROUTER-ID;
                  uses live_ncs_DISABLE-ENFORCE-FIRST-AS;
                  uses live_ncs_BEST-PATH-COST-COMMUNITY;
                  uses live_ncs_BEST-PATH-AIGP-IGNORE;
                  uses live_ncs_BEST-PATH-AS-PATH-LENGTH;
                  uses live_ncs_IGP-REDIST-INTERNAL;
                  uses live_ncs_MULTI-PATH-AS-PATH-IGNORE-ONWARDS;
                  uses live_ncs_DISABLE-FAST-EXTERNAL-FALLOVER;
                  uses live_ncs_UNSAFE-EBGP-POLICY;
                  uses live_ncs_DEFAULT-METRIC;
                  uses live_ncs_DEFAULT-INFO-ORIGINATE;
                  uses live_ncs_BGP-CFG-RPKI-ORIGIN-AS-VALIDITY-SIGNAL-IBGP;
                  uses live_ncs_BGP-CFG-RPKI-BESTPATH-USE-ORIGIN-AS-VALIDITY;
                  uses live_ncs_BEST-PATH-CONFEDERATION-PATHS;
                  uses live_ncs_BEST-PATH-AS-MULTIPATH-RELAX;
                  uses live_ncs_MPLS-ACTIVATED-INTERFACE-TABLE;
                  uses live_ncs_DISABLE-AUTO-SOFT-RESET;
                  uses live_ncs_DISABLE-MSG-LOG;
                  uses live_ncs_GLOBAL-TIMERS;
                  uses live_ncs_BEST-PATH-IGP-METRIC-IGNORE;
                  uses live_ncs_NEXT-HOP-RES-ALLOW-DEFAULT;
                  uses live_ncs_NEXT-HOP-MPLS-FWD-IBGP;
                  uses live_ncs_BFD;
                  uses live_ncs_DISABLE-NEIGHBOR-LOGGING;
                  uses live_ncs_SEND-SOCKET-BUFFER-SIZES;
                  uses live_ncs_BEST-PATH-MED-ALWAYS;
                  uses live_ncs_RECEIVE-SOCKET-BUFFER-SIZES;
                  uses live_ncs_BEST-PATH-ROUTER-ID;
                  uses live_ncs_BEST-PATH-MED-MISSING;
                  uses live_ncs_LOCAL-PREFERENCE;
                }
                container vrf-neighbors {

                  grouping VRF-NEIGHBOR-CONTENT {
                    description
                      "VRF NEIGHBOR CONTENT";
                    container vrf-neighbor-afs {
                      description
                        "Address family type of a VRF neighbor";
                      list vrf-neighbor-af {
                        key "af-name";
                        description
                          "Address family type of a VRF neighbor";
                        leaf af-name {
                          type dt1:Bgp-address-family;
                          description
                            "BGP neighbor address family";
                        }
                        uses live_ncs_NEIGHBOR-AF-LONG-LIVED-GRACEFUL-RESTART-CAPABLE;
                        uses live_ncs_SEND-EXT-COMMUNITY-EBGP;
                        uses live_ncs_ACCEPT-ROUTE-LEGACY-RT;
                        uses live_ncs_AIGP-COST-COMMUNITY;
                        uses live_ncs_SEND-COMMUNITY-EBGP;
                        uses live_ncs_ADVERTISE-DEF-IMP-DISABLE-V6;
                        uses live_ncs_ADVERTISE-DISABLE;
                        uses live_ncs_MAXIMUM-PREFIXES;
                        uses live_ncs_ADVERTISE-BRIDGE-DOMAIN-IMP-DISABLE-V6;
                        uses live_ncs_REMOVE-PRIVATE-AS-ENTIRE-AS-PATH-INBOUND;
                        uses live_ncs_NEXT-HOP-UNCHANGED;
                        uses live_ncs_ADVERTISE-LOCAL-LABELED-ROUTE;
                        uses live_ncs_ADVERTISE-DEF-IMP-DISABLE-V4;
                        uses live_ncs_RPKI-ORIGIN-AS-VALIDATION-DISABLE;
                        uses live_ncs_ADVERTISE-BRIDGE-DOMAIN-IMP-DISABLE-V4;
                        uses live_ncs_FLOWSPEC-VALIDATION;
                        uses live_ncs_ADVERTISE-L2VPN-EVPN;
                        uses live_ncs_ADVERTISE-LOCAL-L2VPN-EVPN;
                        uses live_ncs_ENCAPSULATION-TYPE;
                        uses live_ncs_RPKI-BESTPATH-ORIGIN-AS-ALLOW-INVALID;
                        uses live_ncs_ENFORCE-MULTIPLE-LABELS;
                        uses live_ncs_AS-OVERRIDE;
                        uses live_ncs_MULTIPATH;
                        uses live_ncs_SEND-COMMUNITY-EBGP-GRACEFUL-SHUTDOWN;
                        uses live_ncs_ACTIVATE;
                        uses live_ncs_PREFIX-ORF-POLICY;
                        uses live_ncs_NEIGHBOR-AF-LONG-LIVED-GRACEFUL-RESTART-STALE-TIME;
                        uses live_ncs_SITE-OF-ORIGIN;
                        uses live_ncs_UPDATE-OUT-ORIG-LOOP-CHK-DISABLE;
                        uses live_ncs_AIGP;
                        uses live_ncs_AIGP-SEND-MED;
                        uses live_ncs_ADVERTISE-V6;
                        uses live_ncs_ALLOW-AS-IN;
                        uses live_ncs_ADVERTISE-ORF;
                        uses live_ncs_ROUTE-REFLECTOR-CLIENT;
                        uses live_ncs_NEXT-HOP-SELF;
                        uses live_ncs_ADVERTISE-LOCAL-V6;
                        uses live_ncs_ROUTE-POLICY-IN;
                        uses live_ncs_IMPORT;
                        uses live_ncs_DEFAULT-ORIGINATE;
                        uses live_ncs_SOFT-RECONFIGURATION;
                        uses live_ncs_ADVERTISE-VRF-IMP-DISABLE-V6;
                        uses live_ncs_DEFAULT-WEIGHT;
                        uses live_ncs_AF-GROUP;
                        uses live_ncs_ADVERTISE-V4;
                        uses live_ncs_NEXT-HOP-UNCHANGED-MULTIPATH;
                        uses live_ncs_OPTIMAL-ROUTE-REFLECTION-GROUP;
                        uses live_ncs_ACCEPT-OWN;
                        uses live_ncs_ROUTE-POLICY-OUT;
                        uses live_ncs_ADVERTISE-LOCAL-V4;
                        uses live_ncs_ADVERTISE-PERMANENT-NETWORK;
                        uses live_ncs_REMOVE-PRIVATE-AS-ENTIRE-AS-PATH;
                        uses live_ncs_ADVERTISE-VRF-IMP-DISABLE-V4;
                      }
                    }
                    uses live_ncs_LOCAL-ADDRESS-SUB-NET;
                    uses live_ncs_INTERNAL-VPN-CLIENT-IBGP-CE;
                    uses live_ncs_LOCAL-ADDRESS;
                    uses live_ncs_BMP-ACTIVATE-TABLE;
                    uses live_ncs_EBGP-MULTIHOP;
                    uses live_ncs_SESSION-GROUP-ADD-MEMBER;
                    uses live_ncs_EGRESS-PEER-ENGINEERING;
                    uses live_ncs_REMOTE-AS;
                    uses live_ncs_MERGE-SAFI1-AND4-INBOUND-UPDATES;
                    uses live_ncs_LOCAL-AS;
                    uses live_ncs_NEIGHBOR-GRACEFUL-RESTART-STALEPATH-TIME;
                    uses live_ncs_SHUTDOWN;
                    uses live_ncs_DESCRIPTION;
                    uses live_ncs_NEIGHBOR-GROUP-ADD-MEMBER;
                    uses live_ncs_PASSWORD;
                    uses live_ncs_EBGP-RECV-DMZ;
                    uses live_ncs_ADVERTISEMENT-INTERVAL;
                    uses live_ncs_NEIGHBOR-CLUSTER-ID;
                    uses live_ncs_NEIGHBOR-GRACEFUL-RESTART;
                    uses live_ncs_ENFORCE-FIRST-AS;
                    uses live_ncs_IDLE-WATCH-TIME;
                    uses live_ncs_TCPMSS;
                    uses live_ncs_SESSION-OPEN-MODE;
                    uses live_ncs_BGP-CFG-RPKI-ORIGIN-AS-VALIDATION-DISABLE;
                    uses live_ncs_TOS;
                    uses live_ncs_UPDATE-IN-FILTERING;
                    uses live_ncs_EBGP-SEND-DMZ-ENABLE-MODES;
                    uses live_ncs_MSG-LOG-OUT;
                    uses live_ncs_SUPPRESS-ALL-CAPABILITIES;
                    uses live_ncs_MAX-PEERS;
                    uses live_ncs_AO-KEYCHAIN;
                    uses live_ncs_BGP-CFG-RPKI-BESTPATH-ORIGIN-AS-ALLOW-INVALID;
                    uses live_ncs_RECEIVE-BUFFER-SIZE;
                    uses live_ncs_MSG-LOG-IN;
                    uses live_ncs_ADDITIONAL-PATHS-SEND-CAPABILITY;
                    uses live_ncs_PROPAGATE-DMZ-LINK-BANDWIDTH;
                    uses live_ncs_BFD-ENABLE-MODES;
                    uses live_ncs_SEND-BUFFER-SIZE;
                    uses live_ncs_TTL-SECURITY;
                    uses live_ncs_NEIGHBOR-GRACEFUL-RESTART-TIME;
                    uses live_ncs_TIMERS;
                    uses live_ncs_BFD-MULTIPLIER;
                    uses live_ncs_BFD-MINIMUM-INTERVAL;
                    uses live_ncs_REMOTE-AS-LIST;
                    uses live_ncs_ADDITIONAL-PATHS-RECEIVE-CAPABILITY;
                    uses live_ncs_KEYCHAIN;
                    uses live_ncs_IGNORE-CONNECTED-CHECK-EBGP;
                    uses live_ncs_SUPPRESS-FOUR-BYTE-AS-CAPABILITY;
                    uses live_ncs_UPDATE-SOURCE-INTERFACE;
                    uses live_ncs_GRACEFUL-MAINTENANCE;
                  }
                  list vrf-neighbor {
                    key "neighbor-address";
                    description
                      "A particular VRF peer";
                    leaf neighbor-address {
                      type inet:ip-address-no-zone;
                      description
                        "Neighbor address";
                    }
                    uses VRF-NEIGHBOR-CONTENT;
                  }
                  list vrf-neighbor-prefix-length {
                    key "prefix-length neighbor-address";
                    description
                      "A particular VRF peer";
                    leaf prefix-length {
                      type uint32 {
                        range "0..127";
                      }
                      description
                        "Prefix length";
                    }
                    leaf neighbor-address {
                      type inet:ip-address-no-zone;
                      description
                        "Neighbor address";
                    }
                    uses VRF-NEIGHBOR-CONTENT;
                  }
                  description
                    "BGP VRF peer";
                }
                leaf vrf-name {
                  type xr:Cisco-ios-xr-string;
                  description
                    "VRF name";
                }
              }
            }
            container default-vrf {
              description
                "Global default config";
              container bgp-entity {
                description
                  "Neighbor, neighbor-group, af-group and
                   session-group configuration";
                container neighbors {

                  grouping NEIGHBOR-CONTENT {
                    description
                      "NEIGHBOR CONTENT";
                    container neighbor-afs {
                      description
                        "BGP neighbor AF configuration table";
                      list neighbor-af {
                        key "af-name";
                        description
                          "Address family type of neighbor";
                        leaf af-name {
                          type dt1:Bgp-address-family;
                          description
                            "BGP neighbor address family";
                        }
                        uses live_ncs_NEIGHBOR-AF-LONG-LIVED-GRACEFUL-RESTART-CAPABLE;
                        uses live_ncs_L2VPN-SIGNALLING;
                        uses live_ncs_SEND-EXT-COMMUNITY-EBGP;
                        uses live_ncs_ACCEPT-ROUTE-LEGACY-RT;
                        uses live_ncs_AIGP-COST-COMMUNITY;
                        uses live_ncs_SEND-COMMUNITY-EBGP;
                        uses live_ncs_ADVERTISE-DEF-IMP-DISABLE-V6;
                        uses live_ncs_ADVERTISE-DISABLE;
                        uses live_ncs_SEND-MULTICAST-ATTR;
                        uses live_ncs_MAXIMUM-PREFIXES;
                        uses live_ncs_ADVERTISE-BRIDGE-DOMAIN-IMP-DISABLE-V6;
                        uses live_ncs_REMOVE-PRIVATE-AS-ENTIRE-AS-PATH-INBOUND;
                        uses live_ncs_NEXT-HOP-UNCHANGED;
                        uses live_ncs_ADVERTISE-LOCAL-LABELED-ROUTE;
                        uses live_ncs_ADVERTISE-DEF-IMP-DISABLE-V4;
                        uses live_ncs_RPKI-ORIGIN-AS-VALIDATION-DISABLE;
                        uses live_ncs_ADVERTISE-BRIDGE-DOMAIN-IMP-DISABLE-V4;
                        uses live_ncs_FLOWSPEC-VALIDATION;
                        uses live_ncs_ADVERTISE-L2VPN-EVPN;
                        uses live_ncs_ADVERTISE-LOCAL-L2VPN-EVPN;
                        uses live_ncs_ENCAPSULATION-TYPE;
                        uses live_ncs_RPKI-BESTPATH-ORIGIN-AS-ALLOW-INVALID;
                        uses live_ncs_ENFORCE-MULTIPLE-LABELS;
                        uses live_ncs_AS-OVERRIDE;
                        uses live_ncs_MULTIPATH;
                        uses live_ncs_SEND-COMMUNITY-EBGP-GRACEFUL-SHUTDOWN;
                        uses live_ncs_ACTIVATE;
                        uses live_ncs_PREFIX-ORF-POLICY;
                        uses live_ncs_NEIGHBOR-AF-LONG-LIVED-GRACEFUL-RESTART-STALE-TIME;
                        uses live_ncs_UPDATE-OUT-ORIG-LOOP-CHK-DISABLE;
                        uses live_ncs_AIGP;
                        uses live_ncs_AIGP-SEND-MED;
                        uses live_ncs_ADVERTISE-V6;
                        uses live_ncs_ALLOW-AS-IN;
                        uses live_ncs_ADVERTISE-ORF;
                        uses live_ncs_ROUTE-REFLECTOR-CLIENT;
                        uses live_ncs_NEXT-HOP-SELF;
                        uses live_ncs_ADVERTISE-LOCAL-V6;
                        uses live_ncs_ROUTE-POLICY-IN;
                        uses live_ncs_IMPORT;
                        uses live_ncs_DEFAULT-ORIGINATE;
                        uses live_ncs_SOFT-RECONFIGURATION;
                        uses live_ncs_ADVERTISE-VRF-IMP-DISABLE-V6;
                        uses live_ncs_DEFAULT-WEIGHT;
                        uses live_ncs_AF-GROUP;
                        uses live_ncs_ADVERTISE-V4;
                        uses live_ncs_NEXT-HOP-UNCHANGED-MULTIPATH;
                        uses live_ncs_OPTIMAL-ROUTE-REFLECTION-GROUP;
                        uses live_ncs_ACCEPT-OWN;
                        uses live_ncs_ROUTE-POLICY-OUT;
                        uses live_ncs_ADVERTISE-LOCAL-V4;
                        uses live_ncs_ADVERTISE-PERMANENT-NETWORK;
                        uses live_ncs_REMOVE-PRIVATE-AS-ENTIRE-AS-PATH;
                        uses live_ncs_ADVERTISE-VRF-IMP-DISABLE-V4;
                      }
                    }
                    uses live_ncs_LOCAL-ADDRESS-SUB-NET;
                    uses live_ncs_INTERNAL-VPN-CLIENT-IBGP-CE;
                    uses live_ncs_LOCAL-ADDRESS;
                    uses live_ncs_BMP-ACTIVATE-TABLE;
                    uses live_ncs_EBGP-MULTIHOP;
                    uses live_ncs_SESSION-GROUP-ADD-MEMBER;
                    uses live_ncs_EGRESS-PEER-ENGINEERING;
                    uses live_ncs_REMOTE-AS;
                    uses live_ncs_MERGE-SAFI1-AND4-INBOUND-UPDATES;
                    uses live_ncs_LOCAL-AS;
                    uses live_ncs_NEIGHBOR-GRACEFUL-RESTART-STALEPATH-TIME;
                    uses live_ncs_SHUTDOWN;
                    uses live_ncs_DESCRIPTION;
                    uses live_ncs_NEIGHBOR-GROUP-ADD-MEMBER;
                    uses live_ncs_PASSWORD;
                    uses live_ncs_EBGP-RECV-DMZ;
                    uses live_ncs_ADVERTISEMENT-INTERVAL;
                    uses live_ncs_NEIGHBOR-CLUSTER-ID;
                    uses live_ncs_NEIGHBOR-GRACEFUL-RESTART;
                    uses live_ncs_ENFORCE-FIRST-AS;
                    uses live_ncs_IDLE-WATCH-TIME;
                    uses live_ncs_TCPMSS;
                    uses live_ncs_SESSION-OPEN-MODE;
                    uses live_ncs_BGP-CFG-RPKI-ORIGIN-AS-VALIDATION-DISABLE;
                    uses live_ncs_TOS;
                    uses live_ncs_UPDATE-IN-FILTERING;
                    uses live_ncs_EBGP-SEND-DMZ-ENABLE-MODES;
                    uses live_ncs_MSG-LOG-OUT;
                    uses live_ncs_SUPPRESS-ALL-CAPABILITIES;
                    uses live_ncs_MAX-PEERS;
                    uses live_ncs_AO-KEYCHAIN;
                    uses live_ncs_BGP-CFG-RPKI-BESTPATH-ORIGIN-AS-ALLOW-INVALID;
                    uses live_ncs_RECEIVE-BUFFER-SIZE;
                    uses live_ncs_MSG-LOG-IN;
                    uses live_ncs_ADDITIONAL-PATHS-SEND-CAPABILITY;
                    uses live_ncs_PROPAGATE-DMZ-LINK-BANDWIDTH;
                    uses live_ncs_BFD-ENABLE-MODES;
                    uses live_ncs_SEND-BUFFER-SIZE;
                    uses live_ncs_TTL-SECURITY;
                    uses live_ncs_NEIGHBOR-GRACEFUL-RESTART-TIME;
                    uses live_ncs_TIMERS;
                    uses live_ncs_BFD-MULTIPLIER;
                    uses live_ncs_BFD-MINIMUM-INTERVAL;
                    uses live_ncs_REMOTE-AS-LIST;
                    uses live_ncs_ADDITIONAL-PATHS-RECEIVE-CAPABILITY;
                    uses live_ncs_KEYCHAIN;
                    uses live_ncs_IGNORE-CONNECTED-CHECK-EBGP;
                    uses live_ncs_SUPPRESS-FOUR-BYTE-AS-CAPABILITY;
                    uses live_ncs_UPDATE-SOURCE-INTERFACE;
                    uses live_ncs_GRACEFUL-MAINTENANCE;
                  }
                  list neighbor {
                    key "neighbor-address";
                    description
                      "A particular BGP peer";
                    leaf neighbor-address {
                      type inet:ip-address-no-zone;
                      description
                        "Neighbor address";
                    }
                    uses NEIGHBOR-CONTENT;
                  }
                  list neighbor-prefix-length {
                    key "prefix-length neighbor-address";
                    description
                      "A particular BGP peer";
                    leaf prefix-length {
                      type uint32 {
                        range "0..127";
                      }
                      description
                        "Prefix length";
                    }
                    leaf neighbor-address {
                      type inet:ip-address-no-zone;
                      description
                        "Neighbor address";
                    }
                    uses NEIGHBOR-CONTENT;
                  }
                  description
                    "Neighbor configuration";
                }
                container neighbor-groups {
                  description
                    "Neighbor-group configuration";
                  list neighbor-group {
                    key "neighbor-group-name";
                    description
                      "A particular BGP neighbor group";
                    container neighbor-group-afs {
                      description
                        "BGP neighbor-group AF configuration table";
                      list neighbor-group-af {
                        key "af-name";
                        description
                          "Address family type of neighbor group";
                        leaf af-name {
                          type dt1:Bgp-address-family;
                          description
                            "BGP neighbor group address family";
                        }
                        uses live_ncs_NEIGHBOR-AF-LONG-LIVED-GRACEFUL-RESTART-CAPABLE;
                        uses live_ncs_L2VPN-SIGNALLING;
                        uses live_ncs_SEND-EXT-COMMUNITY-EBGP;
                        uses live_ncs_ACCEPT-ROUTE-LEGACY-RT;
                        uses live_ncs_AIGP-COST-COMMUNITY;
                        uses live_ncs_SEND-COMMUNITY-EBGP;
                        uses live_ncs_ADVERTISE-DEF-IMP-DISABLE-V6;
                        uses live_ncs_ADVERTISE-DISABLE;
                        uses live_ncs_SEND-MULTICAST-ATTR;
                        uses live_ncs_MAXIMUM-PREFIXES;
                        uses live_ncs_ADVERTISE-BRIDGE-DOMAIN-IMP-DISABLE-V6;
                        uses live_ncs_REMOVE-PRIVATE-AS-ENTIRE-AS-PATH-INBOUND;
                        uses live_ncs_NEXT-HOP-UNCHANGED;
                        uses live_ncs_ADVERTISE-LOCAL-LABELED-ROUTE;
                        uses live_ncs_ADVERTISE-DEF-IMP-DISABLE-V4;
                        uses live_ncs_RPKI-ORIGIN-AS-VALIDATION-DISABLE;
                        uses live_ncs_ADVERTISE-BRIDGE-DOMAIN-IMP-DISABLE-V4;
                        uses live_ncs_FLOWSPEC-VALIDATION;
                        uses live_ncs_ADVERTISE-L2VPN-EVPN;
                        uses live_ncs_ADVERTISE-LOCAL-L2VPN-EVPN;
                        uses live_ncs_ENCAPSULATION-TYPE;
                        uses live_ncs_RPKI-BESTPATH-ORIGIN-AS-ALLOW-INVALID;
                        uses live_ncs_ENFORCE-MULTIPLE-LABELS;
                        uses live_ncs_AS-OVERRIDE;
                        uses live_ncs_MULTIPATH;
                        uses live_ncs_SEND-COMMUNITY-EBGP-GRACEFUL-SHUTDOWN;
                        uses live_ncs_ACTIVATE;
                        uses live_ncs_PREFIX-ORF-POLICY;
                        uses live_ncs_NEIGHBOR-AF-LONG-LIVED-GRACEFUL-RESTART-STALE-TIME;
                        uses live_ncs_SITE-OF-ORIGIN;
                        uses live_ncs_UPDATE-OUT-ORIG-LOOP-CHK-DISABLE;
                        uses live_ncs_AIGP;
                        uses live_ncs_AIGP-SEND-MED;
                        uses live_ncs_ADVERTISE-V6;
                        uses live_ncs_ALLOW-AS-IN;
                        uses live_ncs_ADVERTISE-ORF;
                        uses live_ncs_ROUTE-REFLECTOR-CLIENT;
                        uses live_ncs_NEXT-HOP-SELF;
                        uses live_ncs_ADVERTISE-LOCAL-V6;
                        uses live_ncs_ROUTE-POLICY-IN;
                        uses live_ncs_IMPORT;
                        uses live_ncs_DEFAULT-ORIGINATE;
                        uses live_ncs_SOFT-RECONFIGURATION;
                        uses live_ncs_ADVERTISE-VRF-IMP-DISABLE-V6;
                        uses live_ncs_DEFAULT-WEIGHT;
                        uses live_ncs_AF-GROUP;
                        uses live_ncs_ADVERTISE-V4;
                        uses live_ncs_NEXT-HOP-UNCHANGED-MULTIPATH;
                        uses live_ncs_OPTIMAL-ROUTE-REFLECTION-GROUP;
                        uses live_ncs_ACCEPT-OWN;
                        uses live_ncs_ROUTE-POLICY-OUT;
                        uses live_ncs_ADVERTISE-LOCAL-V4;
                        uses live_ncs_ADVERTISE-PERMANENT-NETWORK;
                        uses live_ncs_REMOVE-PRIVATE-AS-ENTIRE-AS-PATH;
                        uses live_ncs_ADVERTISE-VRF-IMP-DISABLE-V4;
                      }
                    }
                    leaf neighbor-group-add-member {
                      type string;
                      description
                        "Inherit configuration from a
                         neighbor-group";
                    }
                    leaf neighbor-group-name {
                      type xr:Cisco-ios-xr-string;
                      description
                        "BGP neighbor group name";
                    }
                    uses live_ncs_LOCAL-ADDRESS-SUB-NET;
                    uses live_ncs_INTERNAL-VPN-CLIENT-IBGP-CE;
                    uses live_ncs_LOCAL-ADDRESS;
                    uses live_ncs_BMP-ACTIVATE-TABLE;
                    uses live_ncs_EBGP-MULTIHOP;
                    uses live_ncs_SESSION-GROUP-ADD-MEMBER;
                    uses live_ncs_EGRESS-PEER-ENGINEERING;
                    uses live_ncs_REMOTE-AS;
                    uses live_ncs_MERGE-SAFI1-AND4-INBOUND-UPDATES;
                    uses live_ncs_LOCAL-AS;
                    uses live_ncs_NEIGHBOR-GRACEFUL-RESTART-STALEPATH-TIME;
                    uses live_ncs_SHUTDOWN;
                    uses live_ncs_DESCRIPTION;
                    uses live_ncs_PASSWORD;
                    uses live_ncs_EBGP-RECV-DMZ;
                    uses live_ncs_ADVERTISEMENT-INTERVAL;
                    uses live_ncs_NEIGHBOR-CLUSTER-ID;
                    uses live_ncs_NEIGHBOR-GRACEFUL-RESTART;
                    uses live_ncs_ENFORCE-FIRST-AS;
                    uses live_ncs_IDLE-WATCH-TIME;
                    uses live_ncs_TCPMSS;
                    uses live_ncs_SESSION-OPEN-MODE;
                    uses live_ncs_BGP-CFG-RPKI-ORIGIN-AS-VALIDATION-DISABLE;
                    uses live_ncs_TOS;
                    uses live_ncs_UPDATE-IN-FILTERING;
                    uses live_ncs_EBGP-SEND-DMZ-ENABLE-MODES;
                    uses live_ncs_MSG-LOG-OUT;
                    uses live_ncs_SUPPRESS-ALL-CAPABILITIES;
                    uses live_ncs_MAX-PEERS;
                    uses live_ncs_AO-KEYCHAIN;
                    uses live_ncs_BGP-CFG-RPKI-BESTPATH-ORIGIN-AS-ALLOW-INVALID;
                    uses live_ncs_RECEIVE-BUFFER-SIZE;
                    uses live_ncs_MSG-LOG-IN;
                    uses live_ncs_ADDITIONAL-PATHS-SEND-CAPABILITY;
                    uses live_ncs_PROPAGATE-DMZ-LINK-BANDWIDTH;
                    uses live_ncs_BFD-ENABLE-MODES;
                    uses live_ncs_SEND-BUFFER-SIZE;
                    uses live_ncs_TTL-SECURITY;
                    uses live_ncs_NEIGHBOR-GRACEFUL-RESTART-TIME;
                    uses live_ncs_TIMERS;
                    uses live_ncs_BFD-MULTIPLIER;
                    uses live_ncs_BFD-MINIMUM-INTERVAL;
                    uses live_ncs_REMOTE-AS-LIST;
                    uses live_ncs_ADDITIONAL-PATHS-RECEIVE-CAPABILITY;
                    uses live_ncs_KEYCHAIN;
                    uses live_ncs_IGNORE-CONNECTED-CHECK-EBGP;
                    uses live_ncs_SUPPRESS-FOUR-BYTE-AS-CAPABILITY;
                    uses live_ncs_UPDATE-SOURCE-INTERFACE;
                    uses live_ncs_CREATE;
                    uses live_ncs_GRACEFUL-MAINTENANCE;
                  }
                }
                container af-groups {
                  description
                    "AF-group configuration";
                  list af-group {
                    key "af-group-name";
                    description
                      "A particular BGP AF group";
                    container af-group-afs {
                      description
                        "AF group configuration table";
                      list af-group-af {
                        key "af-name";
                        description
                          "Address family type of an AF group";
                        leaf af-group {
                          type string;
                          description
                            "Inherit configuration for this
                             address-family from an AF-group";
                        }
                        leaf create {
                          type empty;
                          description
                            "Create this address family group.
                             Deletion of this object causes deletion
                             of all the objects under AFGroup
                             associated with this object.";
                        }
                        leaf af-name {
                          type dt1:Bgp-address-family;
                          description
                            "BGP AF group address family";
                        }
                        uses live_ncs_NEIGHBOR-AF-LONG-LIVED-GRACEFUL-RESTART-CAPABLE;
                        uses live_ncs_L2VPN-SIGNALLING;
                        uses live_ncs_SEND-EXT-COMMUNITY-EBGP;
                        uses live_ncs_ACCEPT-ROUTE-LEGACY-RT;
                        uses live_ncs_AIGP-COST-COMMUNITY;
                        uses live_ncs_SEND-COMMUNITY-EBGP;
                        uses live_ncs_ADVERTISE-DEF-IMP-DISABLE-V6;
                        uses live_ncs_ADVERTISE-DISABLE;
                        uses live_ncs_SEND-MULTICAST-ATTR;
                        uses live_ncs_MAXIMUM-PREFIXES;
                        uses live_ncs_ADVERTISE-BRIDGE-DOMAIN-IMP-DISABLE-V6;
                        uses live_ncs_REMOVE-PRIVATE-AS-ENTIRE-AS-PATH-INBOUND;
                        uses live_ncs_NEXT-HOP-UNCHANGED;
                        uses live_ncs_ADVERTISE-LOCAL-LABELED-ROUTE;
                        uses live_ncs_ADVERTISE-DEF-IMP-DISABLE-V4;
                        uses live_ncs_RPKI-ORIGIN-AS-VALIDATION-DISABLE;
                        uses live_ncs_ADVERTISE-BRIDGE-DOMAIN-IMP-DISABLE-V4;
                        uses live_ncs_FLOWSPEC-VALIDATION;
                        uses live_ncs_ADVERTISE-L2VPN-EVPN;
                        uses live_ncs_ADVERTISE-LOCAL-L2VPN-EVPN;
                        uses live_ncs_ENCAPSULATION-TYPE;
                        uses live_ncs_RPKI-BESTPATH-ORIGIN-AS-ALLOW-INVALID;
                        uses live_ncs_ENFORCE-MULTIPLE-LABELS;
                        uses live_ncs_AS-OVERRIDE;
                        uses live_ncs_MULTIPATH;
                        uses live_ncs_SEND-COMMUNITY-EBGP-GRACEFUL-SHUTDOWN;
                        uses live_ncs_PREFIX-ORF-POLICY;
                        uses live_ncs_NEIGHBOR-AF-LONG-LIVED-GRACEFUL-RESTART-STALE-TIME;
                        uses live_ncs_SITE-OF-ORIGIN;
                        uses live_ncs_UPDATE-OUT-ORIG-LOOP-CHK-DISABLE;
                        uses live_ncs_AIGP;
                        uses live_ncs_AIGP-SEND-MED;
                        uses live_ncs_ADVERTISE-V6;
                        uses live_ncs_ALLOW-AS-IN;
                        uses live_ncs_ADVERTISE-ORF;
                        uses live_ncs_ROUTE-REFLECTOR-CLIENT;
                        uses live_ncs_NEXT-HOP-SELF;
                        uses live_ncs_ADVERTISE-LOCAL-V6;
                        uses live_ncs_ROUTE-POLICY-IN;
                        uses live_ncs_IMPORT;
                        uses live_ncs_DEFAULT-ORIGINATE;
                        uses live_ncs_SOFT-RECONFIGURATION;
                        uses live_ncs_ADVERTISE-VRF-IMP-DISABLE-V6;
                        uses live_ncs_DEFAULT-WEIGHT;
                        uses live_ncs_ADVERTISE-V4;
                        uses live_ncs_NEXT-HOP-UNCHANGED-MULTIPATH;
                        uses live_ncs_OPTIMAL-ROUTE-REFLECTION-GROUP;
                        uses live_ncs_ACCEPT-OWN;
                        uses live_ncs_ROUTE-POLICY-OUT;
                        uses live_ncs_ADVERTISE-LOCAL-V4;
                        uses live_ncs_ADVERTISE-PERMANENT-NETWORK;
                        uses live_ncs_REMOVE-PRIVATE-AS-ENTIRE-AS-PATH;
                        uses live_ncs_ADVERTISE-VRF-IMP-DISABLE-V4;
                      }
                    }
                    leaf af-group-name {
                      type xr:Cisco-ios-xr-string;
                      description
                        "BGP AF group name";
                    }
                  }
                }
                container session-groups {
                  description
                    "Session group configuration";
                  list session-group {
                    key "session-group-name";
                    description
                      "A particular BGP session group";
                    leaf session-group-add-member {
                      type string;
                      description
                        "Inherit address-family independent config
                         from a session-group";
                    }
                    leaf session-group-name {
                      type xr:Cisco-ios-xr-string;
                      description
                        "BGP session group name";
                    }
                    uses live_ncs_LOCAL-ADDRESS-SUB-NET;
                    uses live_ncs_INTERNAL-VPN-CLIENT-IBGP-CE;
                    uses live_ncs_LOCAL-ADDRESS;
                    uses live_ncs_BMP-ACTIVATE-TABLE;
                    uses live_ncs_EBGP-MULTIHOP;
                    uses live_ncs_EGRESS-PEER-ENGINEERING;
                    uses live_ncs_REMOTE-AS;
                    uses live_ncs_MERGE-SAFI1-AND4-INBOUND-UPDATES;
                    uses live_ncs_LOCAL-AS;
                    uses live_ncs_NEIGHBOR-GRACEFUL-RESTART-STALEPATH-TIME;
                    uses live_ncs_SHUTDOWN;
                    uses live_ncs_DESCRIPTION;
                    uses live_ncs_PASSWORD;
                    uses live_ncs_EBGP-RECV-DMZ;
                    uses live_ncs_ADVERTISEMENT-INTERVAL;
                    uses live_ncs_NEIGHBOR-CLUSTER-ID;
                    uses live_ncs_NEIGHBOR-GRACEFUL-RESTART;
                    uses live_ncs_ENFORCE-FIRST-AS;
                    uses live_ncs_IDLE-WATCH-TIME;
                    uses live_ncs_TCPMSS;
                    uses live_ncs_SESSION-OPEN-MODE;
                    uses live_ncs_BGP-CFG-RPKI-ORIGIN-AS-VALIDATION-DISABLE;
                    uses live_ncs_TOS;
                    uses live_ncs_UPDATE-IN-FILTERING;
                    uses live_ncs_EBGP-SEND-DMZ-ENABLE-MODES;
                    uses live_ncs_MSG-LOG-OUT;
                    uses live_ncs_SUPPRESS-ALL-CAPABILITIES;
                    uses live_ncs_MAX-PEERS;
                    uses live_ncs_AO-KEYCHAIN;
                    uses live_ncs_BGP-CFG-RPKI-BESTPATH-ORIGIN-AS-ALLOW-INVALID;
                    uses live_ncs_RECEIVE-BUFFER-SIZE;
                    uses live_ncs_MSG-LOG-IN;
                    uses live_ncs_ADDITIONAL-PATHS-SEND-CAPABILITY;
                    uses live_ncs_PROPAGATE-DMZ-LINK-BANDWIDTH;
                    uses live_ncs_BFD-ENABLE-MODES;
                    uses live_ncs_SEND-BUFFER-SIZE;
                    uses live_ncs_TTL-SECURITY;
                    uses live_ncs_NEIGHBOR-GRACEFUL-RESTART-TIME;
                    uses live_ncs_TIMERS;
                    uses live_ncs_BFD-MULTIPLIER;
                    uses live_ncs_BFD-MINIMUM-INTERVAL;
                    uses live_ncs_REMOTE-AS-LIST;
                    uses live_ncs_ADDITIONAL-PATHS-RECEIVE-CAPABILITY;
                    uses live_ncs_KEYCHAIN;
                    uses live_ncs_IGNORE-CONNECTED-CHECK-EBGP;
                    uses live_ncs_SUPPRESS-FOUR-BYTE-AS-CAPABILITY;
                    uses live_ncs_UPDATE-SOURCE-INTERFACE;
                    uses live_ncs_CREATE;
                    uses live_ncs_GRACEFUL-MAINTENANCE;
                  }
                }
              }
              container global {
                description
                  "Global default config";
                container cluster-id {
                  description
                    "Configure Route-Reflector Cluster-id";
                  leaf cluster-id-number {
                    type uint32 {
                      range "1..4294967295";
                    }
                    description
                      "Route-Reflector Cluster ID as 32 bit
                       quantity";
                  }
                  leaf cluster-id-address {
                    type inet:ipv4-address-no-zone;
                    description
                      "Route-Reflector Cluster ID in IPV4 address
                       format";
                  }
                }
                container write-limit {
                  description
                    "Set write-queue limit for each update group";
                  leaf formatted-messages {
                    type uint32 {
                      range "500..100000000";
                    }
                    // NCS drop default statement
                    description
                      "Number of messages to be formatted per
                       update group";
                  }
                  leaf enqueued-messages {
                    type uint32 {
                      range "500..100000000";
                    }
                    // NCS drop default statement
                    description
                      "Number of messages that can be enqueued in
                       total";
                  }
                  leaf desynchronize {
                    type boolean;
                    // NCS drop default statement
                    description
                      "TRUE to enable desynchronization, FALSE
                       otherwise.";
                  }
                }
                container update-delay {
                  description
                    "Set the max initial delay for sending
                     updates";
                  leaf delay {
                    type uint32 {
                      range "0..3600";
                    }
                    units "second";
                    // NCS drop default statement
                    description
                      "Delay value (seconds)";
                  }
                  leaf always {
                    type boolean;
                    // NCS drop must statement
                    // NCS drop default statement
                    description
                      "Set to TRUE to disable keepalive trigger
                       bestpath and delay is enforced.";
                  }
                }
                container as-league {
                  description
                    "AS League";
                  container peers {
                    description
                      "AS League Peers";
                    list peer {
                      key "as-xx as-yy";
                      description
                        "AS League Peer AS";
                      leaf as-xx {
                        type dt1:Bgp-as-range;
                        description
                          "xx of peer AS xx.yy";
                      }
                      leaf as-yy {
                        type dt1:Bgp-as-range;
                        description
                          "yy of peer AS xx.yy";
                      }
                    }
                  }
                  leaf enable {
                    type empty;
                    description
                      "AS League creation";
                  }
                }
                container rpki-servers {
                  description
                    "RPKI server configuration";
                  list rpki-server {
                    key "server";
                    description
                      "RPKI server configuration";
                    container transport {
                      description
                        "RPKI server transport";
                      leaf transport {
                        type Bgp-rpki-transport;
                        // NCS drop default statement
                        description
                          "RPKI server transport";
                      }
                      leaf port {
                        type xr:Cisco-ios-xr-port-number;
                        // NCS drop default statement
                        description
                          "port";
                      }
                    }
                    leaf enable {
                      type empty;
                      description
                        "RPKI server configuration";
                    }
                    leaf shutdown {
                      type empty;
                      description
                        "RPKI server shutdown";
                    }
                    leaf password {
                      type string;
                      description
                        "RPKI server password";
                    }
                    leaf response-time {
                      type uint32 {
                        range "15..3600";
                      }
                      units "second";
                      description
                        "RPKI server response-time (15-3600
                         seconds)";
                    }
                    leaf username {
                      type string;
                      description
                        "RPKI server username";
                    }
                    leaf refresh-time {
                      type uint32 {
                        range "15..3600";
                      }
                      units "second";
                      description
                        "RPKI server refresh-time (15-3600
                         seconds)";
                    }
                    leaf purge-time {
                      type uint32 {
                        range "30..360";
                      }
                      units "second";
                      description
                        "RPKI server purge-time (30-360 seconds)";
                    }
                    leaf server {
                      type xr:Cisco-ios-xr-string;
                      description
                        "Server address (opaque string)";
                    }
                  }
                }
                container as-list-groups {
                  description
                    "AS-list group lists";
                  list as-list-group {
                    key "as-list-group-name";
                    description
                      "AS-List group";
                    container ases {
                      description
                        "AS list";
                      list as {
                        key "as-xx as-yy";
                        description
                          "AS-List group";
                        leaf as-xx {
                          type dt1:Bgp-as-range;
                          description
                            "xx of AS number/confed peer xx.yy";
                        }
                        leaf as-yy {
                          type dt1:Bgp-as-range;
                          description
                            "yy of AS number/confed peer xx.yy";
                        }
                      }
                    }
                    leaf enable {
                      type empty;
                      description
                        "AS-List group creation";
                    }
                    leaf as-list-group-name {
                      type xr:Cisco-ios-xr-string;
                      description
                        "Group name";
                    }
                  }
                }
                container limits {
                  description
                    "Maximum number that can be configured";
                  leaf maximum-neighbors {
                    type uint32 {
                      range "1..15000";
                    }
                    // NCS drop default statement
                    description
                      "Maximum number of neighbors that can be
                       configured";
                  }
                }
                container confederation-domain {
                  description
                    "Set routing domain confederation AS";
                  leaf as-xx {
                    type dt1:Bgp-as-range;
                    description
                      "xx of AS number xx.yy";
                  }
                  leaf as-yy {
                    type dt1:Bgp-as-range;
                    description
                      "yy of AS number xx.yy";
                  }
                }
                container confederation-peer-ases {
                  description
                    "Define peer ASes in BGP confederation";
                  list confederation-peer-as {
                    key "as-xx as-yy";
                    description
                      "Confederation peer AS";
                    leaf as-xx {
                      type dt1:Bgp-as-range;
                      description
                        "xx of AS number/confed peer xx.yy";
                    }
                    leaf as-yy {
                      type dt1:Bgp-as-range;
                      description
                        "yy of AS number/confed peer xx.yy";
                    }
                  }
                }
                container attribute-filter-groups {
                  description
                    "Attribute-filter groups list";
                  list attribute-filter-group {
                    key "attribute-filter-group-name";
                    description
                      "Attribute-filter group";
                    container attribute-filters {
                      description
                        "Attribute-filter group attributes list";
                      list attribute-filter {
                        key "attribute-start attribute-end";
                        description
                          "Attribute-filter group attribute";
                        leaf attribute-start {
                          type dt1:Bgp-attribute-range;
                          description
                            "Start of attribute range";
                        }
                        leaf attribute-end {
                          type dt1:Bgp-attribute-range;
                          description
                            "End of attribute range";
                        }
                        leaf filter-action {
                          type dt1:Bgp-update-filter-action;
                          // NCS drop mandatory statement
                          description
                            "Filtering action";
                        }
                      }
                    }
                    leaf enable {
                      type empty;
                      description
                        "Attribute-filter group creation";
                    }
                    leaf attribute-filter-group-name {
                      type xr:Cisco-ios-xr-string;
                      description
                        "Group name";
                    }
                  }
                }
                container global-graceful-maintenance-activate {
                  description
                    "Activate Graceful Maintenance Mode for all
                     neighbors with graceful maintenance config";
                  leaf all-neighbors {
                    type boolean;
                    description
                      "Also for neighbors without graceful
                       maintenance config";
                  }
                  leaf retain-routes {
                    type boolean;
                    description
                      "Keep routes in RIB once BGP stops";
                  }
                }
                container global-afs {
                  description
                    "Global AF-specific configuration";
                  list global-af {
                    key "af-name";
                    description
                      "Global AF-specific configuration";
                    container isis-routes {
                      description
                        "Redistribute information for IS-IS routes
                         .";
                      list isis-route {
                        key "instance-name";
                        description
                          "Redistribute IS-IS routes";
                        leaf instance-name {
                          type xr:Cisco-ios-xr-string;
                          description
                            "IS-IS instance name";
                        }
                        leaf default-metric {
                          type Bgp-default-metric-range;
                          description
                            "Default metric";
                        }
                        leaf route-policy-name {
                          type string;
                          description
                            "Route policy name";
                        }
                        leaf redist-type {
                          type xr:Hex-integer;
                          description
                            "Redistribution type: 01 for level 1
                             routes, 02 for level 2 routes, 04 for
                             level 1 inter-area routes. Logical
                             combinations permitted.";
                        }
                      }
                    }
                    container domain-distinguisher {
                      presence "Indicates a domain-distinguisher node is configured.";
                      description
                        "<ASN, router-id> tuple to use to identify
                         the link-state domain";
                      leaf as {
                        type dt1:Bgp-as-range;
                        // NCS drop mandatory statement
                        description
                          "AS Number";
                      }
                      leaf router-id {
                        type inet:ipv4-address-no-zone;
                        // NCS drop mandatory statement
                        description
                          "Router ID";
                      }
                    }
                    container vrf-all {
                      description
                        "Configurations to be inherited to all
                         vrfs";
                      container label-mode {
                        description
                          "MPLS-VPN label allocation mode";
                        leaf label-allocation-mode {
                          type string;
                          description
                            "Label allocation mode: per-ce  Set per
                             CE label mode, per-vrf Set per VRF
                             label mode";
                        }
                        leaf route-policy-name {
                          type string;
                          description
                            "Label mode route policy name";
                        }
                      }
                      leaf rnh-install-format {
                        type Bgp-rnh-install-format;
                        description
                          "RNH install format type: extcomm -
                           install rnh as opaque and extcomms,
                           extcomm-only - install rnh as extcomms
                           only";
                      }
                      leaf enable {
                        type empty;
                        description
                          "Enable vrf all configuration submode";
                      }
                      leaf table-policy {
                        type string;
                        description
                          "Configure policy for installation of
                           routes to RIB";
                      }
                      leaf source-rt-import-policy {
                        type empty;
                        description
                          "Enable sourcing of import route-targets
                           from import-policy";
                      }
                    }
                    container disable-cluster-client-to-client-rrs {
                      description
                        "Disable client-to-client reflection for a
                         cluster";
                      list disable-cluster-client-to-client-rr {
                        // NCS drop must statement
                        key "cluster-type";
                        description
                          "Cluster ID for which reflection is to be
                           disbled";
                        leaf cluster-type {
                          type Bgp-cluster-id;
                          description
                            "Type of cluster-id";
                        }
                        list number {
                          // NCS drop when statement
                          key "cluster-id-number";
                          description
                            "number";
                          leaf cluster-id-number {
                            type uint32 {
                              range "0..4294967295";
                            }
                            description
                              "Cluster ID: if configured as a number";
                          }
                        }
                        list ipv4-address {
                          // NCS drop when statement
                          key "cluster-id-address";
                          description
                            "ipv4 address";
                          leaf cluster-id-address {
                            type inet:ip-address-no-zone;
                            description
                              "Cluster ID: if configured as an IP
                               Address";
                          }
                        }
                      }
                    }
                    container label-delay {
                      presence "Indicates a label-delay node is configured.";
                      description
                        "Delay timer to batch label processing.";
                      leaf seconds {
                        type uint32 {
                          range "0..10";
                        }
                        units "second";
                        // NCS drop mandatory statement
                        description
                          "Delay, seconds part";
                      }
                      leaf milliseconds {
                        type uint32 {
                          range "0..999";
                        }
                        units "millisecond";
                        // NCS drop mandatory statement
                        description
                          "Delay, milliseconds part";
                      }
                    }
                    container ebgp {
                      presence "Indicates a ebgp node is configured.";
                      description
                        "Use eBGP multipaths";
                      leaf paths-value {
                        type uint32 {
                          range "2..64";
                        }
                        // NCS drop mandatory statement
                        description
                          "Number of paths";
                      }
                      leaf unequal-cost {
                        type boolean;
                        // NCS drop default statement
                        description
                          "UNUSED";
                      }
                      leaf selective {
                        type boolean;
                        // NCS drop default statement
                        description
                          "Allow multipaths only from marked
                           neighbors";
                      }
                      leaf order-by-igp-metric {
                        type boolean;
                        // NCS drop default statement
                        description
                          "Order candidate multipaths by IGP metric";
                      }
                    }
                    container eibgp {
                      presence "Indicates a eibgp node is configured.";
                      description
                        "Use eiBGP multipaths";
                      leaf paths-value {
                        type uint32 {
                          range "2..64";
                        }
                        // NCS drop mandatory statement
                        description
                          "Number of paths";
                      }
                      leaf unequal-cost {
                        type boolean;
                        // NCS drop default statement
                        description
                          "UNUSED";
                      }
                      leaf selective {
                        type boolean;
                        // NCS drop default statement
                        description
                          "Allow multipaths only from marked
                           neighbors";
                      }
                      leaf order-by-igp-metric {
                        type boolean;
                        // NCS drop default statement
                        description
                          "Order candidate multipaths by IGP metric";
                      }
                    }
                    container retain-rt {
                      description
                        "Accept received updates with the
                         specified attributes";
                      leaf all {
                        type boolean;
                        description
                          "Whether all RTs are to be retained,
                           default is FALSE";
                      }
                      leaf route-policy-name {
                        type string;
                        description
                          "Route policy name";
                      }
                    }
                    container ibgp {
                      presence "Indicates a ibgp node is configured.";
                      description
                        "Use iBGP multipaths";
                      leaf paths-value {
                        type uint32 {
                          range "2..64";
                        }
                        // NCS drop mandatory statement
                        description
                          "Number of paths";
                      }
                      leaf unequal-cost {
                        type boolean;
                        // NCS drop default statement
                        description
                          "Allow multipaths to have different IGP
                           metrics";
                      }
                      leaf selective {
                        type boolean;
                        // NCS drop default statement
                        description
                          "Allow multipaths only from marked
                           neighbors";
                      }
                      leaf order-by-igp-metric {
                        type boolean;
                        // NCS drop default statement
                        description
                          "Order candidate multipaths by IGP metric";
                      }
                    }
                    container import-delay {
                      presence "Indicates a import-delay node is configured.";
                      description
                        "Delay timer to batch import processing.";
                      leaf seconds {
                        type uint32 {
                          range "0..10";
                        }
                        units "second";
                        // NCS drop mandatory statement
                        description
                          "Delay, seconds part";
                      }
                      leaf milliseconds {
                        type uint32 {
                          range "0..999";
                        }
                        units "millisecond";
                        // NCS drop mandatory statement
                        description
                          "Delay, milliseconds part";
                      }
                    }
                    leaf rnh-install-format {
                      type Bgp-rnh-install-format;
                      description
                        "RNH install format type: extcomm -
                         install rnh as opaque and extcomms,
                         extcomm-only - install rnh as extcomms
                         only";
                    }
                    leaf inter-as-install {
                      type empty;
                      description
                        "Enable install remote MVPN routes to PIM
                         in default VRF";
                    }
                    leaf segmented-mcast {
                      type empty;
                      description
                        "Enable segmented multicast";
                    }
                    leaf implicit-import {
                      type empty;
                      description
                        "Implicit import configuration";
                    }
                    leaf disable-default-martian-check {
                      type empty;
                      description
                        "Disable default Martian Check";
                    }
                    leaf next-hop-critical-trigger-delay {
                      type uint32 {
                        range "0..4294967295";
                      }
                      units "millisecond";
                      // NCS drop default statement
                      description
                        "Next hop Critical Trigger Delay";
                    }
                    leaf next-hop-non-critical-trigger-delay {
                      type uint32 {
                        range "0..4294967295";
                      }
                      units "millisecond";
                      // NCS drop default statement
                      description
                        "Next hop Non-critical Trigger Delay";
                    }
                    leaf label-security-rpf {
                      type empty;
                      description
                        "Calculate label-security RPF lists and
                         install to RIB/LSD";
                    }
                    leaf use-igpsr-label {
                      type empty;
                      description
                        "Use IGP SR label for resolution
                         configuration";
                    }
                    leaf label-retain {
                      type uint32 {
                        range "3..60";
                      }
                      units "minute";
                      description
                        "Label retention time in minutes";
                    }
                    leaf scan-time {
                      type uint32 {
                        range "5..3600";
                      }
                      units "second";
                      // NCS drop default statement
                      description
                        "Configure background scanner interval for
                         this address family";
                    }
                    leaf source-route-target-policy {
                      type string;
                      description
                        "Route policy name to apply to configure
                         source route-target";
                    }
                    leaf rpki-origin-as-validation-disable {
                      type empty;
                      description
                        "RPKI origin-AS validation disable";
                    }
                    leaf update-limit-sub-group-ebgp {
                      type uint32 {
                        range "1..512";
                      }
                      units "megabyte";
                      // NCS drop default statement
                      description
                        "Upper bound on update generation
                         transient memory usage for every EBGP
                         Sub-group";
                    }
                    leaf update-limit-address-family {
                      type uint32 {
                        range "4..2048";
                      }
                      units "megabyte";
                      // NCS drop default statement
                      description
                        "Upper bound on update generation
                         transient memory usage for the
                         address-family";
                    }
                    leaf update-limit-sub-group-ibgp {
                      type uint32 {
                        range "1..512";
                      }
                      units "megabyte";
                      // NCS drop default statement
                      description
                        "Upper bound on update generation
                         transient memory usage for every IBGP
                         Sub-group";
                    }
                    leaf disable-client-to-client-rr {
                      type empty;
                      description
                        "Disable client-to-client reflection";
                    }
                    leaf next-hop-route-policy {
                      type string;
                      description
                        "Next hop policy to filter out nexthop
                         notification";
                    }
                    leaf global-table-mcast {
                      type empty;
                      description
                        "Enable global table multicast";
                    }
                    leaf wait-rib-install {
                      type empty;
                      description
                        "Wait for route install before sending
                         updates to neighbors";
                    }
                    leaf prefix-sid-map {
                      type empty;
                      description
                        "Retrieve prefix sid mapping from SRMS";
                    }
                    leaf af-name {
                      type dt1:Bgp-address-family;
                      description
                        "Address family";
                    }
                    uses live_ncs_RPKI-ORIGIN-AS-VALIDATION-ENABLE;
                    uses live_ncs_AGGREGATE-ADDRESS-TABLE;
                    uses live_ncs_DYNAMIC-MED-INTERVAL;
                    uses live_ncs_OPTIMAL-ROUTE-REFLECTOR-GROUP-TABLE;
                    uses live_ncs_DAMPENING;
                    uses live_ncs_ENABLE;
                    uses live_ncs_RIP-ROUTES;
                    uses live_ncs_LISP-ROUTES;
                    uses live_ncs_STATIC-ROUTES;
                    uses live_ncs_DISTANCE;
                    uses live_ncs_TABLE-POLICY;
                    uses live_ncs_APP-ROUTE-TABLE;
                    uses live_ncs_ATTRIBUTE-DOWNLOAD;
                    uses live_ncs_LABEL-MODE;
                    uses live_ncs_EIGRP-ROUTE-TABLE;
                    uses live_ncs_BEST-EXTERNAL;
                    uses live_ncs_SOURCED-NETWORK-TABLE;
                    uses live_ncs_RPKI-ORIGIN-AS-VALIDITY-SIGNAL-IBGP;
                    uses live_ncs_CONNECTED-ROUTES;
                    uses live_ncs_ADDITIONAL-PATHS-RECEIVE;
                    uses live_ncs_PERMANENT-NETWORK;
                    uses live_ncs_RPKI-BESTPATH-USE-ORIGIN-AS-VALIDITY;
                    uses live_ncs_ALLOCATE-LABEL;
                    uses live_ncs_ADDITIONAL-PATHS-SELECTION;
                    uses live_ncs_BGP-CFG-RPKI-BESTPATH-ORIGIN-AS-ALLOW-INVALID-MP;
                    uses live_ncs_NEXT-HOP-RESOLUTION-PREFIX-LENGTH-MINIMUM;
                    uses live_ncs_RESET-WEIGHT-ON-IMPORT;
                    uses live_ncs_OSPF-ROUTE-TABLE;
                    uses live_ncs_ADDITIONAL-PATHS-SEND;
                    uses live_ncs_ADVERTISE-LOCAL-LABELED-ROUTE-SAFI-UNICAST;
                    uses live_ncs_MOBILE-ROUTES;
                    uses live_ncs_DISABLE-AS-PATH-LOOP-CHECK;
                    uses live_ncs_SUBSCRIBER-ROUTES;
                    uses live_ncs_SEGMENT-ROUTING;
                  }
                }
                container rpki-static-routes {
                  description
                    "RPKI static route configuration";
                  list rpki-static-route {
                    key "address minimum maximum as";
                    description
                      "RPKI static route";
                    leaf address {
                      type inet:ip-address-no-zone;
                      description
                        "Address";
                    }
                    leaf minimum {
                      type uint32 {
                        range "0..128";
                      }
                      description
                        "Minimum Prefix Length";
                    }
                    leaf maximum {
                      type uint32 {
                        range "1..128";
                      }
                      description
                        "Maximum Prefix Length";
                    }
                    leaf as {
                      type uint32 {
                        range "1..4294967295";
                      }
                      description
                        "AS Number";
                    }
                  }
                }
                leaf graceful-restart {
                  type empty;
                  description
                    "Enable graceful restart support";
                }
                leaf update-out-logging {
                  type empty;
                  description
                    "Enables logging of update generation events";
                }
                leaf install-diversion {
                  type empty;
                  description
                    "Install diversion path to RIB/CEF";
                }
                leaf next-hop-trigger-delay {
                  type uint32 {
                    range "0..300";
                  }
                  units "second";
                  // NCS drop default statement
                  description
                    "Set the delay for triggering nexthop
                     recalculations";
                }
                leaf nsr {
                  type boolean;
                  description
                    "TRUE to Enable non-stop routing
                     supportFALSE to Disable non-stop routing
                     support";
                }
                leaf neighbor-logging-detail {
                  type empty;
                  description
                    "Include extra detail in neighbor change
                     messages";
                }
                leaf mvpn {
                  type empty;
                  description
                    "Connect to PIM/PIM6";
                }
                leaf rpki-origin-as-validation-disable {
                  type empty;
                  description
                    "RPKI origin-AS validation disable";
                }
                leaf global-scan-time {
                  type uint32 {
                    range "5..3600";
                  }
                  units "second";
                  // NCS drop default statement
                  description
                    "Configure background scanner interval for
                     generic scanner";
                }
                leaf rpki-origin-as-validation-time {
                  type uint32 {
                    range "0..60";
                  }
                  units "second";
                  description
                    "Prefix validation time (in seconds). Range
                     : 5 - 60. Specify 0 for timer off";
                }
                leaf rpki-bestpath-origin-as-allow-invalid {
                  type empty;
                  description
                    "RPKI bestpath origin-AS allow invalid";
                }
                leaf graceful-restart-purge-time {
                  type uint32 {
                    range "1..6000";
                  }
                  units "second";
                  // NCS drop default statement
                  description
                    "Time before stale routes are purged.";
                }
                leaf enforce-ibgp-out-policy {
                  type empty;
                  description
                    "Allow all attributes to be modified by
                     outbound policy for iBGP peers";
                }
                leaf update-limit-process {
                  type uint32 {
                    range "16..2048";
                  }
                  units "megabyte";
                  // NCS drop default statement
                  description
                    "Upper bound on update generation transient
                     memory usage for the process";
                }
                leaf graceful-restart-time {
                  type uint32 {
                    range "1..4095";
                  }
                  units "second";
                  // NCS drop default statement
                  description
                    "Restart time advertised to neighbors";
                }
                leaf update-error-handling-basic-ibgp-disable {
                  type empty;
                  description
                    "Inbound update basic error-handling for
                     IBGP neighbors";
                }
                leaf read-only {
                  type empty;
                  description
                    "Allow duplicate table config and disable
                     update generation";
                }
                leaf graceful-restart-stalepath-time {
                  type uint32 {
                    range "1..4095";
                  }
                  units "second";
                  // NCS drop default statement
                  description
                    "Maximum time to wait for restart of GR
                     capable peers";
                }
                leaf update-error-handling-extended-ebgp {
                  type empty;
                  description
                    "Inbound update extended error-handling for
                     EBGP neighbors";
                }
                leaf update-error-handling-basic-ebgp-disable {
                  type empty;
                  description
                    "Inbound update basic error-handling for
                     EBGP neighbors";
                }
                leaf graceful-reset {
                  type empty;
                  description
                    "Reset gracefully if configuration change
                     forces a peer reset";
                }
                leaf igp-loop-check {
                  type empty;
                  description
                    "Enable AS-path loop checking for iBGP peers";
                }
                leaf update-error-handling-extended-ibgp {
                  type empty;
                  description
                    "Inbound update extended error-handling for
                     IBGP neighbors";
                }
                uses live_ncs_ROUTER-ID;
                uses live_ncs_DISABLE-ENFORCE-FIRST-AS;
                uses live_ncs_BEST-PATH-COST-COMMUNITY;
                uses live_ncs_BEST-PATH-AIGP-IGNORE;
                uses live_ncs_BEST-PATH-AS-PATH-LENGTH;
                uses live_ncs_IGP-REDIST-INTERNAL;
                uses live_ncs_MULTI-PATH-AS-PATH-IGNORE-ONWARDS;
                uses live_ncs_DISABLE-FAST-EXTERNAL-FALLOVER;
                uses live_ncs_UNSAFE-EBGP-POLICY;
                uses live_ncs_DEFAULT-METRIC;
                uses live_ncs_DEFAULT-INFO-ORIGINATE;
                uses live_ncs_BGP-CFG-RPKI-ORIGIN-AS-VALIDITY-SIGNAL-IBGP;
                uses live_ncs_BGP-CFG-RPKI-BESTPATH-USE-ORIGIN-AS-VALIDITY;
                uses live_ncs_BEST-PATH-CONFEDERATION-PATHS;
                uses live_ncs_BEST-PATH-AS-MULTIPATH-RELAX;
                uses live_ncs_MPLS-ACTIVATED-INTERFACE-TABLE;
                uses live_ncs_DISABLE-AUTO-SOFT-RESET;
                uses live_ncs_DISABLE-MSG-LOG;
                uses live_ncs_GLOBAL-TIMERS;
                uses live_ncs_BEST-PATH-IGP-METRIC-IGNORE;
                uses live_ncs_NEXT-HOP-RES-ALLOW-DEFAULT;
                uses live_ncs_NEXT-HOP-MPLS-FWD-IBGP;
                uses live_ncs_BFD;
                uses live_ncs_DISABLE-NEIGHBOR-LOGGING;
                uses live_ncs_SEND-SOCKET-BUFFER-SIZES;
                uses live_ncs_BEST-PATH-MED-ALWAYS;
                uses live_ncs_RECEIVE-SOCKET-BUFFER-SIZES;
                uses live_ncs_BEST-PATH-ROUTER-ID;
                uses live_ncs_BEST-PATH-MED-MISSING;
                uses live_ncs_LOCAL-PREFERENCE;
              }
            }
            leaf bgp-running {
              type empty;
              description
                "Enable BGP. Deletion of this object causes
                 deletion of all the objects under FourByteAS
                 associated with this object.";
            }
            leaf as {
              type dt1:Bgp-as-range;
              description
                "2-byte or 4-byte Autonomous system number";
            }
          }
        }
      }
    }
    container bmp-server-all {
      tailf:ncs-device-type "netconf";
      tailf:display-when "not(../../ncs:module) or ../../ncs:module[ncs:name='Cisco-IOS-XR-ipv4-bgp-cfg'] or (../../ncs:live-status-protocol[not(ncs:capability)]) or (../../ncs:live-status-protocol/ncs:capability/ncs:module[.='Cisco-IOS-XR-ipv4-bgp-cfg'])";
      description
        "bmp server all";
      container route-monitoring {
        description
          "Enable Route Monitoring capability for the BMP
           servers.
           BGP update messages messages will be
           regenrated with a table walk
          ";
        leaf policy {
          type Bmp-policy-select;
          description
            "Specify if the routes packed in update messages
             should be
             before or after the application of
             route-policy";
        }
        leaf direction {
          type Bmp-route-direction;
          description
            "Specify if the routes should be picked up at
             inbound
             or outbound direction";
        }
      }
      leaf maximum-buffer-size {
        type uint32 {
          range "1..4294967295";
        }
        units "megabyte";
        description
          "Range in MegaBytes for the maximum buffer size
           of BMP message queue.
           The maximum buf-size is
           20% and default buf-size is 15% of the
           platform
           virtual memory max-limit (aka rlimit).
           Please run show bgp process
           performance-statistics
           to see the individual
           values. Unit is in Megabytes";
      }
    }
    container bmp-servers {
      tailf:ncs-device-type "netconf";
      tailf:display-when "not(../../ncs:module) or ../../ncs:module[ncs:name='Cisco-IOS-XR-ipv4-bgp-cfg'] or (../../ncs:live-status-protocol[not(ncs:capability)]) or (../../ncs:live-status-protocol/ncs:capability/ncs:module[.='Cisco-IOS-XR-ipv4-bgp-cfg'])";
      description
        "bmp servers";
      list bmp-server {
        key "server-id";
        description
          "A particular BMP server";
        container initial-refresh-delay {
          description
            "Initial refresh to generate BGP updates";
          leaf delay {
            type uint32 {
              range "1..3600";
            }
            units "second";
            // NCS drop must statement
            description
              "Delay in seconds before sending Refresh
               request to Peers";
          }
          leaf spread {
            type uint32 {
              range "1..3600";
            }
            // NCS drop must statement
            description
              "Spread over which to send initial Refresh
               request to Peers";
          }
          leaf skip {
            type empty;
            // NCS drop must statement
            description
              "Skip Route Refresh request to Peers";
          }
        }
        container host-port {
          description
            "Configure Host Name/Address and Port for BMP
             Server";
          leaf host {
            type string;
            description
              "Name of the BMP server(accepts IPv4/IPv6
               Address format too)";
          }
          leaf port {
            type xr:Cisco-ios-xr-port-number;
            description
              "Port Number of listening BMP server";
          }
        }
        container tos {
          description
            "TOS (Type Of Service)";
          leaf type {
            type dt1:Bgp-tos;
            description
              "Set type of service";
          }
          leaf value {
            type dt1:Bgp-precedence-dscp;
            description
              "TOS value to set";
          }
        }
        leaf create {
          type empty;
          description
            "BMP Server Creation";
        }
        leaf maximum-buffer-size {
          type uint32 {
            range "1..4294967295";
          }
          units "megabyte";
          description
            "Range in MegaBytes for the maximum buffer size
             of BMP message queue.
             The maximum buf-size is
             20% and default buf-size is 15% of the
             platform
             virtual memory max-limit (aka rlimit)
             . Please run show bgp process
             performance-statistics
             to see the individual
             values. Unit is in Megabytes";
        }
        leaf initial-delay {
          type uint32 {
            range "1..3600";
          }
          units "second";
          description
            "Initial connect delay in seconds in sending
             updates";
        }
        leaf flapping-delay {
          type uint32 {
            range "60..3600";
          }
          units "second";
          description
            "Delay in connecting to BMP Server after a flap
             had been detected.";
        }
        leaf status-report-interval {
          type uint32 {
            range "1..3600";
          }
          units "second";
          description
            "Stats reporting period for BMP server";
        }
        leaf description {
          type string;
          description
            "String to describe the BMP server";
        }
        leaf bmptcp-maximum-segment-size {
          type uint32 {
            range "68..10000";
          }
          units "byte";
          description
            "configure TCP maximum segment size.
             Default=16384.";
        }
        leaf bmptcp-keep-alive {
          type uint32 {
            range "0..7200";
          }
          units "second";
          description
            "configure TCP keep alives to be exchanged
             between client and server. Default=1000";
        }
        leaf vrf {
          type string;
          description
            "VRF for BMP Server";
        }
        leaf shutdown {
          type empty;
          description
            "Shutdown connection to BMP server";
        }
        leaf update-source-interface {
          type xr:Interface-name;
          description
            "Select an interface to configure";
        }
        leaf server-id {
          type uint32 {
            range "1..8";
          }
          description
            "BMP Server ID";
        }
      }
    }
  }
  augment "/ncs:devices/ncs:template/ncs:ned-id/ncs:config" {
    leaf asn-format {
      type string;
      // NCS drop default statement
      description
        "Autonomous system number format";
    }
    container bgp {
      description
        "bgp";
      list instance {
        // NCS patched for predictable order
        ordered-by user;
        // NCS drop must statement
        key "instance-name";
        description
          "BGP instance configuration commands";
        leaf instance-name {
          type string;
          description
            "Instance Name. For Default instance use -
             default";
        }
        list instance-as {
          // NCS patched for predictable order
          ordered-by user;
          // NCS drop must statement
          key "as";
          description
            "Autonomous system";
          leaf as {
            type string;
            description
              "Higher 16 bits of 4-byte Autonomous system
               number";
          }
          list four-byte-as {
            // NCS patched for predictable order
            ordered-by user;
            key "as";
            description
              "4-byte Autonomous system";
            container vrfs {
              description
                "VRF config";
              list vrf {
                // NCS patched for predictable order
                ordered-by user;
                key "vrf-name";
                description
                  "VRF config";
                container vrf-global {
                  description
                    "VRF attribute config";
                  container route-distinguisher {
                    description
                      "Route distinguisher";
                    leaf type {
                      type string;
                      description
                        "Type of RD";
                    }
                    leaf as-xx {
                      // NCS drop when statement
                      type string;
                      description
                        "AS number";
                    }
                    leaf as {
                      // NCS drop when statement
                      type string;
                      description
                        "AS number";
                    }
                    leaf as-index {
                      // NCS drop when statement
                      type string;
                      description
                        "ASN Index";
                    }
                    leaf address {
                      // NCS drop when statement
                      type string;
                      description
                        "IP address";
                    }
                    leaf address-index {
                      // NCS drop when statement
                      type string;
                      description
                        "IP address index";
                    }
                  }
                  container vrf-global-afs {
                    description
                      "Global VRF-specific configuration";
                    list vrf-global-af {
                      // NCS patched for predictable order
                      ordered-by user;
                      key "af-name";
                      description
                        "Global VRF AF-specific configuration";
                      container mvpn {
                        description
                          "MVPN configurations";
                        leaf single-forwarder-selection {
                          type string;
                          description
                            "Select MVPN single forwarder selection";
                        }
                      }
                      container ebgp {
                        presence "Indicates a ebgp node is configured.";
                        description
                          "Use eBGP multipaths";
                        leaf paths-value {
                          type string;
                          // NCS drop mandatory statement
                          description
                            "Number of paths";
                        }
                        leaf unequal-cost {
                          type string;
                          // NCS drop default statement
                          description
                            "UNUSED";
                        }
                        leaf selective {
                          type string;
                          // NCS drop default statement
                          description
                            "Allow multipaths only from marked
                             neighbors";
                        }
                        leaf order-by-igp-metric {
                          type string;
                          // NCS drop default statement
                          description
                            "Order candidate multipaths by IGP
                             metric";
                        }
                      }
                      container eibgp {
                        presence "Indicates a eibgp node is configured.";
                        description
                          "Use eiBGP multipaths";
                        leaf paths-value {
                          type string;
                          // NCS drop mandatory statement
                          description
                            "Number of paths";
                        }
                        leaf unequal-cost {
                          type string;
                          // NCS drop default statement
                          description
                            "UNUSED";
                        }
                        leaf selective {
                          type string;
                          // NCS drop default statement
                          description
                            "Allow multipaths only from marked
                             neighbors";
                        }
                        leaf order-by-igp-metric {
                          type string;
                          // NCS drop default statement
                          description
                            "Order candidate multipaths by IGP
                             metric";
                        }
                      }
                      container ibgp {
                        presence "Indicates a ibgp node is configured.";
                        description
                          "Use iBGP multipaths";
                        leaf paths-value {
                          type string;
                          // NCS drop mandatory statement
                          description
                            "Number of paths";
                        }
                        leaf unequal-cost {
                          type string;
                          // NCS drop default statement
                          description
                            "Allow multipaths to have different IGP
                             metrics";
                        }
                        leaf selective {
                          type string;
                          // NCS drop default statement
                          description
                            "Allow multipaths only from marked
                             neighbors";
                        }
                        leaf order-by-igp-metric {
                          type string;
                          // NCS drop default statement
                          description
                            "Order candidate multipaths by IGP
                             metric";
                        }
                      }
                      leaf rt-download {
                        type empty;
                        description
                          "Route-Target download configuration";
                      }
                      leaf allow-vpn-default-originate {
                        type string;
                        description
                          "TRUE to send default orig route to VPN
                           neighborFALSE to not send default
                           originate route ";
                      }
                      leaf af-name {
                        type string;
                        description
                          "Address family";
                      }
                      uses ncs_template_RPKI-ORIGIN-AS-VALIDATION-ENABLE;
                      uses ncs_template_AGGREGATE-ADDRESS-TABLE;
                      uses ncs_template_DYNAMIC-MED-INTERVAL;
                      uses ncs_template_OPTIMAL-ROUTE-REFLECTOR-GROUP-TABLE;
                      uses ncs_template_DAMPENING;
                      uses ncs_template_ENABLE;
                      uses ncs_template_RIP-ROUTES;
                      uses ncs_template_LISP-ROUTES;
                      uses ncs_template_STATIC-ROUTES;
                      uses ncs_template_DISTANCE;
                      uses ncs_template_TABLE-POLICY;
                      uses ncs_template_APP-ROUTE-TABLE;
                      uses ncs_template_ATTRIBUTE-DOWNLOAD;
                      uses ncs_template_LABEL-MODE;
                      uses ncs_template_EIGRP-ROUTE-TABLE;
                      uses ncs_template_BEST-EXTERNAL;
                      uses ncs_template_SOURCED-NETWORK-TABLE;
                      uses ncs_template_RPKI-ORIGIN-AS-VALIDITY-SIGNAL-IBGP;
                      uses ncs_template_CONNECTED-ROUTES;
                      uses ncs_template_ADDITIONAL-PATHS-RECEIVE;
                      uses ncs_template_PERMANENT-NETWORK;
                      uses ncs_template_RPKI-BESTPATH-USE-ORIGIN-AS-VALIDITY;
                      uses ncs_template_ALLOCATE-LABEL;
                      uses ncs_template_ADDITIONAL-PATHS-SELECTION;
                      uses ncs_template_BGP-CFG-RPKI-BESTPATH-ORIGIN-AS-ALLOW-INVALID-MP;
                      uses ncs_template_NEXT-HOP-RESOLUTION-PREFIX-LENGTH-MINIMUM;
                      uses ncs_template_RESET-WEIGHT-ON-IMPORT;
                      uses ncs_template_OSPF-ROUTE-TABLE;
                      uses ncs_template_ADDITIONAL-PATHS-SEND;
                      uses ncs_template_ADVERTISE-LOCAL-LABELED-ROUTE-SAFI-UNICAST;
                      uses ncs_template_MOBILE-ROUTES;
                      uses ncs_template_DISABLE-AS-PATH-LOOP-CHECK;
                      uses ncs_template_SUBSCRIBER-ROUTES;
                      uses ncs_template_SEGMENT-ROUTING;
                    }
                  }
                  leaf exists {
                    type empty;
                    description
                      "Create this VRF. Deletion of this object
                       causes deletion of all the objects under
                       VRF associated with this object.";
                  }
                  uses ncs_template_ROUTER-ID;
                  uses ncs_template_DISABLE-ENFORCE-FIRST-AS;
                  uses ncs_template_BEST-PATH-COST-COMMUNITY;
                  uses ncs_template_BEST-PATH-AIGP-IGNORE;
                  uses ncs_template_BEST-PATH-AS-PATH-LENGTH;
                  uses ncs_template_IGP-REDIST-INTERNAL;
                  uses ncs_template_MULTI-PATH-AS-PATH-IGNORE-ONWARDS;
                  uses ncs_template_DISABLE-FAST-EXTERNAL-FALLOVER;
                  uses ncs_template_UNSAFE-EBGP-POLICY;
                  uses ncs_template_DEFAULT-METRIC;
                  uses ncs_template_DEFAULT-INFO-ORIGINATE;
                  uses ncs_template_BGP-CFG-RPKI-ORIGIN-AS-VALIDITY-SIGNAL-IBGP;
                  uses ncs_template_BGP-CFG-RPKI-BESTPATH-USE-ORIGIN-AS-VALIDITY;
                  uses ncs_template_BEST-PATH-CONFEDERATION-PATHS;
                  uses ncs_template_BEST-PATH-AS-MULTIPATH-RELAX;
                  uses ncs_template_MPLS-ACTIVATED-INTERFACE-TABLE;
                  uses ncs_template_DISABLE-AUTO-SOFT-RESET;
                  uses ncs_template_DISABLE-MSG-LOG;
                  uses ncs_template_GLOBAL-TIMERS;
                  uses ncs_template_BEST-PATH-IGP-METRIC-IGNORE;
                  uses ncs_template_NEXT-HOP-RES-ALLOW-DEFAULT;
                  uses ncs_template_NEXT-HOP-MPLS-FWD-IBGP;
                  uses ncs_template_BFD;
                  uses ncs_template_DISABLE-NEIGHBOR-LOGGING;
                  uses ncs_template_SEND-SOCKET-BUFFER-SIZES;
                  uses ncs_template_BEST-PATH-MED-ALWAYS;
                  uses ncs_template_RECEIVE-SOCKET-BUFFER-SIZES;
                  uses ncs_template_BEST-PATH-ROUTER-ID;
                  uses ncs_template_BEST-PATH-MED-MISSING;
                  uses ncs_template_LOCAL-PREFERENCE;
                }
                container vrf-neighbors {

                  grouping VRF-NEIGHBOR-CONTENT {
                    description
                      "VRF NEIGHBOR CONTENT";
                    container vrf-neighbor-afs {
                      description
                        "Address family type of a VRF neighbor";
                      list vrf-neighbor-af {
                        // NCS patched for predictable order
                        ordered-by user;
                        key "af-name";
                        description
                          "Address family type of a VRF neighbor";
                        leaf af-name {
                          type string;
                          description
                            "BGP neighbor address family";
                        }
                        uses ncs_template_NEIGHBOR-AF-LONG-LIVED-GRACEFUL-RESTART-CAPABLE;
                        uses ncs_template_SEND-EXT-COMMUNITY-EBGP;
                        uses ncs_template_ACCEPT-ROUTE-LEGACY-RT;
                        uses ncs_template_AIGP-COST-COMMUNITY;
                        uses ncs_template_SEND-COMMUNITY-EBGP;
                        uses ncs_template_ADVERTISE-DEF-IMP-DISABLE-V6;
                        uses ncs_template_ADVERTISE-DISABLE;
                        uses ncs_template_MAXIMUM-PREFIXES;
                        uses ncs_template_ADVERTISE-BRIDGE-DOMAIN-IMP-DISABLE-V6;
                        uses ncs_template_REMOVE-PRIVATE-AS-ENTIRE-AS-PATH-INBOUND;
                        uses ncs_template_NEXT-HOP-UNCHANGED;
                        uses ncs_template_ADVERTISE-LOCAL-LABELED-ROUTE;
                        uses ncs_template_ADVERTISE-DEF-IMP-DISABLE-V4;
                        uses ncs_template_RPKI-ORIGIN-AS-VALIDATION-DISABLE;
                        uses ncs_template_ADVERTISE-BRIDGE-DOMAIN-IMP-DISABLE-V4;
                        uses ncs_template_FLOWSPEC-VALIDATION;
                        uses ncs_template_ADVERTISE-L2VPN-EVPN;
                        uses ncs_template_ADVERTISE-LOCAL-L2VPN-EVPN;
                        uses ncs_template_ENCAPSULATION-TYPE;
                        uses ncs_template_RPKI-BESTPATH-ORIGIN-AS-ALLOW-INVALID;
                        uses ncs_template_ENFORCE-MULTIPLE-LABELS;
                        uses ncs_template_AS-OVERRIDE;
                        uses ncs_template_MULTIPATH;
                        uses ncs_template_SEND-COMMUNITY-EBGP-GRACEFUL-SHUTDOWN;
                        uses ncs_template_ACTIVATE;
                        uses ncs_template_PREFIX-ORF-POLICY;
                        uses ncs_template_NEIGHBOR-AF-LONG-LIVED-GRACEFUL-RESTART-STALE-TIME;
                        uses ncs_template_SITE-OF-ORIGIN;
                        uses ncs_template_UPDATE-OUT-ORIG-LOOP-CHK-DISABLE;
                        uses ncs_template_AIGP;
                        uses ncs_template_AIGP-SEND-MED;
                        uses ncs_template_ADVERTISE-V6;
                        uses ncs_template_ALLOW-AS-IN;
                        uses ncs_template_ADVERTISE-ORF;
                        uses ncs_template_ROUTE-REFLECTOR-CLIENT;
                        uses ncs_template_NEXT-HOP-SELF;
                        uses ncs_template_ADVERTISE-LOCAL-V6;
                        uses ncs_template_ROUTE-POLICY-IN;
                        uses ncs_template_IMPORT;
                        uses ncs_template_DEFAULT-ORIGINATE;
                        uses ncs_template_SOFT-RECONFIGURATION;
                        uses ncs_template_ADVERTISE-VRF-IMP-DISABLE-V6;
                        uses ncs_template_DEFAULT-WEIGHT;
                        uses ncs_template_AF-GROUP;
                        uses ncs_template_ADVERTISE-V4;
                        uses ncs_template_NEXT-HOP-UNCHANGED-MULTIPATH;
                        uses ncs_template_OPTIMAL-ROUTE-REFLECTION-GROUP;
                        uses ncs_template_ACCEPT-OWN;
                        uses ncs_template_ROUTE-POLICY-OUT;
                        uses ncs_template_ADVERTISE-LOCAL-V4;
                        uses ncs_template_ADVERTISE-PERMANENT-NETWORK;
                        uses ncs_template_REMOVE-PRIVATE-AS-ENTIRE-AS-PATH;
                        uses ncs_template_ADVERTISE-VRF-IMP-DISABLE-V4;
                      }
                    }
                    uses ncs_template_LOCAL-ADDRESS-SUB-NET;
                    uses ncs_template_INTERNAL-VPN-CLIENT-IBGP-CE;
                    uses ncs_template_LOCAL-ADDRESS;
                    uses ncs_template_BMP-ACTIVATE-TABLE;
                    uses ncs_template_EBGP-MULTIHOP;
                    uses ncs_template_SESSION-GROUP-ADD-MEMBER;
                    uses ncs_template_EGRESS-PEER-ENGINEERING;
                    uses ncs_template_REMOTE-AS;
                    uses ncs_template_MERGE-SAFI1-AND4-INBOUND-UPDATES;
                    uses ncs_template_LOCAL-AS;
                    uses ncs_template_NEIGHBOR-GRACEFUL-RESTART-STALEPATH-TIME;
                    uses ncs_template_SHUTDOWN;
                    uses ncs_template_DESCRIPTION;
                    uses ncs_template_NEIGHBOR-GROUP-ADD-MEMBER;
                    uses ncs_template_PASSWORD;
                    uses ncs_template_EBGP-RECV-DMZ;
                    uses ncs_template_ADVERTISEMENT-INTERVAL;
                    uses ncs_template_NEIGHBOR-CLUSTER-ID;
                    uses ncs_template_NEIGHBOR-GRACEFUL-RESTART;
                    uses ncs_template_ENFORCE-FIRST-AS;
                    uses ncs_template_IDLE-WATCH-TIME;
                    uses ncs_template_TCPMSS;
                    uses ncs_template_SESSION-OPEN-MODE;
                    uses ncs_template_BGP-CFG-RPKI-ORIGIN-AS-VALIDATION-DISABLE;
                    uses ncs_template_TOS;
                    uses ncs_template_UPDATE-IN-FILTERING;
                    uses ncs_template_EBGP-SEND-DMZ-ENABLE-MODES;
                    uses ncs_template_MSG-LOG-OUT;
                    uses ncs_template_SUPPRESS-ALL-CAPABILITIES;
                    uses ncs_template_MAX-PEERS;
                    uses ncs_template_AO-KEYCHAIN;
                    uses ncs_template_BGP-CFG-RPKI-BESTPATH-ORIGIN-AS-ALLOW-INVALID;
                    uses ncs_template_RECEIVE-BUFFER-SIZE;
                    uses ncs_template_MSG-LOG-IN;
                    uses ncs_template_ADDITIONAL-PATHS-SEND-CAPABILITY;
                    uses ncs_template_PROPAGATE-DMZ-LINK-BANDWIDTH;
                    uses ncs_template_BFD-ENABLE-MODES;
                    uses ncs_template_SEND-BUFFER-SIZE;
                    uses ncs_template_TTL-SECURITY;
                    uses ncs_template_NEIGHBOR-GRACEFUL-RESTART-TIME;
                    uses ncs_template_TIMERS;
                    uses ncs_template_BFD-MULTIPLIER;
                    uses ncs_template_BFD-MINIMUM-INTERVAL;
                    uses ncs_template_REMOTE-AS-LIST;
                    uses ncs_template_ADDITIONAL-PATHS-RECEIVE-CAPABILITY;
                    uses ncs_template_KEYCHAIN;
                    uses ncs_template_IGNORE-CONNECTED-CHECK-EBGP;
                    uses ncs_template_SUPPRESS-FOUR-BYTE-AS-CAPABILITY;
                    uses ncs_template_UPDATE-SOURCE-INTERFACE;
                    uses ncs_template_GRACEFUL-MAINTENANCE;
                  }
                  list vrf-neighbor {
                    // NCS patched for predictable order
                    ordered-by user;
                    key "neighbor-address";
                    description
                      "A particular VRF peer";
                    leaf neighbor-address {
                      type string;
                      description
                        "Neighbor address";
                    }
                    uses VRF-NEIGHBOR-CONTENT;
                  }
                  list vrf-neighbor-prefix-length {
                    // NCS patched for predictable order
                    ordered-by user;
                    key "prefix-length neighbor-address";
                    description
                      "A particular VRF peer";
                    leaf prefix-length {
                      type string;
                      description
                        "Prefix length";
                    }
                    leaf neighbor-address {
                      type string;
                      description
                        "Neighbor address";
                    }
                    uses VRF-NEIGHBOR-CONTENT;
                  }
                  description
                    "BGP VRF peer";
                }
                leaf vrf-name {
                  type string;
                  description
                    "VRF name";
                }
              }
            }
            container default-vrf {
              description
                "Global default config";
              container bgp-entity {
                description
                  "Neighbor, neighbor-group, af-group and
                   session-group configuration";
                container neighbors {

                  grouping NEIGHBOR-CONTENT {
                    description
                      "NEIGHBOR CONTENT";
                    container neighbor-afs {
                      description
                        "BGP neighbor AF configuration table";
                      list neighbor-af {
                        // NCS patched for predictable order
                        ordered-by user;
                        key "af-name";
                        description
                          "Address family type of neighbor";
                        leaf af-name {
                          type string;
                          description
                            "BGP neighbor address family";
                        }
                        uses ncs_template_NEIGHBOR-AF-LONG-LIVED-GRACEFUL-RESTART-CAPABLE;
                        uses ncs_template_L2VPN-SIGNALLING;
                        uses ncs_template_SEND-EXT-COMMUNITY-EBGP;
                        uses ncs_template_ACCEPT-ROUTE-LEGACY-RT;
                        uses ncs_template_AIGP-COST-COMMUNITY;
                        uses ncs_template_SEND-COMMUNITY-EBGP;
                        uses ncs_template_ADVERTISE-DEF-IMP-DISABLE-V6;
                        uses ncs_template_ADVERTISE-DISABLE;
                        uses ncs_template_SEND-MULTICAST-ATTR;
                        uses ncs_template_MAXIMUM-PREFIXES;
                        uses ncs_template_ADVERTISE-BRIDGE-DOMAIN-IMP-DISABLE-V6;
                        uses ncs_template_REMOVE-PRIVATE-AS-ENTIRE-AS-PATH-INBOUND;
                        uses ncs_template_NEXT-HOP-UNCHANGED;
                        uses ncs_template_ADVERTISE-LOCAL-LABELED-ROUTE;
                        uses ncs_template_ADVERTISE-DEF-IMP-DISABLE-V4;
                        uses ncs_template_RPKI-ORIGIN-AS-VALIDATION-DISABLE;
                        uses ncs_template_ADVERTISE-BRIDGE-DOMAIN-IMP-DISABLE-V4;
                        uses ncs_template_FLOWSPEC-VALIDATION;
                        uses ncs_template_ADVERTISE-L2VPN-EVPN;
                        uses ncs_template_ADVERTISE-LOCAL-L2VPN-EVPN;
                        uses ncs_template_ENCAPSULATION-TYPE;
                        uses ncs_template_RPKI-BESTPATH-ORIGIN-AS-ALLOW-INVALID;
                        uses ncs_template_ENFORCE-MULTIPLE-LABELS;
                        uses ncs_template_AS-OVERRIDE;
                        uses ncs_template_MULTIPATH;
                        uses ncs_template_SEND-COMMUNITY-EBGP-GRACEFUL-SHUTDOWN;
                        uses ncs_template_ACTIVATE;
                        uses ncs_template_PREFIX-ORF-POLICY;
                        uses ncs_template_NEIGHBOR-AF-LONG-LIVED-GRACEFUL-RESTART-STALE-TIME;
                        uses ncs_template_UPDATE-OUT-ORIG-LOOP-CHK-DISABLE;
                        uses ncs_template_AIGP;
                        uses ncs_template_AIGP-SEND-MED;
                        uses ncs_template_ADVERTISE-V6;
                        uses ncs_template_ALLOW-AS-IN;
                        uses ncs_template_ADVERTISE-ORF;
                        uses ncs_template_ROUTE-REFLECTOR-CLIENT;
                        uses ncs_template_NEXT-HOP-SELF;
                        uses ncs_template_ADVERTISE-LOCAL-V6;
                        uses ncs_template_ROUTE-POLICY-IN;
                        uses ncs_template_IMPORT;
                        uses ncs_template_DEFAULT-ORIGINATE;
                        uses ncs_template_SOFT-RECONFIGURATION;
                        uses ncs_template_ADVERTISE-VRF-IMP-DISABLE-V6;
                        uses ncs_template_DEFAULT-WEIGHT;
                        uses ncs_template_AF-GROUP;
                        uses ncs_template_ADVERTISE-V4;
                        uses ncs_template_NEXT-HOP-UNCHANGED-MULTIPATH;
                        uses ncs_template_OPTIMAL-ROUTE-REFLECTION-GROUP;
                        uses ncs_template_ACCEPT-OWN;
                        uses ncs_template_ROUTE-POLICY-OUT;
                        uses ncs_template_ADVERTISE-LOCAL-V4;
                        uses ncs_template_ADVERTISE-PERMANENT-NETWORK;
                        uses ncs_template_REMOVE-PRIVATE-AS-ENTIRE-AS-PATH;
                        uses ncs_template_ADVERTISE-VRF-IMP-DISABLE-V4;
                      }
                    }
                    uses ncs_template_LOCAL-ADDRESS-SUB-NET;
                    uses ncs_template_INTERNAL-VPN-CLIENT-IBGP-CE;
                    uses ncs_template_LOCAL-ADDRESS;
                    uses ncs_template_BMP-ACTIVATE-TABLE;
                    uses ncs_template_EBGP-MULTIHOP;
                    uses ncs_template_SESSION-GROUP-ADD-MEMBER;
                    uses ncs_template_EGRESS-PEER-ENGINEERING;
                    uses ncs_template_REMOTE-AS;
                    uses ncs_template_MERGE-SAFI1-AND4-INBOUND-UPDATES;
                    uses ncs_template_LOCAL-AS;
                    uses ncs_template_NEIGHBOR-GRACEFUL-RESTART-STALEPATH-TIME;
                    uses ncs_template_SHUTDOWN;
                    uses ncs_template_DESCRIPTION;
                    uses ncs_template_NEIGHBOR-GROUP-ADD-MEMBER;
                    uses ncs_template_PASSWORD;
                    uses ncs_template_EBGP-RECV-DMZ;
                    uses ncs_template_ADVERTISEMENT-INTERVAL;
                    uses ncs_template_NEIGHBOR-CLUSTER-ID;
                    uses ncs_template_NEIGHBOR-GRACEFUL-RESTART;
                    uses ncs_template_ENFORCE-FIRST-AS;
                    uses ncs_template_IDLE-WATCH-TIME;
                    uses ncs_template_TCPMSS;
                    uses ncs_template_SESSION-OPEN-MODE;
                    uses ncs_template_BGP-CFG-RPKI-ORIGIN-AS-VALIDATION-DISABLE;
                    uses ncs_template_TOS;
                    uses ncs_template_UPDATE-IN-FILTERING;
                    uses ncs_template_EBGP-SEND-DMZ-ENABLE-MODES;
                    uses ncs_template_MSG-LOG-OUT;
                    uses ncs_template_SUPPRESS-ALL-CAPABILITIES;
                    uses ncs_template_MAX-PEERS;
                    uses ncs_template_AO-KEYCHAIN;
                    uses ncs_template_BGP-CFG-RPKI-BESTPATH-ORIGIN-AS-ALLOW-INVALID;
                    uses ncs_template_RECEIVE-BUFFER-SIZE;
                    uses ncs_template_MSG-LOG-IN;
                    uses ncs_template_ADDITIONAL-PATHS-SEND-CAPABILITY;
                    uses ncs_template_PROPAGATE-DMZ-LINK-BANDWIDTH;
                    uses ncs_template_BFD-ENABLE-MODES;
                    uses ncs_template_SEND-BUFFER-SIZE;
                    uses ncs_template_TTL-SECURITY;
                    uses ncs_template_NEIGHBOR-GRACEFUL-RESTART-TIME;
                    uses ncs_template_TIMERS;
                    uses ncs_template_BFD-MULTIPLIER;
                    uses ncs_template_BFD-MINIMUM-INTERVAL;
                    uses ncs_template_REMOTE-AS-LIST;
                    uses ncs_template_ADDITIONAL-PATHS-RECEIVE-CAPABILITY;
                    uses ncs_template_KEYCHAIN;
                    uses ncs_template_IGNORE-CONNECTED-CHECK-EBGP;
                    uses ncs_template_SUPPRESS-FOUR-BYTE-AS-CAPABILITY;
                    uses ncs_template_UPDATE-SOURCE-INTERFACE;
                    uses ncs_template_GRACEFUL-MAINTENANCE;
                  }
                  list neighbor {
                    // NCS patched for predictable order
                    ordered-by user;
                    key "neighbor-address";
                    description
                      "A particular BGP peer";
                    leaf neighbor-address {
                      type string;
                      description
                        "Neighbor address";
                    }
                    uses NEIGHBOR-CONTENT;
                  }
                  list neighbor-prefix-length {
                    // NCS patched for predictable order
                    ordered-by user;
                    key "prefix-length neighbor-address";
                    description
                      "A particular BGP peer";
                    leaf prefix-length {
                      type string;
                      description
                        "Prefix length";
                    }
                    leaf neighbor-address {
                      type string;
                      description
                        "Neighbor address";
                    }
                    uses NEIGHBOR-CONTENT;
                  }
                  description
                    "Neighbor configuration";
                }
                container neighbor-groups {
                  description
                    "Neighbor-group configuration";
                  list neighbor-group {
                    // NCS patched for predictable order
                    ordered-by user;
                    key "neighbor-group-name";
                    description
                      "A particular BGP neighbor group";
                    container neighbor-group-afs {
                      description
                        "BGP neighbor-group AF configuration table";
                      list neighbor-group-af {
                        // NCS patched for predictable order
                        ordered-by user;
                        key "af-name";
                        description
                          "Address family type of neighbor group";
                        leaf af-name {
                          type string;
                          description
                            "BGP neighbor group address family";
                        }
                        uses ncs_template_NEIGHBOR-AF-LONG-LIVED-GRACEFUL-RESTART-CAPABLE;
                        uses ncs_template_L2VPN-SIGNALLING;
                        uses ncs_template_SEND-EXT-COMMUNITY-EBGP;
                        uses ncs_template_ACCEPT-ROUTE-LEGACY-RT;
                        uses ncs_template_AIGP-COST-COMMUNITY;
                        uses ncs_template_SEND-COMMUNITY-EBGP;
                        uses ncs_template_ADVERTISE-DEF-IMP-DISABLE-V6;
                        uses ncs_template_ADVERTISE-DISABLE;
                        uses ncs_template_SEND-MULTICAST-ATTR;
                        uses ncs_template_MAXIMUM-PREFIXES;
                        uses ncs_template_ADVERTISE-BRIDGE-DOMAIN-IMP-DISABLE-V6;
                        uses ncs_template_REMOVE-PRIVATE-AS-ENTIRE-AS-PATH-INBOUND;
                        uses ncs_template_NEXT-HOP-UNCHANGED;
                        uses ncs_template_ADVERTISE-LOCAL-LABELED-ROUTE;
                        uses ncs_template_ADVERTISE-DEF-IMP-DISABLE-V4;
                        uses ncs_template_RPKI-ORIGIN-AS-VALIDATION-DISABLE;
                        uses ncs_template_ADVERTISE-BRIDGE-DOMAIN-IMP-DISABLE-V4;
                        uses ncs_template_FLOWSPEC-VALIDATION;
                        uses ncs_template_ADVERTISE-L2VPN-EVPN;
                        uses ncs_template_ADVERTISE-LOCAL-L2VPN-EVPN;
                        uses ncs_template_ENCAPSULATION-TYPE;
                        uses ncs_template_RPKI-BESTPATH-ORIGIN-AS-ALLOW-INVALID;
                        uses ncs_template_ENFORCE-MULTIPLE-LABELS;
                        uses ncs_template_AS-OVERRIDE;
                        uses ncs_template_MULTIPATH;
                        uses ncs_template_SEND-COMMUNITY-EBGP-GRACEFUL-SHUTDOWN;
                        uses ncs_template_ACTIVATE;
                        uses ncs_template_PREFIX-ORF-POLICY;
                        uses ncs_template_NEIGHBOR-AF-LONG-LIVED-GRACEFUL-RESTART-STALE-TIME;
                        uses ncs_template_SITE-OF-ORIGIN;
                        uses ncs_template_UPDATE-OUT-ORIG-LOOP-CHK-DISABLE;
                        uses ncs_template_AIGP;
                        uses ncs_template_AIGP-SEND-MED;
                        uses ncs_template_ADVERTISE-V6;
                        uses ncs_template_ALLOW-AS-IN;
                        uses ncs_template_ADVERTISE-ORF;
                        uses ncs_template_ROUTE-REFLECTOR-CLIENT;
                        uses ncs_template_NEXT-HOP-SELF;
                        uses ncs_template_ADVERTISE-LOCAL-V6;
                        uses ncs_template_ROUTE-POLICY-IN;
                        uses ncs_template_IMPORT;
                        uses ncs_template_DEFAULT-ORIGINATE;
                        uses ncs_template_SOFT-RECONFIGURATION;
                        uses ncs_template_ADVERTISE-VRF-IMP-DISABLE-V6;
                        uses ncs_template_DEFAULT-WEIGHT;
                        uses ncs_template_AF-GROUP;
                        uses ncs_template_ADVERTISE-V4;
                        uses ncs_template_NEXT-HOP-UNCHANGED-MULTIPATH;
                        uses ncs_template_OPTIMAL-ROUTE-REFLECTION-GROUP;
                        uses ncs_template_ACCEPT-OWN;
                        uses ncs_template_ROUTE-POLICY-OUT;
                        uses ncs_template_ADVERTISE-LOCAL-V4;
                        uses ncs_template_ADVERTISE-PERMANENT-NETWORK;
                        uses ncs_template_REMOVE-PRIVATE-AS-ENTIRE-AS-PATH;
                        uses ncs_template_ADVERTISE-VRF-IMP-DISABLE-V4;
                      }
                    }
                    leaf neighbor-group-add-member {
                      type string;
                      description
                        "Inherit configuration from a
                         neighbor-group";
                    }
                    leaf neighbor-group-name {
                      type string;
                      description
                        "BGP neighbor group name";
                    }
                    uses ncs_template_LOCAL-ADDRESS-SUB-NET;
                    uses ncs_template_INTERNAL-VPN-CLIENT-IBGP-CE;
                    uses ncs_template_LOCAL-ADDRESS;
                    uses ncs_template_BMP-ACTIVATE-TABLE;
                    uses ncs_template_EBGP-MULTIHOP;
                    uses ncs_template_SESSION-GROUP-ADD-MEMBER;
                    uses ncs_template_EGRESS-PEER-ENGINEERING;
                    uses ncs_template_REMOTE-AS;
                    uses ncs_template_MERGE-SAFI1-AND4-INBOUND-UPDATES;
                    uses ncs_template_LOCAL-AS;
                    uses ncs_template_NEIGHBOR-GRACEFUL-RESTART-STALEPATH-TIME;
                    uses ncs_template_SHUTDOWN;
                    uses ncs_template_DESCRIPTION;
                    uses ncs_template_PASSWORD;
                    uses ncs_template_EBGP-RECV-DMZ;
                    uses ncs_template_ADVERTISEMENT-INTERVAL;
                    uses ncs_template_NEIGHBOR-CLUSTER-ID;
                    uses ncs_template_NEIGHBOR-GRACEFUL-RESTART;
                    uses ncs_template_ENFORCE-FIRST-AS;
                    uses ncs_template_IDLE-WATCH-TIME;
                    uses ncs_template_TCPMSS;
                    uses ncs_template_SESSION-OPEN-MODE;
                    uses ncs_template_BGP-CFG-RPKI-ORIGIN-AS-VALIDATION-DISABLE;
                    uses ncs_template_TOS;
                    uses ncs_template_UPDATE-IN-FILTERING;
                    uses ncs_template_EBGP-SEND-DMZ-ENABLE-MODES;
                    uses ncs_template_MSG-LOG-OUT;
                    uses ncs_template_SUPPRESS-ALL-CAPABILITIES;
                    uses ncs_template_MAX-PEERS;
                    uses ncs_template_AO-KEYCHAIN;
                    uses ncs_template_BGP-CFG-RPKI-BESTPATH-ORIGIN-AS-ALLOW-INVALID;
                    uses ncs_template_RECEIVE-BUFFER-SIZE;
                    uses ncs_template_MSG-LOG-IN;
                    uses ncs_template_ADDITIONAL-PATHS-SEND-CAPABILITY;
                    uses ncs_template_PROPAGATE-DMZ-LINK-BANDWIDTH;
                    uses ncs_template_BFD-ENABLE-MODES;
                    uses ncs_template_SEND-BUFFER-SIZE;
                    uses ncs_template_TTL-SECURITY;
                    uses ncs_template_NEIGHBOR-GRACEFUL-RESTART-TIME;
                    uses ncs_template_TIMERS;
                    uses ncs_template_BFD-MULTIPLIER;
                    uses ncs_template_BFD-MINIMUM-INTERVAL;
                    uses ncs_template_REMOTE-AS-LIST;
                    uses ncs_template_ADDITIONAL-PATHS-RECEIVE-CAPABILITY;
                    uses ncs_template_KEYCHAIN;
                    uses ncs_template_IGNORE-CONNECTED-CHECK-EBGP;
                    uses ncs_template_SUPPRESS-FOUR-BYTE-AS-CAPABILITY;
                    uses ncs_template_UPDATE-SOURCE-INTERFACE;
                    uses ncs_template_CREATE;
                    uses ncs_template_GRACEFUL-MAINTENANCE;
                  }
                }
                container af-groups {
                  description
                    "AF-group configuration";
                  list af-group {
                    // NCS patched for predictable order
                    ordered-by user;
                    key "af-group-name";
                    description
                      "A particular BGP AF group";
                    container af-group-afs {
                      description
                        "AF group configuration table";
                      list af-group-af {
                        // NCS patched for predictable order
                        ordered-by user;
                        key "af-name";
                        description
                          "Address family type of an AF group";
                        leaf af-group {
                          type string;
                          description
                            "Inherit configuration for this
                             address-family from an AF-group";
                        }
                        leaf create {
                          type empty;
                          description
                            "Create this address family group.
                             Deletion of this object causes deletion
                             of all the objects under AFGroup
                             associated with this object.";
                        }
                        leaf af-name {
                          type string;
                          description
                            "BGP AF group address family";
                        }
                        uses ncs_template_NEIGHBOR-AF-LONG-LIVED-GRACEFUL-RESTART-CAPABLE;
                        uses ncs_template_L2VPN-SIGNALLING;
                        uses ncs_template_SEND-EXT-COMMUNITY-EBGP;
                        uses ncs_template_ACCEPT-ROUTE-LEGACY-RT;
                        uses ncs_template_AIGP-COST-COMMUNITY;
                        uses ncs_template_SEND-COMMUNITY-EBGP;
                        uses ncs_template_ADVERTISE-DEF-IMP-DISABLE-V6;
                        uses ncs_template_ADVERTISE-DISABLE;
                        uses ncs_template_SEND-MULTICAST-ATTR;
                        uses ncs_template_MAXIMUM-PREFIXES;
                        uses ncs_template_ADVERTISE-BRIDGE-DOMAIN-IMP-DISABLE-V6;
                        uses ncs_template_REMOVE-PRIVATE-AS-ENTIRE-AS-PATH-INBOUND;
                        uses ncs_template_NEXT-HOP-UNCHANGED;
                        uses ncs_template_ADVERTISE-LOCAL-LABELED-ROUTE;
                        uses ncs_template_ADVERTISE-DEF-IMP-DISABLE-V4;
                        uses ncs_template_RPKI-ORIGIN-AS-VALIDATION-DISABLE;
                        uses ncs_template_ADVERTISE-BRIDGE-DOMAIN-IMP-DISABLE-V4;
                        uses ncs_template_FLOWSPEC-VALIDATION;
                        uses ncs_template_ADVERTISE-L2VPN-EVPN;
                        uses ncs_template_ADVERTISE-LOCAL-L2VPN-EVPN;
                        uses ncs_template_ENCAPSULATION-TYPE;
                        uses ncs_template_RPKI-BESTPATH-ORIGIN-AS-ALLOW-INVALID;
                        uses ncs_template_ENFORCE-MULTIPLE-LABELS;
                        uses ncs_template_AS-OVERRIDE;
                        uses ncs_template_MULTIPATH;
                        uses ncs_template_SEND-COMMUNITY-EBGP-GRACEFUL-SHUTDOWN;
                        uses ncs_template_PREFIX-ORF-POLICY;
                        uses ncs_template_NEIGHBOR-AF-LONG-LIVED-GRACEFUL-RESTART-STALE-TIME;
                        uses ncs_template_SITE-OF-ORIGIN;
                        uses ncs_template_UPDATE-OUT-ORIG-LOOP-CHK-DISABLE;
                        uses ncs_template_AIGP;
                        uses ncs_template_AIGP-SEND-MED;
                        uses ncs_template_ADVERTISE-V6;
                        uses ncs_template_ALLOW-AS-IN;
                        uses ncs_template_ADVERTISE-ORF;
                        uses ncs_template_ROUTE-REFLECTOR-CLIENT;
                        uses ncs_template_NEXT-HOP-SELF;
                        uses ncs_template_ADVERTISE-LOCAL-V6;
                        uses ncs_template_ROUTE-POLICY-IN;
                        uses ncs_template_IMPORT;
                        uses ncs_template_DEFAULT-ORIGINATE;
                        uses ncs_template_SOFT-RECONFIGURATION;
                        uses ncs_template_ADVERTISE-VRF-IMP-DISABLE-V6;
                        uses ncs_template_DEFAULT-WEIGHT;
                        uses ncs_template_ADVERTISE-V4;
                        uses ncs_template_NEXT-HOP-UNCHANGED-MULTIPATH;
                        uses ncs_template_OPTIMAL-ROUTE-REFLECTION-GROUP;
                        uses ncs_template_ACCEPT-OWN;
                        uses ncs_template_ROUTE-POLICY-OUT;
                        uses ncs_template_ADVERTISE-LOCAL-V4;
                        uses ncs_template_ADVERTISE-PERMANENT-NETWORK;
                        uses ncs_template_REMOVE-PRIVATE-AS-ENTIRE-AS-PATH;
                        uses ncs_template_ADVERTISE-VRF-IMP-DISABLE-V4;
                      }
                    }
                    leaf af-group-name {
                      type string;
                      description
                        "BGP AF group name";
                    }
                  }
                }
                container session-groups {
                  description
                    "Session group configuration";
                  list session-group {
                    // NCS patched for predictable order
                    ordered-by user;
                    key "session-group-name";
                    description
                      "A particular BGP session group";
                    leaf session-group-add-member {
                      type string;
                      description
                        "Inherit address-family independent config
                         from a session-group";
                    }
                    leaf session-group-name {
                      type string;
                      description
                        "BGP session group name";
                    }
                    uses ncs_template_LOCAL-ADDRESS-SUB-NET;
                    uses ncs_template_INTERNAL-VPN-CLIENT-IBGP-CE;
                    uses ncs_template_LOCAL-ADDRESS;
                    uses ncs_template_BMP-ACTIVATE-TABLE;
                    uses ncs_template_EBGP-MULTIHOP;
                    uses ncs_template_EGRESS-PEER-ENGINEERING;
                    uses ncs_template_REMOTE-AS;
                    uses ncs_template_MERGE-SAFI1-AND4-INBOUND-UPDATES;
                    uses ncs_template_LOCAL-AS;
                    uses ncs_template_NEIGHBOR-GRACEFUL-RESTART-STALEPATH-TIME;
                    uses ncs_template_SHUTDOWN;
                    uses ncs_template_DESCRIPTION;
                    uses ncs_template_PASSWORD;
                    uses ncs_template_EBGP-RECV-DMZ;
                    uses ncs_template_ADVERTISEMENT-INTERVAL;
                    uses ncs_template_NEIGHBOR-CLUSTER-ID;
                    uses ncs_template_NEIGHBOR-GRACEFUL-RESTART;
                    uses ncs_template_ENFORCE-FIRST-AS;
                    uses ncs_template_IDLE-WATCH-TIME;
                    uses ncs_template_TCPMSS;
                    uses ncs_template_SESSION-OPEN-MODE;
                    uses ncs_template_BGP-CFG-RPKI-ORIGIN-AS-VALIDATION-DISABLE;
                    uses ncs_template_TOS;
                    uses ncs_template_UPDATE-IN-FILTERING;
                    uses ncs_template_EBGP-SEND-DMZ-ENABLE-MODES;
                    uses ncs_template_MSG-LOG-OUT;
                    uses ncs_template_SUPPRESS-ALL-CAPABILITIES;
                    uses ncs_template_MAX-PEERS;
                    uses ncs_template_AO-KEYCHAIN;
                    uses ncs_template_BGP-CFG-RPKI-BESTPATH-ORIGIN-AS-ALLOW-INVALID;
                    uses ncs_template_RECEIVE-BUFFER-SIZE;
                    uses ncs_template_MSG-LOG-IN;
                    uses ncs_template_ADDITIONAL-PATHS-SEND-CAPABILITY;
                    uses ncs_template_PROPAGATE-DMZ-LINK-BANDWIDTH;
                    uses ncs_template_BFD-ENABLE-MODES;
                    uses ncs_template_SEND-BUFFER-SIZE;
                    uses ncs_template_TTL-SECURITY;
                    uses ncs_template_NEIGHBOR-GRACEFUL-RESTART-TIME;
                    uses ncs_template_TIMERS;
                    uses ncs_template_BFD-MULTIPLIER;
                    uses ncs_template_BFD-MINIMUM-INTERVAL;
                    uses ncs_template_REMOTE-AS-LIST;
                    uses ncs_template_ADDITIONAL-PATHS-RECEIVE-CAPABILITY;
                    uses ncs_template_KEYCHAIN;
                    uses ncs_template_IGNORE-CONNECTED-CHECK-EBGP;
                    uses ncs_template_SUPPRESS-FOUR-BYTE-AS-CAPABILITY;
                    uses ncs_template_UPDATE-SOURCE-INTERFACE;
                    uses ncs_template_CREATE;
                    uses ncs_template_GRACEFUL-MAINTENANCE;
                  }
                }
              }
              container global {
                description
                  "Global default config";
                container cluster-id {
                  description
                    "Configure Route-Reflector Cluster-id";
                  leaf cluster-id-number {
                    type string;
                    description
                      "Route-Reflector Cluster ID as 32 bit
                       quantity";
                  }
                  leaf cluster-id-address {
                    type string;
                    description
                      "Route-Reflector Cluster ID in IPV4 address
                       format";
                  }
                }
                container write-limit {
                  description
                    "Set write-queue limit for each update group";
                  leaf formatted-messages {
                    type string;
                    // NCS drop default statement
                    description
                      "Number of messages to be formatted per
                       update group";
                  }
                  leaf enqueued-messages {
                    type string;
                    // NCS drop default statement
                    description
                      "Number of messages that can be enqueued in
                       total";
                  }
                  leaf desynchronize {
                    type string;
                    // NCS drop default statement
                    description
                      "TRUE to enable desynchronization, FALSE
                       otherwise.";
                  }
                }
                container update-delay {
                  description
                    "Set the max initial delay for sending
                     updates";
                  leaf delay {
                    type string;
                    units "second";
                    // NCS drop default statement
                    description
                      "Delay value (seconds)";
                  }
                  leaf always {
                    type string;
                    // NCS drop must statement
                    // NCS drop default statement
                    description
                      "Set to TRUE to disable keepalive trigger
                       bestpath and delay is enforced.";
                  }
                }
                container as-league {
                  description
                    "AS League";
                  container peers {
                    description
                      "AS League Peers";
                    list peer {
                      // NCS patched for predictable order
                      ordered-by user;
                      key "as-xx as-yy";
                      description
                        "AS League Peer AS";
                      leaf as-xx {
                        type string;
                        description
                          "xx of peer AS xx.yy";
                      }
                      leaf as-yy {
                        type string;
                        description
                          "yy of peer AS xx.yy";
                      }
                    }
                  }
                  leaf enable {
                    type empty;
                    description
                      "AS League creation";
                  }
                }
                container rpki-servers {
                  description
                    "RPKI server configuration";
                  list rpki-server {
                    // NCS patched for predictable order
                    ordered-by user;
                    key "server";
                    description
                      "RPKI server configuration";
                    container transport {
                      description
                        "RPKI server transport";
                      leaf transport {
                        type string;
                        // NCS drop default statement
                        description
                          "RPKI server transport";
                      }
                      leaf port {
                        type string;
                        // NCS drop default statement
                        description
                          "port";
                      }
                    }
                    leaf enable {
                      type empty;
                      description
                        "RPKI server configuration";
                    }
                    leaf shutdown {
                      type empty;
                      description
                        "RPKI server shutdown";
                    }
                    leaf password {
                      type string;
                      description
                        "RPKI server password";
                    }
                    leaf response-time {
                      type string;
                      units "second";
                      description
                        "RPKI server response-time (15-3600
                         seconds)";
                    }
                    leaf username {
                      type string;
                      description
                        "RPKI server username";
                    }
                    leaf refresh-time {
                      type string;
                      units "second";
                      description
                        "RPKI server refresh-time (15-3600
                         seconds)";
                    }
                    leaf purge-time {
                      type string;
                      units "second";
                      description
                        "RPKI server purge-time (30-360 seconds)";
                    }
                    leaf server {
                      type string;
                      description
                        "Server address (opaque string)";
                    }
                  }
                }
                container as-list-groups {
                  description
                    "AS-list group lists";
                  list as-list-group {
                    // NCS patched for predictable order
                    ordered-by user;
                    key "as-list-group-name";
                    description
                      "AS-List group";
                    container ases {
                      description
                        "AS list";
                      list as {
                        // NCS patched for predictable order
                        ordered-by user;
                        key "as-xx as-yy";
                        description
                          "AS-List group";
                        leaf as-xx {
                          type string;
                          description
                            "xx of AS number/confed peer xx.yy";
                        }
                        leaf as-yy {
                          type string;
                          description
                            "yy of AS number/confed peer xx.yy";
                        }
                      }
                    }
                    leaf enable {
                      type empty;
                      description
                        "AS-List group creation";
                    }
                    leaf as-list-group-name {
                      type string;
                      description
                        "Group name";
                    }
                  }
                }
                container limits {
                  description
                    "Maximum number that can be configured";
                  leaf maximum-neighbors {
                    type string;
                    // NCS drop default statement
                    description
                      "Maximum number of neighbors that can be
                       configured";
                  }
                }
                container confederation-domain {
                  description
                    "Set routing domain confederation AS";
                  leaf as-xx {
                    type string;
                    description
                      "xx of AS number xx.yy";
                  }
                  leaf as-yy {
                    type string;
                    description
                      "yy of AS number xx.yy";
                  }
                }
                container confederation-peer-ases {
                  description
                    "Define peer ASes in BGP confederation";
                  list confederation-peer-as {
                    // NCS patched for predictable order
                    ordered-by user;
                    key "as-xx as-yy";
                    description
                      "Confederation peer AS";
                    leaf as-xx {
                      type string;
                      description
                        "xx of AS number/confed peer xx.yy";
                    }
                    leaf as-yy {
                      type string;
                      description
                        "yy of AS number/confed peer xx.yy";
                    }
                  }
                }
                container attribute-filter-groups {
                  description
                    "Attribute-filter groups list";
                  list attribute-filter-group {
                    // NCS patched for predictable order
                    ordered-by user;
                    key "attribute-filter-group-name";
                    description
                      "Attribute-filter group";
                    container attribute-filters {
                      description
                        "Attribute-filter group attributes list";
                      list attribute-filter {
                        // NCS patched for predictable order
                        ordered-by user;
                        key "attribute-start attribute-end";
                        description
                          "Attribute-filter group attribute";
                        leaf attribute-start {
                          type string;
                          description
                            "Start of attribute range";
                        }
                        leaf attribute-end {
                          type string;
                          description
                            "End of attribute range";
                        }
                        leaf filter-action {
                          type string;
                          // NCS drop mandatory statement
                          description
                            "Filtering action";
                        }
                      }
                    }
                    leaf enable {
                      type empty;
                      description
                        "Attribute-filter group creation";
                    }
                    leaf attribute-filter-group-name {
                      type string;
                      description
                        "Group name";
                    }
                  }
                }
                container global-graceful-maintenance-activate {
                  description
                    "Activate Graceful Maintenance Mode for all
                     neighbors with graceful maintenance config";
                  leaf all-neighbors {
                    type string;
                    description
                      "Also for neighbors without graceful
                       maintenance config";
                  }
                  leaf retain-routes {
                    type string;
                    description
                      "Keep routes in RIB once BGP stops";
                  }
                }
                container global-afs {
                  description
                    "Global AF-specific configuration";
                  list global-af {
                    // NCS patched for predictable order
                    ordered-by user;
                    key "af-name";
                    description
                      "Global AF-specific configuration";
                    container isis-routes {
                      description
                        "Redistribute information for IS-IS routes
                         .";
                      list isis-route {
                        // NCS patched for predictable order
                        ordered-by user;
                        key "instance-name";
                        description
                          "Redistribute IS-IS routes";
                        leaf instance-name {
                          type string;
                          description
                            "IS-IS instance name";
                        }
                        leaf default-metric {
                          type string;
                          description
                            "Default metric";
                        }
                        leaf route-policy-name {
                          type string;
                          description
                            "Route policy name";
                        }
                        leaf redist-type {
                          type string;
                          description
                            "Redistribution type: 01 for level 1
                             routes, 02 for level 2 routes, 04 for
                             level 1 inter-area routes. Logical
                             combinations permitted.";
                        }
                      }
                    }
                    container domain-distinguisher {
                      presence "Indicates a domain-distinguisher node is configured.";
                      description
                        "<ASN, router-id> tuple to use to identify
                         the link-state domain";
                      leaf as {
                        type string;
                        // NCS drop mandatory statement
                        description
                          "AS Number";
                      }
                      leaf router-id {
                        type string;
                        // NCS drop mandatory statement
                        description
                          "Router ID";
                      }
                    }
                    container vrf-all {
                      description
                        "Configurations to be inherited to all
                         vrfs";
                      container label-mode {
                        description
                          "MPLS-VPN label allocation mode";
                        leaf label-allocation-mode {
                          type string;
                          description
                            "Label allocation mode: per-ce  Set per
                             CE label mode, per-vrf Set per VRF
                             label mode";
                        }
                        leaf route-policy-name {
                          type string;
                          description
                            "Label mode route policy name";
                        }
                      }
                      leaf rnh-install-format {
                        type string;
                        description
                          "RNH install format type: extcomm -
                           install rnh as opaque and extcomms,
                           extcomm-only - install rnh as extcomms
                           only";
                      }
                      leaf enable {
                        type empty;
                        description
                          "Enable vrf all configuration submode";
                      }
                      leaf table-policy {
                        type string;
                        description
                          "Configure policy for installation of
                           routes to RIB";
                      }
                      leaf source-rt-import-policy {
                        type empty;
                        description
                          "Enable sourcing of import route-targets
                           from import-policy";
                      }
                    }
                    container disable-cluster-client-to-client-rrs {
                      description
                        "Disable client-to-client reflection for a
                         cluster";
                      list disable-cluster-client-to-client-rr {
                        // NCS patched for predictable order
                        ordered-by user;
                        // NCS drop must statement
                        key "cluster-type";
                        description
                          "Cluster ID for which reflection is to be
                           disbled";
                        leaf cluster-type {
                          type string;
                          description
                            "Type of cluster-id";
                        }
                        list number {
                          // NCS patched for predictable order
                          ordered-by user;
                          // NCS drop when statement
                          key "cluster-id-number";
                          description
                            "number";
                          leaf cluster-id-number {
                            type string;
                            description
                              "Cluster ID: if configured as a number";
                          }
                        }
                        list ipv4-address {
                          // NCS patched for predictable order
                          ordered-by user;
                          // NCS drop when statement
                          key "cluster-id-address";
                          description
                            "ipv4 address";
                          leaf cluster-id-address {
                            type string;
                            description
                              "Cluster ID: if configured as an IP
                               Address";
                          }
                        }
                      }
                    }
                    container label-delay {
                      presence "Indicates a label-delay node is configured.";
                      description
                        "Delay timer to batch label processing.";
                      leaf seconds {
                        type string;
                        units "second";
                        // NCS drop mandatory statement
                        description
                          "Delay, seconds part";
                      }
                      leaf milliseconds {
                        type string;
                        units "millisecond";
                        // NCS drop mandatory statement
                        description
                          "Delay, milliseconds part";
                      }
                    }
                    container ebgp {
                      presence "Indicates a ebgp node is configured.";
                      description
                        "Use eBGP multipaths";
                      leaf paths-value {
                        type string;
                        // NCS drop mandatory statement
                        description
                          "Number of paths";
                      }
                      leaf unequal-cost {
                        type string;
                        // NCS drop default statement
                        description
                          "UNUSED";
                      }
                      leaf selective {
                        type string;
                        // NCS drop default statement
                        description
                          "Allow multipaths only from marked
                           neighbors";
                      }
                      leaf order-by-igp-metric {
                        type string;
                        // NCS drop default statement
                        description
                          "Order candidate multipaths by IGP metric";
                      }
                    }
                    container eibgp {
                      presence "Indicates a eibgp node is configured.";
                      description
                        "Use eiBGP multipaths";
                      leaf paths-value {
                        type string;
                        // NCS drop mandatory statement
                        description
                          "Number of paths";
                      }
                      leaf unequal-cost {
                        type string;
                        // NCS drop default statement
                        description
                          "UNUSED";
                      }
                      leaf selective {
                        type string;
                        // NCS drop default statement
                        description
                          "Allow multipaths only from marked
                           neighbors";
                      }
                      leaf order-by-igp-metric {
                        type string;
                        // NCS drop default statement
                        description
                          "Order candidate multipaths by IGP metric";
                      }
                    }
                    container retain-rt {
                      description
                        "Accept received updates with the
                         specified attributes";
                      leaf all {
                        type string;
                        description
                          "Whether all RTs are to be retained,
                           default is FALSE";
                      }
                      leaf route-policy-name {
                        type string;
                        description
                          "Route policy name";
                      }
                    }
                    container ibgp {
                      presence "Indicates a ibgp node is configured.";
                      description
                        "Use iBGP multipaths";
                      leaf paths-value {
                        type string;
                        // NCS drop mandatory statement
                        description
                          "Number of paths";
                      }
                      leaf unequal-cost {
                        type string;
                        // NCS drop default statement
                        description
                          "Allow multipaths to have different IGP
                           metrics";
                      }
                      leaf selective {
                        type string;
                        // NCS drop default statement
                        description
                          "Allow multipaths only from marked
                           neighbors";
                      }
                      leaf order-by-igp-metric {
                        type string;
                        // NCS drop default statement
                        description
                          "Order candidate multipaths by IGP metric";
                      }
                    }
                    container import-delay {
                      presence "Indicates a import-delay node is configured.";
                      description
                        "Delay timer to batch import processing.";
                      leaf seconds {
                        type string;
                        units "second";
                        // NCS drop mandatory statement
                        description
                          "Delay, seconds part";
                      }
                      leaf milliseconds {
                        type string;
                        units "millisecond";
                        // NCS drop mandatory statement
                        description
                          "Delay, milliseconds part";
                      }
                    }
                    leaf rnh-install-format {
                      type string;
                      description
                        "RNH install format type: extcomm -
                         install rnh as opaque and extcomms,
                         extcomm-only - install rnh as extcomms
                         only";
                    }
                    leaf inter-as-install {
                      type empty;
                      description
                        "Enable install remote MVPN routes to PIM
                         in default VRF";
                    }
                    leaf segmented-mcast {
                      type empty;
                      description
                        "Enable segmented multicast";
                    }
                    leaf implicit-import {
                      type empty;
                      description
                        "Implicit import configuration";
                    }
                    leaf disable-default-martian-check {
                      type empty;
                      description
                        "Disable default Martian Check";
                    }
                    leaf next-hop-critical-trigger-delay {
                      type string;
                      units "millisecond";
                      // NCS drop default statement
                      description
                        "Next hop Critical Trigger Delay";
                    }
                    leaf next-hop-non-critical-trigger-delay {
                      type string;
                      units "millisecond";
                      // NCS drop default statement
                      description
                        "Next hop Non-critical Trigger Delay";
                    }
                    leaf label-security-rpf {
                      type empty;
                      description
                        "Calculate label-security RPF lists and
                         install to RIB/LSD";
                    }
                    leaf use-igpsr-label {
                      type empty;
                      description
                        "Use IGP SR label for resolution
                         configuration";
                    }
                    leaf label-retain {
                      type string;
                      units "minute";
                      description
                        "Label retention time in minutes";
                    }
                    leaf scan-time {
                      type string;
                      units "second";
                      // NCS drop default statement
                      description
                        "Configure background scanner interval for
                         this address family";
                    }
                    leaf source-route-target-policy {
                      type string;
                      description
                        "Route policy name to apply to configure
                         source route-target";
                    }
                    leaf rpki-origin-as-validation-disable {
                      type empty;
                      description
                        "RPKI origin-AS validation disable";
                    }
                    leaf update-limit-sub-group-ebgp {
                      type string;
                      units "megabyte";
                      // NCS drop default statement
                      description
                        "Upper bound on update generation
                         transient memory usage for every EBGP
                         Sub-group";
                    }
                    leaf update-limit-address-family {
                      type string;
                      units "megabyte";
                      // NCS drop default statement
                      description
                        "Upper bound on update generation
                         transient memory usage for the
                         address-family";
                    }
                    leaf update-limit-sub-group-ibgp {
                      type string;
                      units "megabyte";
                      // NCS drop default statement
                      description
                        "Upper bound on update generation
                         transient memory usage for every IBGP
                         Sub-group";
                    }
                    leaf disable-client-to-client-rr {
                      type empty;
                      description
                        "Disable client-to-client reflection";
                    }
                    leaf next-hop-route-policy {
                      type string;
                      description
                        "Next hop policy to filter out nexthop
                         notification";
                    }
                    leaf global-table-mcast {
                      type empty;
                      description
                        "Enable global table multicast";
                    }
                    leaf wait-rib-install {
                      type empty;
                      description
                        "Wait for route install before sending
                         updates to neighbors";
                    }
                    leaf prefix-sid-map {
                      type empty;
                      description
                        "Retrieve prefix sid mapping from SRMS";
                    }
                    leaf af-name {
                      type string;
                      description
                        "Address family";
                    }
                    uses ncs_template_RPKI-ORIGIN-AS-VALIDATION-ENABLE;
                    uses ncs_template_AGGREGATE-ADDRESS-TABLE;
                    uses ncs_template_DYNAMIC-MED-INTERVAL;
                    uses ncs_template_OPTIMAL-ROUTE-REFLECTOR-GROUP-TABLE;
                    uses ncs_template_DAMPENING;
                    uses ncs_template_ENABLE;
                    uses ncs_template_RIP-ROUTES;
                    uses ncs_template_LISP-ROUTES;
                    uses ncs_template_STATIC-ROUTES;
                    uses ncs_template_DISTANCE;
                    uses ncs_template_TABLE-POLICY;
                    uses ncs_template_APP-ROUTE-TABLE;
                    uses ncs_template_ATTRIBUTE-DOWNLOAD;
                    uses ncs_template_LABEL-MODE;
                    uses ncs_template_EIGRP-ROUTE-TABLE;
                    uses ncs_template_BEST-EXTERNAL;
                    uses ncs_template_SOURCED-NETWORK-TABLE;
                    uses ncs_template_RPKI-ORIGIN-AS-VALIDITY-SIGNAL-IBGP;
                    uses ncs_template_CONNECTED-ROUTES;
                    uses ncs_template_ADDITIONAL-PATHS-RECEIVE;
                    uses ncs_template_PERMANENT-NETWORK;
                    uses ncs_template_RPKI-BESTPATH-USE-ORIGIN-AS-VALIDITY;
                    uses ncs_template_ALLOCATE-LABEL;
                    uses ncs_template_ADDITIONAL-PATHS-SELECTION;
                    uses ncs_template_BGP-CFG-RPKI-BESTPATH-ORIGIN-AS-ALLOW-INVALID-MP;
                    uses ncs_template_NEXT-HOP-RESOLUTION-PREFIX-LENGTH-MINIMUM;
                    uses ncs_template_RESET-WEIGHT-ON-IMPORT;
                    uses ncs_template_OSPF-ROUTE-TABLE;
                    uses ncs_template_ADDITIONAL-PATHS-SEND;
                    uses ncs_template_ADVERTISE-LOCAL-LABELED-ROUTE-SAFI-UNICAST;
                    uses ncs_template_MOBILE-ROUTES;
                    uses ncs_template_DISABLE-AS-PATH-LOOP-CHECK;
                    uses ncs_template_SUBSCRIBER-ROUTES;
                    uses ncs_template_SEGMENT-ROUTING;
                  }
                }
                container rpki-static-routes {
                  description
                    "RPKI static route configuration";
                  list rpki-static-route {
                    // NCS patched for predictable order
                    ordered-by user;
                    key "address minimum maximum as";
                    description
                      "RPKI static route";
                    leaf address {
                      type string;
                      description
                        "Address";
                    }
                    leaf minimum {
                      type string;
                      description
                        "Minimum Prefix Length";
                    }
                    leaf maximum {
                      type string;
                      description
                        "Maximum Prefix Length";
                    }
                    leaf as {
                      type string;
                      description
                        "AS Number";
                    }
                  }
                }
                leaf graceful-restart {
                  type empty;
                  description
                    "Enable graceful restart support";
                }
                leaf update-out-logging {
                  type empty;
                  description
                    "Enables logging of update generation events";
                }
                leaf install-diversion {
                  type empty;
                  description
                    "Install diversion path to RIB/CEF";
                }
                leaf next-hop-trigger-delay {
                  type string;
                  units "second";
                  // NCS drop default statement
                  description
                    "Set the delay for triggering nexthop
                     recalculations";
                }
                leaf nsr {
                  type string;
                  description
                    "TRUE to Enable non-stop routing
                     supportFALSE to Disable non-stop routing
                     support";
                }
                leaf neighbor-logging-detail {
                  type empty;
                  description
                    "Include extra detail in neighbor change
                     messages";
                }
                leaf mvpn {
                  type empty;
                  description
                    "Connect to PIM/PIM6";
                }
                leaf rpki-origin-as-validation-disable {
                  type empty;
                  description
                    "RPKI origin-AS validation disable";
                }
                leaf global-scan-time {
                  type string;
                  units "second";
                  // NCS drop default statement
                  description
                    "Configure background scanner interval for
                     generic scanner";
                }
                leaf rpki-origin-as-validation-time {
                  type string;
                  units "second";
                  description
                    "Prefix validation time (in seconds). Range
                     : 5 - 60. Specify 0 for timer off";
                }
                leaf rpki-bestpath-origin-as-allow-invalid {
                  type empty;
                  description
                    "RPKI bestpath origin-AS allow invalid";
                }
                leaf graceful-restart-purge-time {
                  type string;
                  units "second";
                  // NCS drop default statement
                  description
                    "Time before stale routes are purged.";
                }
                leaf enforce-ibgp-out-policy {
                  type empty;
                  description
                    "Allow all attributes to be modified by
                     outbound policy for iBGP peers";
                }
                leaf update-limit-process {
                  type string;
                  units "megabyte";
                  // NCS drop default statement
                  description
                    "Upper bound on update generation transient
                     memory usage for the process";
                }
                leaf graceful-restart-time {
                  type string;
                  units "second";
                  // NCS drop default statement
                  description
                    "Restart time advertised to neighbors";
                }
                leaf update-error-handling-basic-ibgp-disable {
                  type empty;
                  description
                    "Inbound update basic error-handling for
                     IBGP neighbors";
                }
                leaf read-only {
                  type empty;
                  description
                    "Allow duplicate table config and disable
                     update generation";
                }
                leaf graceful-restart-stalepath-time {
                  type string;
                  units "second";
                  // NCS drop default statement
                  description
                    "Maximum time to wait for restart of GR
                     capable peers";
                }
                leaf update-error-handling-extended-ebgp {
                  type empty;
                  description
                    "Inbound update extended error-handling for
                     EBGP neighbors";
                }
                leaf update-error-handling-basic-ebgp-disable {
                  type empty;
                  description
                    "Inbound update basic error-handling for
                     EBGP neighbors";
                }
                leaf graceful-reset {
                  type empty;
                  description
                    "Reset gracefully if configuration change
                     forces a peer reset";
                }
                leaf igp-loop-check {
                  type empty;
                  description
                    "Enable AS-path loop checking for iBGP peers";
                }
                leaf update-error-handling-extended-ibgp {
                  type empty;
                  description
                    "Inbound update extended error-handling for
                     IBGP neighbors";
                }
                uses ncs_template_ROUTER-ID;
                uses ncs_template_DISABLE-ENFORCE-FIRST-AS;
                uses ncs_template_BEST-PATH-COST-COMMUNITY;
                uses ncs_template_BEST-PATH-AIGP-IGNORE;
                uses ncs_template_BEST-PATH-AS-PATH-LENGTH;
                uses ncs_template_IGP-REDIST-INTERNAL;
                uses ncs_template_MULTI-PATH-AS-PATH-IGNORE-ONWARDS;
                uses ncs_template_DISABLE-FAST-EXTERNAL-FALLOVER;
                uses ncs_template_UNSAFE-EBGP-POLICY;
                uses ncs_template_DEFAULT-METRIC;
                uses ncs_template_DEFAULT-INFO-ORIGINATE;
                uses ncs_template_BGP-CFG-RPKI-ORIGIN-AS-VALIDITY-SIGNAL-IBGP;
                uses ncs_template_BGP-CFG-RPKI-BESTPATH-USE-ORIGIN-AS-VALIDITY;
                uses ncs_template_BEST-PATH-CONFEDERATION-PATHS;
                uses ncs_template_BEST-PATH-AS-MULTIPATH-RELAX;
                uses ncs_template_MPLS-ACTIVATED-INTERFACE-TABLE;
                uses ncs_template_DISABLE-AUTO-SOFT-RESET;
                uses ncs_template_DISABLE-MSG-LOG;
                uses ncs_template_GLOBAL-TIMERS;
                uses ncs_template_BEST-PATH-IGP-METRIC-IGNORE;
                uses ncs_template_NEXT-HOP-RES-ALLOW-DEFAULT;
                uses ncs_template_NEXT-HOP-MPLS-FWD-IBGP;
                uses ncs_template_BFD;
                uses ncs_template_DISABLE-NEIGHBOR-LOGGING;
                uses ncs_template_SEND-SOCKET-BUFFER-SIZES;
                uses ncs_template_BEST-PATH-MED-ALWAYS;
                uses ncs_template_RECEIVE-SOCKET-BUFFER-SIZES;
                uses ncs_template_BEST-PATH-ROUTER-ID;
                uses ncs_template_BEST-PATH-MED-MISSING;
                uses ncs_template_LOCAL-PREFERENCE;
              }
            }
            leaf bgp-running {
              type empty;
              description
                "Enable BGP. Deletion of this object causes
                 deletion of all the objects under FourByteAS
                 associated with this object.";
            }
            leaf as {
              type string;
              description
                "2-byte or 4-byte Autonomous system number";
            }
          }
        }
      }
    }
    container bmp-server-all {
      description
        "bmp server all";
      container route-monitoring {
        description
          "Enable Route Monitoring capability for the BMP
           servers.
           BGP update messages messages will be
           regenrated with a table walk
          ";
        leaf policy {
          type string;
          description
            "Specify if the routes packed in update messages
             should be
             before or after the application of
             route-policy";
        }
        leaf direction {
          type string;
          description
            "Specify if the routes should be picked up at
             inbound
             or outbound direction";
        }
      }
      leaf maximum-buffer-size {
        type string;
        units "megabyte";
        description
          "Range in MegaBytes for the maximum buffer size
           of BMP message queue.
           The maximum buf-size is
           20% and default buf-size is 15% of the
           platform
           virtual memory max-limit (aka rlimit).
           Please run show bgp process
           performance-statistics
           to see the individual
           values. Unit is in Megabytes";
      }
    }
    container bmp-servers {
      description
        "bmp servers";
      list bmp-server {
        // NCS patched for predictable order
        ordered-by user;
        key "server-id";
        description
          "A particular BMP server";
        container initial-refresh-delay {
          description
            "Initial refresh to generate BGP updates";
          leaf delay {
            type string;
            units "second";
            // NCS drop must statement
            description
              "Delay in seconds before sending Refresh
               request to Peers";
          }
          leaf spread {
            type string;
            // NCS drop must statement
            description
              "Spread over which to send initial Refresh
               request to Peers";
          }
          leaf skip {
            type empty;
            // NCS drop must statement
            description
              "Skip Route Refresh request to Peers";
          }
        }
        container host-port {
          description
            "Configure Host Name/Address and Port for BMP
             Server";
          leaf host {
            type string;
            description
              "Name of the BMP server(accepts IPv4/IPv6
               Address format too)";
          }
          leaf port {
            type string;
            description
              "Port Number of listening BMP server";
          }
        }
        container tos {
          description
            "TOS (Type Of Service)";
          leaf type {
            type string;
            description
              "Set type of service";
          }
          leaf value {
            type string;
            description
              "TOS value to set";
          }
        }
        leaf create {
          type empty;
          description
            "BMP Server Creation";
        }
        leaf maximum-buffer-size {
          type string;
          units "megabyte";
          description
            "Range in MegaBytes for the maximum buffer size
             of BMP message queue.
             The maximum buf-size is
             20% and default buf-size is 15% of the
             platform
             virtual memory max-limit (aka rlimit)
             . Please run show bgp process
             performance-statistics
             to see the individual
             values. Unit is in Megabytes";
        }
        leaf initial-delay {
          type string;
          units "second";
          description
            "Initial connect delay in seconds in sending
             updates";
        }
        leaf flapping-delay {
          type string;
          units "second";
          description
            "Delay in connecting to BMP Server after a flap
             had been detected.";
        }
        leaf status-report-interval {
          type string;
          units "second";
          description
            "Stats reporting period for BMP server";
        }
        leaf description {
          type string;
          description
            "String to describe the BMP server";
        }
        leaf bmptcp-maximum-segment-size {
          type string;
          units "byte";
          description
            "configure TCP maximum segment size.
             Default=16384.";
        }
        leaf bmptcp-keep-alive {
          type string;
          units "second";
          description
            "configure TCP keep alives to be exchanged
             between client and server. Default=1000";
        }
        leaf vrf {
          type string;
          description
            "VRF for BMP Server";
        }
        leaf shutdown {
          type empty;
          description
            "Shutdown connection to BMP server";
        }
        leaf update-source-interface {
          type string;
          description
            "Select an interface to configure";
        }
        leaf server-id {
          type string;
          description
            "BMP Server ID";
        }
      }
    }
  }
  augment "/ncs:devices/ncs:template/ncs:ned-id/ncs:config/a1:vrfs/a1:vrf" {
    container bgp-global {
      description
        "BGP related VRF Global config";
      container route-distinguisher {
        description
          "Route distinguisher";
        leaf type {
          type string;
          description
            "Type of RD";
        }
        leaf as-xx {
          // NCS drop when statement
          type string;
          description
            "AS number";
        }
        leaf as {
          // NCS drop when statement
          type string;
          description
            "AS number";
        }
        leaf as-index {
          // NCS drop when statement
          type string;
          description
            "ASN Index";
        }
        leaf address {
          // NCS drop when statement
          type string;
          description
            "IP address";
        }
        leaf address-index {
          // NCS drop when statement
          type string;
          description
            "IP address index";
        }
      }
    }
    description
      "This augment extends the configuration data of
       'Cisco-IOS-XR-infra-rsi-cfg'";
  }
  augment "/ncs:devices/ncs:device/ncs:live-status/a1:vrfs/a1:vrf" {
    container bgp-global {
      tailf:ncs-device-type "netconf";
      tailf:display-when "not(../../../../ncs:module) or ../../../../ncs:module[ncs:name='Cisco-IOS-XR-ipv4-bgp-cfg'] or (../../../../ncs:live-status-protocol[not(ncs:capability)]) or (../../../../ncs:live-status-protocol/ncs:capability/ncs:module[.='Cisco-IOS-XR-ipv4-bgp-cfg'])";
      description
        "BGP related VRF Global config";
      container route-distinguisher {
        description
          "Route distinguisher";
        leaf type {
          type Bgp-global-route-distinguisher;
          description
            "Type of RD";
        }
        leaf as-xx {
          // NCS drop when statement
          type Bgp-global-as-range;
          description
            "AS number";
        }
        leaf as {
          // NCS drop when statement
          type Bgp-global-as-range;
          description
            "AS number";
        }
        leaf as-index {
          // NCS drop when statement
          type Bgp-global-extcomm-asn-index;
          description
            "ASN Index";
        }
        leaf address {
          // NCS drop when statement
          type inet:ipv4-address-no-zone;
          description
            "IP address";
        }
        leaf address-index {
          // NCS drop when statement
          type Bgp-global-extcomm-v4-addr-index;
          description
            "IP address index";
        }
      }
    }
    description
      "This augment extends the configuration data of
       'Cisco-IOS-XR-infra-rsi-cfg'";
  }
  augment "/ncs:devices/ncs:device/ncs:config/a1:vrfs/a1:vrf" {
    container bgp-global {
      tailf:ncs-device-type "netconf";
      tailf:display-when "not(../../../../ncs:module) or ../../../../ncs:module[ncs:name='Cisco-IOS-XR-ipv4-bgp-cfg']";
      description
        "BGP related VRF Global config";
      container route-distinguisher {
        description
          "Route distinguisher";
        leaf type {
          type Bgp-global-route-distinguisher;
          description
            "Type of RD";
        }
        leaf as-xx {
          when "../type = 'as' or ../type = 'four-byte-as'" {
            tailf:xpath-root 3;
            description
              "../Type = AS or ../Type = FourByteAS";
          }
          type Bgp-global-as-range;
          description
            "AS number";
        }
        leaf as {
          when "../type = 'as' or ../type = 'four-byte-as'" {
            tailf:xpath-root 3;
            description
              "../Type = AS or ../Type = FourByteAS";
          }
          type Bgp-global-as-range;
          description
            "AS number";
        }
        leaf as-index {
          when "../type = 'as' or ../type = 'four-byte-as'" {
            tailf:xpath-root 3;
            description
              "../Type = AS or ../Type = FourByteAS";
          }
          type Bgp-global-extcomm-asn-index;
          description
            "ASN Index";
        }
        leaf address {
          when "../type = 'ipv4-address'" {
            tailf:xpath-root 3;
            description
              "../Type = IPV4Address";
          }
          type inet:ipv4-address-no-zone;
          description
            "IP address";
        }
        leaf address-index {
          when "../type = 'ipv4-address'" {
            tailf:xpath-root 3;
            description
              "../Type = IPV4Address";
          }
          type Bgp-global-extcomm-v4-addr-index;
          description
            "IP address index";
        }
      }
    }
    description
      "This augment extends the configuration data of
       'Cisco-IOS-XR-infra-rsi-cfg'";
  }
  augment "/ncs:devices/ncs:template/ncs:ned-id/ncs:config/a2:snmp/a2:notification" {
    container bgp {
      description
        "BGP4-MIB and CISCO-BGP4-MIB notification
         configuration";
      container bgp4mib {
        description
          "Enable BGP4-MIB and CISCO-BGP4-MIB IPv4-only
           notifications: bgpEstablishedNotification,
           bgpBackwardTransNotification,
           cbgpFsmStateChange, cbgpBackwardTransition,
           cbgpPrefixThresholdExceeded,
           cbgpPrefixThresholdClear.";
        leaf enable {
          type empty;
          description
            "Enable BGP4-MIB and CISCO-BGP4-MIB IPv4-only
             notifications";
        }
        leaf up-down {
          type empty;
          description
            "Enable BGP4-MIB and CISCO-BGP4-MIB IPv4-only
             up/down notifications";
        }
      }
      container cisco-bgp4mib {
        description
          "Enable CISCO-BGP4-MIB v2 notifications:
           cbgpPeer2EstablishedNotification,
           cbgpPeer2BackwardTransNotification,
           cbgpPeer2FsmStateChange,
           cbgpPeer2BackwardTransition,
           cbgpPeer2PrefixThresholdExceeded,
           cbgpPeer2PrefixThresholdClear.";
        leaf enable {
          type empty;
          description
            "Enable CISCO-BGP4-MIB v2 notifications";
        }
        leaf up-down {
          type empty;
          description
            "Enable CISCO-BGP4-MIB v2 up/down notifications";
        }
      }
    }
    description
      "This augment extends the configuration data of
       'Cisco-IOS-XR-snmp-agent-cfg'";
  }
  augment "/ncs:devices/ncs:device/ncs:live-status/a2:snmp/a2:notification" {
    container bgp {
      tailf:ncs-device-type "netconf";
      tailf:display-when "not(../../../../ncs:module) or ../../../../ncs:module[ncs:name='Cisco-IOS-XR-ipv4-bgp-cfg'] or (../../../../ncs:live-status-protocol[not(ncs:capability)]) or (../../../../ncs:live-status-protocol/ncs:capability/ncs:module[.='Cisco-IOS-XR-ipv4-bgp-cfg'])";
      description
        "BGP4-MIB and CISCO-BGP4-MIB notification
         configuration";
      container bgp4mib {
        description
          "Enable BGP4-MIB and CISCO-BGP4-MIB IPv4-only
           notifications: bgpEstablishedNotification,
           bgpBackwardTransNotification,
           cbgpFsmStateChange, cbgpBackwardTransition,
           cbgpPrefixThresholdExceeded,
           cbgpPrefixThresholdClear.";
        leaf enable {
          type empty;
          description
            "Enable BGP4-MIB and CISCO-BGP4-MIB IPv4-only
             notifications";
        }
        leaf up-down {
          type empty;
          description
            "Enable BGP4-MIB and CISCO-BGP4-MIB IPv4-only
             up/down notifications";
        }
      }
      container cisco-bgp4mib {
        description
          "Enable CISCO-BGP4-MIB v2 notifications:
           cbgpPeer2EstablishedNotification,
           cbgpPeer2BackwardTransNotification,
           cbgpPeer2FsmStateChange,
           cbgpPeer2BackwardTransition,
           cbgpPeer2PrefixThresholdExceeded,
           cbgpPeer2PrefixThresholdClear.";
        leaf enable {
          type empty;
          description
            "Enable CISCO-BGP4-MIB v2 notifications";
        }
        leaf up-down {
          type empty;
          description
            "Enable CISCO-BGP4-MIB v2 up/down notifications";
        }
      }
    }
    description
      "This augment extends the configuration data of
       'Cisco-IOS-XR-snmp-agent-cfg'";
  }
  augment "/ncs:devices/ncs:device/ncs:config/a2:snmp/a2:notification" {
    container bgp {
      tailf:ncs-device-type "netconf";
      tailf:display-when "not(../../../../ncs:module) or ../../../../ncs:module[ncs:name='Cisco-IOS-XR-ipv4-bgp-cfg']";
      description
        "BGP4-MIB and CISCO-BGP4-MIB notification
         configuration";
      container bgp4mib {
        description
          "Enable BGP4-MIB and CISCO-BGP4-MIB IPv4-only
           notifications: bgpEstablishedNotification,
           bgpBackwardTransNotification,
           cbgpFsmStateChange, cbgpBackwardTransition,
           cbgpPrefixThresholdExceeded,
           cbgpPrefixThresholdClear.";
        leaf enable {
          type empty;
          description
            "Enable BGP4-MIB and CISCO-BGP4-MIB IPv4-only
             notifications";
        }
        leaf up-down {
          type empty;
          description
            "Enable BGP4-MIB and CISCO-BGP4-MIB IPv4-only
             up/down notifications";
        }
      }
      container cisco-bgp4mib {
        description
          "Enable CISCO-BGP4-MIB v2 notifications:
           cbgpPeer2EstablishedNotification,
           cbgpPeer2BackwardTransNotification,
           cbgpPeer2FsmStateChange,
           cbgpPeer2BackwardTransition,
           cbgpPeer2PrefixThresholdExceeded,
           cbgpPeer2PrefixThresholdClear.";
        leaf enable {
          type empty;
          description
            "Enable CISCO-BGP4-MIB v2 notifications";
        }
        leaf up-down {
          type empty;
          description
            "Enable CISCO-BGP4-MIB v2 up/down notifications";
        }
      }
    }
    description
      "This augment extends the configuration data of
       'Cisco-IOS-XR-snmp-agent-cfg'";
  }
  augment "/ncs:devices/ncs:template/ncs:ned-id/ncs:config/a1:vrfs/a1:vrf/a1:afs/a1:af" {
    container bgp {
      description
        "BGP AF VRF config";
      container import-route-targets {
        description
          "Import Route targets";
        uses ncs_template_ROUTE-TARGET-TABLE;
      }
      container export-route-targets {
        description
          "Export Route targets";
        uses ncs_template_ROUTE-TARGET-TABLE;
      }
      container vrf-to-global-export-route-policy {
        presence "Indicates a vrf-to-global-export-route-policy node is configured.";
        description
          "Route policy for vrf to global export filtering";
        leaf route-policy-name {
          type string;
          // NCS drop mandatory statement
          description
            "Vrf to global export route policy";
        }
        leaf allow-imported-vpn {
          type string;
          description
            "TRUE Enable imported VPN paths to be exported
             to Default VRF.FALSE Disable imported VPN
             paths to be exported to Default VRF.";
        }
      }
      container export-vrf-options {
        description
          "Export VRF options";
        leaf allow-imported-vpn {
          type string;
          description
            "TRUE Enable imported VPN paths to be exported
             to non-default VRFFALSE Disable imported VPN
             paths to be exported to non-default VRF";
        }
        leaf import-stitching-rt {
          type string;
          description
            "TRUE Use stitchng RTs to import extranet
             pathsFALSE Use regular RTs to import extranet
             paths";
        }
      }
      container global-to-vrf-import-route-policy {
        presence "Indicates a global-to-vrf-import-route-policy node is configured.";
        description
          "Route policy for global to vrf import filtering";
        leaf route-policy-name {
          type string;
          // NCS drop mandatory statement
          description
            "Global to vrf import route policy";
        }
        leaf advertise-as-vpn {
          type string;
          description
            "TRUE Enable advertising imported paths to
             PEsFALSE Disable advertising imported paths to
             PEs";
        }
      }
      leaf export-route-policy {
        type string;
        description
          "Route policy for export filtering";
      }
      leaf import-route-policy {
        type string;
        description
          "Route policy for import filtering";
      }
      leaf import-vrf-options {
        type string;
        description
          "TRUE Enable advertising imported paths to
           PEsFALSE Disable advertising imported paths to
           PEs";
      }
      leaf import-from-bridge-domain {
        type string;
        description
          "TRUE Enable advertising local EVPN paths to PEs
           .FALSE Disable advertising local EVPN paths to
           PEs.";
      }
    }
    description
      "This augment extends the configuration data of
       'Cisco-IOS-XR-infra-rsi-cfg'";
  }
  augment "/ncs:devices/ncs:device/ncs:live-status/a1:vrfs/a1:vrf/a1:afs/a1:af" {
    container bgp {
      tailf:ncs-device-type "netconf";
      tailf:display-when "not(../../../../../../ncs:module) or ../../../../../../ncs:module[ncs:name='Cisco-IOS-XR-ipv4-bgp-cfg'] or (../../../../../../ncs:live-status-protocol[not(ncs:capability)]) or (../../../../../../ncs:live-status-protocol/ncs:capability/ncs:module[.='Cisco-IOS-XR-ipv4-bgp-cfg'])";
      description
        "BGP AF VRF config";
      container import-route-targets {
        description
          "Import Route targets";
        uses live_ncs_ROUTE-TARGET-TABLE;
      }
      container export-route-targets {
        description
          "Export Route targets";
        uses live_ncs_ROUTE-TARGET-TABLE;
      }
      container vrf-to-global-export-route-policy {
        presence "Indicates a vrf-to-global-export-route-policy node is configured.";
        description
          "Route policy for vrf to global export filtering";
        leaf route-policy-name {
          type string;
          // NCS drop mandatory statement
          description
            "Vrf to global export route policy";
        }
        leaf allow-imported-vpn {
          type boolean;
          description
            "TRUE Enable imported VPN paths to be exported
             to Default VRF.FALSE Disable imported VPN
             paths to be exported to Default VRF.";
        }
      }
      container export-vrf-options {
        description
          "Export VRF options";
        leaf allow-imported-vpn {
          type boolean;
          description
            "TRUE Enable imported VPN paths to be exported
             to non-default VRFFALSE Disable imported VPN
             paths to be exported to non-default VRF";
        }
        leaf import-stitching-rt {
          type boolean;
          description
            "TRUE Use stitchng RTs to import extranet
             pathsFALSE Use regular RTs to import extranet
             paths";
        }
      }
      container global-to-vrf-import-route-policy {
        presence "Indicates a global-to-vrf-import-route-policy node is configured.";
        description
          "Route policy for global to vrf import filtering";
        leaf route-policy-name {
          type string;
          // NCS drop mandatory statement
          description
            "Global to vrf import route policy";
        }
        leaf advertise-as-vpn {
          type boolean;
          description
            "TRUE Enable advertising imported paths to
             PEsFALSE Disable advertising imported paths to
             PEs";
        }
      }
      leaf export-route-policy {
        type string;
        description
          "Route policy for export filtering";
      }
      leaf import-route-policy {
        type string;
        description
          "Route policy for import filtering";
      }
      leaf import-vrf-options {
        type boolean;
        description
          "TRUE Enable advertising imported paths to
           PEsFALSE Disable advertising imported paths to
           PEs";
      }
      leaf import-from-bridge-domain {
        type boolean;
        description
          "TRUE Enable advertising local EVPN paths to PEs
           .FALSE Disable advertising local EVPN paths to
           PEs.";
      }
    }
    description
      "This augment extends the configuration data of
       'Cisco-IOS-XR-infra-rsi-cfg'";
  }
  augment "/ncs:devices/ncs:device/ncs:config/a1:vrfs/a1:vrf/a1:afs/a1:af" {
    container bgp {
      tailf:ncs-device-type "netconf";
      tailf:display-when "not(../../../../../../ncs:module) or ../../../../../../ncs:module[ncs:name='Cisco-IOS-XR-ipv4-bgp-cfg']";
      description
        "BGP AF VRF config";
      container import-route-targets {
        description
          "Import Route targets";
        uses ROUTE-TARGET-TABLE;
      }
      container export-route-targets {
        description
          "Export Route targets";
        uses ROUTE-TARGET-TABLE;
      }
      container vrf-to-global-export-route-policy {
        presence "Indicates a vrf-to-global-export-route-policy node is configured.";
        description
          "Route policy for vrf to global export filtering";
        leaf route-policy-name {
          type string;
          mandatory true;
          description
            "Vrf to global export route policy";
        }
        leaf allow-imported-vpn {
          type boolean;
          description
            "TRUE Enable imported VPN paths to be exported
             to Default VRF.FALSE Disable imported VPN
             paths to be exported to Default VRF.";
        }
      }
      container export-vrf-options {
        description
          "Export VRF options";
        leaf allow-imported-vpn {
          type boolean;
          description
            "TRUE Enable imported VPN paths to be exported
             to non-default VRFFALSE Disable imported VPN
             paths to be exported to non-default VRF";
        }
        leaf import-stitching-rt {
          type boolean;
          description
            "TRUE Use stitchng RTs to import extranet
             pathsFALSE Use regular RTs to import extranet
             paths";
        }
      }
      container global-to-vrf-import-route-policy {
        presence "Indicates a global-to-vrf-import-route-policy node is configured.";
        description
          "Route policy for global to vrf import filtering";
        leaf route-policy-name {
          type string;
          mandatory true;
          description
            "Global to vrf import route policy";
        }
        leaf advertise-as-vpn {
          type boolean;
          description
            "TRUE Enable advertising imported paths to
             PEsFALSE Disable advertising imported paths to
             PEs";
        }
      }
      leaf export-route-policy {
        type string;
        description
          "Route policy for export filtering";
      }
      leaf import-route-policy {
        type string;
        description
          "Route policy for import filtering";
      }
      leaf import-vrf-options {
        type boolean;
        description
          "TRUE Enable advertising imported paths to
           PEsFALSE Disable advertising imported paths to
           PEs";
      }
      leaf import-from-bridge-domain {
        type boolean;
        description
          "TRUE Enable advertising local EVPN paths to PEs
           .FALSE Disable advertising local EVPN paths to
           PEs.";
      }
    }
    description
      "This augment extends the configuration data of
       'Cisco-IOS-XR-infra-rsi-cfg'";
  }
  augment "/ncs:devices/ncs:template/ncs:ned-id/ncs:config/a1:global-af/a1:afs/a1:af" {
    container bgp {
      description
        "BGP AF VRF config";
      container import-route-targets {
        description
          "Import Route targets";
        uses ncs_template_ROUTE-TARGET-TABLE;
      }
      container export-route-targets {
        description
          "Export Route targets";
        uses ncs_template_ROUTE-TARGET-TABLE;
      }
      container vrf-to-global-export-route-policy {
        presence "Indicates a vrf-to-global-export-route-policy node is configured.";
        description
          "Route policy for vrf to global export filtering";
        leaf route-policy-name {
          type string;
          // NCS drop mandatory statement
          description
            "Vrf to global export route policy";
        }
        leaf allow-imported-vpn {
          type string;
          description
            "TRUE Enable imported VPN paths to be exported
             to Default VRF.FALSE Disable imported VPN
             paths to be exported to Default VRF.";
        }
      }
      container export-vrf-options {
        description
          "Export VRF options";
        leaf allow-imported-vpn {
          type string;
          description
            "TRUE Enable imported VPN paths to be exported
             to non-default VRFFALSE Disable imported VPN
             paths to be exported to non-default VRF";
        }
        leaf import-stitching-rt {
          type string;
          description
            "TRUE Use stitchng RTs to import extranet
             pathsFALSE Use regular RTs to import extranet
             paths";
        }
      }
      container global-to-vrf-import-route-policy {
        presence "Indicates a global-to-vrf-import-route-policy node is configured.";
        description
          "Route policy for global to vrf import filtering";
        leaf route-policy-name {
          type string;
          // NCS drop mandatory statement
          description
            "Global to vrf import route policy";
        }
        leaf advertise-as-vpn {
          type string;
          description
            "TRUE Enable advertising imported paths to
             PEsFALSE Disable advertising imported paths to
             PEs";
        }
      }
      leaf export-route-policy {
        type string;
        description
          "Route policy for export filtering";
      }
      leaf import-route-policy {
        type string;
        description
          "Route policy for import filtering";
      }
      leaf import-vrf-options {
        type string;
        description
          "TRUE Enable advertising imported paths to
           PEsFALSE Disable advertising imported paths to
           PEs";
      }
      leaf import-from-bridge-domain {
        type string;
        description
          "TRUE Enable advertising local EVPN paths to PEs
           .FALSE Disable advertising local EVPN paths to
           PEs.";
      }
    }
    description
      "This augment extends the configuration data of
       'Cisco-IOS-XR-infra-rsi-cfg'";
  }
  augment "/ncs:devices/ncs:device/ncs:live-status/a1:global-af/a1:afs/a1:af" {
    container bgp {
      tailf:ncs-device-type "netconf";
      tailf:display-when "not(../../../../../ncs:module) or ../../../../../ncs:module[ncs:name='Cisco-IOS-XR-ipv4-bgp-cfg'] or (../../../../../ncs:live-status-protocol[not(ncs:capability)]) or (../../../../../ncs:live-status-protocol/ncs:capability/ncs:module[.='Cisco-IOS-XR-ipv4-bgp-cfg'])";
      description
        "BGP AF VRF config";
      container import-route-targets {
        description
          "Import Route targets";
        uses live_ncs_ROUTE-TARGET-TABLE;
      }
      container export-route-targets {
        description
          "Export Route targets";
        uses live_ncs_ROUTE-TARGET-TABLE;
      }
      container vrf-to-global-export-route-policy {
        presence "Indicates a vrf-to-global-export-route-policy node is configured.";
        description
          "Route policy for vrf to global export filtering";
        leaf route-policy-name {
          type string;
          // NCS drop mandatory statement
          description
            "Vrf to global export route policy";
        }
        leaf allow-imported-vpn {
          type boolean;
          description
            "TRUE Enable imported VPN paths to be exported
             to Default VRF.FALSE Disable imported VPN
             paths to be exported to Default VRF.";
        }
      }
      container export-vrf-options {
        description
          "Export VRF options";
        leaf allow-imported-vpn {
          type boolean;
          description
            "TRUE Enable imported VPN paths to be exported
             to non-default VRFFALSE Disable imported VPN
             paths to be exported to non-default VRF";
        }
        leaf import-stitching-rt {
          type boolean;
          description
            "TRUE Use stitchng RTs to import extranet
             pathsFALSE Use regular RTs to import extranet
             paths";
        }
      }
      container global-to-vrf-import-route-policy {
        presence "Indicates a global-to-vrf-import-route-policy node is configured.";
        description
          "Route policy for global to vrf import filtering";
        leaf route-policy-name {
          type string;
          // NCS drop mandatory statement
          description
            "Global to vrf import route policy";
        }
        leaf advertise-as-vpn {
          type boolean;
          description
            "TRUE Enable advertising imported paths to
             PEsFALSE Disable advertising imported paths to
             PEs";
        }
      }
      leaf export-route-policy {
        type string;
        description
          "Route policy for export filtering";
      }
      leaf import-route-policy {
        type string;
        description
          "Route policy for import filtering";
      }
      leaf import-vrf-options {
        type boolean;
        description
          "TRUE Enable advertising imported paths to
           PEsFALSE Disable advertising imported paths to
           PEs";
      }
      leaf import-from-bridge-domain {
        type boolean;
        description
          "TRUE Enable advertising local EVPN paths to PEs
           .FALSE Disable advertising local EVPN paths to
           PEs.";
      }
    }
    description
      "This augment extends the configuration data of
       'Cisco-IOS-XR-infra-rsi-cfg'";
  }
  augment "/ncs:devices/ncs:device/ncs:config/a1:global-af/a1:afs/a1:af" {
    container bgp {
      tailf:ncs-device-type "netconf";
      tailf:display-when "not(../../../../../ncs:module) or ../../../../../ncs:module[ncs:name='Cisco-IOS-XR-ipv4-bgp-cfg']";
      description
        "BGP AF VRF config";
      container import-route-targets {
        description
          "Import Route targets";
        uses ROUTE-TARGET-TABLE;
      }
      container export-route-targets {
        description
          "Export Route targets";
        uses ROUTE-TARGET-TABLE;
      }
      container vrf-to-global-export-route-policy {
        presence "Indicates a vrf-to-global-export-route-policy node is configured.";
        description
          "Route policy for vrf to global export filtering";
        leaf route-policy-name {
          type string;
          mandatory true;
          description
            "Vrf to global export route policy";
        }
        leaf allow-imported-vpn {
          type boolean;
          description
            "TRUE Enable imported VPN paths to be exported
             to Default VRF.FALSE Disable imported VPN
             paths to be exported to Default VRF.";
        }
      }
      container export-vrf-options {
        description
          "Export VRF options";
        leaf allow-imported-vpn {
          type boolean;
          description
            "TRUE Enable imported VPN paths to be exported
             to non-default VRFFALSE Disable imported VPN
             paths to be exported to non-default VRF";
        }
        leaf import-stitching-rt {
          type boolean;
          description
            "TRUE Use stitchng RTs to import extranet
             pathsFALSE Use regular RTs to import extranet
             paths";
        }
      }
      container global-to-vrf-import-route-policy {
        presence "Indicates a global-to-vrf-import-route-policy node is configured.";
        description
          "Route policy for global to vrf import filtering";
        leaf route-policy-name {
          type string;
          mandatory true;
          description
            "Global to vrf import route policy";
        }
        leaf advertise-as-vpn {
          type boolean;
          description
            "TRUE Enable advertising imported paths to
             PEsFALSE Disable advertising imported paths to
             PEs";
        }
      }
      leaf export-route-policy {
        type string;
        description
          "Route policy for export filtering";
      }
      leaf import-route-policy {
        type string;
        description
          "Route policy for import filtering";
      }
      leaf import-vrf-options {
        type boolean;
        description
          "TRUE Enable advertising imported paths to
           PEsFALSE Disable advertising imported paths to
           PEs";
      }
      leaf import-from-bridge-domain {
        type boolean;
        description
          "TRUE Enable advertising local EVPN paths to PEs
           .FALSE Disable advertising local EVPN paths to
           PEs.";
      }
    }
    description
      "This augment extends the configuration data of
       'Cisco-IOS-XR-infra-rsi-cfg'";
  }
}
