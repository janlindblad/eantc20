module Cisco-IOS-XR-ipv4-ospf-act {
  // Generated by yanger -t ncs
  tailf:mount-id f5500-nc-1.0:f5500-nc-1.0;
  tailf:ncs-device-type "netconf";

  namespace "http://cisco.com/ns/yang/Cisco-IOS-XR-ipv4-ospf-act";
  prefix Cisco-IOS-XR-ipv4-ospf-act;

  import Cisco-IOS-XR-types {
    prefix xr;
  }
  import ietf-inet-types {
    prefix inet;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR OSPF action package configuration.

     Copyright (c) 2016-2017 by Cisco Systems, Inc.
     All rights reserved.";

  revision 2016-09-14 {
    description
      "IOS XR 6.2.1 revision.";
  }

  grouping ncs_template_OSPF-STAT-ATTRIBUTES {
    leaf process {
      description
        "Reset OSPF process";
      type empty;
    }
    leaf redistribution {
      description
        "Clear OSPF route redistrbution";
      type empty;
    }
    leaf route {
      description
        "Clear OSPF route table";
      type empty;
    }
    container stats {
      description
        "OSPF counters and statistics";
      leaf spf {
        description
          "SPF statistics";
        type empty;
      }
      leaf message-queue {
        description
          "Message-queue statistics";
        type empty;
      }
      container interface {
        description
          "OSPF interface statistics";
        leaf interface-name {
          type string;
        }
      }
      container neighbor {
        description
          "Neighbor statistics per interface or neighbor id";
        leaf neighbor-id {
          description
            "Neighbor ID";
          type string;
        }
        container interface {
          leaf interface-name {
            description
              "OSPF interface statistics";
            type string;
          }
        }
      }
    }
  }

  grouping ncs_rpc_notif_OSPF-STAT-ATTRIBUTES {
    leaf process {
      description
        "Reset OSPF process";
      type empty;
    }
    leaf redistribution {
      description
        "Clear OSPF route redistrbution";
      type empty;
    }
    leaf route {
      description
        "Clear OSPF route table";
      type empty;
    }
    container stats {
      description
        "OSPF counters and statistics";
      leaf spf {
        description
          "SPF statistics";
        type empty;
      }
      leaf message-queue {
        description
          "Message-queue statistics";
        type empty;
      }
      container interface {
        description
          "OSPF interface statistics";
        leaf interface-name {
          type xr:Interface-name;
        }
      }
      container neighbor {
        description
          "Neighbor statistics per interface or neighbor id";
        leaf neighbor-id {
          description
            "Neighbor ID";
          type inet:ipv4-address;
        }
        container interface {
          leaf interface-name {
            description
              "OSPF interface statistics";
            type xr:Interface-name;
          }
        }
      }
    }
  }

  grouping live_ncs_OSPF-STAT-ATTRIBUTES {
    leaf process {
      description
        "Reset OSPF process";
      type empty;
    }
    leaf redistribution {
      description
        "Clear OSPF route redistrbution";
      type empty;
    }
    leaf route {
      description
        "Clear OSPF route table";
      type empty;
    }
    container stats {
      description
        "OSPF counters and statistics";
      leaf spf {
        description
          "SPF statistics";
        type empty;
      }
      leaf message-queue {
        description
          "Message-queue statistics";
        type empty;
      }
      container interface {
        description
          "OSPF interface statistics";
        leaf interface-name {
          type xr:Interface-name;
        }
      }
      container neighbor {
        description
          "Neighbor statistics per interface or neighbor id";
        leaf neighbor-id {
          description
            "Neighbor ID";
          type inet:ipv4-address;
        }
        container interface {
          leaf interface-name {
            description
              "OSPF interface statistics";
            type xr:Interface-name;
          }
        }
      }
    }
  }

  grouping OSPF-STAT-ATTRIBUTES {
    leaf process {
      description
        "Reset OSPF process";
      type empty;
    }
    leaf redistribution {
      description
        "Clear OSPF route redistrbution";
      type empty;
    }
    leaf route {
      description
        "Clear OSPF route table";
      type empty;
    }
    container stats {
      description
        "OSPF counters and statistics";
      leaf spf {
        description
          "SPF statistics";
        type empty;
      }
      leaf message-queue {
        description
          "Message-queue statistics";
        type empty;
      }
      container interface {
        description
          "OSPF interface statistics";
        leaf interface-name {
          type xr:Interface-name;
        }
      }
      container neighbor {
        description
          "Neighbor statistics per interface or neighbor id";
        leaf neighbor-id {
          description
            "Neighbor ID";
          type inet:ipv4-address;
        }
        container interface {
          leaf interface-name {
            description
              "OSPF interface statistics";
            type xr:Interface-name;
          }
        }
      }
    }
  }

  augment "/ncs:devices/ncs:device/ncs:rpc" {
    container rpc-clear-ospf-instance-vrf {
      tailf:ncs-device-type "netconf";
      tailf:display-when "not(../../ncs:module) or ../../ncs:module[ncs:name='Cisco-IOS-XR-ipv4-ospf-act']";
      tailf:action clear-ospf-instance-vrf {
        tailf:actionpoint ncsproxy {
          tailf:internal;
        }
        description
          "Clear one or more non-default OSPF VRFs in process";
        input {
          container instance {
            description
              "OSPF instance name";
            leaf instance-identifier {
              description
                "OSPF process instance identifier";
              mandatory true;
              type string;
            }
            container vrf {
              description
                "Clear one or more non-default OSPF VRFs in process";
              leaf vrf-name {
                description
                  "OSPF VRF name";
                type string;
              }
              uses ncs_rpc_notif_OSPF-STAT-ATTRIBUTES;
            }
            container all {
              description
                "Clear all non-default OSPF VRFs";
              uses ncs_rpc_notif_OSPF-STAT-ATTRIBUTES;
            }
            container all-inclusive {
              description
                "Clear all non-default and default OSPF VRFs";
              uses ncs_rpc_notif_OSPF-STAT-ATTRIBUTES;
            }
          }
        }
      }
    }
  }
  augment "/ncs:devices/ncs:device-group/ncs:ned-id/ncs:rpc" {
    container rpc-clear-ospf-instance-vrf {
      tailf:ncs-device-type "netconf";
      tailf:display-when "/ncs:devices/ncs:device[ncs:name=current()/../../../ncs:member]/ncs:module[ncs:name='Cisco-IOS-XR-ipv4-ospf-act']";
      tailf:action clear-ospf-instance-vrf {
        tailf:actionpoint ncsproxy {
          tailf:internal;
        }
        description
          "Clear one or more non-default OSPF VRFs in process";
        input {
          container instance {
            description
              "OSPF instance name";
            leaf instance-identifier {
              description
                "OSPF process instance identifier";
              mandatory true;
              type string;
            }
            container vrf {
              description
                "Clear one or more non-default OSPF VRFs in process";
              leaf vrf-name {
                description
                  "OSPF VRF name";
                type string;
              }
              uses ncs_rpc_notif_OSPF-STAT-ATTRIBUTES;
            }
            container all {
              description
                "Clear all non-default OSPF VRFs";
              uses ncs_rpc_notif_OSPF-STAT-ATTRIBUTES;
            }
            container all-inclusive {
              description
                "Clear all non-default and default OSPF VRFs";
              uses ncs_rpc_notif_OSPF-STAT-ATTRIBUTES;
            }
          }
        }
      }
    }
  }
  augment "/ncs:devices/ncs:device/ncs:rpc" {
    container rpc-clear-ospf-process {
      tailf:ncs-device-type "netconf";
      tailf:display-when "not(../../ncs:module) or ../../ncs:module[ncs:name='Cisco-IOS-XR-ipv4-ospf-act']";
      tailf:action clear-ospf-process {
        tailf:actionpoint ncsproxy {
          tailf:internal;
        }
        description
          "Clear (reset) OSPF process";
        input {
          container instance {
            description
              "Clear data from OSPF instance";
            leaf instance-identifier {
              description
                "OSPF process instance identifier";
              type string;
            }
          }
          leaf process {
            description
              "Reset OSPF process";
            mandatory true;
            type empty;
          }
        }
      }
    }
  }
  augment "/ncs:devices/ncs:device-group/ncs:ned-id/ncs:rpc" {
    container rpc-clear-ospf-process {
      tailf:ncs-device-type "netconf";
      tailf:display-when "/ncs:devices/ncs:device[ncs:name=current()/../../../ncs:member]/ncs:module[ncs:name='Cisco-IOS-XR-ipv4-ospf-act']";
      tailf:action clear-ospf-process {
        tailf:actionpoint ncsproxy {
          tailf:internal;
        }
        description
          "Clear (reset) OSPF process";
        input {
          container instance {
            description
              "Clear data from OSPF instance";
            leaf instance-identifier {
              description
                "OSPF process instance identifier";
              type string;
            }
          }
          leaf process {
            description
              "Reset OSPF process";
            mandatory true;
            type empty;
          }
        }
      }
    }
  }
  augment "/ncs:devices/ncs:device/ncs:rpc" {
    container rpc-clear-ospf-statistics-interface {
      tailf:ncs-device-type "netconf";
      tailf:display-when "not(../../ncs:module) or ../../ncs:module[ncs:name='Cisco-IOS-XR-ipv4-ospf-act']";
      tailf:action clear-ospf-statistics-interface {
        tailf:actionpoint ncsproxy {
          tailf:internal;
        }
        description
          "Clear OSPF interface statistics";
        input {
          container instance {
            description
              "Clear data from OSPF instance";
            leaf instance-identifier {
              description
                "OSPF process instance identifier";
              type string;
            }
          }
          container interface {
            leaf interface-name {
              description
                "OSPF interface statistics";
              type xr:Interface-name;
            }
          }
        }
      }
    }
  }
  augment "/ncs:devices/ncs:device-group/ncs:ned-id/ncs:rpc" {
    container rpc-clear-ospf-statistics-interface {
      tailf:ncs-device-type "netconf";
      tailf:display-when "/ncs:devices/ncs:device[ncs:name=current()/../../../ncs:member]/ncs:module[ncs:name='Cisco-IOS-XR-ipv4-ospf-act']";
      tailf:action clear-ospf-statistics-interface {
        tailf:actionpoint ncsproxy {
          tailf:internal;
        }
        description
          "Clear OSPF interface statistics";
        input {
          container instance {
            description
              "Clear data from OSPF instance";
            leaf instance-identifier {
              description
                "OSPF process instance identifier";
              type string;
            }
          }
          container interface {
            leaf interface-name {
              description
                "OSPF interface statistics";
              type xr:Interface-name;
            }
          }
        }
      }
    }
  }
  augment "/ncs:devices/ncs:device/ncs:rpc" {
    container rpc-clear-ospf-statistics-neighbor {
      tailf:ncs-device-type "netconf";
      tailf:display-when "not(../../ncs:module) or ../../ncs:module[ncs:name='Cisco-IOS-XR-ipv4-ospf-act']";
      tailf:action clear-ospf-statistics-neighbor {
        tailf:actionpoint ncsproxy {
          tailf:internal;
        }
        description
          "Clear OSPF neighbor statistics per interface or neighbor id";
        input {
          container instance {
            description
              "Clear data from OSPF instance";
            leaf instance-identifier {
              description
                "OSPF process instance identifier";
              type string;
            }
          }
          container neighbor {
            leaf neighbor-id {
              description
                "Neighbor ID";
              type inet:ipv4-address;
            }
            leaf interface-name {
              description
                "Interface";
              type xr:Interface-name;
            }
          }
        }
      }
    }
  }
  augment "/ncs:devices/ncs:device-group/ncs:ned-id/ncs:rpc" {
    container rpc-clear-ospf-statistics-neighbor {
      tailf:ncs-device-type "netconf";
      tailf:display-when "/ncs:devices/ncs:device[ncs:name=current()/../../../ncs:member]/ncs:module[ncs:name='Cisco-IOS-XR-ipv4-ospf-act']";
      tailf:action clear-ospf-statistics-neighbor {
        tailf:actionpoint ncsproxy {
          tailf:internal;
        }
        description
          "Clear OSPF neighbor statistics per interface or neighbor id";
        input {
          container instance {
            description
              "Clear data from OSPF instance";
            leaf instance-identifier {
              description
                "OSPF process instance identifier";
              type string;
            }
          }
          container neighbor {
            leaf neighbor-id {
              description
                "Neighbor ID";
              type inet:ipv4-address;
            }
            leaf interface-name {
              description
                "Interface";
              type xr:Interface-name;
            }
          }
        }
      }
    }
  }
  augment "/ncs:devices/ncs:device/ncs:rpc" {
    container rpc-clear-ospf-statistics {
      tailf:ncs-device-type "netconf";
      tailf:display-when "not(../../ncs:module) or ../../ncs:module[ncs:name='Cisco-IOS-XR-ipv4-ospf-act']";
      tailf:action clear-ospf-statistics {
        tailf:actionpoint ncsproxy {
          tailf:internal;
        }
        description
          "Clear OSPF counters and statistics";
        input {
          container instance {
            description
              "Clear data from OSPF instance";
            leaf instance-identifier {
              description
                "OSPF process instance identifier";
              type string;
            }
          }
          leaf all {
            description
              "All OSPF counters and statistics";
            type empty;
          }
          leaf message-queue {
            description
              "Message-queue statistics";
            type empty;
          }
          leaf spf {
            description
              "SPF statistics";
            type empty;
          }
          leaf neighbor {
            description
              "Neighbor statistics per neighbor id";
            type empty;
          }
          leaf interface-name {
            description
              "OSPF interface statistics";
            type empty;
          }
        }
      }
    }
  }
  augment "/ncs:devices/ncs:device-group/ncs:ned-id/ncs:rpc" {
    container rpc-clear-ospf-statistics {
      tailf:ncs-device-type "netconf";
      tailf:display-when "/ncs:devices/ncs:device[ncs:name=current()/../../../ncs:member]/ncs:module[ncs:name='Cisco-IOS-XR-ipv4-ospf-act']";
      tailf:action clear-ospf-statistics {
        tailf:actionpoint ncsproxy {
          tailf:internal;
        }
        description
          "Clear OSPF counters and statistics";
        input {
          container instance {
            description
              "Clear data from OSPF instance";
            leaf instance-identifier {
              description
                "OSPF process instance identifier";
              type string;
            }
          }
          leaf all {
            description
              "All OSPF counters and statistics";
            type empty;
          }
          leaf message-queue {
            description
              "Message-queue statistics";
            type empty;
          }
          leaf spf {
            description
              "SPF statistics";
            type empty;
          }
          leaf neighbor {
            description
              "Neighbor statistics per neighbor id";
            type empty;
          }
          leaf interface-name {
            description
              "OSPF interface statistics";
            type empty;
          }
        }
      }
    }
  }
  augment "/ncs:devices/ncs:device/ncs:rpc" {
    container rpc-clear-ospf-redistribution {
      tailf:ncs-device-type "netconf";
      tailf:display-when "not(../../ncs:module) or ../../ncs:module[ncs:name='Cisco-IOS-XR-ipv4-ospf-act']";
      tailf:action clear-ospf-redistribution {
        tailf:actionpoint ncsproxy {
          tailf:internal;
        }
        description
          "Clear OSPF route redistribution";
        input {
          container instance {
            description
              "Clear data from OSPF instance";
            leaf instance-identifier {
              description
                "OSPF process instance identifier";
              type string;
            }
          }
          leaf redistribution {
            description
              "Clear OSPF route redistribution";
            mandatory true;
            type empty;
          }
        }
      }
    }
  }
  augment "/ncs:devices/ncs:device-group/ncs:ned-id/ncs:rpc" {
    container rpc-clear-ospf-redistribution {
      tailf:ncs-device-type "netconf";
      tailf:display-when "/ncs:devices/ncs:device[ncs:name=current()/../../../ncs:member]/ncs:module[ncs:name='Cisco-IOS-XR-ipv4-ospf-act']";
      tailf:action clear-ospf-redistribution {
        tailf:actionpoint ncsproxy {
          tailf:internal;
        }
        description
          "Clear OSPF route redistribution";
        input {
          container instance {
            description
              "Clear data from OSPF instance";
            leaf instance-identifier {
              description
                "OSPF process instance identifier";
              type string;
            }
          }
          leaf redistribution {
            description
              "Clear OSPF route redistribution";
            mandatory true;
            type empty;
          }
        }
      }
    }
  }
  augment "/ncs:devices/ncs:device/ncs:rpc" {
    container rpc-clear-ospf-routes {
      tailf:ncs-device-type "netconf";
      tailf:display-when "not(../../ncs:module) or ../../ncs:module[ncs:name='Cisco-IOS-XR-ipv4-ospf-act']";
      tailf:action clear-ospf-routes {
        tailf:actionpoint ncsproxy {
          tailf:internal;
        }
        description
          "Clear OSPF route table";
        input {
          container instance {
            description
              "Clear data from OSPF instance";
            leaf instance-identifier {
              description
                "OSPF process instance identifier";
              type string;
            }
          }
          leaf route {
            description
              "Clear OSPF route table";
            mandatory true;
            type empty;
          }
        }
      }
    }
  }
  augment "/ncs:devices/ncs:device-group/ncs:ned-id/ncs:rpc" {
    container rpc-clear-ospf-routes {
      tailf:ncs-device-type "netconf";
      tailf:display-when "/ncs:devices/ncs:device[ncs:name=current()/../../../ncs:member]/ncs:module[ncs:name='Cisco-IOS-XR-ipv4-ospf-act']";
      tailf:action clear-ospf-routes {
        tailf:actionpoint ncsproxy {
          tailf:internal;
        }
        description
          "Clear OSPF route table";
        input {
          container instance {
            description
              "Clear data from OSPF instance";
            leaf instance-identifier {
              description
                "OSPF process instance identifier";
              type string;
            }
          }
          leaf route {
            description
              "Clear OSPF route table";
            mandatory true;
            type empty;
          }
        }
      }
    }
  }
}
