module Cisco-IOS-XR-flashmib-cfg {
  // Generated by yanger -t ncs
  tailf:mount-id f5500-nc-1.0:f5500-nc-1.0;
  tailf:ncs-device-type "netconf";

  namespace "http://cisco.com/ns/yang/Cisco-IOS-XR-flashmib-cfg";
  prefix Cisco-IOS-XR-flashmib-cfg;

  import Cisco-IOS-XR-snmp-agent-cfg {
    prefix a1;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR flashmib package configuration.

     This YANG module augments the
       Cisco-IOS-XR-snmp-agent-cfg
     module with configuration data.

     Copyright (c) 2013-2018 by Cisco Systems, Inc.
     All rights reserved.";

  revision 2015-12-15 {
    description
      "Descriptions updated.";
  }
  revision 2015-11-09 {
    description
      "IOS XR 6.0 revision.";
  }

  augment "/ncs:devices/ncs:template/ncs:ned-id/ncs:config/a1:snmp/a1:notification" {
    container flash {
      description
        "CISCO-FLASH-MIB notification configuration";
      leaf insertion {
        type empty;
        description
          "Enable ciscoFlashDeviceInsertedNotif
           notification";
      }
      leaf removal {
        type empty;
        description
          "Enable ciscoFlashDeviceRemovedNotif
           notification";
      }
    }
    description
      "This augment extends the configuration data of
       'Cisco-IOS-XR-snmp-agent-cfg'";
  }
  augment "/ncs:devices/ncs:device/ncs:live-status/a1:snmp/a1:notification" {
    container flash {
      tailf:ncs-device-type "netconf";
      tailf:display-when "not(../../../../ncs:module) or ../../../../ncs:module[ncs:name='Cisco-IOS-XR-flashmib-cfg'] or (../../../../ncs:live-status-protocol[not(ncs:capability)]) or (../../../../ncs:live-status-protocol/ncs:capability/ncs:module[.='Cisco-IOS-XR-flashmib-cfg'])";
      description
        "CISCO-FLASH-MIB notification configuration";
      leaf insertion {
        type empty;
        description
          "Enable ciscoFlashDeviceInsertedNotif
           notification";
      }
      leaf removal {
        type empty;
        description
          "Enable ciscoFlashDeviceRemovedNotif
           notification";
      }
    }
    description
      "This augment extends the configuration data of
       'Cisco-IOS-XR-snmp-agent-cfg'";
  }
  augment "/ncs:devices/ncs:device/ncs:config/a1:snmp/a1:notification" {
    container flash {
      tailf:ncs-device-type "netconf";
      tailf:display-when "not(../../../../ncs:module) or ../../../../ncs:module[ncs:name='Cisco-IOS-XR-flashmib-cfg']";
      description
        "CISCO-FLASH-MIB notification configuration";
      leaf insertion {
        type empty;
        description
          "Enable ciscoFlashDeviceInsertedNotif
           notification";
      }
      leaf removal {
        type empty;
        description
          "Enable ciscoFlashDeviceRemovedNotif
           notification";
      }
    }
    description
      "This augment extends the configuration data of
       'Cisco-IOS-XR-snmp-agent-cfg'";
  }
}
