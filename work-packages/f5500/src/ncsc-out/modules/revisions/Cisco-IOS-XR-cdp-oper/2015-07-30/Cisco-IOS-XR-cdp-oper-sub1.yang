submodule Cisco-IOS-XR-cdp-oper-sub1 {
  // Generated by yanger -t ncs
  tailf:mount-id f5500-nc-1.0:f5500-nc-1.0;

  belongs-to Cisco-IOS-XR-cdp-oper {
    prefix Cisco-IOS-XR-cdp-oper-sub1;
  }

  import ietf-inet-types {
    prefix inet;
  }
  import ietf-yang-types {
    prefix yang;
  }
  import Cisco-IOS-XR-types {
    prefix xr;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR cdp package operational data.

     Copyright (c) 2013-2018 by Cisco Systems, Inc.
     All rights reserved.";

  revision 2015-07-30 {
    description
      "Revison descritption string.";
  }
  revision 2015-01-07 {
    description
      "IOS XR 5.3.1 revision.";
  }

  typedef Cdp-l3-addr-protocol {
    type enumeration {
      enum "ipv4" {
        description
          "IPv4";
      }
      enum "ipv6" {
        description
          "IPv6";
      }
    }
    description
      "Cdp l3 addr protocol";
  }

  typedef In6-addr {
    type inet:ipv6-address;
    description
      "In6 addr";
  }

  typedef Cdp-duplex {
    type enumeration {
      enum "cdp-dplx-none" {
        value 0;
        description
          "cdp dplx none";
      }
      enum "cdp-dplx-half" {
        value 1;
        description
          "cdp dplx half";
      }
      enum "cdp-dplx-full" {
        value 2;
        description
          "cdp dplx full";
      }
    }
    description
      "Cdp duplex";
  }

  typedef Im-state {
    type uint32;
    description
      "Im state";
  }

  grouping ncs_template_CDP-INTERFACE {
    description
      "Information about an interface that CDP is
       running on";
    leaf interface-handle {
      type string;
      description
        "Interface";
    }
    leaf basecaps-state {
      type string;
      description
        "Interface basecaps state";
    }
    leaf cdp-protocol-state {
      type string;
      description
        "CDP protocol state";
    }
    leaf interface-encaps {
      type string;
      description
        "Interface encapsulation";
    }
  }

  grouping ncs_template_CDP-STATS {
    description
      "CDP statistics";
    leaf received-packets {
      type string;
      description
        "Received packets";
    }
    leaf received-packets-v1 {
      type string;
      description
        "Received v1 packets";
    }
    leaf received-packets-v2 {
      type string;
      description
        "Received v2 packets";
    }
    leaf transmitted-packets {
      type string;
      description
        "Transmitted packets";
    }
    leaf transmitted-packets-v1 {
      type string;
      description
        "Transmitted v1 packets";
    }
    leaf transmitted-packets-v2 {
      type string;
      description
        "Transmitted v2 packets";
    }
    leaf header-errors {
      type string;
      description
        "Header syntax errors";
    }
    leaf checksum-errors {
      type string;
      description
        "Checksum errors";
    }
    leaf encapsulation-errors {
      type string;
      description
        "Transmission errors";
    }
    leaf bad-packet-errors {
      type string;
      description
        "Bad packet received and dropped";
    }
    leaf out-of-memory-errors {
      type string;
      description
        "Out-of-memory conditions";
    }
    leaf truncated-packet-errors {
      type string;
      description
        "Truncated messages";
    }
    leaf header-version-errors {
      type string;
      description
        "Can't handle receive version";
    }
    leaf open-file-errors {
      type string;
      description
        "Cannot open file";
    }
  }

  grouping ncs_template_CDP-PROTOCOL-HELLO-ENTRY {
    description
      "CDP Protocol Hello entry";
    list cdp-prot-hello-entry {
      // NCS patched for predictable order
      ordered-by user;
      description
        "Next protocol hello entry in list";
      leaf hello-message {
        type string;
        description
          "Protocol Hello msg";
      }
    }
  }

  grouping ncs_template_CDP-L3-ADDR {
    description
      "CDP L3 ADDR";
    leaf address-type {
      type string;
      description
        "AddressType";
    }
    leaf ipv4-address {
      // NCS drop when statement
      type string;
      description
        "IPv4 address";
    }
    leaf ipv6-address {
      // NCS drop when statement
      type string;
      description
        "IPv6 address";
    }
  }

  grouping ncs_template_CDP-ADDRESS-ENTRY {
    description
      "CDP Address entry";
    list cdp-addr-entry {
      // NCS patched for predictable order
      ordered-by user;
      description
        "Next address entry in list";
      container address {
        description
          "Network layer address";
        uses ncs_template_CDP-L3-ADDR;
      }
    }
  }

  grouping ncs_template_CDP-NEIGHBOR-ENTRY-DETAILS {
    description
      "Detailed neighbor info";
    container network-addresses {
      description
        "List of network addresses ";
      uses ncs_template_CDP-ADDRESS-ENTRY;
    }
    container protocol-hello-list {
      description
        "List of protocol hello entries";
      uses ncs_template_CDP-PROTOCOL-HELLO-ENTRY;
    }
    leaf version {
      type string;
      description
        "Version TLV";
    }
    leaf vtp-domain {
      type string;
      description
        "VTP domain";
    }
    leaf native-vlan {
      type string;
      description
        "Native VLAN";
    }
    leaf duplex {
      type string;
      description
        "Duplex setting";
    }
    leaf system-name {
      type string;
      description
        "SysName";
    }
  }

  grouping ncs_template_CDP-NEIGHBOR {
    description
      "CDP neighbor info";
    list cdp-neighbor {
      // NCS patched for predictable order
      ordered-by user;
      description
        "Next neighbor in the list";
      container detail {
        description
          "Detailed neighbor info";
        uses ncs_template_CDP-NEIGHBOR-ENTRY-DETAILS;
      }
      leaf receiving-interface-name {
        type string;
        description
          "Interface the neighbor entry was received on ";
      }
      leaf device-id {
        type string;
        description
          "Device identifier";
      }
      leaf port-id {
        type string;
        description
          "Outgoing port identifier";
      }
      leaf header-version {
        type string;
        description
          "Version number";
      }
      leaf hold-time {
        type string;
        description
          "Remaining hold time";
      }
      leaf capabilities {
        type string;
        description
          "Capabilities";
      }
      leaf platform {
        type string;
        description
          "Platform type";
      }
    }
  }

  grouping ncs_rpc_notif_CDP-INTERFACE {
    description
      "Information about an interface that CDP is
       running on";
    leaf interface-handle {
      type xr:Interface-name;
      description
        "Interface";
    }
    leaf basecaps-state {
      type Im-state;
      description
        "Interface basecaps state";
    }
    leaf cdp-protocol-state {
      type Im-state;
      description
        "CDP protocol state";
    }
    leaf interface-encaps {
      type string;
      description
        "Interface encapsulation";
    }
  }

  grouping ncs_rpc_notif_CDP-STATS {
    description
      "CDP statistics";
    leaf received-packets {
      type uint32;
      description
        "Received packets";
    }
    leaf received-packets-v1 {
      type uint32;
      description
        "Received v1 packets";
    }
    leaf received-packets-v2 {
      type uint32;
      description
        "Received v2 packets";
    }
    leaf transmitted-packets {
      type uint32;
      description
        "Transmitted packets";
    }
    leaf transmitted-packets-v1 {
      type uint32;
      description
        "Transmitted v1 packets";
    }
    leaf transmitted-packets-v2 {
      type uint32;
      description
        "Transmitted v2 packets";
    }
    leaf header-errors {
      type uint32;
      description
        "Header syntax errors";
    }
    leaf checksum-errors {
      type uint32;
      description
        "Checksum errors";
    }
    leaf encapsulation-errors {
      type uint32;
      description
        "Transmission errors";
    }
    leaf bad-packet-errors {
      type uint32;
      description
        "Bad packet received and dropped";
    }
    leaf out-of-memory-errors {
      type uint32;
      description
        "Out-of-memory conditions";
    }
    leaf truncated-packet-errors {
      type uint32;
      description
        "Truncated messages";
    }
    leaf header-version-errors {
      type uint32;
      description
        "Can't handle receive version";
    }
    leaf open-file-errors {
      type uint32;
      description
        "Cannot open file";
    }
  }

  grouping ncs_rpc_notif_CDP-PROTOCOL-HELLO-ENTRY {
    description
      "CDP Protocol Hello entry";
    list cdp-prot-hello-entry {
      description
        "Next protocol hello entry in list";
      leaf hello-message {
        type yang:hex-string;
        description
          "Protocol Hello msg";
      }
    }
  }

  grouping ncs_rpc_notif_CDP-L3-ADDR {
    description
      "CDP L3 ADDR";
    leaf address-type {
      type Cdp-l3-addr-protocol;
      description
        "AddressType";
    }
    leaf ipv4-address {
      when "../address-type = 'ipv4'" {
        tailf:xpath-root 3;
        description
          "../AddressType = 'IPv4'";
      }
      type inet:ipv4-address;
      description
        "IPv4 address";
    }
    leaf ipv6-address {
      when "../address-type = 'ipv6'" {
        tailf:xpath-root 3;
        description
          "../AddressType = 'IPv6'";
      }
      type In6-addr;
      description
        "IPv6 address";
    }
  }

  grouping ncs_rpc_notif_CDP-ADDRESS-ENTRY {
    description
      "CDP Address entry";
    list cdp-addr-entry {
      description
        "Next address entry in list";
      container address {
        description
          "Network layer address";
        uses ncs_rpc_notif_CDP-L3-ADDR;
      }
    }
  }

  grouping ncs_rpc_notif_CDP-NEIGHBOR-ENTRY-DETAILS {
    description
      "Detailed neighbor info";
    container network-addresses {
      description
        "List of network addresses ";
      uses ncs_rpc_notif_CDP-ADDRESS-ENTRY;
    }
    container protocol-hello-list {
      description
        "List of protocol hello entries";
      uses ncs_rpc_notif_CDP-PROTOCOL-HELLO-ENTRY;
    }
    leaf version {
      type string;
      description
        "Version TLV";
    }
    leaf vtp-domain {
      type string;
      description
        "VTP domain";
    }
    leaf native-vlan {
      type uint32;
      description
        "Native VLAN";
    }
    leaf duplex {
      type Cdp-duplex;
      description
        "Duplex setting";
    }
    leaf system-name {
      type string;
      description
        "SysName";
    }
  }

  grouping ncs_rpc_notif_CDP-NEIGHBOR {
    description
      "CDP neighbor info";
    list cdp-neighbor {
      description
        "Next neighbor in the list";
      container detail {
        description
          "Detailed neighbor info";
        uses ncs_rpc_notif_CDP-NEIGHBOR-ENTRY-DETAILS;
      }
      leaf receiving-interface-name {
        type xr:Interface-name;
        description
          "Interface the neighbor entry was received on ";
      }
      leaf device-id {
        type string;
        description
          "Device identifier";
      }
      leaf port-id {
        type string;
        description
          "Outgoing port identifier";
      }
      leaf header-version {
        type uint8;
        description
          "Version number";
      }
      leaf hold-time {
        type uint16;
        description
          "Remaining hold time";
      }
      leaf capabilities {
        type string;
        description
          "Capabilities";
      }
      leaf platform {
        type string;
        description
          "Platform type";
      }
    }
  }

  grouping live_ncs_CDP-INTERFACE {
    description
      "Information about an interface that CDP is
       running on";
    leaf interface-handle {
      type xr:Interface-name;
      description
        "Interface";
    }
    leaf basecaps-state {
      type Im-state;
      description
        "Interface basecaps state";
    }
    leaf cdp-protocol-state {
      type Im-state;
      description
        "CDP protocol state";
    }
    leaf interface-encaps {
      type string;
      description
        "Interface encapsulation";
    }
  }

  grouping live_ncs_CDP-STATS {
    description
      "CDP statistics";
    leaf received-packets {
      type uint32;
      description
        "Received packets";
    }
    leaf received-packets-v1 {
      type uint32;
      description
        "Received v1 packets";
    }
    leaf received-packets-v2 {
      type uint32;
      description
        "Received v2 packets";
    }
    leaf transmitted-packets {
      type uint32;
      description
        "Transmitted packets";
    }
    leaf transmitted-packets-v1 {
      type uint32;
      description
        "Transmitted v1 packets";
    }
    leaf transmitted-packets-v2 {
      type uint32;
      description
        "Transmitted v2 packets";
    }
    leaf header-errors {
      type uint32;
      description
        "Header syntax errors";
    }
    leaf checksum-errors {
      type uint32;
      description
        "Checksum errors";
    }
    leaf encapsulation-errors {
      type uint32;
      description
        "Transmission errors";
    }
    leaf bad-packet-errors {
      type uint32;
      description
        "Bad packet received and dropped";
    }
    leaf out-of-memory-errors {
      type uint32;
      description
        "Out-of-memory conditions";
    }
    leaf truncated-packet-errors {
      type uint32;
      description
        "Truncated messages";
    }
    leaf header-version-errors {
      type uint32;
      description
        "Can't handle receive version";
    }
    leaf open-file-errors {
      type uint32;
      description
        "Cannot open file";
    }
  }

  grouping live_ncs_CDP-PROTOCOL-HELLO-ENTRY {
    description
      "CDP Protocol Hello entry";
    list cdp-prot-hello-entry {
      description
        "Next protocol hello entry in list";
      leaf hello-message {
        type yang:hex-string;
        description
          "Protocol Hello msg";
      }
    }
  }

  grouping live_ncs_CDP-L3-ADDR {
    description
      "CDP L3 ADDR";
    leaf address-type {
      type Cdp-l3-addr-protocol;
      description
        "AddressType";
    }
    leaf ipv4-address {
      // NCS drop when statement
      type inet:ipv4-address;
      description
        "IPv4 address";
    }
    leaf ipv6-address {
      // NCS drop when statement
      type In6-addr;
      description
        "IPv6 address";
    }
  }

  grouping live_ncs_CDP-ADDRESS-ENTRY {
    description
      "CDP Address entry";
    list cdp-addr-entry {
      description
        "Next address entry in list";
      container address {
        description
          "Network layer address";
        uses live_ncs_CDP-L3-ADDR;
      }
    }
  }

  grouping live_ncs_CDP-NEIGHBOR-ENTRY-DETAILS {
    description
      "Detailed neighbor info";
    container network-addresses {
      description
        "List of network addresses ";
      uses live_ncs_CDP-ADDRESS-ENTRY;
    }
    container protocol-hello-list {
      description
        "List of protocol hello entries";
      uses live_ncs_CDP-PROTOCOL-HELLO-ENTRY;
    }
    leaf version {
      type string;
      description
        "Version TLV";
    }
    leaf vtp-domain {
      type string;
      description
        "VTP domain";
    }
    leaf native-vlan {
      type uint32;
      description
        "Native VLAN";
    }
    leaf duplex {
      type Cdp-duplex;
      description
        "Duplex setting";
    }
    leaf system-name {
      type string;
      description
        "SysName";
    }
  }

  grouping live_ncs_CDP-NEIGHBOR {
    description
      "CDP neighbor info";
    list cdp-neighbor {
      description
        "Next neighbor in the list";
      container detail {
        description
          "Detailed neighbor info";
        uses live_ncs_CDP-NEIGHBOR-ENTRY-DETAILS;
      }
      leaf receiving-interface-name {
        type xr:Interface-name;
        description
          "Interface the neighbor entry was received on ";
      }
      leaf device-id {
        type string;
        description
          "Device identifier";
      }
      leaf port-id {
        type string;
        description
          "Outgoing port identifier";
      }
      leaf header-version {
        type uint8;
        description
          "Version number";
      }
      leaf hold-time {
        type uint16;
        description
          "Remaining hold time";
      }
      leaf capabilities {
        type string;
        description
          "Capabilities";
      }
      leaf platform {
        type string;
        description
          "Platform type";
      }
    }
  }

  grouping CDP-INTERFACE {
    description
      "Information about an interface that CDP is
       running on";
    leaf interface-handle {
      type xr:Interface-name;
      description
        "Interface";
    }
    leaf basecaps-state {
      type Im-state;
      description
        "Interface basecaps state";
    }
    leaf cdp-protocol-state {
      type Im-state;
      description
        "CDP protocol state";
    }
    leaf interface-encaps {
      type string;
      description
        "Interface encapsulation";
    }
  }

  grouping CDP-STATS {
    description
      "CDP statistics";
    leaf received-packets {
      type uint32;
      description
        "Received packets";
    }
    leaf received-packets-v1 {
      type uint32;
      description
        "Received v1 packets";
    }
    leaf received-packets-v2 {
      type uint32;
      description
        "Received v2 packets";
    }
    leaf transmitted-packets {
      type uint32;
      description
        "Transmitted packets";
    }
    leaf transmitted-packets-v1 {
      type uint32;
      description
        "Transmitted v1 packets";
    }
    leaf transmitted-packets-v2 {
      type uint32;
      description
        "Transmitted v2 packets";
    }
    leaf header-errors {
      type uint32;
      description
        "Header syntax errors";
    }
    leaf checksum-errors {
      type uint32;
      description
        "Checksum errors";
    }
    leaf encapsulation-errors {
      type uint32;
      description
        "Transmission errors";
    }
    leaf bad-packet-errors {
      type uint32;
      description
        "Bad packet received and dropped";
    }
    leaf out-of-memory-errors {
      type uint32;
      description
        "Out-of-memory conditions";
    }
    leaf truncated-packet-errors {
      type uint32;
      description
        "Truncated messages";
    }
    leaf header-version-errors {
      type uint32;
      description
        "Can't handle receive version";
    }
    leaf open-file-errors {
      type uint32;
      description
        "Cannot open file";
    }
  }

  grouping CDP-PROTOCOL-HELLO-ENTRY {
    description
      "CDP Protocol Hello entry";
    list cdp-prot-hello-entry {
      description
        "Next protocol hello entry in list";
      leaf hello-message {
        type yang:hex-string;
        description
          "Protocol Hello msg";
      }
    }
  }

  grouping CDP-L3-ADDR {
    description
      "CDP L3 ADDR";
    leaf address-type {
      type Cdp-l3-addr-protocol;
      description
        "AddressType";
    }
    leaf ipv4-address {
      when "../address-type = 'ipv4'" {
        tailf:xpath-root 3;
        description
          "../AddressType = 'IPv4'";
      }
      type inet:ipv4-address;
      description
        "IPv4 address";
    }
    leaf ipv6-address {
      when "../address-type = 'ipv6'" {
        tailf:xpath-root 3;
        description
          "../AddressType = 'IPv6'";
      }
      type In6-addr;
      description
        "IPv6 address";
    }
  }

  grouping CDP-ADDRESS-ENTRY {
    description
      "CDP Address entry";
    list cdp-addr-entry {
      description
        "Next address entry in list";
      container address {
        description
          "Network layer address";
        uses CDP-L3-ADDR;
      }
    }
  }

  grouping CDP-NEIGHBOR-ENTRY-DETAILS {
    description
      "Detailed neighbor info";
    container network-addresses {
      description
        "List of network addresses ";
      uses CDP-ADDRESS-ENTRY;
    }
    container protocol-hello-list {
      description
        "List of protocol hello entries";
      uses CDP-PROTOCOL-HELLO-ENTRY;
    }
    leaf version {
      type string;
      description
        "Version TLV";
    }
    leaf vtp-domain {
      type string;
      description
        "VTP domain";
    }
    leaf native-vlan {
      type uint32;
      description
        "Native VLAN";
    }
    leaf duplex {
      type Cdp-duplex;
      description
        "Duplex setting";
    }
    leaf system-name {
      type string;
      description
        "SysName";
    }
  }

  grouping CDP-NEIGHBOR {
    description
      "CDP neighbor info";
    list cdp-neighbor {
      description
        "Next neighbor in the list";
      container detail {
        description
          "Detailed neighbor info";
        uses CDP-NEIGHBOR-ENTRY-DETAILS;
      }
      leaf receiving-interface-name {
        type xr:Interface-name;
        description
          "Interface the neighbor entry was received on ";
      }
      leaf device-id {
        type string;
        description
          "Device identifier";
      }
      leaf port-id {
        type string;
        description
          "Outgoing port identifier";
      }
      leaf header-version {
        type uint8;
        description
          "Version number";
      }
      leaf hold-time {
        type uint16;
        description
          "Remaining hold time";
      }
      leaf capabilities {
        type string;
        description
          "Capabilities";
      }
      leaf platform {
        type string;
        description
          "Platform type";
      }
    }
  }
}
