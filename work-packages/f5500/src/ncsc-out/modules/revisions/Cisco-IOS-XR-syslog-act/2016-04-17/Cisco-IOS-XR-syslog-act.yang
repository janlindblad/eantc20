module Cisco-IOS-XR-syslog-act {
  // Generated by yanger -t ncs
  tailf:mount-id f5500-nc-1.0:f5500-nc-1.0;
  tailf:ncs-device-type "netconf";

  namespace "http://cisco.com/ns/yang/Cisco-IOS-XR-syslog-act";
  prefix Cisco-IOS-XR-syslog-act;

  import ietf-syslog-types {
    prefix log;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     This module contains definitions
     for the following management objects:
     syslog: Global Syslog messaging data

     Copyright (c) 2016 by Cisco Systems, Inc.
     All rights reserved.";

  revision 2016-04-17 {
    description
      "IOS XR 6.1.1 revision.";
  }

  augment "/ncs:devices/ncs:device/ncs:rpc" {
    container rpc-logmsg {
      tailf:ncs-device-type "netconf";
      tailf:display-when "not(../../ncs:module) or ../../ncs:module[ncs:name='Cisco-IOS-XR-syslog-act']";
      tailf:action logmsg {
        tailf:actionpoint ncsproxy {
          tailf:internal;
        }
        input {
          leaf severity {
            type log:severity;
            description
              "Set serverity level";
            mandatory true;
          }
          leaf message {
            type string;
            description
              "Message body.";
            mandatory true;
          }
        }
      }
    }
  }
  augment "/ncs:devices/ncs:device-group/ncs:ned-id/ncs:rpc" {
    container rpc-logmsg {
      tailf:ncs-device-type "netconf";
      tailf:display-when "/ncs:devices/ncs:device[ncs:name=current()/../../../ncs:member]/ncs:module[ncs:name='Cisco-IOS-XR-syslog-act']";
      tailf:action logmsg {
        tailf:actionpoint ncsproxy {
          tailf:internal;
        }
        input {
          leaf severity {
            type log:severity;
            description
              "Set serverity level";
            mandatory true;
          }
          leaf message {
            type string;
            description
              "Message body.";
            mandatory true;
          }
        }
      }
    }
  }
}
