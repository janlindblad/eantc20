submodule Cisco-IOS-XR-es-acl-oper-sub1 {
  // Generated by yanger -t ncs
  tailf:mount-id f5500-nc-1.0:f5500-nc-1.0;

  belongs-to Cisco-IOS-XR-es-acl-oper {
    prefix Cisco-IOS-XR-es-acl-oper-sub1;
  }

  import Cisco-IOS-XR-types {
    prefix xr;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR es-acl package operational data.

     Copyright (c) 2013-2018 by Cisco Systems, Inc.
     All rights reserved.";

  revision 2017-05-01 {
    description
      "Fixing backward compatibility error in module.";
  }
  revision 2015-11-09 {
    description
      "IOS XR 6.0 revision.";
  }

  typedef Acl-ace {
    type Acl-ace1;
    description
      "ACE Types";
  }

  typedef Acl-ace1 {
    type enumeration {
      enum "normal" {
        description
          "This is Normal ACE";
      }
      enum "remark" {
        description
          "This is Remark ACE";
      }
      enum "abf" {
        description
          "This is ABF ACE";
      }
    }
    description
      "ACE Types";
  }

  typedef Acl-action {
    type enumeration {
      enum "deny" {
        value 0;
        description
          "Deny";
      }
      enum "permit" {
        value 1;
        description
          "Permit";
      }
      enum "encrypt" {
        value 2;
        description
          "Encrypt";
      }
      enum "bypass" {
        value 3;
        description
          "Bypass";
      }
      enum "fallthrough" {
        value 4;
        description
          "Fallthrough";
      }
      enum "invalid" {
        value 5;
        description
          "Invalid";
      }
    }
    description
      "Acl action";
  }

  grouping ncs_template_ES-ACL-EDM-ACE {
    description
      "ACLE bag";
    leaf ace-type {
      type string;
      description
        "ACE type (acl, remark)";
    }
    leaf ace-sequence-number {
      type string;
      description
        "ACE sequence number";
    }
    leaf hits {
      type string;
      description
        "ACE hit number";
    }
    leaf grant {
      type string;
      description
        "Grant value permit/deny ";
    }
    leaf source-address {
      type string;
      description
        "Source MAC address";
    }
    leaf source-wild-card-bits {
      type string;
      description
        "Source wild card bits";
    }
    leaf destination-address {
      type string;
      description
        "Destination MAC address";
    }
    leaf destination-wild-card-bits {
      type string;
      description
        "Destination wild card bits";
    }
    leaf ether-type-number {
      type string;
      description
        "Ethernet type Number";
    }
    leaf vlan1 {
      type string;
      description
        "VLAN ID/range lower limit";
    }
    leaf vlan2 {
      type string;
      description
        "VLAN ID range higher limit";
    }
    leaf cos {
      type string;
      description
        "COS value";
    }
    leaf dei {
      type string;
      description
        "DEI bit";
    }
    leaf inner-header-vlan1 {
      type string;
      description
        "Inner header VLAN ID/range lower limit";
    }
    leaf inner-header-vlan2 {
      type string;
      description
        "Inner header VLAN ID range higher limit";
    }
    leaf inner-header-cos {
      type string;
      description
        "Inner header COS value";
    }
    leaf inner-header-dei {
      type string;
      description
        "Inner header DEI bit";
    }
    leaf capture {
      type string;
      description
        "Capture option, TRUE if enabled";
    }
    leaf log-option {
      type string;
      description
        "Log option";
    }
    leaf remark {
      type string;
      description
        "Remark string";
    }
    leaf acl-name {
      type string;
      description
        "Acl Name";
    }
    leaf sequence-string {
      type string;
      description
        "Sequence Sring";
    }
  }

  grouping ncs_template_ES-ACL-EDM-OOR-DETAIL {
    description
      "Oor deatil config BAG";
    leaf current-configured-ac-ls {
      type string;
      description
        "Current configured acls";
    }
    leaf current-configured-ac-es {
      type string;
      description
        "Current configured aces";
    }
    leaf maximum-configurable-ac-ls {
      type string;
      description
        "max configurable acls";
    }
    leaf maximum-configurable-ac-es {
      type string;
      description
        "max configurable aces";
    }
  }

  grouping ncs_rpc_notif_ES-ACL-EDM-ACE {
    description
      "ACLE bag";
    leaf ace-type {
      type Acl-ace;
      description
        "ACE type (acl, remark)";
    }
    leaf ace-sequence-number {
      type uint32;
      description
        "ACE sequence number";
    }
    leaf hits {
      type uint64;
      description
        "ACE hit number";
    }
    leaf grant {
      type Acl-action;
      description
        "Grant value permit/deny ";
    }
    leaf source-address {
      type xr:Osi-system-id;
      description
        "Source MAC address";
    }
    leaf source-wild-card-bits {
      type xr:Osi-system-id;
      description
        "Source wild card bits";
    }
    leaf destination-address {
      type xr:Osi-system-id;
      description
        "Destination MAC address";
    }
    leaf destination-wild-card-bits {
      type xr:Osi-system-id;
      description
        "Destination wild card bits";
    }
    leaf ether-type-number {
      type uint16;
      description
        "Ethernet type Number";
    }
    leaf vlan1 {
      type uint16;
      description
        "VLAN ID/range lower limit";
    }
    leaf vlan2 {
      type uint16;
      description
        "VLAN ID range higher limit";
    }
    leaf cos {
      type uint8;
      description
        "COS value";
    }
    leaf dei {
      type uint8;
      description
        "DEI bit";
    }
    leaf inner-header-vlan1 {
      type uint16;
      description
        "Inner header VLAN ID/range lower limit";
    }
    leaf inner-header-vlan2 {
      type uint16;
      description
        "Inner header VLAN ID range higher limit";
    }
    leaf inner-header-cos {
      type uint8;
      description
        "Inner header COS value";
    }
    leaf inner-header-dei {
      type uint8;
      description
        "Inner header DEI bit";
    }
    leaf capture {
      type boolean;
      description
        "Capture option, TRUE if enabled";
    }
    leaf log-option {
      type uint8;
      description
        "Log option";
    }
    leaf remark {
      type string;
      description
        "Remark string";
    }
    leaf acl-name {
      type string;
      description
        "Acl Name";
    }
    leaf sequence-string {
      type string;
      description
        "Sequence Sring";
    }
  }

  grouping ncs_rpc_notif_ES-ACL-EDM-OOR-DETAIL {
    description
      "Oor deatil config BAG";
    leaf current-configured-ac-ls {
      type uint32;
      description
        "Current configured acls";
    }
    leaf current-configured-ac-es {
      type uint32;
      description
        "Current configured aces";
    }
    leaf maximum-configurable-ac-ls {
      type uint32;
      description
        "max configurable acls";
    }
    leaf maximum-configurable-ac-es {
      type uint32;
      description
        "max configurable aces";
    }
  }

  grouping live_ncs_ES-ACL-EDM-ACE {
    description
      "ACLE bag";
    leaf ace-type {
      type Acl-ace;
      description
        "ACE type (acl, remark)";
    }
    leaf ace-sequence-number {
      type uint32;
      description
        "ACE sequence number";
    }
    leaf hits {
      type uint64;
      description
        "ACE hit number";
    }
    leaf grant {
      type Acl-action;
      description
        "Grant value permit/deny ";
    }
    leaf source-address {
      type xr:Osi-system-id;
      description
        "Source MAC address";
    }
    leaf source-wild-card-bits {
      type xr:Osi-system-id;
      description
        "Source wild card bits";
    }
    leaf destination-address {
      type xr:Osi-system-id;
      description
        "Destination MAC address";
    }
    leaf destination-wild-card-bits {
      type xr:Osi-system-id;
      description
        "Destination wild card bits";
    }
    leaf ether-type-number {
      type uint16;
      description
        "Ethernet type Number";
    }
    leaf vlan1 {
      type uint16;
      description
        "VLAN ID/range lower limit";
    }
    leaf vlan2 {
      type uint16;
      description
        "VLAN ID range higher limit";
    }
    leaf cos {
      type uint8;
      description
        "COS value";
    }
    leaf dei {
      type uint8;
      description
        "DEI bit";
    }
    leaf inner-header-vlan1 {
      type uint16;
      description
        "Inner header VLAN ID/range lower limit";
    }
    leaf inner-header-vlan2 {
      type uint16;
      description
        "Inner header VLAN ID range higher limit";
    }
    leaf inner-header-cos {
      type uint8;
      description
        "Inner header COS value";
    }
    leaf inner-header-dei {
      type uint8;
      description
        "Inner header DEI bit";
    }
    leaf capture {
      type boolean;
      description
        "Capture option, TRUE if enabled";
    }
    leaf log-option {
      type uint8;
      description
        "Log option";
    }
    leaf remark {
      type string;
      description
        "Remark string";
    }
    leaf acl-name {
      type string;
      description
        "Acl Name";
    }
    leaf sequence-string {
      type string;
      description
        "Sequence Sring";
    }
  }

  grouping live_ncs_ES-ACL-EDM-OOR-DETAIL {
    description
      "Oor deatil config BAG";
    leaf current-configured-ac-ls {
      type uint32;
      description
        "Current configured acls";
    }
    leaf current-configured-ac-es {
      type uint32;
      description
        "Current configured aces";
    }
    leaf maximum-configurable-ac-ls {
      type uint32;
      description
        "max configurable acls";
    }
    leaf maximum-configurable-ac-es {
      type uint32;
      description
        "max configurable aces";
    }
  }

  grouping ES-ACL-EDM-ACE {
    description
      "ACLE bag";
    leaf ace-type {
      type Acl-ace;
      description
        "ACE type (acl, remark)";
    }
    leaf ace-sequence-number {
      type uint32;
      description
        "ACE sequence number";
    }
    leaf hits {
      type uint64;
      description
        "ACE hit number";
    }
    leaf grant {
      type Acl-action;
      description
        "Grant value permit/deny ";
    }
    leaf source-address {
      type xr:Osi-system-id;
      description
        "Source MAC address";
    }
    leaf source-wild-card-bits {
      type xr:Osi-system-id;
      description
        "Source wild card bits";
    }
    leaf destination-address {
      type xr:Osi-system-id;
      description
        "Destination MAC address";
    }
    leaf destination-wild-card-bits {
      type xr:Osi-system-id;
      description
        "Destination wild card bits";
    }
    leaf ether-type-number {
      type uint16;
      description
        "Ethernet type Number";
    }
    leaf vlan1 {
      type uint16;
      description
        "VLAN ID/range lower limit";
    }
    leaf vlan2 {
      type uint16;
      description
        "VLAN ID range higher limit";
    }
    leaf cos {
      type uint8;
      description
        "COS value";
    }
    leaf dei {
      type uint8;
      description
        "DEI bit";
    }
    leaf inner-header-vlan1 {
      type uint16;
      description
        "Inner header VLAN ID/range lower limit";
    }
    leaf inner-header-vlan2 {
      type uint16;
      description
        "Inner header VLAN ID range higher limit";
    }
    leaf inner-header-cos {
      type uint8;
      description
        "Inner header COS value";
    }
    leaf inner-header-dei {
      type uint8;
      description
        "Inner header DEI bit";
    }
    leaf capture {
      type boolean;
      description
        "Capture option, TRUE if enabled";
    }
    leaf log-option {
      type uint8;
      description
        "Log option";
    }
    leaf remark {
      type string;
      description
        "Remark string";
    }
    leaf acl-name {
      type string;
      description
        "Acl Name";
    }
    leaf sequence-string {
      type string;
      description
        "Sequence Sring";
    }
  }

  grouping ES-ACL-EDM-OOR-DETAIL {
    description
      "Oor deatil config BAG";
    leaf current-configured-ac-ls {
      type uint32;
      description
        "Current configured acls";
    }
    leaf current-configured-ac-es {
      type uint32;
      description
        "Current configured aces";
    }
    leaf maximum-configurable-ac-ls {
      type uint32;
      description
        "max configurable acls";
    }
    leaf maximum-configurable-ac-es {
      type uint32;
      description
        "max configurable aces";
    }
  }
}
