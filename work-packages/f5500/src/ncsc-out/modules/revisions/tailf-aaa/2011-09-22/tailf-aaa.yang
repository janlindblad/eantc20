module tailf-aaa {
  // Generated by yanger -t ncs
  tailf:mount-id f5500-nc-1.0:f5500-nc-1.0;
  tailf:ncs-device-type "netconf";

  namespace "http://tail-f.com/ns/aaa/1.1";
  prefix aaa;

  import tailf-common {
    prefix tailf;
  }
  import "f5500-nc-1.0" {
    prefix "f5500-nc-1.0";
  }
  import tailf-ncs {
    prefix ncs;
  }

  organization
    "Tail-f Systems";
  contact
    "Cisco Systems, Inc.
     Customer Service

     Postal: 170 West Tasman Drive
     San Jose, CA 95134

     Tel: +1 800 553-NETS

     E-mail: cs-yang@cisco.com";
  description
    "This module contains definitions
     for the Calvados model objects.

     This module defines the Tail-f AAA data model.

     Copyright (c) 2012-2018 by Cisco Systems, Inc.
     All rights reserved.";

  revision 2011-09-22 {
    description
      "Released as part of ConfD-3.7.";
  }

  typedef builtinModes {
    type enumeration {
      enum "exec";
      enum "configure";
    }
  }

  typedef modeStr {
    type union {
      type string;
      type builtinModes;
    }
  }

  typedef levelInt {
    type int32 {
      range "0 .. 15";
    }
  }

  typedef passwdStr {
    type tailf:md5-digest-string;
  }

  typedef Action {
    type enumeration {
      enum "accept";
      enum "reject";
      enum "accept_log";
    }
  }

  typedef cmdOperationType {
    type enumeration {
      enum "r";
      enum "rx";
      enum "x";
    }
  }

  typedef dataOperationType {
    type enumeration {
      enum "r";
      enum "rx";
      enum "x";
      enum "rw";
      enum "rwx";
      enum "wx";
      enum "w";
      enum "c";
      enum "cr";
      enum "cu";
      enum "cd";
      enum "cx";
      enum "cru";
      enum "crd";
      enum "crx";
      enum "cud";
      enum "cux";
      enum "cdx";
      enum "crud";
      enum "crux";
      enum "crdx";
      enum "cudx";
      enum "crudx";
      enum "ru";
      enum "rd";
      enum "rud";
      enum "rux";
      enum "rdx";
      enum "u";
      enum "ud";
      enum "ux";
      enum "d";
      enum "dx";
    }
  }

  typedef display-level {
    type uint64 {
      range "1 .. 64";
    }
  }

  typedef idle-timeout {
    type uint64 {
      range "0 .. 8192";
    }
  }

  typedef history {
    type uint64 {
      range "0 .. 8192";
    }
  }

  grouping ncs_template_session-params {
    leaf complete-on-space {
      type string;
    }
    leaf ignore-leading-space {
      type string;
    }
    leaf idle-timeout {
      type string;
    }
    leaf paginate {
      type string;
    }
    leaf history {
      type string;
    }
    leaf autowizard {
      type string;
    }
    leaf show-defaults {
      type string;
    }
    leaf display-level {
      type string;
    }
    leaf prompt1 {
      type string;
    }
    leaf prompt2 {
      type string;
    }
  }

  grouping ncs_rpc_notif_session-params {
    leaf complete-on-space {
      type boolean;
    }
    leaf ignore-leading-space {
      type boolean;
    }
    leaf idle-timeout {
      type idle-timeout;
    }
    leaf paginate {
      type boolean;
    }
    leaf history {
      type history;
    }
    leaf autowizard {
      type boolean;
    }
    leaf show-defaults {
      type boolean;
    }
    leaf display-level {
      type display-level;
    }
    leaf prompt1 {
      type string;
    }
    leaf prompt2 {
      type string;
    }
  }

  grouping live_ncs_session-params {
    leaf complete-on-space {
      type boolean;
    }
    leaf ignore-leading-space {
      type boolean;
    }
    leaf idle-timeout {
      type idle-timeout;
    }
    leaf paginate {
      type boolean;
    }
    leaf history {
      type history;
    }
    leaf autowizard {
      type boolean;
    }
    leaf show-defaults {
      type boolean;
    }
    leaf display-level {
      type display-level;
    }
    leaf prompt1 {
      type string;
    }
    leaf prompt2 {
      type string;
    }
  }

  grouping session-params {
    leaf complete-on-space {
      type boolean;
    }
    leaf ignore-leading-space {
      type boolean;
    }
    leaf idle-timeout {
      type idle-timeout;
    }
    leaf paginate {
      type boolean;
    }
    leaf history {
      type history;
    }
    leaf autowizard {
      type boolean;
    }
    leaf show-defaults {
      type boolean;
    }
    leaf display-level {
      type display-level;
    }
    leaf prompt1 {
      type string;
    }
    leaf prompt2 {
      type string;
    }
  }

  augment "/ncs:devices/ncs:device/ncs:config" {
    container aaa {
      tailf:ncs-device-type "netconf";
      tailf:display-when "not(../../ncs:module) or ../../ncs:module[ncs:name='tailf-aaa']";
      container authentication {
        container users {
          list user {
            key "name";
            ordered-by user;
            max-elements 1024;
            leaf name {
              type string;
            }
            leaf uid {
              type uint32;
              default "9000";
            }
            leaf gid {
              type uint32;
              default "100";
            }
            leaf password {
              type passwdStr;
              mandatory true;
            }
            leaf ssh_keydir {
              type string;
              default "/home/sshdir";
            }
            leaf homedir {
              type string;
              default "/home/homedir";
            }
          }
        }
        container groups {
          list group {
            key "name";
            max-elements 32;
            leaf name {
              type string;
            }
            leaf gid {
              type uint32;
              default "100";
            }
            leaf users {
              type string;
              default "%%__system_user__%%";
            }
          }
        }
        container login {
          container group {
            leaf tacacs {
              type empty;
            }
          }
        }
      }
      container authorization {
        container cmdrules {
          list cmdrule {
            key "index";
            leaf index {
              type uint32;
            }
            leaf context {
              type string;
              mandatory true;
            }
            leaf command {
              type string;
              mandatory true;
            }
            leaf group {
              type string;
              mandatory true;
            }
            leaf ops {
              type cmdOperationType;
              mandatory true;
            }
            leaf action {
              type Action;
              mandatory true;
            }
          }
        }
        container datarules {
          list datarule {
            key "index";
            leaf index {
              type uint32;
            }
            leaf namespace {
              type string;
              mandatory true;
            }
            leaf context {
              type string;
              default "*";
            }
            leaf keypath {
              type string;
              mandatory true;
            }
            leaf group {
              type string;
              mandatory true;
            }
            leaf ops {
              type dataOperationType;
              mandatory true;
            }
            leaf action {
              type Action;
              mandatory true;
            }
          }
        }
        container commands {
          container group {
            leaf tacacs {
              type empty;
            }
            leaf none {
              type empty;
            }
          }
        }
      }
      container accounting {
        container commands {
          container group {
            leaf tacacs {
              type empty;
            }
          }
        }
      }
      container ios {
        presence "";
        list level {
          key "nr";
          min-elements 2;
          leaf nr {
            type levelInt;
          }
          leaf secret {
            type passwdStr;
          }
          leaf password {
            type passwdStr;
          }
          leaf prompt {
            type string;
            default "\\h# ";
          }
        }
        list privilege {
          key "mode";
          leaf mode {
            type modeStr;
          }
          list level {
            key "nr";
            min-elements 1;
            max-elements 15;
            leaf nr {
              type levelInt;
            }
            list command {
              key "name";
              leaf name {
                type string;
              }
            }
          }
        }
      }
    }
    list alias {
      tailf:ncs-device-type "netconf";
      tailf:display-when "not(../ncs:module) or ../ncs:module[ncs:name='tailf-aaa']";
      key "name";
      leaf name {
        type string;
      }
      leaf expansion {
        type string;
        mandatory true;
      }
    }
    container session {
      tailf:ncs-device-type "netconf";
      tailf:display-when "not(../../ncs:module) or ../../ncs:module[ncs:name='tailf-aaa']";
      uses session-params;
      presence "";
    }
    list user {
      tailf:ncs-device-type "netconf";
      tailf:display-when "not(../ncs:module) or ../ncs:module[ncs:name='tailf-aaa']";
      key "name";
      leaf name {
        type string;
      }
      leaf description {
        type string;
      }
      list alias {
        key "name";
        leaf name {
          type string;
        }
        leaf expansion {
          type string;
          mandatory true;
        }
      }
      container session {
        uses session-params;
      }
    }
  }
  augment "/ncs:devices/ncs:device/ncs:live-status" {
    container aaa {
      tailf:ncs-device-type "netconf";
      tailf:display-when "not(../../ncs:module) or ../../ncs:module[ncs:name='tailf-aaa'] or (../../ncs:live-status-protocol[not(ncs:capability)]) or (../../ncs:live-status-protocol/ncs:capability/ncs:module[.='tailf-aaa'])";
      container authentication {
        container users {
          list user {
            key "name";
            ordered-by user;
            // NCS drop max-elements statement
            leaf name {
              type string;
            }
            leaf uid {
              type uint32;
              // NCS drop default statement
            }
            leaf gid {
              type uint32;
              // NCS drop default statement
            }
            leaf password {
              type passwdStr;
              // NCS drop mandatory statement
            }
            leaf ssh_keydir {
              type string;
              // NCS drop default statement
            }
            leaf homedir {
              type string;
              // NCS drop default statement
            }
          }
        }
        container groups {
          list group {
            key "name";
            // NCS drop max-elements statement
            leaf name {
              type string;
            }
            leaf gid {
              type uint32;
              // NCS drop default statement
            }
            leaf users {
              type string;
              // NCS drop default statement
            }
          }
        }
        container login {
          container group {
            leaf tacacs {
              type empty;
            }
          }
        }
      }
      container authorization {
        container cmdrules {
          list cmdrule {
            key "index";
            leaf index {
              type uint32;
            }
            leaf context {
              type string;
              // NCS drop mandatory statement
            }
            leaf command {
              type string;
              // NCS drop mandatory statement
            }
            leaf group {
              type string;
              // NCS drop mandatory statement
            }
            leaf ops {
              type cmdOperationType;
              // NCS drop mandatory statement
            }
            leaf action {
              type Action;
              // NCS drop mandatory statement
            }
          }
        }
        container datarules {
          list datarule {
            key "index";
            leaf index {
              type uint32;
            }
            leaf namespace {
              type string;
              // NCS drop mandatory statement
            }
            leaf context {
              type string;
              // NCS drop default statement
            }
            leaf keypath {
              type string;
              // NCS drop mandatory statement
            }
            leaf group {
              type string;
              // NCS drop mandatory statement
            }
            leaf ops {
              type dataOperationType;
              // NCS drop mandatory statement
            }
            leaf action {
              type Action;
              // NCS drop mandatory statement
            }
          }
        }
        container commands {
          container group {
            leaf tacacs {
              type empty;
            }
            leaf none {
              type empty;
            }
          }
        }
      }
      container accounting {
        container commands {
          container group {
            leaf tacacs {
              type empty;
            }
          }
        }
      }
      container ios {
        presence "";
        list level {
          key "nr";
          // NCS drop min-elements statement
          leaf nr {
            type levelInt;
          }
          leaf secret {
            type passwdStr;
          }
          leaf password {
            type passwdStr;
          }
          leaf prompt {
            type string;
            // NCS drop default statement
          }
        }
        list privilege {
          key "mode";
          leaf mode {
            type modeStr;
          }
          list level {
            key "nr";
            // NCS drop min-elements statement
            // NCS drop max-elements statement
            leaf nr {
              type levelInt;
            }
            list command {
              key "name";
              leaf name {
                type string;
              }
            }
          }
        }
      }
    }
    list alias {
      tailf:ncs-device-type "netconf";
      tailf:display-when "not(../ncs:module) or ../ncs:module[ncs:name='tailf-aaa'] or (../ncs:live-status-protocol[not(ncs:capability)]) or (../ncs:live-status-protocol/ncs:capability/ncs:module[.='tailf-aaa'])";
      key "name";
      leaf name {
        type string;
      }
      leaf expansion {
        type string;
        // NCS drop mandatory statement
      }
    }
    container session {
      tailf:ncs-device-type "netconf";
      tailf:display-when "not(../../ncs:module) or ../../ncs:module[ncs:name='tailf-aaa'] or (../../ncs:live-status-protocol[not(ncs:capability)]) or (../../ncs:live-status-protocol/ncs:capability/ncs:module[.='tailf-aaa'])";
      uses live_ncs_session-params;
      presence "";
    }
    list user {
      tailf:ncs-device-type "netconf";
      tailf:display-when "not(../ncs:module) or ../ncs:module[ncs:name='tailf-aaa'] or (../ncs:live-status-protocol[not(ncs:capability)]) or (../ncs:live-status-protocol/ncs:capability/ncs:module[.='tailf-aaa'])";
      key "name";
      leaf name {
        type string;
      }
      leaf description {
        type string;
      }
      list alias {
        key "name";
        leaf name {
          type string;
        }
        leaf expansion {
          type string;
          // NCS drop mandatory statement
        }
      }
      container session {
        uses live_ncs_session-params;
      }
    }
  }
  augment "/ncs:devices/ncs:template/ncs:ned-id/ncs:config" {
    container aaa {
      container authentication {
        container users {
          list user {
            // NCS patched for predictable order
            ordered-by user;
            key "name";
            // NCS drop max-elements statement
            leaf name {
              type string;
            }
            leaf uid {
              type string;
              // NCS drop default statement
            }
            leaf gid {
              type string;
              // NCS drop default statement
            }
            leaf password {
              type string;
              // NCS drop mandatory statement
            }
            leaf ssh_keydir {
              type string;
              // NCS drop default statement
            }
            leaf homedir {
              type string;
              // NCS drop default statement
            }
          }
        }
        container groups {
          list group {
            // NCS patched for predictable order
            ordered-by user;
            key "name";
            // NCS drop max-elements statement
            leaf name {
              type string;
            }
            leaf gid {
              type string;
              // NCS drop default statement
            }
            leaf users {
              type string;
              // NCS drop default statement
            }
          }
        }
        container login {
          container group {
            leaf tacacs {
              type empty;
            }
          }
        }
      }
      container authorization {
        container cmdrules {
          list cmdrule {
            // NCS patched for predictable order
            ordered-by user;
            key "index";
            leaf index {
              type string;
            }
            leaf context {
              type string;
              // NCS drop mandatory statement
            }
            leaf command {
              type string;
              // NCS drop mandatory statement
            }
            leaf group {
              type string;
              // NCS drop mandatory statement
            }
            leaf ops {
              type string;
              // NCS drop mandatory statement
            }
            leaf action {
              type string;
              // NCS drop mandatory statement
            }
          }
        }
        container datarules {
          list datarule {
            // NCS patched for predictable order
            ordered-by user;
            key "index";
            leaf index {
              type string;
            }
            leaf namespace {
              type string;
              // NCS drop mandatory statement
            }
            leaf context {
              type string;
              // NCS drop default statement
            }
            leaf keypath {
              type string;
              // NCS drop mandatory statement
            }
            leaf group {
              type string;
              // NCS drop mandatory statement
            }
            leaf ops {
              type string;
              // NCS drop mandatory statement
            }
            leaf action {
              type string;
              // NCS drop mandatory statement
            }
          }
        }
        container commands {
          container group {
            leaf tacacs {
              type empty;
            }
            leaf none {
              type empty;
            }
          }
        }
      }
      container accounting {
        container commands {
          container group {
            leaf tacacs {
              type empty;
            }
          }
        }
      }
      container ios {
        presence "";
        list level {
          // NCS patched for predictable order
          ordered-by user;
          key "nr";
          // NCS drop min-elements statement
          leaf nr {
            type string;
          }
          leaf secret {
            type string;
          }
          leaf password {
            type string;
          }
          leaf prompt {
            type string;
            // NCS drop default statement
          }
        }
        list privilege {
          // NCS patched for predictable order
          ordered-by user;
          key "mode";
          leaf mode {
            type string;
          }
          list level {
            // NCS patched for predictable order
            ordered-by user;
            key "nr";
            // NCS drop min-elements statement
            // NCS drop max-elements statement
            leaf nr {
              type string;
            }
            list command {
              // NCS patched for predictable order
              ordered-by user;
              key "name";
              leaf name {
                type string;
              }
            }
          }
        }
      }
    }
    list alias {
      // NCS patched for predictable order
      ordered-by user;
      key "name";
      leaf name {
        type string;
      }
      leaf expansion {
        type string;
        // NCS drop mandatory statement
      }
    }
    container session {
      uses ncs_template_session-params;
      presence "";
    }
    list user {
      // NCS patched for predictable order
      ordered-by user;
      key "name";
      leaf name {
        type string;
      }
      leaf description {
        type string;
      }
      list alias {
        // NCS patched for predictable order
        ordered-by user;
        key "name";
        leaf name {
          type string;
        }
        leaf expansion {
          type string;
          // NCS drop mandatory statement
        }
      }
      container session {
        uses ncs_template_session-params;
      }
    }
  }
}
