module Cisco-IOS-XR-ascii-ltrace-oper {
  // Generated by yanger -t ncs
  tailf:mount-id f5500-nc-1.0:f5500-nc-1.0;
  tailf:ncs-device-type "netconf";

  namespace "http://cisco.com/ns/yang/Cisco-IOS-XR-ascii-ltrace-oper";
  prefix Cisco-IOS-XR-ascii-ltrace-oper;

  import Cisco-IOS-XR-types {
    prefix xr;
  }
  include Cisco-IOS-XR-ascii-ltrace-oper-sub1 {
    revision-date 2018-01-21;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ascii-ltrace package operational data.

     This module contains definitions
     for the following management objects:
       ltrace: ASCII ltrace data

     Copyright (c) 2013-2018 by Cisco Systems, Inc.
     All rights reserved.";

  revision 2018-01-21 {
    description
      "Initial feature";
  }
  revision 2015-11-09 {
    description
      "IOS XR 6.0 revision.";
  }

  augment "/ncs:devices/ncs:device/ncs:config" {
    // NCS drop config false container ltrace
  }
  augment "/ncs:devices/ncs:device/ncs:live-status" {
    container ltrace {
      tailf:ncs-device-type "netconf";
      tailf:display-when "not(../../ncs:module) or ../../ncs:module[ncs:name='Cisco-IOS-XR-ascii-ltrace-oper'] or (../../ncs:live-status-protocol[not(ncs:capability)]) or (../../ncs:live-status-protocol/ncs:capability/ncs:module[.='Cisco-IOS-XR-ascii-ltrace-oper'])";
      description
        "ASCII ltrace data";
      container features {
        description
          "feature";
        list feature {
          description
            "feature";
          container traces {
            description
              "trace";
            list trace {
              key "ltrace-id";
              description
                "trace";
              leaf ltrace-id {
                type uint32;
                description
                  "Ltrace ID of ltrace";
              }
              uses live_ncs_ASCII-LTRACE;
            }
          }
          leaf feature-name {
            type xr:Cisco-ios-xr-string;
            description
              "feature name";
          }
          leaf trace-buf {
            type xr:Cisco-ios-xr-string;
            description
              "trace buffer name";
          }
        }
      }
    }
  }
  augment "/ncs:devices/ncs:template/ncs:ned-id/ncs:config" {
    // NCS drop config false container ltrace
  }
}
