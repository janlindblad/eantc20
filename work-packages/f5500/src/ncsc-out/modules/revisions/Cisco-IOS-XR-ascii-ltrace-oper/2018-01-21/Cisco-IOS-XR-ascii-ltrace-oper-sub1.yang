submodule Cisco-IOS-XR-ascii-ltrace-oper-sub1 {
  // Generated by yanger -t ncs
  tailf:mount-id f5500-nc-1.0:f5500-nc-1.0;

  belongs-to Cisco-IOS-XR-ascii-ltrace-oper {
    prefix Cisco-IOS-XR-ascii-ltrace-oper-sub1;
  }

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ascii-ltrace package operational data.

     Copyright (c) 2013-2018 by Cisco Systems, Inc.
     All rights reserved.";

  revision 2018-01-21 {
    description
      "Initial feature";
  }
  revision 2015-11-09 {
    description
      "IOS XR 6.0 revision.";
  }

  grouping ncs_template_ASCII-LTRACE {
    description
      "Information of a Ltrace Point";
    leaf timestamp {
      type string;
      description
        "timestamp";
    }
    leaf line {
      type string;
      description
        "a single line of a trace point";
    }
  }

  grouping ncs_rpc_notif_ASCII-LTRACE {
    description
      "Information of a Ltrace Point";
    leaf timestamp {
      type string;
      description
        "timestamp";
    }
    leaf line {
      type string;
      description
        "a single line of a trace point";
    }
  }

  grouping live_ncs_ASCII-LTRACE {
    description
      "Information of a Ltrace Point";
    leaf timestamp {
      type string;
      description
        "timestamp";
    }
    leaf line {
      type string;
      description
        "a single line of a trace point";
    }
  }

  grouping ASCII-LTRACE {
    description
      "Information of a Ltrace Point";
    leaf timestamp {
      type string;
      description
        "timestamp";
    }
    leaf line {
      type string;
      description
        "a single line of a trace point";
    }
  }
}
