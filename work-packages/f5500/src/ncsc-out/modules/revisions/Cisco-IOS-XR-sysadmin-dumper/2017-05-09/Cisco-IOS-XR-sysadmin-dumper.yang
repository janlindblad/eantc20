module Cisco-IOS-XR-sysadmin-dumper {
  // Generated by yanger -t ncs
  tailf:mount-id f5500-nc-1.0:f5500-nc-1.0;
  tailf:ncs-device-type "netconf";

  namespace "http://www.cisco.com/ns/yang/Cisco-IOS-XR-sysadmin-dumper";
  prefix Cisco-IOS-XR-sysadmin-dumper;

  import "f5500-nc-1.0" {
    prefix "f5500-nc-1.0";
  }
  import tailf-ncs {
    prefix ncs;
  }
  import tailf-common {
    prefix tailf;
  }

  organization
    "Cisco Systems Inc.";
  contact
    "Cisco Systems, Inc.
     Customer Service

     Postal: 170 West Tasman Drive
     San Jose, CA 95134

     Tel: +1 800 553-NETS

     E-mail: cs-yang@cisco.com";
  description
    "This module contains definitions
     for the Calvados model objects.

     This module contains a collection of YANG
     definitions for Cisco IOS-XR SysAdmin dumper to
     configure file path options to copy the core files to.

     Copyright(c) 2015-2017 by Cisco Systems, Inc.
     All rights reserved.

     Copyright (c) 2012-2018 by Cisco Systems, Inc.
     All rights reserved.";

  revision 2017-05-09 {
    description
      "Modified module name, namespace and filename
       to adhere to standard notation";
  }

  augment "/ncs:devices/ncs:device/ncs:config" {
    container exception {
      tailf:ncs-device-type "netconf";
      tailf:display-when "not(../../ncs:module) or ../../ncs:module[ncs:name='Cisco-IOS-XR-sysadmin-dumper']";
      list choice {
        key "order";
        leaf order {
          type int32 {
            range "1 .. 3";
          }
        }
        leaf filepath {
          type string;
          mandatory true;
        }
      }
    }
  }
  augment "/ncs:devices/ncs:device/ncs:live-status" {
    container exception {
      tailf:ncs-device-type "netconf";
      tailf:display-when "not(../../ncs:module) or ../../ncs:module[ncs:name='Cisco-IOS-XR-sysadmin-dumper'] or (../../ncs:live-status-protocol[not(ncs:capability)]) or (../../ncs:live-status-protocol/ncs:capability/ncs:module[.='Cisco-IOS-XR-sysadmin-dumper'])";
      list choice {
        key "order";
        leaf order {
          type int32 {
            range "1 .. 3";
          }
        }
        leaf filepath {
          type string;
          // NCS drop mandatory statement
        }
      }
    }
  }
  augment "/ncs:devices/ncs:template/ncs:ned-id/ncs:config" {
    container exception {
      list choice {
        // NCS patched for predictable order
        ordered-by user;
        key "order";
        leaf order {
          type string;
        }
        leaf filepath {
          type string;
          // NCS drop mandatory statement
        }
      }
    }
  }
}
