module Cisco-IOS-XR-infra-rsi-cfg {
  // Generated by yanger -t ncs
  tailf:mount-id f5500-nc-1.0:f5500-nc-1.0;
  tailf:ncs-device-type "netconf";

  namespace "http://cisco.com/ns/yang/Cisco-IOS-XR-infra-rsi-cfg";
  prefix Cisco-IOS-XR-infra-rsi-cfg;

  import Cisco-IOS-XR-types {
    prefix xr;
  }
  import Cisco-IOS-XR-ifmgr-cfg {
    prefix a1;
  }
  import Cisco-IOS-XR-snmp-agent-cfg {
    prefix a2;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR infra-rsi package configuration.

     This module contains definitions
     for the following management objects:
       vrfs: VRF configuration
       global-af: global af
       srlg: srlg
       vrf-groups: vrf groups
       selective-vrf-download: selective vrf download

     This YANG module augments the
       Cisco-IOS-XR-ifmgr-cfg,
       Cisco-IOS-XR-snmp-agent-cfg
     modules with configuration data.

     Copyright (c) 2013-2018 by Cisco Systems, Inc.
     All rights reserved.";

  revision 2018-06-15 {
    description
      "Allow min..max in range when min == max.";
  }
  revision 2017-05-01 {
    description
      "Fixing backward compatibility error in module.";
  }
  revision 2016-12-19 {
    description
      "IOS XR 6.2.1 revision.";
  }
  revision 2015-01-07 {
    description
      "IOS XR 5.3.1 revision.";
  }

  typedef Srlg-priority {
    type enumeration {
      enum "critical" {
        value 0;
        description
          "Critical";
      }
      enum "high" {
        value 1;
        description
          "High";
      }
      enum "default" {
        value 2;
        description
          "Default";
      }
      enum "low" {
        value 3;
        description
          "Low";
      }
      enum "very-low" {
        value 4;
        description
          "Very low";
      }
    }
    description
      "Srlg priority";
  }

  typedef Vrf-address-family {
    type enumeration {
      enum "ipv4" {
        value 1;
        description
          "IPv4";
      }
      enum "ipv6" {
        value 2;
        description
          "IPv6";
      }
    }
    description
      "Vrf address family";
  }

  typedef Vrf-sub-address-family {
    type enumeration {
      enum "unicast" {
        value 1;
        description
          "Unicast";
      }
      enum "multicast" {
        value 2;
        description
          "Multicast";
      }
      enum "flow-spec" {
        value 133;
        description
          "Flow spec";
      }
    }
    description
      "Vrf sub address family";
  }

  grouping ncs_template_AF-TABLE {
    description
      "Common node of vrf, global-af";
    container afs {
      description
        "VRF address family configuration";
      list af {
        // NCS patched for predictable order
        ordered-by user;
        key "af-name saf-name topology-name";
        description
          "VRF address family configuration";
        leaf create {
          type empty;
          description
            "VRF configuration for a particular address
             family";
        }
        leaf af-name {
          type string;
          description
            "Address family";
        }
        leaf saf-name {
          type string;
          description
            "Sub-Address family";
        }
        leaf topology-name {
          type string;
          description
            "Topology name";
        }
      }
    }
  }

  grouping ncs_rpc_notif_AF-TABLE {
    description
      "Common node of vrf, global-af";
    container afs {
      description
        "VRF address family configuration";
      list af {
        key "af-name saf-name topology-name";
        description
          "VRF address family configuration";
        leaf create {
          type empty;
          description
            "VRF configuration for a particular address
             family";
        }
        leaf af-name {
          type Vrf-address-family;
          description
            "Address family";
        }
        leaf saf-name {
          type Vrf-sub-address-family;
          description
            "Sub-Address family";
        }
        leaf topology-name {
          type xr:Cisco-ios-xr-string {
            length "1..244";
          }
          description
            "Topology name";
        }
      }
    }
  }

  grouping live_ncs_AF-TABLE {
    description
      "Common node of vrf, global-af";
    container afs {
      description
        "VRF address family configuration";
      list af {
        key "af-name saf-name topology-name";
        description
          "VRF address family configuration";
        leaf create {
          type empty;
          description
            "VRF configuration for a particular address
             family";
        }
        leaf af-name {
          type Vrf-address-family;
          description
            "Address family";
        }
        leaf saf-name {
          type Vrf-sub-address-family;
          description
            "Sub-Address family";
        }
        leaf topology-name {
          type xr:Cisco-ios-xr-string {
            length "1..244";
          }
          description
            "Topology name";
        }
      }
    }
  }

  grouping AF-TABLE {
    description
      "Common node of vrf, global-af";
    container afs {
      description
        "VRF address family configuration";
      list af {
        key "af-name saf-name topology-name";
        description
          "VRF address family configuration";
        leaf create {
          type empty;
          description
            "VRF configuration for a particular address
             family";
        }
        leaf af-name {
          type Vrf-address-family;
          description
            "Address family";
        }
        leaf saf-name {
          type Vrf-sub-address-family;
          description
            "Sub-Address family";
        }
        leaf topology-name {
          type xr:Cisco-ios-xr-string {
            length "1..244";
          }
          description
            "Topology name";
        }
      }
    }
  }

  augment "/ncs:devices/ncs:device/ncs:config" {
    container vrfs {
      tailf:ncs-device-type "netconf";
      tailf:display-when "not(../../ncs:module) or ../../ncs:module[ncs:name='Cisco-IOS-XR-infra-rsi-cfg']";
      description
        "VRF configuration";
      list vrf {
        key "vrf-name";
        description
          "VRF configuration";
        container vpn-id {
          presence "Indicates a vpn-id node is configured.";
          description
            "VPN-ID for the VRF";
          leaf vpn-oui {
            type uint32 {
              range "0..16777215";
            }
            mandatory true;
            description
              "OUI of VPNID OUI";
          }
          leaf vpn-index {
            type uint32 {
              range "0..4294967295";
            }
            mandatory true;
            description
              "Index of VPNID Index";
          }
        }
        leaf fallback-vrf {
          type xr:Cisco-ios-xr-string {
            length "1..32";
          }
          description
            "Fallback VRF";
        }
        leaf remote-route-filter-disable {
          type empty;
          description
            "For disabling remote route filtering for this
             VRF on core-facing card";
        }
        leaf create {
          type empty;
          description
            "VRF global configuration";
        }
        leaf mode-big {
          type empty;
          description
            "Configuration enable of big VRF";
        }
        leaf description {
          type string {
            length "1..244";
          }
          description
            "A textual description of the VRF";
        }
        leaf vrf-name {
          type xr:Cisco-ios-xr-string {
            length "1..32";
          }
          description
            "VRF name";
        }
        uses AF-TABLE;
      }
    }
    container global-af {
      tailf:ncs-device-type "netconf";
      tailf:display-when "not(../../ncs:module) or ../../ncs:module[ncs:name='Cisco-IOS-XR-infra-rsi-cfg']";
      description
        "global af";
      uses AF-TABLE;
    }
    container srlg {
      tailf:ncs-device-type "netconf";
      tailf:display-when "not(../../ncs:module) or ../../ncs:module[ncs:name='Cisco-IOS-XR-infra-rsi-cfg']";
      description
        "srlg";
      container interfaces {
        description
          "Set of interfaces configured with SRLG";
        list interface {
          key "interface-name";
          description
            "Interface configurations";
          container include-optical {
            description
              "Include optical configuration for an interface";
            leaf enable {
              type empty;
              description
                "Enable SRLG interface include optical";
            }
            leaf priority {
              type Srlg-priority;
              default "default";
              description
                "Priority for optical domain values";
            }
          }
          container interface-group {
            description
              "Group configuration for an interface";
            container group-names {
              description
                "Set of group name under an interface";
              list group-name {
                key "group-name-index";
                description
                  "Group name included under interface";
                leaf group-name-index {
                  type uint32 {
                    range "1";
                  }
                  description
                    "Group name index";
                }
                leaf group-name {
                  type string;
                  mandatory true;
                  description
                    "Group name";
                }
                leaf srlg-priority {
                  type Srlg-priority;
                  default "default";
                  description
                    "SRLG priority";
                }
              }
            }
            leaf enable {
              type empty;
              description
                "Enable SRLG interface group submode";
            }
          }
          container values {
            description
              "SRLG Value configuration for an interface";
            list value {
              key "srlg-index";
              description
                "SRLG value data";
              leaf srlg-index {
                type uint32 {
                  range "1..65535";
                }
                description
                  "SRLG index";
              }
              leaf srlg-value {
                type uint32 {
                  range "0..4294967295";
                }
                mandatory true;
                description
                  "SRLG value";
              }
              leaf srlg-priority {
                type Srlg-priority;
                default "default";
                description
                  "SRLG priority";
              }
            }
          }
          container interface-srlg-names {
            description
              "SRLG Name configuration for an interface";
            list interface-srlg-name {
              key "srlg-name";
              description
                "SRLG name data";
              leaf srlg-name {
                type xr:Cisco-ios-xr-string {
                  length "1..64";
                }
                description
                  "SRLG name";
              }
            }
          }
          leaf enable {
            type empty;
            description
              "Enable SRLG interface";
          }
          leaf interface-name {
            type xr:Interface-name;
            description
              "Interface name";
          }
        }
      }
      container srlg-names {
        description
          "Set of SRLG name configuration";
        list srlg-name {
          key "srlg-name";
          description
            "SRLG name configuration";
          leaf srlg-name {
            type xr:Cisco-ios-xr-string {
              length "1..64";
            }
            description
              "SRLG name";
          }
          leaf srlg-value {
            type uint32 {
              range "0..4294967295";
            }
            mandatory true;
            description
              "SRLG value";
          }
        }
      }
      container groups {
        description
          "Set of groups configured with SRLG";
        list group {
          key "group-name";
          description
            "Group configurations";
          container group-values {
            description
              "Set of SRLG values configured under a group";
            list group-value {
              key "srlg-index";
              description
                "Group SRLG values with attribute";
              leaf srlg-index {
                type uint32 {
                  range "1..65535";
                }
                description
                  "SRLG index";
              }
              leaf srlg-value {
                type uint32 {
                  range "0..4294967295";
                }
                mandatory true;
                description
                  "SRLG value";
              }
              leaf srlg-priority {
                type Srlg-priority;
                default "default";
                description
                  "SRLG priority";
              }
            }
          }
          leaf enable {
            type empty;
            description
              "Enable SRLG group";
          }
          leaf group-name {
            type xr:Cisco-ios-xr-string;
            description
              "Group name";
          }
        }
      }
      container inherit-nodes {
        description
          "Set of inherit nodes configured with SRLG";
        list inherit-node {
          key "inherit-node-name";
          description
            "Inherit node configurations";
          container inherit-node-values {
            description
              "Set of SRLG values configured under an inherit
               node";
            list inherit-node-value {
              key "srlg-index";
              description
                "Inherit node SRLG value with attributes";
              leaf srlg-index {
                type uint32 {
                  range "1..65535";
                }
                description
                  "SRLG index";
              }
              leaf srlg-value {
                type uint32 {
                  range "0..4294967295";
                }
                mandatory true;
                description
                  "SRLG value";
              }
              leaf srlg-priority {
                type Srlg-priority;
                default "default";
                description
                  "SRLG priority";
              }
            }
          }
          leaf enable {
            type empty;
            description
              "Enable SRLG inherit node";
          }
          leaf inherit-node-name {
            type xr:Pq-node-id;
            description
              "The inherit node name";
          }
        }
      }
      leaf enable {
        type empty;
        description
          "Enable SRLG";
      }
    }
    container vrf-groups {
      tailf:ncs-device-type "netconf";
      tailf:display-when "not(../../ncs:module) or ../../ncs:module[ncs:name='Cisco-IOS-XR-infra-rsi-cfg']";
      description
        "vrf groups";
      list vrf-group {
        key "vrf-group-name";
        description
          "VRF group configuration";
        container vrfs {
          description
            "Set of VRFs configured under a VRF group";
          list vrf {
            key "vrf-name";
            description
              "VRF configuration";
            leaf vrf-name {
              type xr:Cisco-ios-xr-string {
                length "1..32";
              }
              description
                "VRF name";
            }
          }
        }
        leaf enable {
          type empty;
          description
            "Enable VRF group";
        }
        leaf vrf-group-name {
          type xr:Cisco-ios-xr-string {
            length "1..32";
          }
          description
            "VRF group name";
        }
      }
    }
    container selective-vrf-download {
      tailf:ncs-device-type "netconf";
      tailf:display-when "not(../../ncs:module) or ../../ncs:module[ncs:name='Cisco-IOS-XR-infra-rsi-cfg']";
      description
        "selective vrf download";
      leaf disable {
        type empty;
        description
          "Disable selective VRF download";
      }
    }
  }
  augment "/ncs:devices/ncs:device/ncs:live-status" {
    container vrfs {
      tailf:ncs-device-type "netconf";
      tailf:display-when "not(../../ncs:module) or ../../ncs:module[ncs:name='Cisco-IOS-XR-infra-rsi-cfg'] or (../../ncs:live-status-protocol[not(ncs:capability)]) or (../../ncs:live-status-protocol/ncs:capability/ncs:module[.='Cisco-IOS-XR-infra-rsi-cfg'])";
      description
        "VRF configuration";
      list vrf {
        key "vrf-name";
        description
          "VRF configuration";
        container vpn-id {
          presence "Indicates a vpn-id node is configured.";
          description
            "VPN-ID for the VRF";
          leaf vpn-oui {
            type uint32 {
              range "0..16777215";
            }
            // NCS drop mandatory statement
            description
              "OUI of VPNID OUI";
          }
          leaf vpn-index {
            type uint32 {
              range "0..4294967295";
            }
            // NCS drop mandatory statement
            description
              "Index of VPNID Index";
          }
        }
        leaf fallback-vrf {
          type xr:Cisco-ios-xr-string {
            length "1..32";
          }
          description
            "Fallback VRF";
        }
        leaf remote-route-filter-disable {
          type empty;
          description
            "For disabling remote route filtering for this
             VRF on core-facing card";
        }
        leaf create {
          type empty;
          description
            "VRF global configuration";
        }
        leaf mode-big {
          type empty;
          description
            "Configuration enable of big VRF";
        }
        leaf description {
          type string {
            length "1..244";
          }
          description
            "A textual description of the VRF";
        }
        leaf vrf-name {
          type xr:Cisco-ios-xr-string {
            length "1..32";
          }
          description
            "VRF name";
        }
        uses live_ncs_AF-TABLE;
      }
    }
    container global-af {
      tailf:ncs-device-type "netconf";
      tailf:display-when "not(../../ncs:module) or ../../ncs:module[ncs:name='Cisco-IOS-XR-infra-rsi-cfg'] or (../../ncs:live-status-protocol[not(ncs:capability)]) or (../../ncs:live-status-protocol/ncs:capability/ncs:module[.='Cisco-IOS-XR-infra-rsi-cfg'])";
      description
        "global af";
      uses live_ncs_AF-TABLE;
    }
    container srlg {
      tailf:ncs-device-type "netconf";
      tailf:display-when "not(../../ncs:module) or ../../ncs:module[ncs:name='Cisco-IOS-XR-infra-rsi-cfg'] or (../../ncs:live-status-protocol[not(ncs:capability)]) or (../../ncs:live-status-protocol/ncs:capability/ncs:module[.='Cisco-IOS-XR-infra-rsi-cfg'])";
      description
        "srlg";
      container interfaces {
        description
          "Set of interfaces configured with SRLG";
        list interface {
          key "interface-name";
          description
            "Interface configurations";
          container include-optical {
            description
              "Include optical configuration for an interface";
            leaf enable {
              type empty;
              description
                "Enable SRLG interface include optical";
            }
            leaf priority {
              type Srlg-priority;
              // NCS drop default statement
              description
                "Priority for optical domain values";
            }
          }
          container interface-group {
            description
              "Group configuration for an interface";
            container group-names {
              description
                "Set of group name under an interface";
              list group-name {
                key "group-name-index";
                description
                  "Group name included under interface";
                leaf group-name-index {
                  type uint32 {
                    range "1";
                  }
                  description
                    "Group name index";
                }
                leaf group-name {
                  type string;
                  // NCS drop mandatory statement
                  description
                    "Group name";
                }
                leaf srlg-priority {
                  type Srlg-priority;
                  // NCS drop default statement
                  description
                    "SRLG priority";
                }
              }
            }
            leaf enable {
              type empty;
              description
                "Enable SRLG interface group submode";
            }
          }
          container values {
            description
              "SRLG Value configuration for an interface";
            list value {
              key "srlg-index";
              description
                "SRLG value data";
              leaf srlg-index {
                type uint32 {
                  range "1..65535";
                }
                description
                  "SRLG index";
              }
              leaf srlg-value {
                type uint32 {
                  range "0..4294967295";
                }
                // NCS drop mandatory statement
                description
                  "SRLG value";
              }
              leaf srlg-priority {
                type Srlg-priority;
                // NCS drop default statement
                description
                  "SRLG priority";
              }
            }
          }
          container interface-srlg-names {
            description
              "SRLG Name configuration for an interface";
            list interface-srlg-name {
              key "srlg-name";
              description
                "SRLG name data";
              leaf srlg-name {
                type xr:Cisco-ios-xr-string {
                  length "1..64";
                }
                description
                  "SRLG name";
              }
            }
          }
          leaf enable {
            type empty;
            description
              "Enable SRLG interface";
          }
          leaf interface-name {
            type xr:Interface-name;
            description
              "Interface name";
          }
        }
      }
      container srlg-names {
        description
          "Set of SRLG name configuration";
        list srlg-name {
          key "srlg-name";
          description
            "SRLG name configuration";
          leaf srlg-name {
            type xr:Cisco-ios-xr-string {
              length "1..64";
            }
            description
              "SRLG name";
          }
          leaf srlg-value {
            type uint32 {
              range "0..4294967295";
            }
            // NCS drop mandatory statement
            description
              "SRLG value";
          }
        }
      }
      container groups {
        description
          "Set of groups configured with SRLG";
        list group {
          key "group-name";
          description
            "Group configurations";
          container group-values {
            description
              "Set of SRLG values configured under a group";
            list group-value {
              key "srlg-index";
              description
                "Group SRLG values with attribute";
              leaf srlg-index {
                type uint32 {
                  range "1..65535";
                }
                description
                  "SRLG index";
              }
              leaf srlg-value {
                type uint32 {
                  range "0..4294967295";
                }
                // NCS drop mandatory statement
                description
                  "SRLG value";
              }
              leaf srlg-priority {
                type Srlg-priority;
                // NCS drop default statement
                description
                  "SRLG priority";
              }
            }
          }
          leaf enable {
            type empty;
            description
              "Enable SRLG group";
          }
          leaf group-name {
            type xr:Cisco-ios-xr-string;
            description
              "Group name";
          }
        }
      }
      container inherit-nodes {
        description
          "Set of inherit nodes configured with SRLG";
        list inherit-node {
          key "inherit-node-name";
          description
            "Inherit node configurations";
          container inherit-node-values {
            description
              "Set of SRLG values configured under an inherit
               node";
            list inherit-node-value {
              key "srlg-index";
              description
                "Inherit node SRLG value with attributes";
              leaf srlg-index {
                type uint32 {
                  range "1..65535";
                }
                description
                  "SRLG index";
              }
              leaf srlg-value {
                type uint32 {
                  range "0..4294967295";
                }
                // NCS drop mandatory statement
                description
                  "SRLG value";
              }
              leaf srlg-priority {
                type Srlg-priority;
                // NCS drop default statement
                description
                  "SRLG priority";
              }
            }
          }
          leaf enable {
            type empty;
            description
              "Enable SRLG inherit node";
          }
          leaf inherit-node-name {
            type xr:Pq-node-id;
            description
              "The inherit node name";
          }
        }
      }
      leaf enable {
        type empty;
        description
          "Enable SRLG";
      }
    }
    container vrf-groups {
      tailf:ncs-device-type "netconf";
      tailf:display-when "not(../../ncs:module) or ../../ncs:module[ncs:name='Cisco-IOS-XR-infra-rsi-cfg'] or (../../ncs:live-status-protocol[not(ncs:capability)]) or (../../ncs:live-status-protocol/ncs:capability/ncs:module[.='Cisco-IOS-XR-infra-rsi-cfg'])";
      description
        "vrf groups";
      list vrf-group {
        key "vrf-group-name";
        description
          "VRF group configuration";
        container vrfs {
          description
            "Set of VRFs configured under a VRF group";
          list vrf {
            key "vrf-name";
            description
              "VRF configuration";
            leaf vrf-name {
              type xr:Cisco-ios-xr-string {
                length "1..32";
              }
              description
                "VRF name";
            }
          }
        }
        leaf enable {
          type empty;
          description
            "Enable VRF group";
        }
        leaf vrf-group-name {
          type xr:Cisco-ios-xr-string {
            length "1..32";
          }
          description
            "VRF group name";
        }
      }
    }
    container selective-vrf-download {
      tailf:ncs-device-type "netconf";
      tailf:display-when "not(../../ncs:module) or ../../ncs:module[ncs:name='Cisco-IOS-XR-infra-rsi-cfg'] or (../../ncs:live-status-protocol[not(ncs:capability)]) or (../../ncs:live-status-protocol/ncs:capability/ncs:module[.='Cisco-IOS-XR-infra-rsi-cfg'])";
      description
        "selective vrf download";
      leaf disable {
        type empty;
        description
          "Disable selective VRF download";
      }
    }
  }
  augment "/ncs:devices/ncs:template/ncs:ned-id/ncs:config" {
    container vrfs {
      description
        "VRF configuration";
      list vrf {
        // NCS patched for predictable order
        ordered-by user;
        key "vrf-name";
        description
          "VRF configuration";
        container vpn-id {
          presence "Indicates a vpn-id node is configured.";
          description
            "VPN-ID for the VRF";
          leaf vpn-oui {
            type string;
            // NCS drop mandatory statement
            description
              "OUI of VPNID OUI";
          }
          leaf vpn-index {
            type string;
            // NCS drop mandatory statement
            description
              "Index of VPNID Index";
          }
        }
        leaf fallback-vrf {
          type string;
          description
            "Fallback VRF";
        }
        leaf remote-route-filter-disable {
          type empty;
          description
            "For disabling remote route filtering for this
             VRF on core-facing card";
        }
        leaf create {
          type empty;
          description
            "VRF global configuration";
        }
        leaf mode-big {
          type empty;
          description
            "Configuration enable of big VRF";
        }
        leaf description {
          type string;
          description
            "A textual description of the VRF";
        }
        leaf vrf-name {
          type string;
          description
            "VRF name";
        }
        uses ncs_template_AF-TABLE;
      }
    }
    container global-af {
      description
        "global af";
      uses ncs_template_AF-TABLE;
    }
    container srlg {
      description
        "srlg";
      container interfaces {
        description
          "Set of interfaces configured with SRLG";
        list interface {
          // NCS patched for predictable order
          ordered-by user;
          key "interface-name";
          description
            "Interface configurations";
          container include-optical {
            description
              "Include optical configuration for an interface";
            leaf enable {
              type empty;
              description
                "Enable SRLG interface include optical";
            }
            leaf priority {
              type string;
              // NCS drop default statement
              description
                "Priority for optical domain values";
            }
          }
          container interface-group {
            description
              "Group configuration for an interface";
            container group-names {
              description
                "Set of group name under an interface";
              list group-name {
                // NCS patched for predictable order
                ordered-by user;
                key "group-name-index";
                description
                  "Group name included under interface";
                leaf group-name-index {
                  type string;
                  description
                    "Group name index";
                }
                leaf group-name {
                  type string;
                  // NCS drop mandatory statement
                  description
                    "Group name";
                }
                leaf srlg-priority {
                  type string;
                  // NCS drop default statement
                  description
                    "SRLG priority";
                }
              }
            }
            leaf enable {
              type empty;
              description
                "Enable SRLG interface group submode";
            }
          }
          container values {
            description
              "SRLG Value configuration for an interface";
            list value {
              // NCS patched for predictable order
              ordered-by user;
              key "srlg-index";
              description
                "SRLG value data";
              leaf srlg-index {
                type string;
                description
                  "SRLG index";
              }
              leaf srlg-value {
                type string;
                // NCS drop mandatory statement
                description
                  "SRLG value";
              }
              leaf srlg-priority {
                type string;
                // NCS drop default statement
                description
                  "SRLG priority";
              }
            }
          }
          container interface-srlg-names {
            description
              "SRLG Name configuration for an interface";
            list interface-srlg-name {
              // NCS patched for predictable order
              ordered-by user;
              key "srlg-name";
              description
                "SRLG name data";
              leaf srlg-name {
                type string;
                description
                  "SRLG name";
              }
            }
          }
          leaf enable {
            type empty;
            description
              "Enable SRLG interface";
          }
          leaf interface-name {
            type string;
            description
              "Interface name";
          }
        }
      }
      container srlg-names {
        description
          "Set of SRLG name configuration";
        list srlg-name {
          // NCS patched for predictable order
          ordered-by user;
          key "srlg-name";
          description
            "SRLG name configuration";
          leaf srlg-name {
            type string;
            description
              "SRLG name";
          }
          leaf srlg-value {
            type string;
            // NCS drop mandatory statement
            description
              "SRLG value";
          }
        }
      }
      container groups {
        description
          "Set of groups configured with SRLG";
        list group {
          // NCS patched for predictable order
          ordered-by user;
          key "group-name";
          description
            "Group configurations";
          container group-values {
            description
              "Set of SRLG values configured under a group";
            list group-value {
              // NCS patched for predictable order
              ordered-by user;
              key "srlg-index";
              description
                "Group SRLG values with attribute";
              leaf srlg-index {
                type string;
                description
                  "SRLG index";
              }
              leaf srlg-value {
                type string;
                // NCS drop mandatory statement
                description
                  "SRLG value";
              }
              leaf srlg-priority {
                type string;
                // NCS drop default statement
                description
                  "SRLG priority";
              }
            }
          }
          leaf enable {
            type empty;
            description
              "Enable SRLG group";
          }
          leaf group-name {
            type string;
            description
              "Group name";
          }
        }
      }
      container inherit-nodes {
        description
          "Set of inherit nodes configured with SRLG";
        list inherit-node {
          // NCS patched for predictable order
          ordered-by user;
          key "inherit-node-name";
          description
            "Inherit node configurations";
          container inherit-node-values {
            description
              "Set of SRLG values configured under an inherit
               node";
            list inherit-node-value {
              // NCS patched for predictable order
              ordered-by user;
              key "srlg-index";
              description
                "Inherit node SRLG value with attributes";
              leaf srlg-index {
                type string;
                description
                  "SRLG index";
              }
              leaf srlg-value {
                type string;
                // NCS drop mandatory statement
                description
                  "SRLG value";
              }
              leaf srlg-priority {
                type string;
                // NCS drop default statement
                description
                  "SRLG priority";
              }
            }
          }
          leaf enable {
            type empty;
            description
              "Enable SRLG inherit node";
          }
          leaf inherit-node-name {
            type string;
            description
              "The inherit node name";
          }
        }
      }
      leaf enable {
        type empty;
        description
          "Enable SRLG";
      }
    }
    container vrf-groups {
      description
        "vrf groups";
      list vrf-group {
        // NCS patched for predictable order
        ordered-by user;
        key "vrf-group-name";
        description
          "VRF group configuration";
        container vrfs {
          description
            "Set of VRFs configured under a VRF group";
          list vrf {
            // NCS patched for predictable order
            ordered-by user;
            key "vrf-name";
            description
              "VRF configuration";
            leaf vrf-name {
              type string;
              description
                "VRF name";
            }
          }
        }
        leaf enable {
          type empty;
          description
            "Enable VRF group";
        }
        leaf vrf-group-name {
          type string;
          description
            "VRF group name";
        }
      }
    }
    container selective-vrf-download {
      description
        "selective vrf download";
      leaf disable {
        type empty;
        description
          "Disable selective VRF download";
      }
    }
  }
  augment "/ncs:devices/ncs:template/ncs:ned-id/ncs:config/a1:interface-configurations/a1:interface-configuration" {
    leaf vrf {
      type string;
      description
        "Assign the interface to a VRF";
    }
    description
      "This augment extends the configuration data of
       'Cisco-IOS-XR-ifmgr-cfg'";
  }
  augment "/ncs:devices/ncs:device/ncs:live-status/a1:interface-configurations/a1:interface-configuration" {
    leaf vrf {
      tailf:ncs-device-type "netconf";
      tailf:display-when "not(../../../../ncs:module) or ../../../../ncs:module[ncs:name='Cisco-IOS-XR-infra-rsi-cfg'] or (../../../../ncs:live-status-protocol[not(ncs:capability)]) or (../../../../ncs:live-status-protocol/ncs:capability/ncs:module[.='Cisco-IOS-XR-infra-rsi-cfg'])";
      type xr:Cisco-ios-xr-string {
        length "1..32";
      }
      description
        "Assign the interface to a VRF";
    }
    description
      "This augment extends the configuration data of
       'Cisco-IOS-XR-ifmgr-cfg'";
  }
  augment "/ncs:devices/ncs:device/ncs:config/a1:interface-configurations/a1:interface-configuration" {
    leaf vrf {
      tailf:ncs-device-type "netconf";
      tailf:display-when "not(../../../../ncs:module) or ../../../../ncs:module[ncs:name='Cisco-IOS-XR-infra-rsi-cfg']";
      type xr:Cisco-ios-xr-string {
        length "1..32";
      }
      description
        "Assign the interface to a VRF";
    }
    description
      "This augment extends the configuration data of
       'Cisco-IOS-XR-ifmgr-cfg'";
  }
  augment "/ncs:devices/ncs:template/ncs:ned-id/ncs:config/a1:interface-configurations/a1:interface-configuration" {
    container afs {
      list af {
        // NCS patched for predictable order
        ordered-by user;
        key "af-name saf-name";
        description
          "The presence of this object enables the
           givenaddress-family and topology on the
           interface.";
        leaf af-name {
          type string;
          description
            "Address-family";
        }
        leaf saf-name {
          type string;
          description
            "Sub-address-family";
        }
      }
      list af-topology-name {
        // NCS patched for predictable order
        ordered-by user;
        key "topology-name af-name saf-name";
        description
          "The presence of this object enables the
           givenaddress-family and topology on the
           interface.";
        leaf topology-name {
          type string;
          description
            "Topology name";
        }
        leaf af-name {
          type string;
          description
            "Address-family";
        }
        leaf saf-name {
          type string;
          description
            "Sub-address-family";
        }
      }
      description
        "Per-address-family and topology configuration";
    }
    description
      "This augment extends the configuration data of
       'Cisco-IOS-XR-ifmgr-cfg'";
  }
  augment "/ncs:devices/ncs:device/ncs:live-status/a1:interface-configurations/a1:interface-configuration" {
    container afs {
      tailf:ncs-device-type "netconf";
      tailf:display-when "not(../../../../ncs:module) or ../../../../ncs:module[ncs:name='Cisco-IOS-XR-infra-rsi-cfg'] or (../../../../ncs:live-status-protocol[not(ncs:capability)]) or (../../../../ncs:live-status-protocol/ncs:capability/ncs:module[.='Cisco-IOS-XR-infra-rsi-cfg'])";
      list af {
        key "af-name saf-name";
        description
          "The presence of this object enables the
           givenaddress-family and topology on the
           interface.";
        leaf af-name {
          type Vrf-address-family;
          description
            "Address-family";
        }
        leaf saf-name {
          type Vrf-sub-address-family;
          description
            "Sub-address-family";
        }
      }
      list af-topology-name {
        key "topology-name af-name saf-name";
        description
          "The presence of this object enables the
           givenaddress-family and topology on the
           interface.";
        leaf topology-name {
          type xr:Cisco-ios-xr-string {
            length "1..32";
          }
          description
            "Topology name";
        }
        leaf af-name {
          type Vrf-address-family;
          description
            "Address-family";
        }
        leaf saf-name {
          type Vrf-sub-address-family;
          description
            "Sub-address-family";
        }
      }
      description
        "Per-address-family and topology configuration";
    }
    description
      "This augment extends the configuration data of
       'Cisco-IOS-XR-ifmgr-cfg'";
  }
  augment "/ncs:devices/ncs:device/ncs:config/a1:interface-configurations/a1:interface-configuration" {
    container afs {
      tailf:ncs-device-type "netconf";
      tailf:display-when "not(../../../../ncs:module) or ../../../../ncs:module[ncs:name='Cisco-IOS-XR-infra-rsi-cfg']";
      list af {
        key "af-name saf-name";
        description
          "The presence of this object enables the
           givenaddress-family and topology on the
           interface.";
        leaf af-name {
          type Vrf-address-family;
          description
            "Address-family";
        }
        leaf saf-name {
          type Vrf-sub-address-family;
          description
            "Sub-address-family";
        }
      }
      list af-topology-name {
        key "topology-name af-name saf-name";
        description
          "The presence of this object enables the
           givenaddress-family and topology on the
           interface.";
        leaf topology-name {
          type xr:Cisco-ios-xr-string {
            length "1..32";
          }
          description
            "Topology name";
        }
        leaf af-name {
          type Vrf-address-family;
          description
            "Address-family";
        }
        leaf saf-name {
          type Vrf-sub-address-family;
          description
            "Sub-address-family";
        }
      }
      description
        "Per-address-family and topology configuration";
    }
    description
      "This augment extends the configuration data of
       'Cisco-IOS-XR-ifmgr-cfg'";
  }
  augment "/ncs:devices/ncs:template/ncs:ned-id/ncs:config/a2:snmp/a2:notification" {
    container selective-vrf-download {
      description
        "CISCO-SELECTIVE-VRF-DOWNLOAD-MIB notification
         configuration";
      leaf role-change {
        type empty;
        description
          "Enable csvdEntityRoleChangeNotification
           notification";
      }
    }
    description
      "This augment extends the configuration data of
       'Cisco-IOS-XR-snmp-agent-cfg'";
  }
  augment "/ncs:devices/ncs:device/ncs:live-status/a2:snmp/a2:notification" {
    container selective-vrf-download {
      tailf:ncs-device-type "netconf";
      tailf:display-when "not(../../../../ncs:module) or ../../../../ncs:module[ncs:name='Cisco-IOS-XR-infra-rsi-cfg'] or (../../../../ncs:live-status-protocol[not(ncs:capability)]) or (../../../../ncs:live-status-protocol/ncs:capability/ncs:module[.='Cisco-IOS-XR-infra-rsi-cfg'])";
      description
        "CISCO-SELECTIVE-VRF-DOWNLOAD-MIB notification
         configuration";
      leaf role-change {
        type empty;
        description
          "Enable csvdEntityRoleChangeNotification
           notification";
      }
    }
    description
      "This augment extends the configuration data of
       'Cisco-IOS-XR-snmp-agent-cfg'";
  }
  augment "/ncs:devices/ncs:device/ncs:config/a2:snmp/a2:notification" {
    container selective-vrf-download {
      tailf:ncs-device-type "netconf";
      tailf:display-when "not(../../../../ncs:module) or ../../../../ncs:module[ncs:name='Cisco-IOS-XR-infra-rsi-cfg']";
      description
        "CISCO-SELECTIVE-VRF-DOWNLOAD-MIB notification
         configuration";
      leaf role-change {
        type empty;
        description
          "Enable csvdEntityRoleChangeNotification
           notification";
      }
    }
    description
      "This augment extends the configuration data of
       'Cisco-IOS-XR-snmp-agent-cfg'";
  }
}
