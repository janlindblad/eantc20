module Cisco-IOS-XR-infra-statsd-cfg {
  // Generated by yanger -t ncs
  tailf:mount-id f5500-nc-1.0:f5500-nc-1.0;
  tailf:ncs-device-type "netconf";

  namespace "http://cisco.com/ns/yang/Cisco-IOS-XR-infra-statsd-cfg";
  prefix Cisco-IOS-XR-infra-statsd-cfg;

  import Cisco-IOS-XR-ifmgr-cfg {
    prefix a1;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR infra-statsd package configuration.

     This module contains definitions
     for the following management objects:
       statistics: Global statistics configuration

     This YANG module augments the
       Cisco-IOS-XR-ifmgr-cfg
     module with configuration data.

     Copyright (c) 2013-2018 by Cisco Systems, Inc.
     All rights reserved.";

  revision 2017-05-01 {
    description
      "Fixing backward compatibility error in module.";
  }
  revision 2015-11-09 {
    description
      "IOS XR 6.0 revision.";
  }

  augment "/ncs:devices/ncs:device/ncs:config" {
    container statistics {
      tailf:ncs-device-type "netconf";
      tailf:display-when "not(../../ncs:module) or ../../ncs:module[ncs:name='Cisco-IOS-XR-infra-statsd-cfg']";
      description
        "Global statistics configuration";
      container period {
        description
          "Collection period for statistics polling";
        container service-accounting {
          description
            "Collection polling period for service
             accounting collectors";
          leaf polling-period {
            type uint32 {
              range "30..3600";
            }
            must 'not(../polling-disable)' {
              tailf:xpath-root 3;
            }
            description
              "Collection polling period for service
               accounting collectors";
          }
          leaf polling-disable {
            type empty;
            must 'not(../polling-period)' {
              tailf:xpath-root 3;
            }
            description
              "Disable periodic statistics polling for
               service accounting collectors";
          }
        }
      }
    }
  }
  augment "/ncs:devices/ncs:device/ncs:live-status" {
    container statistics {
      tailf:ncs-device-type "netconf";
      tailf:display-when "not(../../ncs:module) or ../../ncs:module[ncs:name='Cisco-IOS-XR-infra-statsd-cfg'] or (../../ncs:live-status-protocol[not(ncs:capability)]) or (../../ncs:live-status-protocol/ncs:capability/ncs:module[.='Cisco-IOS-XR-infra-statsd-cfg'])";
      description
        "Global statistics configuration";
      container period {
        description
          "Collection period for statistics polling";
        container service-accounting {
          description
            "Collection polling period for service
             accounting collectors";
          leaf polling-period {
            type uint32 {
              range "30..3600";
            }
            // NCS drop must statement
            description
              "Collection polling period for service
               accounting collectors";
          }
          leaf polling-disable {
            type empty;
            // NCS drop must statement
            description
              "Disable periodic statistics polling for
               service accounting collectors";
          }
        }
      }
    }
  }
  augment "/ncs:devices/ncs:template/ncs:ned-id/ncs:config" {
    container statistics {
      description
        "Global statistics configuration";
      container period {
        description
          "Collection period for statistics polling";
        container service-accounting {
          description
            "Collection polling period for service
             accounting collectors";
          leaf polling-period {
            type string;
            // NCS drop must statement
            description
              "Collection polling period for service
               accounting collectors";
          }
          leaf polling-disable {
            type empty;
            // NCS drop must statement
            description
              "Disable periodic statistics polling for
               service accounting collectors";
          }
        }
      }
    }
  }
  augment "/ncs:devices/ncs:template/ncs:ned-id/ncs:config/a1:interface-configurations/a1:interface-configuration" {
    container statistics {
      description
        "Per-interface statistics configuration";
      leaf load-interval {
        type string;
        // NCS drop default statement
        description
          "Specify interval for load calculation for an
           interface";
      }
    }
    description
      "This augment extends the configuration data of
       'Cisco-IOS-XR-ifmgr-cfg'";
  }
  augment "/ncs:devices/ncs:device/ncs:live-status/a1:interface-configurations/a1:interface-configuration" {
    container statistics {
      tailf:ncs-device-type "netconf";
      tailf:display-when "not(../../../../ncs:module) or ../../../../ncs:module[ncs:name='Cisco-IOS-XR-infra-statsd-cfg'] or (../../../../ncs:live-status-protocol[not(ncs:capability)]) or (../../../../ncs:live-status-protocol/ncs:capability/ncs:module[.='Cisco-IOS-XR-infra-statsd-cfg'])";
      description
        "Per-interface statistics configuration";
      leaf load-interval {
        type uint32 {
          range "0..600";
        }
        // NCS drop default statement
        description
          "Specify interval for load calculation for an
           interface";
      }
    }
    description
      "This augment extends the configuration data of
       'Cisco-IOS-XR-ifmgr-cfg'";
  }
  augment "/ncs:devices/ncs:device/ncs:config/a1:interface-configurations/a1:interface-configuration" {
    container statistics {
      tailf:ncs-device-type "netconf";
      tailf:display-when "not(../../../../ncs:module) or ../../../../ncs:module[ncs:name='Cisco-IOS-XR-infra-statsd-cfg']";
      description
        "Per-interface statistics configuration";
      leaf load-interval {
        type uint32 {
          range "0..600";
        }
        default "300";
        description
          "Specify interval for load calculation for an
           interface";
      }
    }
    description
      "This augment extends the configuration data of
       'Cisco-IOS-XR-ifmgr-cfg'";
  }
}
