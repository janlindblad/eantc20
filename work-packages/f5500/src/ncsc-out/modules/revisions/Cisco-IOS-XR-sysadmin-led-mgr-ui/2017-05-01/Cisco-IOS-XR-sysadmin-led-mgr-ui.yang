module Cisco-IOS-XR-sysadmin-led-mgr-ui {
  // Generated by yanger -t ncs
  tailf:mount-id f5500-nc-1.0:f5500-nc-1.0;
  tailf:ncs-device-type "netconf";

  namespace "http://www.cisco.com/ns/yang/Cisco-IOS-XR-sysadmin-led-mgr-ui";
  prefix Cisco-IOS-XR-sysadmin-led-mgr-ui;

  import Cisco-IOS-XR-sysadmin-show-trace {
    prefix show_trace;
  }
  import "f5500-nc-1.0" {
    prefix "f5500-nc-1.0";
  }
  import tailf-ncs {
    prefix ncs;
  }
  import tailf-common {
    prefix tailf;
  }

  organization
    "Cisco Systems Inc.";
  contact
    "Cisco Systems, Inc.
     Customer Service

     Postal: 170 West Tasman Drive
     San Jose, CA 95134

     Tel: +1 800 553-NETS

     E-mail: cs-yang@cisco.com";
  description
    "This module contains definitions
     for the Calvados model objects.

     This module provides CLI for Status, ATTN, ALARM LED's.

     Copyright (c) 2012-2018 by Cisco Systems, Inc.
     All rights reserved.";

  revision 2017-05-01 {
    description
      "Namespace change to comply with Cisco guidelines on namespace";
  }

  grouping ncs_template_hw-module-config-group {
    uses ncs_template_hw-module-attention-led-config-group;
  }

  grouping ncs_template_hw-module-attention-led-config-group {
    container attention-led {
      list location {
        // NCS patched for predictable order
        ordered-by user;
        key "location";
        leaf location {
          type string;
          // NCS drop mandatory statement
        }
      }
    }
  }

  grouping ncs_rpc_notif_hw-module-config-group {
    uses ncs_rpc_notif_hw-module-attention-led-config-group;
  }

  grouping ncs_rpc_notif_hw-module-attention-led-config-group {
    container attention-led {
      list location {
        key "location";
        leaf location {
          type string {
            pattern '([0-255])|((0?[0-9]|1[0-5])/(FC(0?[0-5])))|((0?[0-9]|1[0-5])/(RP(0?[0-1])))|((0?[0-9]|1[0-5])/(0?[0-9]|1[0-5])(/[1-2])?)|((F[0-3])/(FC(0?[0-9]|1[0-1])))|((F[0-3])/(SC(0?[0-1])))|(0?[0-9]/(SC(0?[0-1])))|(0?[0-9]/(FT(0?[0-2])))|(0?[0-9]/(PM(0?[0-9])))';
          }
          mandatory true;
        }
      }
    }
  }

  grouping live_ncs_hw-module-config-group {
    uses live_ncs_hw-module-attention-led-config-group;
  }

  grouping live_ncs_hw-module-attention-led-config-group {
    container attention-led {
      list location {
        key "location";
        leaf location {
          type string {
            pattern '([0-255])|((0?[0-9]|1[0-5])/(FC(0?[0-5])))|((0?[0-9]|1[0-5])/(RP(0?[0-1])))|((0?[0-9]|1[0-5])/(0?[0-9]|1[0-5])(/[1-2])?)|((F[0-3])/(FC(0?[0-9]|1[0-1])))|((F[0-3])/(SC(0?[0-1])))|(0?[0-9]/(SC(0?[0-1])))|(0?[0-9]/(FT(0?[0-2])))|(0?[0-9]/(PM(0?[0-9])))';
          }
          // NCS drop mandatory statement
        }
      }
    }
  }

  grouping hw-module-config-group {
    uses hw-module-attention-led-config-group;
  }

  grouping hw-module-attention-led-config-group {
    container attention-led {
      list location {
        key "location";
        leaf location {
          type string {
            pattern '([0-255])|((0?[0-9]|1[0-5])/(FC(0?[0-5])))|((0?[0-9]|1[0-5])/(RP(0?[0-1])))|((0?[0-9]|1[0-5])/(0?[0-9]|1[0-5])(/[1-2])?)|((F[0-3])/(FC(0?[0-9]|1[0-1])))|((F[0-3])/(SC(0?[0-1])))|(0?[0-9]/(SC(0?[0-1])))|(0?[0-9]/(FT(0?[0-2])))|(0?[0-9]/(PM(0?[0-9])))';
          }
          mandatory true;
        }
      }
    }
  }

  augment "/ncs:devices/ncs:device/ncs:config" {
    // NCS drop config false container led
  }
  augment "/ncs:devices/ncs:device/ncs:live-status" {
    container led {
      tailf:ncs-device-type "netconf";
      tailf:display-when "not(../../ncs:module) or ../../ncs:module[ncs:name='Cisco-IOS-XR-sysadmin-led-mgr-ui'] or (../../ncs:live-status-protocol[not(ncs:capability)]) or (../../ncs:live-status-protocol/ncs:capability/ncs:module[.='Cisco-IOS-XR-sysadmin-led-mgr-ui'])";
      description
        "Calvados Led Manager Status, Attn, Alarm inventory";
      list location {
        key "location";
        leaf location {
          type string;
        }
        list led_attributes {
          key "led_name";
          leaf location {
            type string;
          }
          leaf print_header {
            type boolean;
            // NCS drop default statement
          }
          leaf loc_header {
            type boolean;
            // NCS drop default statement
          }
          leaf led_name {
            type string;
          }
          leaf led_mode {
            type string;
          }
          leaf led_color {
            type string;
          }
        }
      }
      uses show_trace:live_ncs_traceable;
    }
  }
  augment "/ncs:devices/ncs:template/ncs:ned-id/ncs:config" {
    // NCS drop config false container led
  }
}
