module Cisco-IOS-XR-sysadmin-aaa-disaster-recovery {
  // Generated by yanger -t ncs
  tailf:mount-id f5500-nc-1.0:f5500-nc-1.0;
  tailf:ncs-device-type "netconf";

  namespace "http://www.cisco.com/ns/yang/Cisco-IOS-XR-sysadmin-aaa-disaster-recovery";
  prefix Cisco-IOS-XR-sysadmin-aaa-disaster-recovery;

  import tailf-common {
    prefix tailf;
  }
  import tailf-aaa {
    prefix aaa;
  }
  import "f5500-nc-1.0" {
    prefix "f5500-nc-1.0";
  }
  import tailf-ncs {
    prefix ncs;
  }

  organization
    "Cisco Systems Inc.";
  contact
    "clos-mgbl@cisco.com";
  description
    "This module contains definitions
     for the Calvados model objects.

     This module defines the system users authentication
     credentials and virtual IP that can be modified in
     runtime.

     Copyright (c) 2012-2018 by Cisco Systems, Inc.
     All rights reserved.";

  revision 2017-05-10 {
    description
      "Namespace changed from disaster-recovery to Cisco-IOS-XR-sysadmin-aaa-disaster-recovery";
  }

  augment "/ncs:devices/ncs:template/ncs:ned-id/ncs:config/aaa:aaa" {
    container disaster-recovery {
      leaf username {
        type string;
      }
      leaf password {
        type string;
      }
    }
  }
  augment "/ncs:devices/ncs:device/ncs:live-status/aaa:aaa" {
    container disaster-recovery {
      tailf:ncs-device-type "netconf";
      tailf:display-when "not(../../../ncs:module) or ../../../ncs:module[ncs:name='Cisco-IOS-XR-sysadmin-aaa-disaster-recovery'] or (../../../ncs:live-status-protocol[not(ncs:capability)]) or (../../../ncs:live-status-protocol/ncs:capability/ncs:module[.='Cisco-IOS-XR-sysadmin-aaa-disaster-recovery'])";
      leaf username {
        type leafref {
          path "/ncs:devices/ncs:device/ncs:live-status/aaa:aaa/aaa:authentication/aaa:users/aaa:user/aaa:name" {
            tailf:xpath-root 3;
          }
        }
      }
      leaf password {
        type tailf:md5-digest-string;
      }
    }
  }
  augment "/ncs:devices/ncs:device/ncs:config/aaa:aaa" {
    container disaster-recovery {
      tailf:ncs-device-type "netconf";
      tailf:display-when "not(../../../ncs:module) or ../../../ncs:module[ncs:name='Cisco-IOS-XR-sysadmin-aaa-disaster-recovery']";
      leaf username {
        type leafref {
          path "/ncs:devices/ncs:device/ncs:config/aaa:aaa/aaa:authentication/aaa:users/aaa:user/aaa:name" {
            tailf:xpath-root 3;
          }
        }
      }
      leaf password {
        type tailf:md5-digest-string;
      }
    }
  }
}
