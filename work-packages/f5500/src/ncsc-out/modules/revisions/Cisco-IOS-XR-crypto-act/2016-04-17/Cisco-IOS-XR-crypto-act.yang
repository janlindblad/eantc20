module Cisco-IOS-XR-crypto-act {
  // Generated by yanger -t ncs
  tailf:mount-id f5500-nc-1.0:f5500-nc-1.0;
  tailf:ncs-device-type "netconf";

  namespace "http://cisco.com/ns/yang/Cisco-IOS-XR-crypto-act";
  prefix Cisco-IOS-XR-crypto-act;

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2016-2018 by Cisco Systems, Inc.
     All rights reserved.";

  revision 2016-04-17 {
    description
      "IOS XR 6.1.1 revision.";
  }

  grouping ncs_template_KEY-MODULUS {
    leaf key-label {
      description
        "RSA keypair label";
      type string;
    }
    leaf key-modulus {
      description
        "Key modulus in the range of 512 to 4096 for your General Purpose Keypair. Choosing a key modulus greater than 512 may take a few minutes";
      type string;
      // NCS drop mandatory statement
    }
  }

  grouping ncs_rpc_notif_KEY-MODULUS {
    leaf key-label {
      description
        "RSA keypair label";
      type string;
    }
    leaf key-modulus {
      description
        "Key modulus in the range of 512 to 4096 for your General Purpose Keypair. Choosing a key modulus greater than 512 may take a few minutes";
      type int32 {
        range "512..4096";
      }
      mandatory true;
    }
  }

  grouping live_ncs_KEY-MODULUS {
    leaf key-label {
      description
        "RSA keypair label";
      type string;
    }
    leaf key-modulus {
      description
        "Key modulus in the range of 512 to 4096 for your General Purpose Keypair. Choosing a key modulus greater than 512 may take a few minutes";
      type int32 {
        range "512..4096";
      }
      // NCS drop mandatory statement
    }
  }

  grouping KEY-MODULUS {
    leaf key-label {
      description
        "RSA keypair label";
      type string;
    }
    leaf key-modulus {
      description
        "Key modulus in the range of 512 to 4096 for your General Purpose Keypair. Choosing a key modulus greater than 512 may take a few minutes";
      type int32 {
        range "512..4096";
      }
      mandatory true;
    }
  }

  augment "/ncs:devices/ncs:device/ncs:rpc" {
    container rpc-ca-trustpool-import-url-clean {
      tailf:ncs-device-type "netconf";
      tailf:display-when "not(../../ncs:module) or ../../ncs:module[ncs:name='Cisco-IOS-XR-crypto-act']";
      tailf:action ca-trustpool-import-url-clean {
        tailf:actionpoint ncsproxy {
          tailf:internal;
        }
        description
          "Remove downloaded certificates in trustpool";
        input {
          leaf url {
            description
              "in URL format";
            type string;
          }
        }
      }
    }
  }
  augment "/ncs:devices/ncs:device-group/ncs:ned-id/ncs:rpc" {
    container rpc-ca-trustpool-import-url-clean {
      tailf:ncs-device-type "netconf";
      tailf:display-when "/ncs:devices/ncs:device[ncs:name=current()/../../../ncs:member]/ncs:module[ncs:name='Cisco-IOS-XR-crypto-act']";
      tailf:action ca-trustpool-import-url-clean {
        tailf:actionpoint ncsproxy {
          tailf:internal;
        }
        description
          "Remove downloaded certificates in trustpool";
        input {
          leaf url {
            description
              "in URL format";
            type string;
          }
        }
      }
    }
  }
  augment "/ncs:devices/ncs:device/ncs:rpc" {
    container rpc-ca-trustpool-import-url {
      tailf:ncs-device-type "netconf";
      tailf:display-when "not(../../ncs:module) or ../../ncs:module[ncs:name='Cisco-IOS-XR-crypto-act']";
      tailf:action ca-trustpool-import-url {
        tailf:actionpoint ncsproxy {
          tailf:internal;
        }
        description
          "Manual import trustpool certificates from URL";
        input {
          leaf url {
            description
              "in URL format";
            type string;
          }
        }
      }
    }
  }
  augment "/ncs:devices/ncs:device-group/ncs:ned-id/ncs:rpc" {
    container rpc-ca-trustpool-import-url {
      tailf:ncs-device-type "netconf";
      tailf:display-when "/ncs:devices/ncs:device[ncs:name=current()/../../../ncs:member]/ncs:module[ncs:name='Cisco-IOS-XR-crypto-act']";
      tailf:action ca-trustpool-import-url {
        tailf:actionpoint ncsproxy {
          tailf:internal;
        }
        description
          "Manual import trustpool certificates from URL";
        input {
          leaf url {
            description
              "in URL format";
            type string;
          }
        }
      }
    }
  }
  augment "/ncs:devices/ncs:device/ncs:rpc" {
    container rpc-ca-crl-request {
      tailf:ncs-device-type "netconf";
      tailf:display-when "not(../../ncs:module) or ../../ncs:module[ncs:name='Cisco-IOS-XR-crypto-act']";
      tailf:action ca-crl-request {
        tailf:actionpoint ncsproxy {
          tailf:internal;
        }
        description
          "Actions on certificate revocation lists";
        input {
          leaf uri {
            description
              "CRL Distribution Point in URI format";
            type string;
            mandatory true;
          }
        }
        output {
          leaf certificate {
            type string;
            description
              "Certificate returned";
            mandatory true;
          }
        }
      }
    }
  }
  augment "/ncs:devices/ncs:device-group/ncs:ned-id/ncs:rpc" {
    container rpc-ca-crl-request {
      tailf:ncs-device-type "netconf";
      tailf:display-when "/ncs:devices/ncs:device[ncs:name=current()/../../../ncs:member]/ncs:module[ncs:name='Cisco-IOS-XR-crypto-act']";
      tailf:action ca-crl-request {
        tailf:actionpoint ncsproxy {
          tailf:internal;
        }
        description
          "Actions on certificate revocation lists";
        input {
          leaf uri {
            description
              "CRL Distribution Point in URI format";
            type string;
            mandatory true;
          }
        }
        output {
          container "device" {
            leaf "name" {
              type string;
            }
            leaf "info" {
              type string;
            }
            container "result" {
              leaf certificate {
                type string;
                description
                  "Certificate returned";
                mandatory true;
              }
            }
          }
        }
      }
    }
  }
  augment "/ncs:devices/ncs:device/ncs:rpc" {
    container rpc-ca-cancel-enroll {
      tailf:ncs-device-type "netconf";
      tailf:display-when "not(../../ncs:module) or ../../ncs:module[ncs:name='Cisco-IOS-XR-crypto-act']";
      tailf:action ca-cancel-enroll {
        tailf:actionpoint ncsproxy {
          tailf:internal;
        }
        description
          "Cancel enrollment from a CA";
        input {
          leaf server-name {
            description
              "CA Server Name";
            type string;
            mandatory true;
          }
        }
      }
    }
  }
  augment "/ncs:devices/ncs:device-group/ncs:ned-id/ncs:rpc" {
    container rpc-ca-cancel-enroll {
      tailf:ncs-device-type "netconf";
      tailf:display-when "/ncs:devices/ncs:device[ncs:name=current()/../../../ncs:member]/ncs:module[ncs:name='Cisco-IOS-XR-crypto-act']";
      tailf:action ca-cancel-enroll {
        tailf:actionpoint ncsproxy {
          tailf:internal;
        }
        description
          "Cancel enrollment from a CA";
        input {
          leaf server-name {
            description
              "CA Server Name";
            type string;
            mandatory true;
          }
        }
      }
    }
  }
  augment "/ncs:devices/ncs:device/ncs:rpc" {
    container rpc-ca-import-certificate {
      tailf:ncs-device-type "netconf";
      tailf:display-when "not(../../ncs:module) or ../../ncs:module[ncs:name='Cisco-IOS-XR-crypto-act']";
      tailf:action ca-import-certificate {
        tailf:actionpoint ncsproxy {
          tailf:internal;
        }
        description
          "Import a certificate from a s/tftp server or the terminal";
        input {
          leaf server-name {
            description
              "CA Server Name";
            type string;
            mandatory true;
          }
        }
      }
    }
  }
  augment "/ncs:devices/ncs:device-group/ncs:ned-id/ncs:rpc" {
    container rpc-ca-import-certificate {
      tailf:ncs-device-type "netconf";
      tailf:display-when "/ncs:devices/ncs:device[ncs:name=current()/../../../ncs:member]/ncs:module[ncs:name='Cisco-IOS-XR-crypto-act']";
      tailf:action ca-import-certificate {
        tailf:actionpoint ncsproxy {
          tailf:internal;
        }
        description
          "Import a certificate from a s/tftp server or the terminal";
        input {
          leaf server-name {
            description
              "CA Server Name";
            type string;
            mandatory true;
          }
        }
      }
    }
  }
  augment "/ncs:devices/ncs:device/ncs:rpc" {
    container rpc-ca-enroll {
      tailf:ncs-device-type "netconf";
      tailf:display-when "not(../../ncs:module) or ../../ncs:module[ncs:name='Cisco-IOS-XR-crypto-act']";
      tailf:action ca-enroll {
        tailf:actionpoint ncsproxy {
          tailf:internal;
        }
        description
          "Request a certificate from a CA";
        input {
          leaf server-name {
            description
              "CA Server Name";
            type string;
            mandatory true;
          }
        }
      }
    }
  }
  augment "/ncs:devices/ncs:device-group/ncs:ned-id/ncs:rpc" {
    container rpc-ca-enroll {
      tailf:ncs-device-type "netconf";
      tailf:display-when "/ncs:devices/ncs:device[ncs:name=current()/../../../ncs:member]/ncs:module[ncs:name='Cisco-IOS-XR-crypto-act']";
      tailf:action ca-enroll {
        tailf:actionpoint ncsproxy {
          tailf:internal;
        }
        description
          "Request a certificate from a CA";
        input {
          leaf server-name {
            description
              "CA Server Name";
            type string;
            mandatory true;
          }
        }
      }
    }
  }
  augment "/ncs:devices/ncs:device/ncs:rpc" {
    container rpc-ca-authenticate {
      tailf:ncs-device-type "netconf";
      tailf:display-when "not(../../ncs:module) or ../../ncs:module[ncs:name='Cisco-IOS-XR-crypto-act']";
      tailf:action ca-authenticate {
        tailf:actionpoint ncsproxy {
          tailf:internal;
        }
        description
          "Get the certification authority certificate";
        input {
          leaf server-name {
            description
              "CA Server Name";
            type string;
            mandatory true;
          }
        }
      }
    }
  }
  augment "/ncs:devices/ncs:device-group/ncs:ned-id/ncs:rpc" {
    container rpc-ca-authenticate {
      tailf:ncs-device-type "netconf";
      tailf:display-when "/ncs:devices/ncs:device[ncs:name=current()/../../../ncs:member]/ncs:module[ncs:name='Cisco-IOS-XR-crypto-act']";
      tailf:action ca-authenticate {
        tailf:actionpoint ncsproxy {
          tailf:internal;
        }
        description
          "Get the certification authority certificate";
        input {
          leaf server-name {
            description
              "CA Server Name";
            type string;
            mandatory true;
          }
        }
      }
    }
  }
  augment "/ncs:devices/ncs:device/ncs:rpc" {
    container rpc-key-import-authentication-rsa {
      tailf:ncs-device-type "netconf";
      tailf:display-when "not(../../ncs:module) or ../../ncs:module[ncs:name='Cisco-IOS-XR-crypto-act']";
      tailf:action key-import-authentication-rsa {
        tailf:actionpoint ncsproxy {
          tailf:internal;
        }
        description
          "Remove RSA authentication key";
        input {
          leaf path {
            description
              "Path to RSA pubkey file";
            type string;
            mandatory true;
          }
        }
      }
    }
  }
  augment "/ncs:devices/ncs:device-group/ncs:ned-id/ncs:rpc" {
    container rpc-key-import-authentication-rsa {
      tailf:ncs-device-type "netconf";
      tailf:display-when "/ncs:devices/ncs:device[ncs:name=current()/../../../ncs:member]/ncs:module[ncs:name='Cisco-IOS-XR-crypto-act']";
      tailf:action key-import-authentication-rsa {
        tailf:actionpoint ncsproxy {
          tailf:internal;
        }
        description
          "Remove RSA authentication key";
        input {
          leaf path {
            description
              "Path to RSA pubkey file";
            type string;
            mandatory true;
          }
        }
      }
    }
  }
  augment "/ncs:devices/ncs:device/ncs:rpc" {
    container rpc-key-zeroize-authentication-rsa {
      tailf:ncs-device-type "netconf";
      tailf:display-when "not(../../ncs:module) or ../../ncs:module[ncs:name='Cisco-IOS-XR-crypto-act']";
      tailf:action key-zeroize-authentication-rsa {
        tailf:actionpoint ncsproxy {
          tailf:internal;
        }
        description
          "Remove RSA authentication key";
      }
    }
  }
  augment "/ncs:devices/ncs:device-group/ncs:ned-id/ncs:rpc" {
    container rpc-key-zeroize-authentication-rsa {
      tailf:ncs-device-type "netconf";
      tailf:display-when "/ncs:devices/ncs:device[ncs:name=current()/../../../ncs:member]/ncs:module[ncs:name='Cisco-IOS-XR-crypto-act']";
      tailf:action key-zeroize-authentication-rsa {
        tailf:actionpoint ncsproxy {
          tailf:internal;
        }
        description
          "Remove RSA authentication key";
      }
    }
  }
  augment "/ncs:devices/ncs:device/ncs:rpc" {
    container rpc-key-zeroize-ecdsa {
      tailf:ncs-device-type "netconf";
      tailf:display-when "not(../../ncs:module) or ../../ncs:module[ncs:name='Cisco-IOS-XR-crypto-act']";
      tailf:action key-zeroize-ecdsa {
        tailf:actionpoint ncsproxy {
          tailf:internal;
        }
        description
          "Remove ECDSA key of curve type nistp256 | nistp384 | nistp521";
        input {
          leaf key-modulus {
            mandatory true;
            type enumeration {
              enum "nistp256" {
                value 0;
              }
              enum "nistp384" {
                value 1;
              }
              enum "nistp521" {
                value 2;
              }
            }
          }
          leaf key-label {
            description
              "ECDSA key label";
            type string;
          }
        }
      }
    }
  }
  augment "/ncs:devices/ncs:device-group/ncs:ned-id/ncs:rpc" {
    container rpc-key-zeroize-ecdsa {
      tailf:ncs-device-type "netconf";
      tailf:display-when "/ncs:devices/ncs:device[ncs:name=current()/../../../ncs:member]/ncs:module[ncs:name='Cisco-IOS-XR-crypto-act']";
      tailf:action key-zeroize-ecdsa {
        tailf:actionpoint ncsproxy {
          tailf:internal;
        }
        description
          "Remove ECDSA key of curve type nistp256 | nistp384 | nistp521";
        input {
          leaf key-modulus {
            mandatory true;
            type enumeration {
              enum "nistp256" {
                value 0;
              }
              enum "nistp384" {
                value 1;
              }
              enum "nistp521" {
                value 2;
              }
            }
          }
          leaf key-label {
            description
              "ECDSA key label";
            type string;
          }
        }
      }
    }
  }
  augment "/ncs:devices/ncs:device/ncs:rpc" {
    container rpc-key-zeroize-dsa {
      tailf:ncs-device-type "netconf";
      tailf:display-when "not(../../ncs:module) or ../../ncs:module[ncs:name='Cisco-IOS-XR-crypto-act']";
      tailf:action key-zeroize-dsa {
        tailf:actionpoint ncsproxy {
          tailf:internal;
        }
        description
          "Remove DSA keys";
      }
    }
  }
  augment "/ncs:devices/ncs:device-group/ncs:ned-id/ncs:rpc" {
    container rpc-key-zeroize-dsa {
      tailf:ncs-device-type "netconf";
      tailf:display-when "/ncs:devices/ncs:device[ncs:name=current()/../../../ncs:member]/ncs:module[ncs:name='Cisco-IOS-XR-crypto-act']";
      tailf:action key-zeroize-dsa {
        tailf:actionpoint ncsproxy {
          tailf:internal;
        }
        description
          "Remove DSA keys";
      }
    }
  }
  augment "/ncs:devices/ncs:device/ncs:rpc" {
    container rpc-key-zeroize-rsa {
      tailf:ncs-device-type "netconf";
      tailf:display-when "not(../../ncs:module) or ../../ncs:module[ncs:name='Cisco-IOS-XR-crypto-act']";
      tailf:action key-zeroize-rsa {
        tailf:actionpoint ncsproxy {
          tailf:internal;
        }
        description
          "Remove RSA keys";
        input {
          leaf key-label {
            description
              "RSA key label";
            type string;
          }
        }
      }
    }
  }
  augment "/ncs:devices/ncs:device-group/ncs:ned-id/ncs:rpc" {
    container rpc-key-zeroize-rsa {
      tailf:ncs-device-type "netconf";
      tailf:display-when "/ncs:devices/ncs:device[ncs:name=current()/../../../ncs:member]/ncs:module[ncs:name='Cisco-IOS-XR-crypto-act']";
      tailf:action key-zeroize-rsa {
        tailf:actionpoint ncsproxy {
          tailf:internal;
        }
        description
          "Remove RSA keys";
        input {
          leaf key-label {
            description
              "RSA key label";
            type string;
          }
        }
      }
    }
  }
  augment "/ncs:devices/ncs:device/ncs:rpc" {
    container rpc-key-generate-ecdsa {
      tailf:ncs-device-type "netconf";
      tailf:display-when "not(../../ncs:module) or ../../ncs:module[ncs:name='Cisco-IOS-XR-crypto-act']";
      tailf:action key-generate-ecdsa {
        tailf:actionpoint ncsproxy {
          tailf:internal;
        }
        description
          "Generate a ECDSA key of curve type nistp256 | nistp384 | nistp521";
        input {
          leaf key-modulus {
            mandatory true;
            type enumeration {
              enum "nistp256" {
                value 0;
              }
              enum "nistp384" {
                value 1;
              }
              enum "nistp521" {
                value 2;
              }
            }
          }
          leaf key-label {
            description
              "ECDSA key label";
            type string;
          }
        }
      }
    }
  }
  augment "/ncs:devices/ncs:device-group/ncs:ned-id/ncs:rpc" {
    container rpc-key-generate-ecdsa {
      tailf:ncs-device-type "netconf";
      tailf:display-when "/ncs:devices/ncs:device[ncs:name=current()/../../../ncs:member]/ncs:module[ncs:name='Cisco-IOS-XR-crypto-act']";
      tailf:action key-generate-ecdsa {
        tailf:actionpoint ncsproxy {
          tailf:internal;
        }
        description
          "Generate a ECDSA key of curve type nistp256 | nistp384 | nistp521";
        input {
          leaf key-modulus {
            mandatory true;
            type enumeration {
              enum "nistp256" {
                value 0;
              }
              enum "nistp384" {
                value 1;
              }
              enum "nistp521" {
                value 2;
              }
            }
          }
          leaf key-label {
            description
              "ECDSA key label";
            type string;
          }
        }
      }
    }
  }
  augment "/ncs:devices/ncs:device/ncs:rpc" {
    container rpc-key-generate-dsa {
      tailf:ncs-device-type "netconf";
      tailf:display-when "not(../../ncs:module) or ../../ncs:module[ncs:name='Cisco-IOS-XR-crypto-act']";
      tailf:action key-generate-dsa {
        tailf:actionpoint ncsproxy {
          tailf:internal;
        }
        description
          "Generate DSA keys";
        input {
          leaf key-modulus {
            description
              "Key modulus size can be 512, 768 or 1024 bits.";
            type int32 {
              range "512|768|1024";
            }
            mandatory true;
          }
        }
      }
    }
  }
  augment "/ncs:devices/ncs:device-group/ncs:ned-id/ncs:rpc" {
    container rpc-key-generate-dsa {
      tailf:ncs-device-type "netconf";
      tailf:display-when "/ncs:devices/ncs:device[ncs:name=current()/../../../ncs:member]/ncs:module[ncs:name='Cisco-IOS-XR-crypto-act']";
      tailf:action key-generate-dsa {
        tailf:actionpoint ncsproxy {
          tailf:internal;
        }
        description
          "Generate DSA keys";
        input {
          leaf key-modulus {
            description
              "Key modulus size can be 512, 768 or 1024 bits.";
            type int32 {
              range "512|768|1024";
            }
            mandatory true;
          }
        }
      }
    }
  }
  augment "/ncs:devices/ncs:device/ncs:rpc" {
    container rpc-key-generate-rsa {
      tailf:ncs-device-type "netconf";
      tailf:display-when "not(../../ncs:module) or ../../ncs:module[ncs:name='Cisco-IOS-XR-crypto-act']";
      tailf:action key-generate-rsa {
        tailf:actionpoint ncsproxy {
          tailf:internal;
        }
        description
          "Generate seperate RSA key pairs for signing and encryption";
        input {
          uses ncs_rpc_notif_KEY-MODULUS;
        }
      }
    }
  }
  augment "/ncs:devices/ncs:device-group/ncs:ned-id/ncs:rpc" {
    container rpc-key-generate-rsa {
      tailf:ncs-device-type "netconf";
      tailf:display-when "/ncs:devices/ncs:device[ncs:name=current()/../../../ncs:member]/ncs:module[ncs:name='Cisco-IOS-XR-crypto-act']";
      tailf:action key-generate-rsa {
        tailf:actionpoint ncsproxy {
          tailf:internal;
        }
        description
          "Generate seperate RSA key pairs for signing and encryption";
        input {
          uses ncs_rpc_notif_KEY-MODULUS;
        }
      }
    }
  }
  augment "/ncs:devices/ncs:device/ncs:rpc" {
    container rpc-key-generate-rsa-usage-keys {
      tailf:ncs-device-type "netconf";
      tailf:display-when "not(../../ncs:module) or ../../ncs:module[ncs:name='Cisco-IOS-XR-crypto-act']";
      tailf:action key-generate-rsa-usage-keys {
        tailf:actionpoint ncsproxy {
          tailf:internal;
        }
        description
          "Generate seperate RSA key pairs for signing and encryption";
        input {
          uses ncs_rpc_notif_KEY-MODULUS;
        }
      }
    }
  }
  augment "/ncs:devices/ncs:device-group/ncs:ned-id/ncs:rpc" {
    container rpc-key-generate-rsa-usage-keys {
      tailf:ncs-device-type "netconf";
      tailf:display-when "/ncs:devices/ncs:device[ncs:name=current()/../../../ncs:member]/ncs:module[ncs:name='Cisco-IOS-XR-crypto-act']";
      tailf:action key-generate-rsa-usage-keys {
        tailf:actionpoint ncsproxy {
          tailf:internal;
        }
        description
          "Generate seperate RSA key pairs for signing and encryption";
        input {
          uses ncs_rpc_notif_KEY-MODULUS;
        }
      }
    }
  }
  augment "/ncs:devices/ncs:device/ncs:rpc" {
    container rpc-key-generate-rsa-general-keys {
      tailf:ncs-device-type "netconf";
      tailf:display-when "not(../../ncs:module) or ../../ncs:module[ncs:name='Cisco-IOS-XR-crypto-act']";
      tailf:action key-generate-rsa-general-keys {
        tailf:actionpoint ncsproxy {
          tailf:internal;
        }
        description
          "Generate a general purpose RSA key pair for signing and encryption";
        input {
          uses ncs_rpc_notif_KEY-MODULUS;
        }
      }
    }
  }
  augment "/ncs:devices/ncs:device-group/ncs:ned-id/ncs:rpc" {
    container rpc-key-generate-rsa-general-keys {
      tailf:ncs-device-type "netconf";
      tailf:display-when "/ncs:devices/ncs:device[ncs:name=current()/../../../ncs:member]/ncs:module[ncs:name='Cisco-IOS-XR-crypto-act']";
      tailf:action key-generate-rsa-general-keys {
        tailf:actionpoint ncsproxy {
          tailf:internal;
        }
        description
          "Generate a general purpose RSA key pair for signing and encryption";
        input {
          uses ncs_rpc_notif_KEY-MODULUS;
        }
      }
    }
  }
}
