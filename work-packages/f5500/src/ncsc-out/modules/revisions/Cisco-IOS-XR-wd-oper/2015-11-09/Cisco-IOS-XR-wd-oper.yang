module Cisco-IOS-XR-wd-oper {
  // Generated by yanger -t ncs
  tailf:mount-id f5500-nc-1.0:f5500-nc-1.0;
  tailf:ncs-device-type "netconf";

  namespace "http://cisco.com/ns/yang/Cisco-IOS-XR-wd-oper";
  prefix Cisco-IOS-XR-wd-oper;

  import Cisco-IOS-XR-types {
    prefix xr;
  }
  include Cisco-IOS-XR-wd-oper-sub1 {
    revision-date 2015-11-09;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR wd package operational data.

     This module contains definitions
     for the following management objects:
       watchdog: Watchdog information

     Copyright (c) 2013-2018 by Cisco Systems, Inc.
     All rights reserved.";

  revision 2015-11-09 {
    description
      "IOS XR 6.0 revision.";
  }

  augment "/ncs:devices/ncs:device/ncs:config" {
    // NCS drop config false container watchdog
  }
  augment "/ncs:devices/ncs:device/ncs:live-status" {
    container watchdog {
      tailf:ncs-device-type "netconf";
      tailf:display-when "not(../../ncs:module) or ../../ncs:module[ncs:name='Cisco-IOS-XR-wd-oper'] or (../../ncs:live-status-protocol[not(ncs:capability)]) or (../../ncs:live-status-protocol/ncs:capability/ncs:module[.='Cisco-IOS-XR-wd-oper'])";
      description
        "Watchdog information";
      container nodes {
        description
          "List of nodes";
        list node {
          key "node-name";
          description
            "Node ID";
          container threshold-memory {
            description
              "Threshold memory";
            container default {
              description
                "System default memory";
              uses live_ncs_MEMORY-THRESHOLD;
            }
            container configured {
              description
                "Memory configured by user";
              uses live_ncs_CONF-MEM-THRESHOLD;
            }
          }
          container memory-state {
            description
              "Memory state";
            uses live_ncs_MEMORY-DETAILS;
          }
          container overload-state {
            description
              "Display overload control state";
            uses live_ncs_OVERLOAD-CONTROL;
          }
          leaf node-name {
            type xr:Node-id;
            description
              "Node name";
          }
        }
      }
    }
  }
  augment "/ncs:devices/ncs:template/ncs:ned-id/ncs:config" {
    // NCS drop config false container watchdog
  }
}
