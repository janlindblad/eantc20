module nc-notifications {
  // Generated by yanger -t ncs
  tailf:mount-id f5500-nc-1.0:f5500-nc-1.0;
  tailf:ncs-device-type "netconf";

  namespace "urn:ietf:params:xml:ns:netmod:notification";
  prefix nc-notifications;

  import ietf-yang-types {
    prefix yang;
  }
  import notifications {
    prefix ncEvent;
  }
  import "f5500-nc-1.0" {
    prefix "f5500-nc-1.0";
  }
  import tailf-ncs {
    prefix ncs;
  }
  import tailf-common {
    prefix tailf;
  }

  organization
    "IETF NETCONF WG";
  contact
    "netconf@ietf.org";
  description
    "Conversion of the 'manageEvent' XSD in the NETCONF
     Notifications RFC.";

  revision 2008-07-14 {
    description
      "Initial revision.";
    reference "RFC 5277: NETCONF Event Notifications";
  }

  augment "/ncs:devices/ncs:device/ncs:netconf-notifications/ncs:received-notifications/ncs:notification/ncs:data" {
    container notificationComplete {
      presence "";
      config false;
      description
        "This notification is sent to signal the end of a notification
         subscription. It is sent in the case that stopTime was
         specified during the creation of the subscription.";
    }
  }
  augment "/ncs:devices/ncs:device/ncs:netconf-notifications/ncs:received-notifications/ncs:notification/ncs:data" {
    container replayComplete {
      presence "";
      config false;
      description
        "This notification is sent to signal the end of a replay
         portion of a subscription.";
    }
  }
  augment "/ncs:devices/ncs:device/ncs:config" {
    // NCS drop config false container netconf
  }
  augment "/ncs:devices/ncs:device/ncs:live-status" {
    container netconf {
      presence "In NCS this node is optional";
      tailf:ncs-device-type "netconf";
      tailf:display-when "not(../../ncs:capability) or ../../ncs:capability[ncs:uri='urn:ietf:params:netconf:capability:notification:1.0']";
      description
        "Top-level element in the notification namespace";
      container streams {
        description
          "The list of event streams supported by the system. When
           a query is issued, the returned set of streams is
           determined based on user privileges.";
        list stream {
          key "name";
          // NCS drop min-elements statement
          description
            "Stream name, description and other information.";
          leaf name {
            type ncEvent:streamNameType;
            description
              "The name of the event stream. If this is the default
               NETCONF stream, this must have the value 'NETCONF'.";
          }
          leaf description {
            type string;
            // NCS drop mandatory statement
            description
              "A description of the event stream, including such
               information as the type of events that are sent over
               this stream.";
          }
          leaf replaySupport {
            type boolean;
            // NCS drop mandatory statement
            description
              "A description of the event stream, including such
               information as the type of events that are sent over
               this stream.";
          }
          leaf replayLogCreationTime {
            type yang:date-and-time;
            description
              "The timestamp of the creation of the log used to support
               the replay function on this stream. Note that this might
               be earlier then the earliest available notification in
               the log. This object is updated if the log resets for
               some reason.  This object MUST be present if replay is
               supported.";
          }
        }
      }
    }
  }
  augment "/ncs:devices/ncs:template/ncs:ned-id/ncs:config" {
    // NCS drop config false container netconf
  }
}
