module Cisco-IOS-XR-config-valid-ccv-oper {
  // Generated by yanger -t ncs
  tailf:mount-id f5500-nc-1.0:f5500-nc-1.0;
  tailf:ncs-device-type "netconf";

  namespace "http://cisco.com/ns/yang/Cisco-IOS-XR-config-valid-ccv-oper";
  prefix Cisco-IOS-XR-config-valid-ccv-oper;

  import Cisco-IOS-XR-config-cfgmgr-oper {
    prefix a1;
  }
  include Cisco-IOS-XR-config-valid-ccv-oper-sub1 {
    revision-date 2015-11-09;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR config-valid-ccv package operational data.

     This YANG module augments the
       Cisco-IOS-XR-config-cfgmgr-oper
     module with state data.

     Copyright (c) 2013-2018 by Cisco Systems, Inc.
     All rights reserved.";

  revision 2015-11-09 {
    description
      "IOS XR 6.0 revision.";
  }

  augment "/ncs:devices/ncs:device/ncs:live-status/a1:config/a1:global" {
    container validation {
      tailf:ncs-device-type "netconf";
      tailf:display-when "not(../../../../ncs:module) or ../../../../ncs:module[ncs:name='Cisco-IOS-XR-config-valid-ccv-oper'] or (../../../../ncs:live-status-protocol[not(ncs:capability)]) or (../../../../ncs:live-status-protocol/ncs:capability/ncs:module[.='Cisco-IOS-XR-config-valid-ccv-oper'])";
      description
        "Configuration validation operational data";
      container unsupported-configs {
        description
          "Unsupported config warnings present in running
           configuration";
        list unsupported-config {
          key "xpath";
          description
            "Information about an unsupported warning";
          leaf xpath {
            type string;
            description
              "XPath of the unsupported configuration";
          }
          uses live_ncs_CCV-YVE-VALIDATION-FAILURE-ITEM-BAG;
        }
      }
      container persistent-failures {
        description
          "Validation failures present in running
           configuration";
        list persistent-failure {
          key "xpath";
          description
            "Information about a validation failure";
          leaf xpath {
            type string;
            description
              "XPath of the failed configuration";
          }
          uses live_ncs_CCV-YVE-VALIDATION-FAILURE-ITEM-BAG;
        }
      }
    }
    description
      "This augment extends the operational data of
       'Cisco-IOS-XR-config-cfgmgr-oper'";
  }
}
