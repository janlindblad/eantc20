submodule Cisco-IOS-XR-perf-meas-oper-sub1 {
  // Generated by yanger -t ncs
  tailf:mount-id f5500-nc-1.0:f5500-nc-1.0;

  belongs-to Cisco-IOS-XR-perf-meas-oper {
    prefix Cisco-IOS-XR-perf-meas-oper-sub1;
  }

  import ietf-inet-types {
    prefix inet;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR perf-meas package operational data.

     Copyright (c) 2013-2018 by Cisco Systems, Inc.
     All rights reserved.";

  revision 2017-10-17 {
    description
      "Revision Zero.";
  }
  revision 2015-11-09 {
    description
      "IOS XR 6.0 revision.";
  }

  grouping ncs_template_PM-RESP-INTF-BAG {
    description
      "PM Responder Interface bag";
    container interface-counters {
      description
        "Per interface responder counters";
      uses ncs_template_PM-COUNTER-RESP-BAG;
    }
    leaf interface-name-xr {
      type string;
      description
        "Interface name";
    }
    leaf interface-handle {
      type string;
      description
        "Interface handle";
    }
    leaf source-address {
      type string;
      description
        "Source Address";
    }
    leaf source-v6-address {
      type string;
      description
        "Source V6 Address";
    }
    leaf packet-rate {
      type string;
      description
        "Incoming packet rate";
    }
    leaf packet-rate-high-water-mark {
      type string;
      description
        "Incoming packet rate high water mark";
    }
    leaf cleanup-time-remaining {
      type string;
      units "second";
      description
        "Seconds until an inactive interface is cleaned
         up";
    }
  }

  grouping ncs_template_PM-COUNTER-RESP-BAG {
    description
      "PM Responder counters";
    leaf reply-packet-sent {
      type string;
      description
        "Response packets sent";
    }
    leaf reply-packet-sent-error {
      type string;
      description
        "Response packets sent error";
    }
    leaf query-packet-received {
      type string;
      description
        "Response packets received";
    }
    leaf received-packet-error-urotlv-not-present {
      type string;
      description
        "Received packet error, URO TLV not present";
    }
    leaf received-packet-error-invalid-source-port-number {
      type string;
      description
        "Received packet error, invalid source port
         number";
    }
    leaf received-packet-error-no-source-address {
      type string;
      description
        "Received packet error, no source address";
    }
    leaf received-packet-error-no-return-path {
      type string;
      description
        "Received packet error, no return path";
    }
    leaf received-packet-error-invalid-querier-control-code {
      type string;
      description
        "Received packet error, invalid querier control
         code";
    }
    leaf received-packet-error-unsupported-timestamp-format {
      type string;
      description
        "Received packet error, unsupported timestamp
         format";
    }
    leaf received-packet-error-timestamp-not-available {
      type string;
      description
        "Received packet error, timestamp not available";
    }
    leaf received-packet-error-unsupported-mandatory-tlv {
      type string;
      description
        "Received packet error, unsupported mandatory TLV";
    }
    leaf received-packet-error-invalid-packet {
      type string;
      description
        "Received packet error, invalid packet";
    }
  }

  grouping ncs_template_PM-RESP-SUMMARY-BAG {
    description
      "PM Responder summary bag";
    container responder-counters {
      description
        "Global responder counters";
      uses ncs_template_PM-COUNTER-RESP-BAG;
    }
    leaf total-interfaces {
      type string;
      description
        "Number of interfaces in the responder cache";
    }
    leaf packet-rate {
      type string;
      description
        "Global incoming packet rate";
    }
    leaf packet-rate-high-water-mark {
      type string;
      description
        "Global incoming packet rate high water mark";
    }
  }

  grouping ncs_rpc_notif_PM-RESP-INTF-BAG {
    description
      "PM Responder Interface bag";
    container interface-counters {
      description
        "Per interface responder counters";
      uses ncs_rpc_notif_PM-COUNTER-RESP-BAG;
    }
    leaf interface-name-xr {
      type string;
      description
        "Interface name";
    }
    leaf interface-handle {
      type uint32;
      description
        "Interface handle";
    }
    leaf source-address {
      type inet:ipv4-address;
      description
        "Source Address";
    }
    leaf source-v6-address {
      type inet:ipv6-address;
      description
        "Source V6 Address";
    }
    leaf packet-rate {
      type uint32;
      description
        "Incoming packet rate";
    }
    leaf packet-rate-high-water-mark {
      type uint32;
      description
        "Incoming packet rate high water mark";
    }
    leaf cleanup-time-remaining {
      type uint32;
      units "second";
      description
        "Seconds until an inactive interface is cleaned
         up";
    }
  }

  grouping ncs_rpc_notif_PM-COUNTER-RESP-BAG {
    description
      "PM Responder counters";
    leaf reply-packet-sent {
      type uint64;
      description
        "Response packets sent";
    }
    leaf reply-packet-sent-error {
      type uint64;
      description
        "Response packets sent error";
    }
    leaf query-packet-received {
      type uint64;
      description
        "Response packets received";
    }
    leaf received-packet-error-urotlv-not-present {
      type uint64;
      description
        "Received packet error, URO TLV not present";
    }
    leaf received-packet-error-invalid-source-port-number {
      type uint64;
      description
        "Received packet error, invalid source port
         number";
    }
    leaf received-packet-error-no-source-address {
      type uint64;
      description
        "Received packet error, no source address";
    }
    leaf received-packet-error-no-return-path {
      type uint64;
      description
        "Received packet error, no return path";
    }
    leaf received-packet-error-invalid-querier-control-code {
      type uint64;
      description
        "Received packet error, invalid querier control
         code";
    }
    leaf received-packet-error-unsupported-timestamp-format {
      type uint64;
      description
        "Received packet error, unsupported timestamp
         format";
    }
    leaf received-packet-error-timestamp-not-available {
      type uint64;
      description
        "Received packet error, timestamp not available";
    }
    leaf received-packet-error-unsupported-mandatory-tlv {
      type uint64;
      description
        "Received packet error, unsupported mandatory TLV";
    }
    leaf received-packet-error-invalid-packet {
      type uint64;
      description
        "Received packet error, invalid packet";
    }
  }

  grouping ncs_rpc_notif_PM-RESP-SUMMARY-BAG {
    description
      "PM Responder summary bag";
    container responder-counters {
      description
        "Global responder counters";
      uses ncs_rpc_notif_PM-COUNTER-RESP-BAG;
    }
    leaf total-interfaces {
      type uint32;
      description
        "Number of interfaces in the responder cache";
    }
    leaf packet-rate {
      type uint32;
      description
        "Global incoming packet rate";
    }
    leaf packet-rate-high-water-mark {
      type uint32;
      description
        "Global incoming packet rate high water mark";
    }
  }

  grouping live_ncs_PM-RESP-INTF-BAG {
    description
      "PM Responder Interface bag";
    container interface-counters {
      description
        "Per interface responder counters";
      uses live_ncs_PM-COUNTER-RESP-BAG;
    }
    leaf interface-name-xr {
      type string;
      description
        "Interface name";
    }
    leaf interface-handle {
      type uint32;
      description
        "Interface handle";
    }
    leaf source-address {
      type inet:ipv4-address;
      description
        "Source Address";
    }
    leaf source-v6-address {
      type inet:ipv6-address;
      description
        "Source V6 Address";
    }
    leaf packet-rate {
      type uint32;
      description
        "Incoming packet rate";
    }
    leaf packet-rate-high-water-mark {
      type uint32;
      description
        "Incoming packet rate high water mark";
    }
    leaf cleanup-time-remaining {
      type uint32;
      units "second";
      description
        "Seconds until an inactive interface is cleaned
         up";
    }
  }

  grouping live_ncs_PM-COUNTER-RESP-BAG {
    description
      "PM Responder counters";
    leaf reply-packet-sent {
      type uint64;
      description
        "Response packets sent";
    }
    leaf reply-packet-sent-error {
      type uint64;
      description
        "Response packets sent error";
    }
    leaf query-packet-received {
      type uint64;
      description
        "Response packets received";
    }
    leaf received-packet-error-urotlv-not-present {
      type uint64;
      description
        "Received packet error, URO TLV not present";
    }
    leaf received-packet-error-invalid-source-port-number {
      type uint64;
      description
        "Received packet error, invalid source port
         number";
    }
    leaf received-packet-error-no-source-address {
      type uint64;
      description
        "Received packet error, no source address";
    }
    leaf received-packet-error-no-return-path {
      type uint64;
      description
        "Received packet error, no return path";
    }
    leaf received-packet-error-invalid-querier-control-code {
      type uint64;
      description
        "Received packet error, invalid querier control
         code";
    }
    leaf received-packet-error-unsupported-timestamp-format {
      type uint64;
      description
        "Received packet error, unsupported timestamp
         format";
    }
    leaf received-packet-error-timestamp-not-available {
      type uint64;
      description
        "Received packet error, timestamp not available";
    }
    leaf received-packet-error-unsupported-mandatory-tlv {
      type uint64;
      description
        "Received packet error, unsupported mandatory TLV";
    }
    leaf received-packet-error-invalid-packet {
      type uint64;
      description
        "Received packet error, invalid packet";
    }
  }

  grouping live_ncs_PM-RESP-SUMMARY-BAG {
    description
      "PM Responder summary bag";
    container responder-counters {
      description
        "Global responder counters";
      uses live_ncs_PM-COUNTER-RESP-BAG;
    }
    leaf total-interfaces {
      type uint32;
      description
        "Number of interfaces in the responder cache";
    }
    leaf packet-rate {
      type uint32;
      description
        "Global incoming packet rate";
    }
    leaf packet-rate-high-water-mark {
      type uint32;
      description
        "Global incoming packet rate high water mark";
    }
  }

  grouping PM-RESP-INTF-BAG {
    description
      "PM Responder Interface bag";
    container interface-counters {
      description
        "Per interface responder counters";
      uses PM-COUNTER-RESP-BAG;
    }
    leaf interface-name-xr {
      type string;
      description
        "Interface name";
    }
    leaf interface-handle {
      type uint32;
      description
        "Interface handle";
    }
    leaf source-address {
      type inet:ipv4-address;
      description
        "Source Address";
    }
    leaf source-v6-address {
      type inet:ipv6-address;
      description
        "Source V6 Address";
    }
    leaf packet-rate {
      type uint32;
      description
        "Incoming packet rate";
    }
    leaf packet-rate-high-water-mark {
      type uint32;
      description
        "Incoming packet rate high water mark";
    }
    leaf cleanup-time-remaining {
      type uint32;
      units "second";
      description
        "Seconds until an inactive interface is cleaned
         up";
    }
  }

  grouping PM-COUNTER-RESP-BAG {
    description
      "PM Responder counters";
    leaf reply-packet-sent {
      type uint64;
      description
        "Response packets sent";
    }
    leaf reply-packet-sent-error {
      type uint64;
      description
        "Response packets sent error";
    }
    leaf query-packet-received {
      type uint64;
      description
        "Response packets received";
    }
    leaf received-packet-error-urotlv-not-present {
      type uint64;
      description
        "Received packet error, URO TLV not present";
    }
    leaf received-packet-error-invalid-source-port-number {
      type uint64;
      description
        "Received packet error, invalid source port
         number";
    }
    leaf received-packet-error-no-source-address {
      type uint64;
      description
        "Received packet error, no source address";
    }
    leaf received-packet-error-no-return-path {
      type uint64;
      description
        "Received packet error, no return path";
    }
    leaf received-packet-error-invalid-querier-control-code {
      type uint64;
      description
        "Received packet error, invalid querier control
         code";
    }
    leaf received-packet-error-unsupported-timestamp-format {
      type uint64;
      description
        "Received packet error, unsupported timestamp
         format";
    }
    leaf received-packet-error-timestamp-not-available {
      type uint64;
      description
        "Received packet error, timestamp not available";
    }
    leaf received-packet-error-unsupported-mandatory-tlv {
      type uint64;
      description
        "Received packet error, unsupported mandatory TLV";
    }
    leaf received-packet-error-invalid-packet {
      type uint64;
      description
        "Received packet error, invalid packet";
    }
  }

  grouping PM-RESP-SUMMARY-BAG {
    description
      "PM Responder summary bag";
    container responder-counters {
      description
        "Global responder counters";
      uses PM-COUNTER-RESP-BAG;
    }
    leaf total-interfaces {
      type uint32;
      description
        "Number of interfaces in the responder cache";
    }
    leaf packet-rate {
      type uint32;
      description
        "Global incoming packet rate";
    }
    leaf packet-rate-high-water-mark {
      type uint32;
      description
        "Global incoming packet rate high water mark";
    }
  }
}
