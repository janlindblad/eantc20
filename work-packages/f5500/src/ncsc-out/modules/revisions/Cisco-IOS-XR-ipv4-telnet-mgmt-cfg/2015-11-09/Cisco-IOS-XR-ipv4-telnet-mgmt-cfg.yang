module Cisco-IOS-XR-ipv4-telnet-mgmt-cfg {
  // Generated by yanger -t ncs
  tailf:mount-id f5500-nc-1.0:f5500-nc-1.0;
  tailf:ncs-device-type "netconf";

  namespace "http://cisco.com/ns/yang/Cisco-IOS-XR-ipv4-telnet-mgmt-cfg";
  prefix Cisco-IOS-XR-ipv4-telnet-mgmt-cfg;

  import Cisco-IOS-XR-types {
    prefix xr;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ipv4-telnet-mgmt package configuration.

     This module contains definitions
     for the following management objects:
       telnet: Global Telnet configuration commands

     Copyright (c) 2013-2018 by Cisco Systems, Inc.
     All rights reserved.";

  revision 2015-11-09 {
    description
      "IOS XR 6.0 revision.";
  }
  revision 2015-10-30 {
    description
      "Descriptions updated.";
  }

  augment "/ncs:devices/ncs:device/ncs:config" {
    container telnet {
      tailf:ncs-device-type "netconf";
      tailf:display-when "not(../../ncs:module) or ../../ncs:module[ncs:name='Cisco-IOS-XR-ipv4-telnet-mgmt-cfg']";
      description
        "Global Telnet configuration commands";
      container vrfs {
        description
          "VRF name for telnet service";
        list vrf {
          key "vrf-name";
          description
            "VRF name for telnet service";
          container ipv4 {
            description
              "IPv4 configuration";
            leaf dscp {
              type uint32 {
                range "0..63";
              }
              description
                "Specify the DSCP value";
            }
          }
          leaf vrf-name {
            type xr:Cisco-ios-xr-string;
            description
              "VRF name";
          }
        }
      }
    }
  }
  augment "/ncs:devices/ncs:device/ncs:live-status" {
    container telnet {
      tailf:ncs-device-type "netconf";
      tailf:display-when "not(../../ncs:module) or ../../ncs:module[ncs:name='Cisco-IOS-XR-ipv4-telnet-mgmt-cfg'] or (../../ncs:live-status-protocol[not(ncs:capability)]) or (../../ncs:live-status-protocol/ncs:capability/ncs:module[.='Cisco-IOS-XR-ipv4-telnet-mgmt-cfg'])";
      description
        "Global Telnet configuration commands";
      container vrfs {
        description
          "VRF name for telnet service";
        list vrf {
          key "vrf-name";
          description
            "VRF name for telnet service";
          container ipv4 {
            description
              "IPv4 configuration";
            leaf dscp {
              type uint32 {
                range "0..63";
              }
              description
                "Specify the DSCP value";
            }
          }
          leaf vrf-name {
            type xr:Cisco-ios-xr-string;
            description
              "VRF name";
          }
        }
      }
    }
  }
  augment "/ncs:devices/ncs:template/ncs:ned-id/ncs:config" {
    container telnet {
      description
        "Global Telnet configuration commands";
      container vrfs {
        description
          "VRF name for telnet service";
        list vrf {
          // NCS patched for predictable order
          ordered-by user;
          key "vrf-name";
          description
            "VRF name for telnet service";
          container ipv4 {
            description
              "IPv4 configuration";
            leaf dscp {
              type string;
              description
                "Specify the DSCP value";
            }
          }
          leaf vrf-name {
            type string;
            description
              "VRF name";
          }
        }
      }
    }
  }
}
