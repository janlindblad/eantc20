module Cisco-IOS-XR-mpls-lsd-oper {
  // Generated by yanger -t ncs
  tailf:mount-id f5500-nc-1.0:f5500-nc-1.0;
  tailf:ncs-device-type "netconf";

  namespace "http://cisco.com/ns/yang/Cisco-IOS-XR-mpls-lsd-oper";
  prefix Cisco-IOS-XR-mpls-lsd-oper;

  import ietf-inet-types {
    prefix inet;
  }
  import Cisco-IOS-XR-types {
    prefix xr;
  }
  include Cisco-IOS-XR-mpls-lsd-oper-sub1 {
    revision-date 2017-09-07;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR mpls-lsd package operational data.

     This module contains definitions
     for the following management objects:
       mpls-lsd-nodes: Location MPLS LSD operational data
       mpls-lsd: mpls lsd

     Copyright (c) 2013-2018 by Cisco Systems, Inc.
     All rights reserved.";

  revision 2017-09-07 {
    description
      "Fixed type translation error.";
  }
  revision 2017-05-01 {
    description
      "Fixing backward compatibility error in module.";
  }
  revision 2015-11-09 {
    description
      "IOS XR 6.0 revision.";
  }

  grouping ncs_template_REWRITE-SUMMARY {
    description
      "Common node of mpls-lsd, mpls-lsd-node";
    container rewrite-summary {
      description
        "Rewrite Summary ";
      uses ncs_template_MPLS-LSD-RW-SUM;
    }
  }

  grouping ncs_template_LABEL-SUMMARY {
    description
      "Common node of mpls-lsd, mpls-lsd-node";
    container label-summary {
      description
        "Dynamic label range";
      uses ncs_template_MPLS-LSD-LBL-SUM;
    }
  }

  grouping ncs_template_LABEL-TABLE {
    description
      "Common node of mpls-lsd, mpls-lsd-node";
    container labels {
      description
        "Table of labels";
      list label {
        // NCS patched for predictable order
        ordered-by user;
        key "label-id";
        description
          "Data for label";
        leaf label-id {
          type string;
          description
            "Label value";
        }
        uses ncs_template_MPLS-LSD-LBL;
      }
    }
  }

  grouping ncs_template_FRR-DATABASE {
    description
      "Common node of mpls-lsd, mpls-lsd-node";
    container frr-database {
      description
        "FRR database";
      container tunnel-midpoints {
        description
          "Table of FRR database entries - Tunnel
           midpoints";
        list tunnel-midpoint {
          // NCS patched for predictable order
          ordered-by user;
          key "label";
          description
            "Data for FRR database entry - Tunnel midpoint";
          leaf label {
            type string;
            description
              "Label value";
          }
          uses ncs_template_MPLS-LSD-FRR-DB-ENTRY;
        }
      }
      container tunnel-heads {
        description
          "Table of FRR database entries - Tunnel heads";
        list tunnel-head {
          // NCS patched for predictable order
          ordered-by user;
          key "interface-name";
          description
            "Data for FRR database entry - Tunnel head";
          leaf interface-name {
            type string;
            description
              "Tunnel interface";
          }
          uses ncs_template_MPLS-LSD-FRR-DB-ENTRY;
        }
      }
      container tunnel-head-summary {
        description
          "Summary data for FRR database entry - Tunnel
           head";
        uses ncs_template_MPLS-LSD-FRR-DB-SUM;
      }
      container summary-protected-interfaces {
        description
          "Sumary table of Protected Interfaces";
        list summary-protected-interface {
          // NCS patched for predictable order
          ordered-by user;
          key "interface-name";
          description
            "Data for MPLS interface";
          leaf interface-name {
            type string;
            description
              "Interface";
          }
          uses ncs_template_MPLS-LSD-FRR-DB-SUM;
        }
      }
      container tunnel-summary {
        description
          "Summary data for FRR database entry";
        uses ncs_template_MPLS-LSD-FRR-DB-SUM;
      }
      container tunnel-midpoint-summary {
        description
          "Summary data for FRR database entry - Tunnel
           midpoint";
        uses ncs_template_MPLS-LSD-FRR-DB-SUM;
      }
    }
  }

  grouping ncs_template_LABEL-RANGE {
    description
      "Common node of mpls-lsd, mpls-lsd-node";
    container label-range {
      description
        "Label range";
      uses ncs_template_MPLS-LSD-LBL-RANGE;
    }
  }

  grouping ncs_template_CLIENT-TABLE {
    description
      "Common node of mpls-lsd, mpls-lsd-node";
    container clients {
      description
        "Table of MPLS clients using LSD";
      list client {
        // NCS patched for predictable order
        ordered-by user;
        key "client-name";
        description
          "Data for MPLS client using LSD";
        leaf client-name {
          type string;
          description
            "Client Instance name in the form of
             'Application-<client_name>' or
             'BCDL_Agent-<index:parent_index>'";
        }
        uses ncs_template_MPLS-LSD-CLIENT;
      }
    }
  }

  grouping ncs_template_LABEL-SUMMARY-VRF-TABLE {
    description
      "Common node of mpls-lsd, mpls-lsd-nodeCommon node
       of mpls-lsd, mpls-lsd-node";
    container label-summary-vrfs {
      description
        "Dynamic label range summary by VRF";
      list label-summary-vrf {
        // NCS patched for predictable order
        ordered-by user;
        key "vrf-name";
        description
          "Dynamic label range summary by VRF";
        leaf vrf-name {
          type string;
          description
            "VRF name";
        }
        uses ncs_template_MPLS-LSD-LBL-SUM;
      }
    }
  }

  grouping ncs_template_APPLICATION-TABLE {
    description
      "Common node of mpls-lsd, mpls-lsd-node";
    container applications {
      description
        "Table of MPLS applications using LSD";
      list application {
        // NCS patched for predictable order
        ordered-by user;
        key "application-name";
        description
          "Data for MPLS application using LSD";
        leaf application-name {
          type string;
          description
            "Application Instance name in the form of
             '<app_type_name>[:<instance>]'";
        }
        uses ncs_template_MPLS-LSD-APP;
      }
    }
  }

  grouping ncs_template_REWRITE-SUMMARY-VRF-TABLE {
    description
      "Common node of mpls-lsd, mpls-lsd-node";
    container rewrite-summary-vrfs {
      description
        "Rewrite Summary by VRF";
      list rewrite-summary-vrf {
        // NCS patched for predictable order
        ordered-by user;
        key "vrf-name";
        description
          "Rewrite summary by VRF VRF-name";
        leaf vrf-name {
          type string;
          description
            "VRF name";
        }
        uses ncs_template_MPLS-LSD-RW-SUM;
      }
    }
  }

  grouping ncs_template_INTERFACE-TABLE {
    description
      "Common node of mpls-lsd, mpls-lsd-node";
    container interfaces {
      description
        "Table of MPLS interfaces";
      list interface {
        // NCS patched for predictable order
        ordered-by user;
        key "interface-name";
        description
          "Data for MPLS interface";
        leaf interface-name {
          type string;
          description
            "Interface";
        }
        uses ncs_template_MPLS-LSD-INTF;
      }
    }
  }

  grouping ncs_template_REWRITE {
    description
      "Common node of mpls-lsd, mpls-lsd-node";
    container rewrite {
      description
        "Table of rewrites";
      container rewrite-label-range-cnts {
        description
          "Table of Label Range Counters";
        list rewrite-label-range-cnt {
          // NCS patched for predictable order
          ordered-by user;
          description
            "Label Range Counters";
          leaf label-range-type {
            type string;
            description
              "Label Range Type";
          }
          leaf label-range-index {
            type string;
            description
              "Label Range Index";
          }
          uses ncs_template_MPLS-LSD-RW;
        }
      }
      container rewrite-pws {
        description
          "Table of Rewrites";
        list rewrite-pw {
          // NCS patched for predictable order
          ordered-by user;
          key "pw-list-id";
          description
            "FPI rewrite for PW List";
          leaf pw-list-id {
            type string;
            description
              "PW List ID";
          }
          uses ncs_template_MPLS-LSD-RW;
        }
      }
      container rewrite-ipv4s {
        description
          "Table of Rewrites";
        list rewrite-ipv4 {
          // NCS patched for predictable order
          ordered-by user;
          description
            "FPI rewrite for label";
          leaf rsi-table-name {
            type string;
            description
              "RSI table name";
          }
          leaf rsi-table-id {
            type string;
            description
              "RSI table ID";
          }
          leaf prefix {
            type string;
            description
              "IPv4 Prefix";
          }
          leaf prefix-length {
            type string;
            description
              "Prefix length";
          }
          uses ncs_template_MPLS-LSD-RW;
        }
      }
      container rewrite-tes {
        description
          "Table of Traffic Engineering Rewrites";
        list rewrite-te {
          // NCS patched for predictable order
          ordered-by user;
          key "interface-name";
          description
            "FPI rewrite for TE";
          leaf interface-name {
            type string;
            description
              "Tunnel interface";
          }
          uses ncs_template_MPLS-LSD-RW;
        }
      }
      container rewrite-labels {
        description
          "Table of Rewrites";
        list rewrite-label {
          // NCS patched for predictable order
          ordered-by user;
          key "label-id";
          description
            "FPI rewrite for label";
          leaf label-id {
            type string;
            description
              "Label value";
          }
          uses ncs_template_MPLS-LSD-RW;
        }
      }
    }
  }

  grouping ncs_rpc_notif_REWRITE-SUMMARY {
    description
      "Common node of mpls-lsd, mpls-lsd-node";
    container rewrite-summary {
      description
        "Rewrite Summary ";
      uses ncs_rpc_notif_MPLS-LSD-RW-SUM;
    }
  }

  grouping ncs_rpc_notif_LABEL-SUMMARY {
    description
      "Common node of mpls-lsd, mpls-lsd-node";
    container label-summary {
      description
        "Dynamic label range";
      uses ncs_rpc_notif_MPLS-LSD-LBL-SUM;
    }
  }

  grouping ncs_rpc_notif_LABEL-TABLE {
    description
      "Common node of mpls-lsd, mpls-lsd-node";
    container labels {
      description
        "Table of labels";
      list label {
        key "label-id";
        description
          "Data for label";
        leaf label-id {
          type uint32;
          description
            "Label value";
        }
        uses ncs_rpc_notif_MPLS-LSD-LBL;
      }
    }
  }

  grouping ncs_rpc_notif_FRR-DATABASE {
    description
      "Common node of mpls-lsd, mpls-lsd-node";
    container frr-database {
      description
        "FRR database";
      container tunnel-midpoints {
        description
          "Table of FRR database entries - Tunnel
           midpoints";
        list tunnel-midpoint {
          key "label";
          description
            "Data for FRR database entry - Tunnel midpoint";
          leaf label {
            type uint32;
            description
              "Label value";
          }
          uses ncs_rpc_notif_MPLS-LSD-FRR-DB-ENTRY;
        }
      }
      container tunnel-heads {
        description
          "Table of FRR database entries - Tunnel heads";
        list tunnel-head {
          key "interface-name";
          description
            "Data for FRR database entry - Tunnel head";
          leaf interface-name {
            type xr:Interface-name;
            description
              "Tunnel interface";
          }
          uses ncs_rpc_notif_MPLS-LSD-FRR-DB-ENTRY;
        }
      }
      container tunnel-head-summary {
        description
          "Summary data for FRR database entry - Tunnel
           head";
        uses ncs_rpc_notif_MPLS-LSD-FRR-DB-SUM;
      }
      container summary-protected-interfaces {
        description
          "Sumary table of Protected Interfaces";
        list summary-protected-interface {
          key "interface-name";
          description
            "Data for MPLS interface";
          leaf interface-name {
            type xr:Interface-name;
            description
              "Interface";
          }
          uses ncs_rpc_notif_MPLS-LSD-FRR-DB-SUM;
        }
      }
      container tunnel-summary {
        description
          "Summary data for FRR database entry";
        uses ncs_rpc_notif_MPLS-LSD-FRR-DB-SUM;
      }
      container tunnel-midpoint-summary {
        description
          "Summary data for FRR database entry - Tunnel
           midpoint";
        uses ncs_rpc_notif_MPLS-LSD-FRR-DB-SUM;
      }
    }
  }

  grouping ncs_rpc_notif_LABEL-RANGE {
    description
      "Common node of mpls-lsd, mpls-lsd-node";
    container label-range {
      description
        "Label range";
      uses ncs_rpc_notif_MPLS-LSD-LBL-RANGE;
    }
  }

  grouping ncs_rpc_notif_CLIENT-TABLE {
    description
      "Common node of mpls-lsd, mpls-lsd-node";
    container clients {
      description
        "Table of MPLS clients using LSD";
      list client {
        key "client-name";
        description
          "Data for MPLS client using LSD";
        leaf client-name {
          type xr:Cisco-ios-xr-string;
          description
            "Client Instance name in the form of
             'Application-<client_name>' or
             'BCDL_Agent-<index:parent_index>'";
        }
        uses ncs_rpc_notif_MPLS-LSD-CLIENT;
      }
    }
  }

  grouping ncs_rpc_notif_LABEL-SUMMARY-VRF-TABLE {
    description
      "Common node of mpls-lsd, mpls-lsd-nodeCommon node
       of mpls-lsd, mpls-lsd-node";
    container label-summary-vrfs {
      description
        "Dynamic label range summary by VRF";
      list label-summary-vrf {
        key "vrf-name";
        description
          "Dynamic label range summary by VRF";
        leaf vrf-name {
          type xr:Cisco-ios-xr-string;
          description
            "VRF name";
        }
        uses ncs_rpc_notif_MPLS-LSD-LBL-SUM;
      }
    }
  }

  grouping ncs_rpc_notif_APPLICATION-TABLE {
    description
      "Common node of mpls-lsd, mpls-lsd-node";
    container applications {
      description
        "Table of MPLS applications using LSD";
      list application {
        key "application-name";
        description
          "Data for MPLS application using LSD";
        leaf application-name {
          type xr:Cisco-ios-xr-string;
          description
            "Application Instance name in the form of
             '<app_type_name>[:<instance>]'";
        }
        uses ncs_rpc_notif_MPLS-LSD-APP;
      }
    }
  }

  grouping ncs_rpc_notif_REWRITE-SUMMARY-VRF-TABLE {
    description
      "Common node of mpls-lsd, mpls-lsd-node";
    container rewrite-summary-vrfs {
      description
        "Rewrite Summary by VRF";
      list rewrite-summary-vrf {
        key "vrf-name";
        description
          "Rewrite summary by VRF VRF-name";
        leaf vrf-name {
          type xr:Cisco-ios-xr-string;
          description
            "VRF name";
        }
        uses ncs_rpc_notif_MPLS-LSD-RW-SUM;
      }
    }
  }

  grouping ncs_rpc_notif_INTERFACE-TABLE {
    description
      "Common node of mpls-lsd, mpls-lsd-node";
    container interfaces {
      description
        "Table of MPLS interfaces";
      list interface {
        key "interface-name";
        description
          "Data for MPLS interface";
        leaf interface-name {
          type xr:Interface-name;
          description
            "Interface";
        }
        uses ncs_rpc_notif_MPLS-LSD-INTF;
      }
    }
  }

  grouping ncs_rpc_notif_REWRITE {
    description
      "Common node of mpls-lsd, mpls-lsd-node";
    container rewrite {
      description
        "Table of rewrites";
      container rewrite-label-range-cnts {
        description
          "Table of Label Range Counters";
        list rewrite-label-range-cnt {
          description
            "Label Range Counters";
          leaf label-range-type {
            type uint32;
            description
              "Label Range Type";
          }
          leaf label-range-index {
            type uint32;
            description
              "Label Range Index";
          }
          uses ncs_rpc_notif_MPLS-LSD-RW;
        }
      }
      container rewrite-pws {
        description
          "Table of Rewrites";
        list rewrite-pw {
          key "pw-list-id";
          description
            "FPI rewrite for PW List";
          leaf pw-list-id {
            type uint32;
            description
              "PW List ID";
          }
          uses ncs_rpc_notif_MPLS-LSD-RW;
        }
      }
      container rewrite-ipv4s {
        description
          "Table of Rewrites";
        list rewrite-ipv4 {
          description
            "FPI rewrite for label";
          leaf rsi-table-name {
            type xr:Cisco-ios-xr-string;
            description
              "RSI table name";
          }
          leaf rsi-table-id {
            type xr:Hex-integer;
            description
              "RSI table ID";
          }
          leaf prefix {
            type inet:ipv4-address-no-zone;
            description
              "IPv4 Prefix";
          }
          leaf prefix-length {
            type uint32;
            description
              "Prefix length";
          }
          uses ncs_rpc_notif_MPLS-LSD-RW;
        }
      }
      container rewrite-tes {
        description
          "Table of Traffic Engineering Rewrites";
        list rewrite-te {
          key "interface-name";
          description
            "FPI rewrite for TE";
          leaf interface-name {
            type xr:Interface-name;
            description
              "Tunnel interface";
          }
          uses ncs_rpc_notif_MPLS-LSD-RW;
        }
      }
      container rewrite-labels {
        description
          "Table of Rewrites";
        list rewrite-label {
          key "label-id";
          description
            "FPI rewrite for label";
          leaf label-id {
            type uint32;
            description
              "Label value";
          }
          uses ncs_rpc_notif_MPLS-LSD-RW;
        }
      }
    }
  }

  grouping live_ncs_REWRITE-SUMMARY {
    description
      "Common node of mpls-lsd, mpls-lsd-node";
    container rewrite-summary {
      description
        "Rewrite Summary ";
      uses live_ncs_MPLS-LSD-RW-SUM;
    }
  }

  grouping live_ncs_LABEL-SUMMARY {
    description
      "Common node of mpls-lsd, mpls-lsd-node";
    container label-summary {
      description
        "Dynamic label range";
      uses live_ncs_MPLS-LSD-LBL-SUM;
    }
  }

  grouping live_ncs_LABEL-TABLE {
    description
      "Common node of mpls-lsd, mpls-lsd-node";
    container labels {
      description
        "Table of labels";
      list label {
        key "label-id";
        description
          "Data for label";
        leaf label-id {
          type uint32;
          description
            "Label value";
        }
        uses live_ncs_MPLS-LSD-LBL;
      }
    }
  }

  grouping live_ncs_FRR-DATABASE {
    description
      "Common node of mpls-lsd, mpls-lsd-node";
    container frr-database {
      description
        "FRR database";
      container tunnel-midpoints {
        description
          "Table of FRR database entries - Tunnel
           midpoints";
        list tunnel-midpoint {
          key "label";
          description
            "Data for FRR database entry - Tunnel midpoint";
          leaf label {
            type uint32;
            description
              "Label value";
          }
          uses live_ncs_MPLS-LSD-FRR-DB-ENTRY;
        }
      }
      container tunnel-heads {
        description
          "Table of FRR database entries - Tunnel heads";
        list tunnel-head {
          key "interface-name";
          description
            "Data for FRR database entry - Tunnel head";
          leaf interface-name {
            type xr:Interface-name;
            description
              "Tunnel interface";
          }
          uses live_ncs_MPLS-LSD-FRR-DB-ENTRY;
        }
      }
      container tunnel-head-summary {
        description
          "Summary data for FRR database entry - Tunnel
           head";
        uses live_ncs_MPLS-LSD-FRR-DB-SUM;
      }
      container summary-protected-interfaces {
        description
          "Sumary table of Protected Interfaces";
        list summary-protected-interface {
          key "interface-name";
          description
            "Data for MPLS interface";
          leaf interface-name {
            type xr:Interface-name;
            description
              "Interface";
          }
          uses live_ncs_MPLS-LSD-FRR-DB-SUM;
        }
      }
      container tunnel-summary {
        description
          "Summary data for FRR database entry";
        uses live_ncs_MPLS-LSD-FRR-DB-SUM;
      }
      container tunnel-midpoint-summary {
        description
          "Summary data for FRR database entry - Tunnel
           midpoint";
        uses live_ncs_MPLS-LSD-FRR-DB-SUM;
      }
    }
  }

  grouping live_ncs_LABEL-RANGE {
    description
      "Common node of mpls-lsd, mpls-lsd-node";
    container label-range {
      description
        "Label range";
      uses live_ncs_MPLS-LSD-LBL-RANGE;
    }
  }

  grouping live_ncs_CLIENT-TABLE {
    description
      "Common node of mpls-lsd, mpls-lsd-node";
    container clients {
      description
        "Table of MPLS clients using LSD";
      list client {
        key "client-name";
        description
          "Data for MPLS client using LSD";
        leaf client-name {
          type xr:Cisco-ios-xr-string;
          description
            "Client Instance name in the form of
             'Application-<client_name>' or
             'BCDL_Agent-<index:parent_index>'";
        }
        uses live_ncs_MPLS-LSD-CLIENT;
      }
    }
  }

  grouping live_ncs_LABEL-SUMMARY-VRF-TABLE {
    description
      "Common node of mpls-lsd, mpls-lsd-nodeCommon node
       of mpls-lsd, mpls-lsd-node";
    container label-summary-vrfs {
      description
        "Dynamic label range summary by VRF";
      list label-summary-vrf {
        key "vrf-name";
        description
          "Dynamic label range summary by VRF";
        leaf vrf-name {
          type xr:Cisco-ios-xr-string;
          description
            "VRF name";
        }
        uses live_ncs_MPLS-LSD-LBL-SUM;
      }
    }
  }

  grouping live_ncs_APPLICATION-TABLE {
    description
      "Common node of mpls-lsd, mpls-lsd-node";
    container applications {
      description
        "Table of MPLS applications using LSD";
      list application {
        key "application-name";
        description
          "Data for MPLS application using LSD";
        leaf application-name {
          type xr:Cisco-ios-xr-string;
          description
            "Application Instance name in the form of
             '<app_type_name>[:<instance>]'";
        }
        uses live_ncs_MPLS-LSD-APP;
      }
    }
  }

  grouping live_ncs_REWRITE-SUMMARY-VRF-TABLE {
    description
      "Common node of mpls-lsd, mpls-lsd-node";
    container rewrite-summary-vrfs {
      description
        "Rewrite Summary by VRF";
      list rewrite-summary-vrf {
        key "vrf-name";
        description
          "Rewrite summary by VRF VRF-name";
        leaf vrf-name {
          type xr:Cisco-ios-xr-string;
          description
            "VRF name";
        }
        uses live_ncs_MPLS-LSD-RW-SUM;
      }
    }
  }

  grouping live_ncs_INTERFACE-TABLE {
    description
      "Common node of mpls-lsd, mpls-lsd-node";
    container interfaces {
      description
        "Table of MPLS interfaces";
      list interface {
        key "interface-name";
        description
          "Data for MPLS interface";
        leaf interface-name {
          type xr:Interface-name;
          description
            "Interface";
        }
        uses live_ncs_MPLS-LSD-INTF;
      }
    }
  }

  grouping live_ncs_REWRITE {
    description
      "Common node of mpls-lsd, mpls-lsd-node";
    container rewrite {
      description
        "Table of rewrites";
      container rewrite-label-range-cnts {
        description
          "Table of Label Range Counters";
        list rewrite-label-range-cnt {
          description
            "Label Range Counters";
          leaf label-range-type {
            type uint32;
            description
              "Label Range Type";
          }
          leaf label-range-index {
            type uint32;
            description
              "Label Range Index";
          }
          uses live_ncs_MPLS-LSD-RW;
        }
      }
      container rewrite-pws {
        description
          "Table of Rewrites";
        list rewrite-pw {
          key "pw-list-id";
          description
            "FPI rewrite for PW List";
          leaf pw-list-id {
            type uint32;
            description
              "PW List ID";
          }
          uses live_ncs_MPLS-LSD-RW;
        }
      }
      container rewrite-ipv4s {
        description
          "Table of Rewrites";
        list rewrite-ipv4 {
          description
            "FPI rewrite for label";
          leaf rsi-table-name {
            type xr:Cisco-ios-xr-string;
            description
              "RSI table name";
          }
          leaf rsi-table-id {
            type xr:Hex-integer;
            description
              "RSI table ID";
          }
          leaf prefix {
            type inet:ipv4-address-no-zone;
            description
              "IPv4 Prefix";
          }
          leaf prefix-length {
            type uint32;
            description
              "Prefix length";
          }
          uses live_ncs_MPLS-LSD-RW;
        }
      }
      container rewrite-tes {
        description
          "Table of Traffic Engineering Rewrites";
        list rewrite-te {
          key "interface-name";
          description
            "FPI rewrite for TE";
          leaf interface-name {
            type xr:Interface-name;
            description
              "Tunnel interface";
          }
          uses live_ncs_MPLS-LSD-RW;
        }
      }
      container rewrite-labels {
        description
          "Table of Rewrites";
        list rewrite-label {
          key "label-id";
          description
            "FPI rewrite for label";
          leaf label-id {
            type uint32;
            description
              "Label value";
          }
          uses live_ncs_MPLS-LSD-RW;
        }
      }
    }
  }

  grouping REWRITE-SUMMARY {
    description
      "Common node of mpls-lsd, mpls-lsd-node";
    container rewrite-summary {
      description
        "Rewrite Summary ";
      uses MPLS-LSD-RW-SUM;
    }
  }

  grouping LABEL-SUMMARY {
    description
      "Common node of mpls-lsd, mpls-lsd-node";
    container label-summary {
      description
        "Dynamic label range";
      uses MPLS-LSD-LBL-SUM;
    }
  }

  grouping LABEL-TABLE {
    description
      "Common node of mpls-lsd, mpls-lsd-node";
    container labels {
      description
        "Table of labels";
      list label {
        key "label-id";
        description
          "Data for label";
        leaf label-id {
          type uint32;
          description
            "Label value";
        }
        uses MPLS-LSD-LBL;
      }
    }
  }

  grouping FRR-DATABASE {
    description
      "Common node of mpls-lsd, mpls-lsd-node";
    container frr-database {
      description
        "FRR database";
      container tunnel-midpoints {
        description
          "Table of FRR database entries - Tunnel
           midpoints";
        list tunnel-midpoint {
          key "label";
          description
            "Data for FRR database entry - Tunnel midpoint";
          leaf label {
            type uint32;
            description
              "Label value";
          }
          uses MPLS-LSD-FRR-DB-ENTRY;
        }
      }
      container tunnel-heads {
        description
          "Table of FRR database entries - Tunnel heads";
        list tunnel-head {
          key "interface-name";
          description
            "Data for FRR database entry - Tunnel head";
          leaf interface-name {
            type xr:Interface-name;
            description
              "Tunnel interface";
          }
          uses MPLS-LSD-FRR-DB-ENTRY;
        }
      }
      container tunnel-head-summary {
        description
          "Summary data for FRR database entry - Tunnel
           head";
        uses MPLS-LSD-FRR-DB-SUM;
      }
      container summary-protected-interfaces {
        description
          "Sumary table of Protected Interfaces";
        list summary-protected-interface {
          key "interface-name";
          description
            "Data for MPLS interface";
          leaf interface-name {
            type xr:Interface-name;
            description
              "Interface";
          }
          uses MPLS-LSD-FRR-DB-SUM;
        }
      }
      container tunnel-summary {
        description
          "Summary data for FRR database entry";
        uses MPLS-LSD-FRR-DB-SUM;
      }
      container tunnel-midpoint-summary {
        description
          "Summary data for FRR database entry - Tunnel
           midpoint";
        uses MPLS-LSD-FRR-DB-SUM;
      }
    }
  }

  grouping LABEL-RANGE {
    description
      "Common node of mpls-lsd, mpls-lsd-node";
    container label-range {
      description
        "Label range";
      uses MPLS-LSD-LBL-RANGE;
    }
  }

  grouping CLIENT-TABLE {
    description
      "Common node of mpls-lsd, mpls-lsd-node";
    container clients {
      description
        "Table of MPLS clients using LSD";
      list client {
        key "client-name";
        description
          "Data for MPLS client using LSD";
        leaf client-name {
          type xr:Cisco-ios-xr-string;
          description
            "Client Instance name in the form of
             'Application-<client_name>' or
             'BCDL_Agent-<index:parent_index>'";
        }
        uses MPLS-LSD-CLIENT;
      }
    }
  }

  grouping LABEL-SUMMARY-VRF-TABLE {
    description
      "Common node of mpls-lsd, mpls-lsd-nodeCommon node
       of mpls-lsd, mpls-lsd-node";
    container label-summary-vrfs {
      description
        "Dynamic label range summary by VRF";
      list label-summary-vrf {
        key "vrf-name";
        description
          "Dynamic label range summary by VRF";
        leaf vrf-name {
          type xr:Cisco-ios-xr-string;
          description
            "VRF name";
        }
        uses MPLS-LSD-LBL-SUM;
      }
    }
  }

  grouping APPLICATION-TABLE {
    description
      "Common node of mpls-lsd, mpls-lsd-node";
    container applications {
      description
        "Table of MPLS applications using LSD";
      list application {
        key "application-name";
        description
          "Data for MPLS application using LSD";
        leaf application-name {
          type xr:Cisco-ios-xr-string;
          description
            "Application Instance name in the form of
             '<app_type_name>[:<instance>]'";
        }
        uses MPLS-LSD-APP;
      }
    }
  }

  grouping REWRITE-SUMMARY-VRF-TABLE {
    description
      "Common node of mpls-lsd, mpls-lsd-node";
    container rewrite-summary-vrfs {
      description
        "Rewrite Summary by VRF";
      list rewrite-summary-vrf {
        key "vrf-name";
        description
          "Rewrite summary by VRF VRF-name";
        leaf vrf-name {
          type xr:Cisco-ios-xr-string;
          description
            "VRF name";
        }
        uses MPLS-LSD-RW-SUM;
      }
    }
  }

  grouping INTERFACE-TABLE {
    description
      "Common node of mpls-lsd, mpls-lsd-node";
    container interfaces {
      description
        "Table of MPLS interfaces";
      list interface {
        key "interface-name";
        description
          "Data for MPLS interface";
        leaf interface-name {
          type xr:Interface-name;
          description
            "Interface";
        }
        uses MPLS-LSD-INTF;
      }
    }
  }

  grouping REWRITE {
    description
      "Common node of mpls-lsd, mpls-lsd-node";
    container rewrite {
      description
        "Table of rewrites";
      container rewrite-label-range-cnts {
        description
          "Table of Label Range Counters";
        list rewrite-label-range-cnt {
          description
            "Label Range Counters";
          leaf label-range-type {
            type uint32;
            description
              "Label Range Type";
          }
          leaf label-range-index {
            type uint32;
            description
              "Label Range Index";
          }
          uses MPLS-LSD-RW;
        }
      }
      container rewrite-pws {
        description
          "Table of Rewrites";
        list rewrite-pw {
          key "pw-list-id";
          description
            "FPI rewrite for PW List";
          leaf pw-list-id {
            type uint32;
            description
              "PW List ID";
          }
          uses MPLS-LSD-RW;
        }
      }
      container rewrite-ipv4s {
        description
          "Table of Rewrites";
        list rewrite-ipv4 {
          description
            "FPI rewrite for label";
          leaf rsi-table-name {
            type xr:Cisco-ios-xr-string;
            description
              "RSI table name";
          }
          leaf rsi-table-id {
            type xr:Hex-integer;
            description
              "RSI table ID";
          }
          leaf prefix {
            type inet:ipv4-address-no-zone;
            description
              "IPv4 Prefix";
          }
          leaf prefix-length {
            type uint32;
            description
              "Prefix length";
          }
          uses MPLS-LSD-RW;
        }
      }
      container rewrite-tes {
        description
          "Table of Traffic Engineering Rewrites";
        list rewrite-te {
          key "interface-name";
          description
            "FPI rewrite for TE";
          leaf interface-name {
            type xr:Interface-name;
            description
              "Tunnel interface";
          }
          uses MPLS-LSD-RW;
        }
      }
      container rewrite-labels {
        description
          "Table of Rewrites";
        list rewrite-label {
          key "label-id";
          description
            "FPI rewrite for label";
          leaf label-id {
            type uint32;
            description
              "Label value";
          }
          uses MPLS-LSD-RW;
        }
      }
    }
  }

  augment "/ncs:devices/ncs:device/ncs:config" {
    // NCS drop config false container 'mpls-lsd-nodes'
    // NCS drop config false container 'mpls-lsd'
  }
  augment "/ncs:devices/ncs:device/ncs:live-status" {
    container mpls-lsd-nodes {
      tailf:ncs-device-type "netconf";
      tailf:display-when "not(../../ncs:module) or ../../ncs:module[ncs:name='Cisco-IOS-XR-mpls-lsd-oper'] or (../../ncs:live-status-protocol[not(ncs:capability)]) or (../../ncs:live-status-protocol/ncs:capability/ncs:module[.='Cisco-IOS-XR-mpls-lsd-oper'])";
      description
        "Location MPLS LSD operational data";
      list mpls-lsd-node {
        key "node-name";
        description
          "The MPLS LSD operational data for a particular
           node";
        leaf node-name {
          type xr:Node-id;
          description
            "The identifier for the node";
        }
        uses live_ncs_CLIENT-TABLE;
        uses live_ncs_LABEL-SUMMARY;
        uses live_ncs_LABEL-TABLE;
        uses live_ncs_FRR-DATABASE;
        uses live_ncs_REWRITE;
        uses live_ncs_REWRITE-SUMMARY;
        uses live_ncs_APPLICATION-TABLE;
        uses live_ncs_LABEL-SUMMARY-VRF-TABLE;
        uses live_ncs_LABEL-RANGE;
        uses live_ncs_REWRITE-SUMMARY-VRF-TABLE;
        uses live_ncs_INTERFACE-TABLE;
      }
    }
    container mpls-lsd {
      tailf:ncs-device-type "netconf";
      tailf:display-when "not(../../ncs:module) or ../../ncs:module[ncs:name='Cisco-IOS-XR-mpls-lsd-oper'] or (../../ncs:live-status-protocol[not(ncs:capability)]) or (../../ncs:live-status-protocol/ncs:capability/ncs:module[.='Cisco-IOS-XR-mpls-lsd-oper'])";
      description
        "mpls lsd";
      uses live_ncs_CLIENT-TABLE;
      uses live_ncs_LABEL-SUMMARY;
      uses live_ncs_LABEL-TABLE;
      uses live_ncs_FRR-DATABASE;
      uses live_ncs_REWRITE;
      uses live_ncs_REWRITE-SUMMARY;
      uses live_ncs_APPLICATION-TABLE;
      uses live_ncs_LABEL-SUMMARY-VRF-TABLE;
      uses live_ncs_LABEL-RANGE;
      uses live_ncs_REWRITE-SUMMARY-VRF-TABLE;
      uses live_ncs_INTERFACE-TABLE;
    }
  }
  augment "/ncs:devices/ncs:template/ncs:ned-id/ncs:config" {
    // NCS drop config false container 'mpls-lsd-nodes'
    // NCS drop config false container 'mpls-lsd'
  }
}
