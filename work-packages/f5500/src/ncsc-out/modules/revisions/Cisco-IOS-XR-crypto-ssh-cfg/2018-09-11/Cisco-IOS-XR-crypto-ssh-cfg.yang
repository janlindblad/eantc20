module Cisco-IOS-XR-crypto-ssh-cfg {
  // Generated by yanger -t ncs
  tailf:mount-id f5500-nc-1.0:f5500-nc-1.0;
  tailf:ncs-device-type "netconf";

  namespace "http://cisco.com/ns/yang/Cisco-IOS-XR-crypto-ssh-cfg";
  prefix Cisco-IOS-XR-crypto-ssh-cfg;

  import Cisco-IOS-XR-types {
    prefix xr;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR crypto-ssh package configuration.

     This module contains definitions
     for the following management objects:
       ssh: Secure Shell configuration

     Copyright (c) 2013-2018 by Cisco Systems, Inc.
     All rights reserved.";

  revision 2018-09-11 {
    description
      "Added backup ssh server schema";
  }
  revision 2018-05-24 {
    description
      "Changes in enable cipher aes-cbc schema and added enable cipher 3des-cbc support";
  }
  revision 2018-04-04 {
    description
      "Changes in ssh kexchange algorithms schema";
  }
  revision 2017-11-21 {
    description
      "Resolving dependency issue with SAM";
  }
  revision 2017-07-15 {
    description
      "Fixing client rekey support.";
  }
  revision 2017-05-01 {
    description
      "Fixing backward compatibility error in module.";
  }
  revision 2015-07-30 {
    description
      "Descriptions updated.";
  }
  revision 2015-07-13 {
    description
      "IOS XR 5.3.2 revision.";
  }
  revision 2015-01-07 {
    description
      "IOS XR 5.3.1 revision.";
  }

  grouping ncs_template_VRF {
    description
      "Common node of vrf-table, netconf-vrf-table";
    list vrf {
      // NCS patched for predictable order
      ordered-by user;
      key "vrf-name";
      description
        "Enter VRF name";
      leaf vrf-name {
        type string;
        description
          "Enter VRF name";
      }
      leaf enable {
        type empty;
        // NCS drop mandatory statement
        description
          "Enable to use VRF";
      }
      leaf ipv4-access-list {
        type string;
        description
          "SSH v4 access-list name";
      }
      leaf ipv6-access-list {
        type string;
        description
          "SSH v6 access-list name";
      }
    }
  }

  grouping ncs_template_KEY-EXCHANGE {
    description
      "Common node of client-algo, server-algo";
    container key-exchanges {
      description
        "Key exchange algorithm";
      leaf-list key-exchange {
        // NCS patched for predictable order
        ordered-by user;
        type string;
        // NCS drop max-elements statement
        description
          "key exchange algorithm";
      }
    }
  }

  grouping ncs_rpc_notif_VRF {
    description
      "Common node of vrf-table, netconf-vrf-table";
    list vrf {
      key "vrf-name";
      description
        "Enter VRF name";
      leaf vrf-name {
        type xr:Cisco-ios-xr-string {
          length "1..32";
        }
        description
          "Enter VRF name";
      }
      leaf enable {
        type empty;
        mandatory true;
        description
          "Enable to use VRF";
      }
      leaf ipv4-access-list {
        type xr:Cisco-ios-xr-string {
          length "1..32";
        }
        description
          "SSH v4 access-list name";
      }
      leaf ipv6-access-list {
        type xr:Cisco-ios-xr-string {
          length "1..32";
        }
        description
          "SSH v6 access-list name";
      }
    }
  }

  grouping ncs_rpc_notif_KEY-EXCHANGE {
    description
      "Common node of client-algo, server-algo";
    container key-exchanges {
      description
        "Key exchange algorithm";
      leaf-list key-exchange {
        type string {
          length "1..32";
        }
        max-elements 5;
        description
          "key exchange algorithm";
      }
    }
  }

  grouping live_ncs_VRF {
    description
      "Common node of vrf-table, netconf-vrf-table";
    list vrf {
      key "vrf-name";
      description
        "Enter VRF name";
      leaf vrf-name {
        type xr:Cisco-ios-xr-string {
          length "1..32";
        }
        description
          "Enter VRF name";
      }
      leaf enable {
        type empty;
        // NCS drop mandatory statement
        description
          "Enable to use VRF";
      }
      leaf ipv4-access-list {
        type xr:Cisco-ios-xr-string {
          length "1..32";
        }
        description
          "SSH v4 access-list name";
      }
      leaf ipv6-access-list {
        type xr:Cisco-ios-xr-string {
          length "1..32";
        }
        description
          "SSH v6 access-list name";
      }
    }
  }

  grouping live_ncs_KEY-EXCHANGE {
    description
      "Common node of client-algo, server-algo";
    container key-exchanges {
      description
        "Key exchange algorithm";
      leaf-list key-exchange {
        type string {
          length "1..32";
        }
        // NCS drop max-elements statement
        description
          "key exchange algorithm";
      }
    }
  }

  grouping VRF {
    description
      "Common node of vrf-table, netconf-vrf-table";
    list vrf {
      key "vrf-name";
      description
        "Enter VRF name";
      leaf vrf-name {
        type xr:Cisco-ios-xr-string {
          length "1..32";
        }
        description
          "Enter VRF name";
      }
      leaf enable {
        type empty;
        mandatory true;
        description
          "Enable to use VRF";
      }
      leaf ipv4-access-list {
        type xr:Cisco-ios-xr-string {
          length "1..32";
        }
        description
          "SSH v4 access-list name";
      }
      leaf ipv6-access-list {
        type xr:Cisco-ios-xr-string {
          length "1..32";
        }
        description
          "SSH v6 access-list name";
      }
    }
  }

  grouping KEY-EXCHANGE {
    description
      "Common node of client-algo, server-algo";
    container key-exchanges {
      description
        "Key exchange algorithm";
      leaf-list key-exchange {
        type string {
          length "1..32";
        }
        max-elements 5;
        description
          "key exchange algorithm";
      }
    }
  }

  augment "/ncs:devices/ncs:device/ncs:config" {
    container ssh {
      tailf:ncs-device-type "netconf";
      tailf:display-when "not(../../ncs:module) or ../../ncs:module[ncs:name='Cisco-IOS-XR-crypto-ssh-cfg']";
      description
        "Secure Shell configuration";
      container client {
        description
          "Provide SSH client service";
        container client-algo {
          description
            "Cisco ssh algorithms";
          uses KEY-EXCHANGE;
        }
        container client-enable {
          description
            "clientenable";
          container client-cipher {
            description
              "Enable AES-CBC and 3DES_CBC for ssh client";
            leaf aes-cbc {
              type boolean;
              default "false";
              description
                "Enable AES-CBC ciphers";
            }
            leaf tripledes-cbc {
              type boolean;
              default "false";
              description
                "Enable 3DES-CBC cipher";
            }
          }
        }
        leaf rekey-volume {
          type uint32 {
            range "1024..4095";
          }
          default "1024";
          description
            "Configure client volume-based rekey for SSH";
        }
        leaf host-public-key {
          type string;
          description
            "Filename - where to store known host file";
        }
        leaf client-vrf {
          type xr:Cisco-ios-xr-string {
            length "1..32";
          }
          description
            "Source interface VRF for ssh client sessions";
        }
        leaf v2 {
          type empty;
          description
            "Cisco ssh client force protocol version 2 only";
        }
        leaf tcp-window-scale {
          type uint32 {
            range "1..14";
          }
          default "1";
          description
            "Set SSH Client Tcp Window Scale factor";
        }
        leaf rekey-time {
          type uint32 {
            range "30..1440";
          }
          units "minute";
          default "60";
          description
            "Configure client time-based rekey for SSH";
        }
        leaf source-interface {
          type xr:Interface-name;
          description
            "Source interface for ssh client sessions";
        }
        leaf dscp {
          type uint32 {
            range "0..63";
          }
          description
            "Cisco sshd DSCP value";
        }
      }
      container server {
        description
          "Provide SSH server service";
        container disable {
          description
            "disable";
          container hmac {
            description
              "hmac";
            leaf hmac-sha512 {
              type boolean;
              default "false";
              description
                "Disable Hmac-sha2-512 negotiation";
            }
          }
        }
        container enable {
          description
            "enable";
          container cipher {
            description
              "Enable AES-CBC and 3DES-CBC ciphers";
            leaf aes-cbc {
              type boolean;
              default "false";
              description
                "Enable aes-cbc ciphers";
            }
            leaf tripledes-cbc {
              type boolean;
              default "false";
              description
                "Enable 3des-cbc cipher";
            }
          }
        }
        container vrf-table {
          description
            "Cisco sshd VRF name";
          uses VRF;
        }
        container server-algo {
          description
            "Cisco ssh algorithms";
          uses KEY-EXCHANGE;
        }
        container capability {
          description
            "Capability";
          leaf netconf-xml {
            type boolean;
            default "false";
            description
              "Enable Netconf-XML stack on port 22";
          }
        }
        container netconf-vrf-table {
          description
            "Cisco sshd Netconf VRF name";
          uses VRF;
        }
        leaf rekey-volume {
          type uint32 {
            range "1024..4095";
          }
          default "1024";
          description
            "Configure volume-based rekey for SSH";
        }
        leaf session-limit {
          type uint32 {
            range "1..110";
          }
          description
            "Cisco sshd session-limit of service requests";
        }
        leaf netconf {
          type uint32 {
            range "1..65535";
          }
          default "830";
          description
            "port number on which ssh service to be started
             for netconf";
        }
        leaf v2 {
          type empty;
          description
            "Cisco sshd force protocol version 2 only";
        }
        leaf tcp-window-scale {
          type uint32 {
            range "1..14";
          }
          default "1";
          description
            "Set SSH Server Tcp Window Scale factor";
        }
        leaf rekey-time {
          type uint32 {
            range "30..1440";
          }
          units "minute";
          default "60";
          description
            "Time Period in minutes, defalut 60";
        }
        leaf logging {
          type empty;
          description
            "Enable ssh server logging";
        }
        leaf rate-limit {
          type uint32 {
            range "1..600";
          }
          default "60";
          description
            "Cisco sshd rate-limit of service requests";
        }
        leaf timeout {
          type uint32 {
            range "5..120";
          }
          units "second";
          default "30";
          description
            "Timeout value between 5-120 seconds defalut 30";
        }
        leaf dscp {
          type uint32 {
            range "0..63";
          }
          description
            "Cisco sshd DSCP value";
        }
      }
      container backup-server {
        description
          "Provide SSH server service";
        container backup-port-vrf {
          presence "Indicates a backup-port-vrf node is configured.";
          description
            "backup server config";
          leaf port {
            type uint32 {
              range "11000..15000";
            }
            mandatory true;
            description
              "Port number";
          }
          leaf vrf-name {
            type xr:Cisco-ios-xr-string {
              length "1..32";
            }
            mandatory true;
            description
              "VRF name (max:32 chars)";
          }
        }
      }
    }
  }
  augment "/ncs:devices/ncs:device/ncs:live-status" {
    container ssh {
      tailf:ncs-device-type "netconf";
      tailf:display-when "not(../../ncs:module) or ../../ncs:module[ncs:name='Cisco-IOS-XR-crypto-ssh-cfg'] or (../../ncs:live-status-protocol[not(ncs:capability)]) or (../../ncs:live-status-protocol/ncs:capability/ncs:module[.='Cisco-IOS-XR-crypto-ssh-cfg'])";
      description
        "Secure Shell configuration";
      container client {
        description
          "Provide SSH client service";
        container client-algo {
          description
            "Cisco ssh algorithms";
          uses live_ncs_KEY-EXCHANGE;
        }
        container client-enable {
          description
            "clientenable";
          container client-cipher {
            description
              "Enable AES-CBC and 3DES_CBC for ssh client";
            leaf aes-cbc {
              type boolean;
              // NCS drop default statement
              description
                "Enable AES-CBC ciphers";
            }
            leaf tripledes-cbc {
              type boolean;
              // NCS drop default statement
              description
                "Enable 3DES-CBC cipher";
            }
          }
        }
        leaf rekey-volume {
          type uint32 {
            range "1024..4095";
          }
          // NCS drop default statement
          description
            "Configure client volume-based rekey for SSH";
        }
        leaf host-public-key {
          type string;
          description
            "Filename - where to store known host file";
        }
        leaf client-vrf {
          type xr:Cisco-ios-xr-string {
            length "1..32";
          }
          description
            "Source interface VRF for ssh client sessions";
        }
        leaf v2 {
          type empty;
          description
            "Cisco ssh client force protocol version 2 only";
        }
        leaf tcp-window-scale {
          type uint32 {
            range "1..14";
          }
          // NCS drop default statement
          description
            "Set SSH Client Tcp Window Scale factor";
        }
        leaf rekey-time {
          type uint32 {
            range "30..1440";
          }
          units "minute";
          // NCS drop default statement
          description
            "Configure client time-based rekey for SSH";
        }
        leaf source-interface {
          type xr:Interface-name;
          description
            "Source interface for ssh client sessions";
        }
        leaf dscp {
          type uint32 {
            range "0..63";
          }
          description
            "Cisco sshd DSCP value";
        }
      }
      container server {
        description
          "Provide SSH server service";
        container disable {
          description
            "disable";
          container hmac {
            description
              "hmac";
            leaf hmac-sha512 {
              type boolean;
              // NCS drop default statement
              description
                "Disable Hmac-sha2-512 negotiation";
            }
          }
        }
        container enable {
          description
            "enable";
          container cipher {
            description
              "Enable AES-CBC and 3DES-CBC ciphers";
            leaf aes-cbc {
              type boolean;
              // NCS drop default statement
              description
                "Enable aes-cbc ciphers";
            }
            leaf tripledes-cbc {
              type boolean;
              // NCS drop default statement
              description
                "Enable 3des-cbc cipher";
            }
          }
        }
        container vrf-table {
          description
            "Cisco sshd VRF name";
          uses live_ncs_VRF;
        }
        container server-algo {
          description
            "Cisco ssh algorithms";
          uses live_ncs_KEY-EXCHANGE;
        }
        container capability {
          description
            "Capability";
          leaf netconf-xml {
            type boolean;
            // NCS drop default statement
            description
              "Enable Netconf-XML stack on port 22";
          }
        }
        container netconf-vrf-table {
          description
            "Cisco sshd Netconf VRF name";
          uses live_ncs_VRF;
        }
        leaf rekey-volume {
          type uint32 {
            range "1024..4095";
          }
          // NCS drop default statement
          description
            "Configure volume-based rekey for SSH";
        }
        leaf session-limit {
          type uint32 {
            range "1..110";
          }
          description
            "Cisco sshd session-limit of service requests";
        }
        leaf netconf {
          type uint32 {
            range "1..65535";
          }
          // NCS drop default statement
          description
            "port number on which ssh service to be started
             for netconf";
        }
        leaf v2 {
          type empty;
          description
            "Cisco sshd force protocol version 2 only";
        }
        leaf tcp-window-scale {
          type uint32 {
            range "1..14";
          }
          // NCS drop default statement
          description
            "Set SSH Server Tcp Window Scale factor";
        }
        leaf rekey-time {
          type uint32 {
            range "30..1440";
          }
          units "minute";
          // NCS drop default statement
          description
            "Time Period in minutes, defalut 60";
        }
        leaf logging {
          type empty;
          description
            "Enable ssh server logging";
        }
        leaf rate-limit {
          type uint32 {
            range "1..600";
          }
          // NCS drop default statement
          description
            "Cisco sshd rate-limit of service requests";
        }
        leaf timeout {
          type uint32 {
            range "5..120";
          }
          units "second";
          // NCS drop default statement
          description
            "Timeout value between 5-120 seconds defalut 30";
        }
        leaf dscp {
          type uint32 {
            range "0..63";
          }
          description
            "Cisco sshd DSCP value";
        }
      }
      container backup-server {
        description
          "Provide SSH server service";
        container backup-port-vrf {
          presence "Indicates a backup-port-vrf node is configured.";
          description
            "backup server config";
          leaf port {
            type uint32 {
              range "11000..15000";
            }
            // NCS drop mandatory statement
            description
              "Port number";
          }
          leaf vrf-name {
            type xr:Cisco-ios-xr-string {
              length "1..32";
            }
            // NCS drop mandatory statement
            description
              "VRF name (max:32 chars)";
          }
        }
      }
    }
  }
  augment "/ncs:devices/ncs:template/ncs:ned-id/ncs:config" {
    container ssh {
      description
        "Secure Shell configuration";
      container client {
        description
          "Provide SSH client service";
        container client-algo {
          description
            "Cisco ssh algorithms";
          uses ncs_template_KEY-EXCHANGE;
        }
        container client-enable {
          description
            "clientenable";
          container client-cipher {
            description
              "Enable AES-CBC and 3DES_CBC for ssh client";
            leaf aes-cbc {
              type string;
              // NCS drop default statement
              description
                "Enable AES-CBC ciphers";
            }
            leaf tripledes-cbc {
              type string;
              // NCS drop default statement
              description
                "Enable 3DES-CBC cipher";
            }
          }
        }
        leaf rekey-volume {
          type string;
          // NCS drop default statement
          description
            "Configure client volume-based rekey for SSH";
        }
        leaf host-public-key {
          type string;
          description
            "Filename - where to store known host file";
        }
        leaf client-vrf {
          type string;
          description
            "Source interface VRF for ssh client sessions";
        }
        leaf v2 {
          type empty;
          description
            "Cisco ssh client force protocol version 2 only";
        }
        leaf tcp-window-scale {
          type string;
          // NCS drop default statement
          description
            "Set SSH Client Tcp Window Scale factor";
        }
        leaf rekey-time {
          type string;
          units "minute";
          // NCS drop default statement
          description
            "Configure client time-based rekey for SSH";
        }
        leaf source-interface {
          type string;
          description
            "Source interface for ssh client sessions";
        }
        leaf dscp {
          type string;
          description
            "Cisco sshd DSCP value";
        }
      }
      container server {
        description
          "Provide SSH server service";
        container disable {
          description
            "disable";
          container hmac {
            description
              "hmac";
            leaf hmac-sha512 {
              type string;
              // NCS drop default statement
              description
                "Disable Hmac-sha2-512 negotiation";
            }
          }
        }
        container enable {
          description
            "enable";
          container cipher {
            description
              "Enable AES-CBC and 3DES-CBC ciphers";
            leaf aes-cbc {
              type string;
              // NCS drop default statement
              description
                "Enable aes-cbc ciphers";
            }
            leaf tripledes-cbc {
              type string;
              // NCS drop default statement
              description
                "Enable 3des-cbc cipher";
            }
          }
        }
        container vrf-table {
          description
            "Cisco sshd VRF name";
          uses ncs_template_VRF;
        }
        container server-algo {
          description
            "Cisco ssh algorithms";
          uses ncs_template_KEY-EXCHANGE;
        }
        container capability {
          description
            "Capability";
          leaf netconf-xml {
            type string;
            // NCS drop default statement
            description
              "Enable Netconf-XML stack on port 22";
          }
        }
        container netconf-vrf-table {
          description
            "Cisco sshd Netconf VRF name";
          uses ncs_template_VRF;
        }
        leaf rekey-volume {
          type string;
          // NCS drop default statement
          description
            "Configure volume-based rekey for SSH";
        }
        leaf session-limit {
          type string;
          description
            "Cisco sshd session-limit of service requests";
        }
        leaf netconf {
          type string;
          // NCS drop default statement
          description
            "port number on which ssh service to be started
             for netconf";
        }
        leaf v2 {
          type empty;
          description
            "Cisco sshd force protocol version 2 only";
        }
        leaf tcp-window-scale {
          type string;
          // NCS drop default statement
          description
            "Set SSH Server Tcp Window Scale factor";
        }
        leaf rekey-time {
          type string;
          units "minute";
          // NCS drop default statement
          description
            "Time Period in minutes, defalut 60";
        }
        leaf logging {
          type empty;
          description
            "Enable ssh server logging";
        }
        leaf rate-limit {
          type string;
          // NCS drop default statement
          description
            "Cisco sshd rate-limit of service requests";
        }
        leaf timeout {
          type string;
          units "second";
          // NCS drop default statement
          description
            "Timeout value between 5-120 seconds defalut 30";
        }
        leaf dscp {
          type string;
          description
            "Cisco sshd DSCP value";
        }
      }
      container backup-server {
        description
          "Provide SSH server service";
        container backup-port-vrf {
          presence "Indicates a backup-port-vrf node is configured.";
          description
            "backup server config";
          leaf port {
            type string;
            // NCS drop mandatory statement
            description
              "Port number";
          }
          leaf vrf-name {
            type string;
            // NCS drop mandatory statement
            description
              "VRF name (max:32 chars)";
          }
        }
      }
    }
  }
}
