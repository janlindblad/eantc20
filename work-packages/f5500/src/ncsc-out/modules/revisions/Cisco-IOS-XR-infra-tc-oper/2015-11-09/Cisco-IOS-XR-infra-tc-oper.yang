module Cisco-IOS-XR-infra-tc-oper {
  // Generated by yanger -t ncs
  tailf:mount-id f5500-nc-1.0:f5500-nc-1.0;
  tailf:ncs-device-type "netconf";

  namespace "http://cisco.com/ns/yang/Cisco-IOS-XR-infra-tc-oper";
  prefix Cisco-IOS-XR-infra-tc-oper;

  import Cisco-IOS-XR-types {
    prefix xr;
  }
  include Cisco-IOS-XR-infra-tc-oper-sub1 {
    revision-date 2015-11-09;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR infra-tc package operational data.

     This module contains definitions
     for the following management objects:
       traffic-collector: Global Traffic Collector configuration
         commands

     Copyright (c) 2013-2018 by Cisco Systems, Inc.
     All rights reserved.";

  revision 2015-11-09 {
    description
      "IOS XR 6.0 revision.";
  }

  typedef Tc-oper-local-label {
    type uint32 {
      range "16..1048575";
    }
    description
      "Tc oper local label";
  }

  typedef Tc-oper-af-name {
    type enumeration {
      enum "ipv4" {
        value 0;
        description
          "IPv4";
      }
      enum "ipv6" {
        value 1;
        description
          "IPv6";
      }
    }
    description
      "Tc oper af name";
  }

  grouping ncs_template_AF-TABLE {
    description
      "Common node of default-vrf, traffic-collector";
    container afs {
      description
        "Address Family specific operational data";
      list af {
        // NCS patched for predictable order
        ordered-by user;
        key "af-name";
        description
          "Operational data for given Address Family";
        container counters {
          description
            "Show Counters";
          container prefixes {
            description
              "Prefix Database";
            list prefix {
              // NCS patched for predictable order
              ordered-by user;
              description
                "Show Prefix Counter";
              leaf ipaddr {
                type string;
                description
                  "IP Address";
              }
              leaf mask {
                type string;
                description
                  "Prefix Mask";
              }
              leaf label {
                type string;
                description
                  "Local Label";
              }
              uses ncs_template_TC-MGMT-PREFIX-DATA;
            }
          }
          container tunnels {
            description
              "Tunnels";
            list tunnel {
              // NCS patched for predictable order
              ordered-by user;
              key "interface-name";
              description
                "Tunnel information";
              leaf interface-name {
                type string;
                description
                  "The Interface Name";
              }
              uses ncs_template_TC-MGMT-TUNNEL-DATA;
            }
          }
        }
        leaf af-name {
          type string;
          description
            "Address Family name";
        }
      }
    }
  }

  grouping ncs_rpc_notif_AF-TABLE {
    description
      "Common node of default-vrf, traffic-collector";
    container afs {
      description
        "Address Family specific operational data";
      list af {
        key "af-name";
        description
          "Operational data for given Address Family";
        container counters {
          description
            "Show Counters";
          container prefixes {
            description
              "Prefix Database";
            list prefix {
              description
                "Show Prefix Counter";
              leaf ipaddr {
                type xr:Cisco-ios-xr-string;
                description
                  "IP Address";
              }
              leaf mask {
                type xr:Cisco-ios-xr-string;
                description
                  "Prefix Mask";
              }
              leaf label {
                type Tc-oper-local-label;
                description
                  "Local Label";
              }
              uses ncs_rpc_notif_TC-MGMT-PREFIX-DATA;
            }
          }
          container tunnels {
            description
              "Tunnels";
            list tunnel {
              key "interface-name";
              description
                "Tunnel information";
              leaf interface-name {
                type xr:Interface-name;
                description
                  "The Interface Name";
              }
              uses ncs_rpc_notif_TC-MGMT-TUNNEL-DATA;
            }
          }
        }
        leaf af-name {
          type Tc-oper-af-name;
          description
            "Address Family name";
        }
      }
    }
  }

  grouping live_ncs_AF-TABLE {
    description
      "Common node of default-vrf, traffic-collector";
    container afs {
      description
        "Address Family specific operational data";
      list af {
        key "af-name";
        description
          "Operational data for given Address Family";
        container counters {
          description
            "Show Counters";
          container prefixes {
            description
              "Prefix Database";
            list prefix {
              description
                "Show Prefix Counter";
              leaf ipaddr {
                type xr:Cisco-ios-xr-string;
                description
                  "IP Address";
              }
              leaf mask {
                type xr:Cisco-ios-xr-string;
                description
                  "Prefix Mask";
              }
              leaf label {
                type Tc-oper-local-label;
                description
                  "Local Label";
              }
              uses live_ncs_TC-MGMT-PREFIX-DATA;
            }
          }
          container tunnels {
            description
              "Tunnels";
            list tunnel {
              key "interface-name";
              description
                "Tunnel information";
              leaf interface-name {
                type xr:Interface-name;
                description
                  "The Interface Name";
              }
              uses live_ncs_TC-MGMT-TUNNEL-DATA;
            }
          }
        }
        leaf af-name {
          type Tc-oper-af-name;
          description
            "Address Family name";
        }
      }
    }
  }

  grouping AF-TABLE {
    description
      "Common node of default-vrf, traffic-collector";
    container afs {
      description
        "Address Family specific operational data";
      list af {
        key "af-name";
        description
          "Operational data for given Address Family";
        container counters {
          description
            "Show Counters";
          container prefixes {
            description
              "Prefix Database";
            list prefix {
              description
                "Show Prefix Counter";
              leaf ipaddr {
                type xr:Cisco-ios-xr-string;
                description
                  "IP Address";
              }
              leaf mask {
                type xr:Cisco-ios-xr-string;
                description
                  "Prefix Mask";
              }
              leaf label {
                type Tc-oper-local-label;
                description
                  "Local Label";
              }
              uses TC-MGMT-PREFIX-DATA;
            }
          }
          container tunnels {
            description
              "Tunnels";
            list tunnel {
              key "interface-name";
              description
                "Tunnel information";
              leaf interface-name {
                type xr:Interface-name;
                description
                  "The Interface Name";
              }
              uses TC-MGMT-TUNNEL-DATA;
            }
          }
        }
        leaf af-name {
          type Tc-oper-af-name;
          description
            "Address Family name";
        }
      }
    }
  }

  augment "/ncs:devices/ncs:device/ncs:config" {
    // NCS drop config false container 'traffic-collector'
  }
  augment "/ncs:devices/ncs:device/ncs:live-status" {
    container traffic-collector {
      tailf:ncs-device-type "netconf";
      tailf:display-when "not(../../ncs:module) or ../../ncs:module[ncs:name='Cisco-IOS-XR-infra-tc-oper'] or (../../ncs:live-status-protocol[not(ncs:capability)]) or (../../ncs:live-status-protocol/ncs:capability/ncs:module[.='Cisco-IOS-XR-infra-tc-oper'])";
      description
        "Global Traffic Collector configuration commands";
      container external-interfaces {
        description
          "External Interface";
        list external-interface {
          key "interface-name";
          description
            "External Interface ";
          leaf interface-name {
            type xr:Interface-name;
            description
              "The Interface Name";
          }
          uses live_ncs_TC-MGMT-EXT-IF-DATA;
        }
      }
      container summary {
        description
          "Traffic Collector summary";
        uses live_ncs_TC-MGMT-SUMMARY;
      }
      container vrf-table {
        description
          "VRF specific operational data";
        container default-vrf {
          description
            "DefaultVRF specific operational data";
          uses live_ncs_AF-TABLE;
        }
      }
      uses live_ncs_AF-TABLE;
    }
  }
  augment "/ncs:devices/ncs:template/ncs:ned-id/ncs:config" {
    // NCS drop config false container 'traffic-collector'
  }
}
