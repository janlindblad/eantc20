module Cisco-IOS-XR-drivers-mpa-infra-cfg {
  // Generated by yanger -t ncs
  tailf:mount-id f5500-nc-1.0:f5500-nc-1.0;
  tailf:ncs-device-type "netconf";

  namespace "http://cisco.com/ns/yang/Cisco-IOS-XR-drivers-mpa-infra-cfg";
  prefix Cisco-IOS-XR-drivers-mpa-infra-cfg;

  import Cisco-IOS-XR-types {
    prefix xr;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR drivers-mpa-infra package configuration.

     This module contains definitions
     for the following management objects:
       hardware-module: Configure subslot h/w module

     Copyright (c) 2013-2018 by Cisco Systems, Inc.
     All rights reserved.";

  revision 2015-11-09 {
    description
      "IOS XR 6.0 revision.";
  }

  typedef Hw-module-shutdown-power-mode {
    type enumeration {
      enum "powered" {
        value 2;
        description
          "Keep the showdown module powered (default)";
      }
    }
    description
      "Hw module shutdown power mode";
  }

  augment "/ncs:devices/ncs:device/ncs:config" {
    container hardware-module {
      tailf:ncs-device-type "netconf";
      tailf:display-when "not(../../ncs:module) or ../../ncs:module[ncs:name='Cisco-IOS-XR-drivers-mpa-infra-cfg']";
      description
        "Configure subslot h/w module";
      container nodes {
        description
          " subslot h/w module";
        list node {
          key "node-name";
          description
            "The identifier for a SPA node";
          leaf shutdown {
            type Hw-module-shutdown-power-mode;
            description
              "Shutdown a subslot h/w module";
          }
          leaf node-name {
            type xr:Node-id;
            description
              "A SPA node";
          }
        }
      }
    }
  }
  augment "/ncs:devices/ncs:device/ncs:live-status" {
    container hardware-module {
      tailf:ncs-device-type "netconf";
      tailf:display-when "not(../../ncs:module) or ../../ncs:module[ncs:name='Cisco-IOS-XR-drivers-mpa-infra-cfg'] or (../../ncs:live-status-protocol[not(ncs:capability)]) or (../../ncs:live-status-protocol/ncs:capability/ncs:module[.='Cisco-IOS-XR-drivers-mpa-infra-cfg'])";
      description
        "Configure subslot h/w module";
      container nodes {
        description
          " subslot h/w module";
        list node {
          key "node-name";
          description
            "The identifier for a SPA node";
          leaf shutdown {
            type Hw-module-shutdown-power-mode;
            description
              "Shutdown a subslot h/w module";
          }
          leaf node-name {
            type xr:Node-id;
            description
              "A SPA node";
          }
        }
      }
    }
  }
  augment "/ncs:devices/ncs:template/ncs:ned-id/ncs:config" {
    container hardware-module {
      description
        "Configure subslot h/w module";
      container nodes {
        description
          " subslot h/w module";
        list node {
          // NCS patched for predictable order
          ordered-by user;
          key "node-name";
          description
            "The identifier for a SPA node";
          leaf shutdown {
            type string;
            description
              "Shutdown a subslot h/w module";
          }
          leaf node-name {
            type string;
            description
              "A SPA node";
          }
        }
      }
    }
  }
}
