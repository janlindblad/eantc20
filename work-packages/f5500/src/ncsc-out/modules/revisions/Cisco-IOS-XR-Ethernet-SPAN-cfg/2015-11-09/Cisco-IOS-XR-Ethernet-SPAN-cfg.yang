module Cisco-IOS-XR-Ethernet-SPAN-cfg {
  // Generated by yanger -t ncs
  tailf:mount-id f5500-nc-1.0:f5500-nc-1.0;
  tailf:ncs-device-type "netconf";

  namespace "http://cisco.com/ns/yang/Cisco-IOS-XR-Ethernet-SPAN-cfg";
  prefix Cisco-IOS-XR-Ethernet-SPAN-cfg;

  import ietf-inet-types {
    prefix inet;
  }
  import Cisco-IOS-XR-types {
    prefix xr;
  }
  import Cisco-IOS-XR-Ethernet-SPAN-datatypes {
    prefix dt1;
  }
  import Cisco-IOS-XR-ifmgr-cfg {
    prefix a1;
  }
  import Cisco-IOS-XR-l2vpn-cfg {
    prefix a2;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR Ethernet-SPAN package configuration.

     This module contains definitions
     for the following management objects:
       span-monitor-session: none

     This YANG module augments the
       Cisco-IOS-XR-ifmgr-cfg,
       Cisco-IOS-XR-l2vpn-cfg
     modules with configuration data.

     Copyright (c) 2013-2018 by Cisco Systems, Inc.
     All rights reserved.";

  revision 2015-11-09 {
    description
      "IOS XR 6.0 revision.";
  }

  typedef Span-destination {
    type enumeration {
      enum "interface" {
        value 0;
        description
          "Destination Interface";
      }
      enum "pseudowire" {
        value 1;
        description
          "Destination Pseudowire";
      }
      enum "ipv4-address" {
        value 2;
        description
          "Destination next-hop IPv4 address";
      }
      enum "ipv6-address" {
        value 3;
        description
          "Destination next-hop IPv6 address";
      }
    }
    description
      "Span destination";
  }

  typedef Span-mirror-interval {
    type enumeration {
      enum "512" {
        value 1;
        description
          "Mirror 1 in every 512 packets";
      }
      enum "1k" {
        value 2;
        description
          "Mirror 1 in every 1024 packets";
      }
      enum "2k" {
        value 3;
        description
          "Mirror 1 in every 2048 packets";
      }
      enum "4k" {
        value 4;
        description
          "Mirror 1 in every 4096 packets";
      }
      enum "8k" {
        value 5;
        description
          "Mirror 1 in every 8192 packets";
      }
      enum "16k" {
        value 6;
        description
          "Mirror 1 in every 16384 packets";
      }
    }
    description
      "Span mirror interval";
  }

  typedef Span-traffic-direction {
    type enumeration {
      enum "rx-only" {
        value 1;
        description
          "Replicate only received (ingress) traffic";
      }
      enum "tx-only" {
        value 2;
        description
          "Replicate only transmitted (egress) traffic";
      }
    }
    description
      "Span traffic direction";
  }

  grouping ncs_template_MIRROR-INTERVAL {
    description
      "Common node of span-monitor-session,
       span-monitor-session";
    leaf mirror-interval {
      type string;
      description
        "Specify the mirror interval";
    }
  }

  grouping ncs_template_MIRROR-FIRST {
    description
      "Common node of span-monitor-session,
       span-monitor-session";
    leaf mirror-first {
      type string;
      units "byte";
      description
        "Mirror a specified number of bytes from start of
         packet";
    }
  }

  grouping ncs_template_SPAN-MONITOR-SESSION-TABLE {
    description
      "Common node of ip-subscriber, ppp,
       subscriber-service";
    container span-monitor-sessions {
      description
        "Monitor Session container for this template";
      list span-monitor-session {
        // NCS patched for predictable order
        ordered-by user;
        key "session-class";
        description
          "Configuration for a particular class of Monitor
           Session";
        leaf session-class {
          type string;
          description
            "Session Class";
        }
        uses ncs_template_MIRROR-FIRST;
        uses ncs_template_ATTACHMENT;
        uses ncs_template_MIRROR-INTERVAL;
        uses ncs_template_ACL;
      }
    }
  }

  grouping ncs_template_ETHERNET-SPAN-INTERFACE-CFG-SPAN-MONITOR-SESSION-TABLE {
    description
      "Common node of ip-subscriber, ppp,
       subscriber-serviceCommon node of
       interface-configuration, l2-transport";
    container span-monitor-sessions {
      description
        "Monitor Session container for this source
         interface";
      list span-monitor-session {
        // NCS patched for predictable order
        ordered-by user;
        key "session-class";
        description
          "Configuration for a particular class of Monitor
           Session";
        leaf session-class {
          type string;
          description
            "Session Class";
        }
        uses ncs_template_MIRROR-FIRST;
        uses ncs_template_ATTACHMENT;
        uses ncs_template_MIRROR-INTERVAL;
        uses ncs_template_ACL;
      }
    }
  }

  grouping ncs_template_ACL {
    description
      "Common node of span-monitor-session,
       span-monitor-session";
    container acl {
      presence "Indicates a acl node is configured.";
      description
        "Enable ACL matching for traffic mirroring";
      leaf acl-enable {
        type empty;
        // NCS drop mandatory statement
        description
          "Enable ACL";
      }
      leaf acl-name {
        type string;
        description
          "ACL Name";
      }
    }
  }

  grouping ncs_template_ATTACHMENT {
    description
      "Common node of span-monitor-session,
       span-monitor-session";
    container attachment {
      presence "Indicates a attachment node is configured.";
      description
        "Attach the interface to a Monitor Session";
      leaf session-name {
        type string;
        // NCS drop mandatory statement
        description
          "Session Name";
      }
      leaf direction {
        type string;
        description
          "Specify the direction of traffic to replicate
           (optional)";
      }
      leaf port-level-enable {
        type empty;
        description
          "Enable port level traffic mirroring";
      }
    }
  }

  grouping ncs_rpc_notif_MIRROR-INTERVAL {
    description
      "Common node of span-monitor-session,
       span-monitor-session";
    leaf mirror-interval {
      type Span-mirror-interval;
      description
        "Specify the mirror interval";
    }
  }

  grouping ncs_rpc_notif_MIRROR-FIRST {
    description
      "Common node of span-monitor-session,
       span-monitor-session";
    leaf mirror-first {
      type uint32 {
        range "1..10000";
      }
      units "byte";
      description
        "Mirror a specified number of bytes from start of
         packet";
    }
  }

  grouping ncs_rpc_notif_SPAN-MONITOR-SESSION-TABLE {
    description
      "Common node of ip-subscriber, ppp,
       subscriber-service";
    container span-monitor-sessions {
      description
        "Monitor Session container for this template";
      list span-monitor-session {
        key "session-class";
        description
          "Configuration for a particular class of Monitor
           Session";
        leaf session-class {
          type dt1:Span-session-class;
          description
            "Session Class";
        }
        uses ncs_rpc_notif_MIRROR-FIRST;
        uses ncs_rpc_notif_ATTACHMENT;
        uses ncs_rpc_notif_MIRROR-INTERVAL;
        uses ncs_rpc_notif_ACL;
      }
    }
  }

  grouping ncs_rpc_notif_ETHERNET-SPAN-INTERFACE-CFG-SPAN-MONITOR-SESSION-TABLE {
    description
      "Common node of ip-subscriber, ppp,
       subscriber-serviceCommon node of
       interface-configuration, l2-transport";
    container span-monitor-sessions {
      description
        "Monitor Session container for this source
         interface";
      list span-monitor-session {
        key "session-class";
        description
          "Configuration for a particular class of Monitor
           Session";
        leaf session-class {
          type dt1:Span-session-class;
          description
            "Session Class";
        }
        uses ncs_rpc_notif_MIRROR-FIRST;
        uses ncs_rpc_notif_ATTACHMENT;
        uses ncs_rpc_notif_MIRROR-INTERVAL;
        uses ncs_rpc_notif_ACL;
      }
    }
  }

  grouping ncs_rpc_notif_ACL {
    description
      "Common node of span-monitor-session,
       span-monitor-session";
    container acl {
      presence "Indicates a acl node is configured.";
      description
        "Enable ACL matching for traffic mirroring";
      leaf acl-enable {
        type empty;
        mandatory true;
        description
          "Enable ACL";
      }
      leaf acl-name {
        type dt1:Span-acl-name;
        description
          "ACL Name";
      }
    }
  }

  grouping ncs_rpc_notif_ATTACHMENT {
    description
      "Common node of span-monitor-session,
       span-monitor-session";
    container attachment {
      presence "Indicates a attachment node is configured.";
      description
        "Attach the interface to a Monitor Session";
      leaf session-name {
        type dt1:Span-session-name;
        mandatory true;
        description
          "Session Name";
      }
      leaf direction {
        type Span-traffic-direction;
        description
          "Specify the direction of traffic to replicate
           (optional)";
      }
      leaf port-level-enable {
        type empty;
        description
          "Enable port level traffic mirroring";
      }
    }
  }

  grouping live_ncs_MIRROR-INTERVAL {
    description
      "Common node of span-monitor-session,
       span-monitor-session";
    leaf mirror-interval {
      type Span-mirror-interval;
      description
        "Specify the mirror interval";
    }
  }

  grouping live_ncs_MIRROR-FIRST {
    description
      "Common node of span-monitor-session,
       span-monitor-session";
    leaf mirror-first {
      type uint32 {
        range "1..10000";
      }
      units "byte";
      description
        "Mirror a specified number of bytes from start of
         packet";
    }
  }

  grouping live_ncs_SPAN-MONITOR-SESSION-TABLE {
    description
      "Common node of ip-subscriber, ppp,
       subscriber-service";
    container span-monitor-sessions {
      description
        "Monitor Session container for this template";
      list span-monitor-session {
        key "session-class";
        description
          "Configuration for a particular class of Monitor
           Session";
        leaf session-class {
          type dt1:Span-session-class;
          description
            "Session Class";
        }
        uses live_ncs_MIRROR-FIRST;
        uses live_ncs_ATTACHMENT;
        uses live_ncs_MIRROR-INTERVAL;
        uses live_ncs_ACL;
      }
    }
  }

  grouping live_ncs_ETHERNET-SPAN-INTERFACE-CFG-SPAN-MONITOR-SESSION-TABLE {
    description
      "Common node of ip-subscriber, ppp,
       subscriber-serviceCommon node of
       interface-configuration, l2-transport";
    container span-monitor-sessions {
      description
        "Monitor Session container for this source
         interface";
      list span-monitor-session {
        key "session-class";
        description
          "Configuration for a particular class of Monitor
           Session";
        leaf session-class {
          type dt1:Span-session-class;
          description
            "Session Class";
        }
        uses live_ncs_MIRROR-FIRST;
        uses live_ncs_ATTACHMENT;
        uses live_ncs_MIRROR-INTERVAL;
        uses live_ncs_ACL;
      }
    }
  }

  grouping live_ncs_ACL {
    description
      "Common node of span-monitor-session,
       span-monitor-session";
    container acl {
      presence "Indicates a acl node is configured.";
      description
        "Enable ACL matching for traffic mirroring";
      leaf acl-enable {
        type empty;
        // NCS drop mandatory statement
        description
          "Enable ACL";
      }
      leaf acl-name {
        type dt1:Span-acl-name;
        description
          "ACL Name";
      }
    }
  }

  grouping live_ncs_ATTACHMENT {
    description
      "Common node of span-monitor-session,
       span-monitor-session";
    container attachment {
      presence "Indicates a attachment node is configured.";
      description
        "Attach the interface to a Monitor Session";
      leaf session-name {
        type dt1:Span-session-name;
        // NCS drop mandatory statement
        description
          "Session Name";
      }
      leaf direction {
        type Span-traffic-direction;
        description
          "Specify the direction of traffic to replicate
           (optional)";
      }
      leaf port-level-enable {
        type empty;
        description
          "Enable port level traffic mirroring";
      }
    }
  }

  grouping MIRROR-INTERVAL {
    description
      "Common node of span-monitor-session,
       span-monitor-session";
    leaf mirror-interval {
      type Span-mirror-interval;
      description
        "Specify the mirror interval";
    }
  }

  grouping MIRROR-FIRST {
    description
      "Common node of span-monitor-session,
       span-monitor-session";
    leaf mirror-first {
      type uint32 {
        range "1..10000";
      }
      units "byte";
      description
        "Mirror a specified number of bytes from start of
         packet";
    }
  }

  grouping SPAN-MONITOR-SESSION-TABLE {
    description
      "Common node of ip-subscriber, ppp,
       subscriber-service";
    container span-monitor-sessions {
      description
        "Monitor Session container for this template";
      list span-monitor-session {
        key "session-class";
        description
          "Configuration for a particular class of Monitor
           Session";
        leaf session-class {
          type dt1:Span-session-class;
          description
            "Session Class";
        }
        uses MIRROR-FIRST;
        uses ATTACHMENT;
        uses MIRROR-INTERVAL;
        uses ACL;
      }
    }
  }

  grouping ETHERNET-SPAN-INTERFACE-CFG-SPAN-MONITOR-SESSION-TABLE {
    description
      "Common node of ip-subscriber, ppp,
       subscriber-serviceCommon node of
       interface-configuration, l2-transport";
    container span-monitor-sessions {
      description
        "Monitor Session container for this source
         interface";
      list span-monitor-session {
        key "session-class";
        description
          "Configuration for a particular class of Monitor
           Session";
        leaf session-class {
          type dt1:Span-session-class;
          description
            "Session Class";
        }
        uses MIRROR-FIRST;
        uses ATTACHMENT;
        uses MIRROR-INTERVAL;
        uses ACL;
      }
    }
  }

  grouping ACL {
    description
      "Common node of span-monitor-session,
       span-monitor-session";
    container acl {
      presence "Indicates a acl node is configured.";
      description
        "Enable ACL matching for traffic mirroring";
      leaf acl-enable {
        type empty;
        mandatory true;
        description
          "Enable ACL";
      }
      leaf acl-name {
        type dt1:Span-acl-name;
        description
          "ACL Name";
      }
    }
  }

  grouping ATTACHMENT {
    description
      "Common node of span-monitor-session,
       span-monitor-session";
    container attachment {
      presence "Indicates a attachment node is configured.";
      description
        "Attach the interface to a Monitor Session";
      leaf session-name {
        type dt1:Span-session-name;
        mandatory true;
        description
          "Session Name";
      }
      leaf direction {
        type Span-traffic-direction;
        description
          "Specify the direction of traffic to replicate
           (optional)";
      }
      leaf port-level-enable {
        type empty;
        description
          "Enable port level traffic mirroring";
      }
    }
  }

  augment "/ncs:devices/ncs:device/ncs:config" {
    container span-monitor-session {
      tailf:ncs-device-type "netconf";
      tailf:display-when "not(../../ncs:module) or ../../ncs:module[ncs:name='Cisco-IOS-XR-Ethernet-SPAN-cfg']";
      description
        "none";
      container sessions {
        description
          "Monitor-session configuration commands";
        list session {
          key "session";
          description
            "Configuration for a particular Monitor Session";
          container destination {
            description
              "Specify a destination";
            leaf destination-type {
              type Span-destination;
              description
                "Specify the type of destination";
            }
            leaf destination-interface-name {
              when "../destination-type = 'interface'" {
                tailf:xpath-root 3;
                description
                  "../DestinationType = Interface";
              }
              type xr:Interface-name;
              description
                "Specify the destination interface name";
            }
            leaf destination-ipv4-address {
              when "../destination-type = 'ipv4-address'" {
                tailf:xpath-root 3;
                description
                  "../DestinationType = IPv4Address";
              }
              type inet:ipv4-address-no-zone;
              description
                "Specify the destination next-hop IPv4 address";
            }
            leaf destination-ipv6-address {
              when "../destination-type = 'ipv6-address'" {
                tailf:xpath-root 3;
                description
                  "../DestinationType = IPv6Address";
              }
              type inet:ipv6-address-no-zone;
              description
                "Specify the destination next-hop IPv6 address";
            }
          }
          leaf class {
            type dt1:Span-session-class;
            default "ethernet";
            description
              "Enable a Monitor Session.  Setting this item
               causes the Monitor Session to be created.";
          }
          leaf discard-class {
            type uint32 {
              range "0..7";
            }
            description
              "Specify the discard class value to be set on
               all traffic mirrored to the destination";
          }
          leaf inject-interface {
            type xr:Interface-name;
            description
              "Specify the inject interface name";
          }
          leaf traffic-class {
            type uint32 {
              range "0..7";
            }
            description
              "Specify the traffic class value to be set on
               all traffic mirrored to the destination";
          }
          leaf session {
            type dt1:Span-session-name;
            description
              "Session Name";
          }
        }
      }
    }
  }
  augment "/ncs:devices/ncs:device/ncs:live-status" {
    container span-monitor-session {
      tailf:ncs-device-type "netconf";
      tailf:display-when "not(../../ncs:module) or ../../ncs:module[ncs:name='Cisco-IOS-XR-Ethernet-SPAN-cfg'] or (../../ncs:live-status-protocol[not(ncs:capability)]) or (../../ncs:live-status-protocol/ncs:capability/ncs:module[.='Cisco-IOS-XR-Ethernet-SPAN-cfg'])";
      description
        "none";
      container sessions {
        description
          "Monitor-session configuration commands";
        list session {
          key "session";
          description
            "Configuration for a particular Monitor Session";
          container destination {
            description
              "Specify a destination";
            leaf destination-type {
              type Span-destination;
              description
                "Specify the type of destination";
            }
            leaf destination-interface-name {
              // NCS drop when statement
              type xr:Interface-name;
              description
                "Specify the destination interface name";
            }
            leaf destination-ipv4-address {
              // NCS drop when statement
              type inet:ipv4-address-no-zone;
              description
                "Specify the destination next-hop IPv4 address";
            }
            leaf destination-ipv6-address {
              // NCS drop when statement
              type inet:ipv6-address-no-zone;
              description
                "Specify the destination next-hop IPv6 address";
            }
          }
          leaf class {
            type dt1:Span-session-class;
            // NCS drop default statement
            description
              "Enable a Monitor Session.  Setting this item
               causes the Monitor Session to be created.";
          }
          leaf discard-class {
            type uint32 {
              range "0..7";
            }
            description
              "Specify the discard class value to be set on
               all traffic mirrored to the destination";
          }
          leaf inject-interface {
            type xr:Interface-name;
            description
              "Specify the inject interface name";
          }
          leaf traffic-class {
            type uint32 {
              range "0..7";
            }
            description
              "Specify the traffic class value to be set on
               all traffic mirrored to the destination";
          }
          leaf session {
            type dt1:Span-session-name;
            description
              "Session Name";
          }
        }
      }
    }
  }
  augment "/ncs:devices/ncs:template/ncs:ned-id/ncs:config" {
    container span-monitor-session {
      description
        "none";
      container sessions {
        description
          "Monitor-session configuration commands";
        list session {
          // NCS patched for predictable order
          ordered-by user;
          key "session";
          description
            "Configuration for a particular Monitor Session";
          container destination {
            description
              "Specify a destination";
            leaf destination-type {
              type string;
              description
                "Specify the type of destination";
            }
            leaf destination-interface-name {
              // NCS drop when statement
              type string;
              description
                "Specify the destination interface name";
            }
            leaf destination-ipv4-address {
              // NCS drop when statement
              type string;
              description
                "Specify the destination next-hop IPv4 address";
            }
            leaf destination-ipv6-address {
              // NCS drop when statement
              type string;
              description
                "Specify the destination next-hop IPv6 address";
            }
          }
          leaf class {
            type string;
            // NCS drop default statement
            description
              "Enable a Monitor Session.  Setting this item
               causes the Monitor Session to be created.";
          }
          leaf discard-class {
            type string;
            description
              "Specify the discard class value to be set on
               all traffic mirrored to the destination";
          }
          leaf inject-interface {
            type string;
            description
              "Specify the inject interface name";
          }
          leaf traffic-class {
            type string;
            description
              "Specify the traffic class value to be set on
               all traffic mirrored to the destination";
          }
          leaf session {
            type string;
            description
              "Session Name";
          }
        }
      }
    }
  }
  augment "/ncs:devices/ncs:template/ncs:ned-id/ncs:config/a1:interface-configurations/a1:interface-configuration/a2:l2-transport" {
    description
      "This augment extends the configuration data of
       'Cisco-IOS-XR-l2vpn-cfg'";
    uses ncs_template_ETHERNET-SPAN-INTERFACE-CFG-SPAN-MONITOR-SESSION-TABLE;
  }
  augment "/ncs:devices/ncs:device/ncs:live-status/a1:interface-configurations/a1:interface-configuration/a2:l2-transport" {
    description
      "This augment extends the configuration data of
       'Cisco-IOS-XR-l2vpn-cfg'";
    uses live_ncs_ETHERNET-SPAN-INTERFACE-CFG-SPAN-MONITOR-SESSION-TABLE {
      refine span-monitor-sessions {
        tailf:ncs-device-type "netconf";
        tailf:display-when "not(../../../../../ncs:module) or ../../../../../ncs:module[ncs:name='Cisco-IOS-XR-Ethernet-SPAN-cfg'] or (../../../../../ncs:live-status-protocol[not(ncs:capability)]) or (../../../../../ncs:live-status-protocol/ncs:capability/ncs:module[.='Cisco-IOS-XR-Ethernet-SPAN-cfg'])";
      }
    }
  }
  augment "/ncs:devices/ncs:device/ncs:config/a1:interface-configurations/a1:interface-configuration/a2:l2-transport" {
    description
      "This augment extends the configuration data of
       'Cisco-IOS-XR-l2vpn-cfg'";
    uses ETHERNET-SPAN-INTERFACE-CFG-SPAN-MONITOR-SESSION-TABLE {
      refine span-monitor-sessions {
        tailf:ncs-device-type "netconf";
        tailf:display-when "not(../../../../../ncs:module) or ../../../../../ncs:module[ncs:name='Cisco-IOS-XR-Ethernet-SPAN-cfg']";
      }
    }
  }
  augment "/ncs:devices/ncs:template/ncs:ned-id/ncs:config/a1:interface-configurations/a1:interface-configuration" {
    description
      "This augment extends the configuration data of
       'Cisco-IOS-XR-ifmgr-cfg'";
    uses ncs_template_ETHERNET-SPAN-INTERFACE-CFG-SPAN-MONITOR-SESSION-TABLE;
  }
  augment "/ncs:devices/ncs:device/ncs:live-status/a1:interface-configurations/a1:interface-configuration" {
    description
      "This augment extends the configuration data of
       'Cisco-IOS-XR-ifmgr-cfg'";
    uses live_ncs_ETHERNET-SPAN-INTERFACE-CFG-SPAN-MONITOR-SESSION-TABLE {
      refine span-monitor-sessions {
        tailf:ncs-device-type "netconf";
        tailf:display-when "not(../../../../ncs:module) or ../../../../ncs:module[ncs:name='Cisco-IOS-XR-Ethernet-SPAN-cfg'] or (../../../../ncs:live-status-protocol[not(ncs:capability)]) or (../../../../ncs:live-status-protocol/ncs:capability/ncs:module[.='Cisco-IOS-XR-Ethernet-SPAN-cfg'])";
      }
    }
  }
  augment "/ncs:devices/ncs:device/ncs:config/a1:interface-configurations/a1:interface-configuration" {
    description
      "This augment extends the configuration data of
       'Cisco-IOS-XR-ifmgr-cfg'";
    uses ETHERNET-SPAN-INTERFACE-CFG-SPAN-MONITOR-SESSION-TABLE {
      refine span-monitor-sessions {
        tailf:ncs-device-type "netconf";
        tailf:display-when "not(../../../../ncs:module) or ../../../../ncs:module[ncs:name='Cisco-IOS-XR-Ethernet-SPAN-cfg']";
      }
    }
  }
}
