submodule Cisco-IOS-XR-mpls-ldp-oper-sub2 {
  // Generated by yanger -t ncs
  tailf:mount-id f5500-nc-1.0:f5500-nc-1.0;

  belongs-to Cisco-IOS-XR-mpls-ldp-oper {
    prefix Cisco-IOS-XR-mpls-ldp-oper-sub2;
  }

  import ietf-inet-types {
    prefix inet;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR mpls-ldp package operational data.

     Copyright (c) 2013-2018 by Cisco Systems, Inc.
     All rights reserved.";

  revision 2017-09-07 {
    description
      "Fixed type translation error.";
  }
  revision 2017-05-01 {
    description
      "Fixing backward compatibility error in module.";
  }
  revision 2015-11-09 {
    description
      "IOS XR 6.0 revision.";
  }

  typedef L2vpn-ldp-pw-fec {
    type enumeration {
      enum "fec128" {
        description
          "FEC 128 pseudowire type";
      }
      enum "fec129" {
        description
          "FEC 129 pseudowire type";
      }
      enum "fec130" {
        description
          "FEC 130 pseudowire type";
      }
      enum "invalid" {
        description
          "FEC not applicable";
      }
    }
    description
      "L2vpn ldp pw fec";
  }

  typedef L2vpn-ldp-pw-agi {
    type enumeration {
      enum "rd" {
        description
          "AGI type RD";
      }
    }
    description
      "L2vpn ldp pw agi";
  }

  typedef L2vpn-ldp-pw-aii {
    type enumeration {
      enum "local-id" {
        description
          "AII Type 1";
      }
      enum "type2" {
        description
          "AII Type 2";
      }
    }
    description
      "L2vpn ldp pw aii";
  }

  grouping ncs_template_L2VPN-LDP-PW-FEC-130 {
    description
      "L2VPN LDP PW FEC 130";
    container agi {
      description
        "AGI";
      uses ncs_template_L2VPN-LDP-PW-AGI;
    }
    container saii {
      description
        "Source Attachment Individual Identifier";
      uses ncs_template_L2VPN-LDP-PW-AII;
    }
  }

  grouping ncs_template_L2VPN-LDP-PW-AII2 {
    description
      "L2VPN LDP PW AII2";
    leaf gobal-id {
      type string;
      description
        "Global ID";
    }
    leaf prefix {
      type string;
      description
        "Prefix";
    }
    leaf ac-id {
      type string;
      description
        "AC ID";
    }
  }

  grouping ncs_template_L2VPN-LDP-PW-AII1 {
    description
      "L2VPN LDP PW AII1";
    leaf local-id {
      type string;
      description
        "Local Identifier";
    }
  }

  grouping ncs_template_L2VPN-LDP-PW-AII {
    description
      "L2VPN LDP PW AII";
    container aii1 {
      // NCS drop when statement
      description
        "aii1";
      uses ncs_template_L2VPN-LDP-PW-AII1;
    }
    container aii2 {
      // NCS drop when statement
      description
        "aii2";
      uses ncs_template_L2VPN-LDP-PW-AII2;
    }
    leaf aii-type {
      type string;
      description
        "AIIType";
    }
  }

  grouping ncs_template_L2VPN-LDP-PW-AGI1 {
    description
      "L2VPN LDP PW AGI1";
    leaf rd {
      type string;
      description
        "Route Distinguisher";
    }
  }

  grouping ncs_template_L2VPN-LDP-PW-AGI {
    description
      "L2VPN LDP PW AGI";
    container agi1 {
      // NCS drop when statement
      description
        "agi1";
      uses ncs_template_L2VPN-LDP-PW-AGI1;
    }
    leaf agi-type {
      type string;
      description
        "AGIType";
    }
  }

  grouping ncs_template_L2VPN-LDP-PW-FEC-129 {
    description
      "L2VPN LDP PW FEC 129";
    container agi {
      description
        "AGI";
      uses ncs_template_L2VPN-LDP-PW-AGI;
    }
    container saii {
      description
        "Source Attachment Individual Identifier";
      uses ncs_template_L2VPN-LDP-PW-AII;
    }
    container taii {
      description
        "Target Attachment Individual Identifier";
      uses ncs_template_L2VPN-LDP-PW-AII;
    }
  }

  grouping ncs_template_L2VPN-LDP-PW-FEC-128 {
    description
      "L2VPN LDP PW FEC 128";
    leaf pseudowire-id {
      type string;
      description
        "Pseudowire ID";
    }
  }

  grouping ncs_template_L2VPN-LDP-PW-FEC-INFO {
    description
      "L2VPN LDP PW FEC INFO";
    container fec128 {
      // NCS drop when statement
      description
        "fec128";
      uses ncs_template_L2VPN-LDP-PW-FEC-128;
    }
    container fec129 {
      // NCS drop when statement
      description
        "fec129";
      uses ncs_template_L2VPN-LDP-PW-FEC-129;
    }
    container fec130 {
      // NCS drop when statement
      description
        "fec130";
      uses ncs_template_L2VPN-LDP-PW-FEC-130;
    }
    leaf fe-ctype {
      type string;
      description
        "FECType";
    }
  }

  grouping ncs_template_L2VPN-LDP-ATOM {
    description
      "L2VPN AToM-DB information";
    container fec-info {
      description
        "Pseudowire FEC information";
      uses ncs_template_L2VPN-LDP-PW-FEC-INFO;
    }
    leaf peer-id-xr {
      type string;
      description
        "Peer ID";
    }
    leaf mapping-tlv-count {
      type string;
      description
        "TLV Count from Label Mapping Message";
    }
    leaf notification-tlv-count {
      type string;
      description
        "TLV Count from Notification Message";
    }
  }

  grouping ncs_rpc_notif_L2VPN-LDP-PW-FEC-130 {
    description
      "L2VPN LDP PW FEC 130";
    container agi {
      description
        "AGI";
      uses ncs_rpc_notif_L2VPN-LDP-PW-AGI;
    }
    container saii {
      description
        "Source Attachment Individual Identifier";
      uses ncs_rpc_notif_L2VPN-LDP-PW-AII;
    }
  }

  grouping ncs_rpc_notif_L2VPN-LDP-PW-AII2 {
    description
      "L2VPN LDP PW AII2";
    leaf gobal-id {
      type uint32;
      description
        "Global ID";
    }
    leaf prefix {
      type uint32;
      description
        "Prefix";
    }
    leaf ac-id {
      type uint32;
      description
        "AC ID";
    }
  }

  grouping ncs_rpc_notif_L2VPN-LDP-PW-AII1 {
    description
      "L2VPN LDP PW AII1";
    leaf local-id {
      type inet:ipv4-address;
      description
        "Local Identifier";
    }
  }

  grouping ncs_rpc_notif_L2VPN-LDP-PW-AII {
    description
      "L2VPN LDP PW AII";
    container aii1 {
      when "../aii-type = 'local-id'" {
        tailf:xpath-root 3;
        description
          "../AIIType = 'LocalID'";
      }
      description
        "aii1";
      uses ncs_rpc_notif_L2VPN-LDP-PW-AII1;
    }
    container aii2 {
      when "../aii-type = 'type2'" {
        tailf:xpath-root 3;
        description
          "../AIIType = 'Type2'";
      }
      description
        "aii2";
      uses ncs_rpc_notif_L2VPN-LDP-PW-AII2;
    }
    leaf aii-type {
      type L2vpn-ldp-pw-aii;
      description
        "AIIType";
    }
  }

  grouping ncs_rpc_notif_L2VPN-LDP-PW-AGI1 {
    description
      "L2VPN LDP PW AGI1";
    leaf rd {
      type uint64;
      description
        "Route Distinguisher";
    }
  }

  grouping ncs_rpc_notif_L2VPN-LDP-PW-AGI {
    description
      "L2VPN LDP PW AGI";
    container agi1 {
      when "../agi-type = 'rd'" {
        tailf:xpath-root 3;
        description
          "../AGIType = 'RD'";
      }
      description
        "agi1";
      uses ncs_rpc_notif_L2VPN-LDP-PW-AGI1;
    }
    leaf agi-type {
      type L2vpn-ldp-pw-agi;
      description
        "AGIType";
    }
  }

  grouping ncs_rpc_notif_L2VPN-LDP-PW-FEC-129 {
    description
      "L2VPN LDP PW FEC 129";
    container agi {
      description
        "AGI";
      uses ncs_rpc_notif_L2VPN-LDP-PW-AGI;
    }
    container saii {
      description
        "Source Attachment Individual Identifier";
      uses ncs_rpc_notif_L2VPN-LDP-PW-AII;
    }
    container taii {
      description
        "Target Attachment Individual Identifier";
      uses ncs_rpc_notif_L2VPN-LDP-PW-AII;
    }
  }

  grouping ncs_rpc_notif_L2VPN-LDP-PW-FEC-128 {
    description
      "L2VPN LDP PW FEC 128";
    leaf pseudowire-id {
      type uint32;
      description
        "Pseudowire ID";
    }
  }

  grouping ncs_rpc_notif_L2VPN-LDP-PW-FEC-INFO {
    description
      "L2VPN LDP PW FEC INFO";
    container fec128 {
      when "../fe-ctype = 'fec128'" {
        tailf:xpath-root 3;
        description
          "../FECType = 'FEC128'";
      }
      description
        "fec128";
      uses ncs_rpc_notif_L2VPN-LDP-PW-FEC-128;
    }
    container fec129 {
      when "../fe-ctype = 'fec129'" {
        tailf:xpath-root 3;
        description
          "../FECType = 'FEC129'";
      }
      description
        "fec129";
      uses ncs_rpc_notif_L2VPN-LDP-PW-FEC-129;
    }
    container fec130 {
      when "../fe-ctype = 'fec130'" {
        tailf:xpath-root 3;
        description
          "../FECType = 'FEC130'";
      }
      description
        "fec130";
      uses ncs_rpc_notif_L2VPN-LDP-PW-FEC-130;
    }
    leaf fe-ctype {
      type L2vpn-ldp-pw-fec;
      description
        "FECType";
    }
  }

  grouping ncs_rpc_notif_L2VPN-LDP-ATOM {
    description
      "L2VPN AToM-DB information";
    container fec-info {
      description
        "Pseudowire FEC information";
      uses ncs_rpc_notif_L2VPN-LDP-PW-FEC-INFO;
    }
    leaf peer-id-xr {
      type inet:ipv4-address;
      description
        "Peer ID";
    }
    leaf mapping-tlv-count {
      type uint32;
      description
        "TLV Count from Label Mapping Message";
    }
    leaf notification-tlv-count {
      type uint32;
      description
        "TLV Count from Notification Message";
    }
  }

  grouping live_ncs_L2VPN-LDP-PW-FEC-130 {
    description
      "L2VPN LDP PW FEC 130";
    container agi {
      description
        "AGI";
      uses live_ncs_L2VPN-LDP-PW-AGI;
    }
    container saii {
      description
        "Source Attachment Individual Identifier";
      uses live_ncs_L2VPN-LDP-PW-AII;
    }
  }

  grouping live_ncs_L2VPN-LDP-PW-AII2 {
    description
      "L2VPN LDP PW AII2";
    leaf gobal-id {
      type uint32;
      description
        "Global ID";
    }
    leaf prefix {
      type uint32;
      description
        "Prefix";
    }
    leaf ac-id {
      type uint32;
      description
        "AC ID";
    }
  }

  grouping live_ncs_L2VPN-LDP-PW-AII1 {
    description
      "L2VPN LDP PW AII1";
    leaf local-id {
      type inet:ipv4-address;
      description
        "Local Identifier";
    }
  }

  grouping live_ncs_L2VPN-LDP-PW-AII {
    description
      "L2VPN LDP PW AII";
    container aii1 {
      // NCS drop when statement
      description
        "aii1";
      uses live_ncs_L2VPN-LDP-PW-AII1;
    }
    container aii2 {
      // NCS drop when statement
      description
        "aii2";
      uses live_ncs_L2VPN-LDP-PW-AII2;
    }
    leaf aii-type {
      type L2vpn-ldp-pw-aii;
      description
        "AIIType";
    }
  }

  grouping live_ncs_L2VPN-LDP-PW-AGI1 {
    description
      "L2VPN LDP PW AGI1";
    leaf rd {
      type uint64;
      description
        "Route Distinguisher";
    }
  }

  grouping live_ncs_L2VPN-LDP-PW-AGI {
    description
      "L2VPN LDP PW AGI";
    container agi1 {
      // NCS drop when statement
      description
        "agi1";
      uses live_ncs_L2VPN-LDP-PW-AGI1;
    }
    leaf agi-type {
      type L2vpn-ldp-pw-agi;
      description
        "AGIType";
    }
  }

  grouping live_ncs_L2VPN-LDP-PW-FEC-129 {
    description
      "L2VPN LDP PW FEC 129";
    container agi {
      description
        "AGI";
      uses live_ncs_L2VPN-LDP-PW-AGI;
    }
    container saii {
      description
        "Source Attachment Individual Identifier";
      uses live_ncs_L2VPN-LDP-PW-AII;
    }
    container taii {
      description
        "Target Attachment Individual Identifier";
      uses live_ncs_L2VPN-LDP-PW-AII;
    }
  }

  grouping live_ncs_L2VPN-LDP-PW-FEC-128 {
    description
      "L2VPN LDP PW FEC 128";
    leaf pseudowire-id {
      type uint32;
      description
        "Pseudowire ID";
    }
  }

  grouping live_ncs_L2VPN-LDP-PW-FEC-INFO {
    description
      "L2VPN LDP PW FEC INFO";
    container fec128 {
      // NCS drop when statement
      description
        "fec128";
      uses live_ncs_L2VPN-LDP-PW-FEC-128;
    }
    container fec129 {
      // NCS drop when statement
      description
        "fec129";
      uses live_ncs_L2VPN-LDP-PW-FEC-129;
    }
    container fec130 {
      // NCS drop when statement
      description
        "fec130";
      uses live_ncs_L2VPN-LDP-PW-FEC-130;
    }
    leaf fe-ctype {
      type L2vpn-ldp-pw-fec;
      description
        "FECType";
    }
  }

  grouping live_ncs_L2VPN-LDP-ATOM {
    description
      "L2VPN AToM-DB information";
    container fec-info {
      description
        "Pseudowire FEC information";
      uses live_ncs_L2VPN-LDP-PW-FEC-INFO;
    }
    leaf peer-id-xr {
      type inet:ipv4-address;
      description
        "Peer ID";
    }
    leaf mapping-tlv-count {
      type uint32;
      description
        "TLV Count from Label Mapping Message";
    }
    leaf notification-tlv-count {
      type uint32;
      description
        "TLV Count from Notification Message";
    }
  }

  grouping L2VPN-LDP-PW-FEC-130 {
    description
      "L2VPN LDP PW FEC 130";
    container agi {
      description
        "AGI";
      uses L2VPN-LDP-PW-AGI;
    }
    container saii {
      description
        "Source Attachment Individual Identifier";
      uses L2VPN-LDP-PW-AII;
    }
  }

  grouping L2VPN-LDP-PW-AII2 {
    description
      "L2VPN LDP PW AII2";
    leaf gobal-id {
      type uint32;
      description
        "Global ID";
    }
    leaf prefix {
      type uint32;
      description
        "Prefix";
    }
    leaf ac-id {
      type uint32;
      description
        "AC ID";
    }
  }

  grouping L2VPN-LDP-PW-AII1 {
    description
      "L2VPN LDP PW AII1";
    leaf local-id {
      type inet:ipv4-address;
      description
        "Local Identifier";
    }
  }

  grouping L2VPN-LDP-PW-AII {
    description
      "L2VPN LDP PW AII";
    container aii1 {
      when "../aii-type = 'local-id'" {
        tailf:xpath-root 3;
        description
          "../AIIType = 'LocalID'";
      }
      description
        "aii1";
      uses L2VPN-LDP-PW-AII1;
    }
    container aii2 {
      when "../aii-type = 'type2'" {
        tailf:xpath-root 3;
        description
          "../AIIType = 'Type2'";
      }
      description
        "aii2";
      uses L2VPN-LDP-PW-AII2;
    }
    leaf aii-type {
      type L2vpn-ldp-pw-aii;
      description
        "AIIType";
    }
  }

  grouping L2VPN-LDP-PW-AGI1 {
    description
      "L2VPN LDP PW AGI1";
    leaf rd {
      type uint64;
      description
        "Route Distinguisher";
    }
  }

  grouping L2VPN-LDP-PW-AGI {
    description
      "L2VPN LDP PW AGI";
    container agi1 {
      when "../agi-type = 'rd'" {
        tailf:xpath-root 3;
        description
          "../AGIType = 'RD'";
      }
      description
        "agi1";
      uses L2VPN-LDP-PW-AGI1;
    }
    leaf agi-type {
      type L2vpn-ldp-pw-agi;
      description
        "AGIType";
    }
  }

  grouping L2VPN-LDP-PW-FEC-129 {
    description
      "L2VPN LDP PW FEC 129";
    container agi {
      description
        "AGI";
      uses L2VPN-LDP-PW-AGI;
    }
    container saii {
      description
        "Source Attachment Individual Identifier";
      uses L2VPN-LDP-PW-AII;
    }
    container taii {
      description
        "Target Attachment Individual Identifier";
      uses L2VPN-LDP-PW-AII;
    }
  }

  grouping L2VPN-LDP-PW-FEC-128 {
    description
      "L2VPN LDP PW FEC 128";
    leaf pseudowire-id {
      type uint32;
      description
        "Pseudowire ID";
    }
  }

  grouping L2VPN-LDP-PW-FEC-INFO {
    description
      "L2VPN LDP PW FEC INFO";
    container fec128 {
      when "../fe-ctype = 'fec128'" {
        tailf:xpath-root 3;
        description
          "../FECType = 'FEC128'";
      }
      description
        "fec128";
      uses L2VPN-LDP-PW-FEC-128;
    }
    container fec129 {
      when "../fe-ctype = 'fec129'" {
        tailf:xpath-root 3;
        description
          "../FECType = 'FEC129'";
      }
      description
        "fec129";
      uses L2VPN-LDP-PW-FEC-129;
    }
    container fec130 {
      when "../fe-ctype = 'fec130'" {
        tailf:xpath-root 3;
        description
          "../FECType = 'FEC130'";
      }
      description
        "fec130";
      uses L2VPN-LDP-PW-FEC-130;
    }
    leaf fe-ctype {
      type L2vpn-ldp-pw-fec;
      description
        "FECType";
    }
  }

  grouping L2VPN-LDP-ATOM {
    description
      "L2VPN AToM-DB information";
    container fec-info {
      description
        "Pseudowire FEC information";
      uses L2VPN-LDP-PW-FEC-INFO;
    }
    leaf peer-id-xr {
      type inet:ipv4-address;
      description
        "Peer ID";
    }
    leaf mapping-tlv-count {
      type uint32;
      description
        "TLV Count from Label Mapping Message";
    }
    leaf notification-tlv-count {
      type uint32;
      description
        "TLV Count from Notification Message";
    }
  }
}
