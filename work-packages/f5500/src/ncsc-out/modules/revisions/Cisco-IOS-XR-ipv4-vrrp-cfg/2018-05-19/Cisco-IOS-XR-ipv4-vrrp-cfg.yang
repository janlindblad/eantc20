module Cisco-IOS-XR-ipv4-vrrp-cfg {
  // Generated by yanger -t ncs
  tailf:mount-id f5500-nc-1.0:f5500-nc-1.0;
  tailf:ncs-device-type "netconf";

  namespace "http://cisco.com/ns/yang/Cisco-IOS-XR-ipv4-vrrp-cfg";
  prefix Cisco-IOS-XR-ipv4-vrrp-cfg;

  import ietf-inet-types {
    prefix inet;
  }
  import Cisco-IOS-XR-types {
    prefix xr;
  }
  import Cisco-IOS-XR-snmp-agent-cfg {
    prefix a1;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ipv4-vrrp package configuration.

     This module contains definitions
     for the following management objects:
       vrrp: VRRP configuration

     This YANG module augments the
       Cisco-IOS-XR-snmp-agent-cfg
     module with configuration data.

     Copyright (c) 2013-2018 by Cisco Systems, Inc.
     All rights reserved.";

  revision 2018-05-19 {
    description
      "Added new path for router configuration enable.";
  }
  revision 2018-05-15 {
    description
      "Modified timer leaf path, removed msec field.";
  }
  revision 2017-11-05 {
    description
      "Corrected boolean values in when statements.";
  }
  revision 2017-05-19 {
    description
      "Marked delay leafs min-delay and reload-delay as mandatory.";
  }
  revision 2017-05-01 {
    description
      "Fixing backward compatibility error in module.";
  }
  revision 2016-12-16 {
    description
      "IOS XR 6.2.1 revision.";
  }
  revision 2015-11-09 {
    description
      "IOS XR 6.0 revision.";
  }

  augment "/ncs:devices/ncs:device/ncs:config" {
    container vrrp {
      tailf:ncs-device-type "netconf";
      tailf:display-when "not(../../ncs:module) or ../../ncs:module[ncs:name='Cisco-IOS-XR-ipv4-vrrp-cfg']";
      description
        "VRRP configuration";
      container logging {
        description
          "VRRP logging options";
        leaf state-change-disable {
          type empty;
          description
            "VRRP state change IOS messages disable";
        }
      }
      container interfaces {
        description
          "Interface configuration table";
        list interface {
          key "interface-name";
          description
            "The interface being configured";
          container ipv6 {
            description
              "IPv6 VRRP configuration";
            container version3 {
              description
                "Version 3 VRRP configuration";
              container virtual-routers {
                description
                  "The VRRP virtual router configuration table";
                list virtual-router {
                  key "vr-id";
                  description
                    "The VRRP virtual router being configured";
                  container global-ipv6-addresses {
                    description
                      "The table of VRRP virtual global IPv6
                       addresses";
                    list global-ipv6-address {
                      key "ip-address";
                      description
                        "A VRRP virtual global IPv6 IP address";
                      leaf ip-address {
                        type inet:ip-address-no-zone;
                        description
                          "VRRP virtual global IPv6 address";
                      }
                    }
                  }
                  container tracks {
                    description
                      "Track an item, reducing priority if it
                       goes down";
                    list track {
                      key "interface-name";
                      description
                        "Object to be tracked";
                      leaf interface-name {
                        type xr:Interface-name;
                        description
                          "Object to be tracked, interface name for
                           interfaces";
                      }
                      leaf priority {
                        type uint32 {
                          range "1..254";
                        }
                        mandatory true;
                        description
                          "Priority decrement";
                      }
                    }
                  }
                  container timer {
                    description
                      "Set advertisement timer";
                    leaf advertisement-time-in-msec {
                      type uint32 {
                        range "100..40950";
                      }
                      units "millisecond";
                      description
                        "Advertisement time in milliseconds";
                    }
                    leaf advertisement-time-in-sec {
                      type uint32 {
                        range "1..40";
                      }
                      units "second";
                      description
                        "Advertisement time in seconds";
                    }
                    leaf forced {
                      type empty;
                      units "millisecond";
                      description
                        "TRUE - Force configured timer values to
                         be used, required when configured in
                         milliseconds";
                    }
                  }
                  container tracked-objects {
                    description
                      "Track an object, reducing priority if it
                       goes down";
                    list tracked-object {
                      key "object-name";
                      description
                        "Object to be tracked";
                      leaf object-name {
                        type xr:Cisco-ios-xr-string;
                        description
                          "Object to be tracked, interface name for
                           interfaces";
                      }
                      leaf priority-decrement {
                        type uint32 {
                          range "1..254";
                        }
                        mandatory true;
                        description
                          "Priority decrement";
                      }
                    }
                  }
                  container link-local-ipv6-address {
                    description
                      "The VRRP IPv6 virtual linklocal address";
                    leaf ip-address {
                      when "../auto-configure = 'false'" {
                        tailf:xpath-root 3;
                        description
                          "../AutoConfigure = 'false'";
                      }
                      type inet:ip-address-no-zone;
                      description
                        "VRRP IPv6 virtual linklocal address";
                    }
                    leaf auto-configure {
                      type boolean;
                      default "false";
                      description
                        "TRUE if the virtual linklocal address is
                         to be autoconfigured FALSE if an IPv6
                         virtual linklocal address is configured";
                    }
                  }
                  leaf bfd {
                    type inet:ip-address-no-zone;
                    description
                      "Enable use of Bidirectional Forwarding
                       Detection for this IP";
                  }
                  leaf priority {
                    type uint32 {
                      range "1..254";
                    }
                    default "100";
                    description
                      "Priority value";
                  }
                  leaf accept-mode-disable {
                    type empty;
                    description
                      "Disable Accept Mode for this virtual
                       IPAddress";
                  }
                  leaf preempt {
                    type uint32 {
                      range "0..3600";
                    }
                    default "0";
                    description
                      "Preempt Master router if higher priority";
                  }
                  leaf session-name {
                    type xr:Cisco-ios-xr-string {
                      length "1..16";
                    }
                    description
                      "VRRP Session Name";
                  }
                  leaf vr-id {
                    type uint32 {
                      range "1..255";
                    }
                    description
                      "VRID Virtual Router Identifier";
                  }
                }
              }
            }
            container slave-virtual-routers {
              description
                "The VRRP slave group configuration table";
              list slave-virtual-router {
                key "slave-virtual-router-id";
                description
                  "The VRRP slave being configured";
                container link-local-ipv6-address {
                  description
                    "The VRRP IPv6 virtual linklocal address";
                  leaf ip-address {
                    when "../auto-configure = 'false'" {
                      tailf:xpath-root 3;
                      description
                        "../AutoConfigure = 'false'";
                    }
                    type inet:ip-address-no-zone;
                    description
                      "VRRP IPv6 virtual linklocal address";
                  }
                  leaf auto-configure {
                    type boolean;
                    default "false";
                    description
                      "TRUE if the virtual linklocal address is
                       to be autoconfigured FALSE if an IPv6
                       virtual linklocal address is configured";
                  }
                }
                container global-ipv6-addresses {
                  description
                    "The table of VRRP virtual global IPv6
                     addresses";
                  list global-ipv6-address {
                    key "ip-address";
                    description
                      "A VRRP virtual global IPv6 IP address";
                    leaf ip-address {
                      type inet:ip-address-no-zone;
                      description
                        "VRRP virtual global IPv6 address";
                    }
                  }
                }
                leaf follow {
                  type string;
                  description
                    "VRRP Session name for this slave to follow";
                }
                leaf accept-mode-disable {
                  type empty;
                  description
                    "Disable Accept Mode for this virtual
                     IPAddress";
                }
                leaf slave-virtual-router-id {
                  type uint32 {
                    range "1..255";
                  }
                  description
                    "Virtual Router ID";
                }
              }
            }
          }
          container delay {
            presence "Indicates a delay node is configured.";
            description
              "Minimum and Reload Delay";
            leaf min-delay {
              type uint32 {
                range "0..10000";
              }
              units "second";
              mandatory true;
              description
                "Minimum delay in seconds";
            }
            leaf reload-delay {
              type uint32 {
                range "0..10000";
              }
              units "second";
              mandatory true;
              description
                "Reload delay in seconds";
            }
          }
          container ipv4 {
            description
              "IPv4 VRRP configuration";
            container version3 {
              description
                "Version 3 VRRP configuration";
              container virtual-routers {
                description
                  "The VRRP virtual router configuration table";
                list virtual-router {
                  key "vr-id";
                  description
                    "The VRRP virtual router being configured";
                  container timer {
                    description
                      "Set advertisement timer";
                    leaf advertisement-time-in-msec {
                      type uint32 {
                        range "100..40950";
                      }
                      units "millisecond";
                      description
                        "Advertisement time in milliseconds";
                    }
                    leaf advertisement-time-in-sec {
                      type uint32 {
                        range "1..40";
                      }
                      units "second";
                      description
                        "Advertisement time in seconds";
                    }
                    leaf forced {
                      type empty;
                      units "millisecond";
                      description
                        "TRUE - Force configured timer values to
                         be used, required when configured in
                         milliseconds";
                    }
                  }
                  container secondary-ipv4-addresses {
                    description
                      "The table of VRRP secondary IPv4 addresses";
                    list secondary-ipv4-address {
                      key "ip-address";
                      description
                        "A VRRP secondary IPv4 address";
                      leaf ip-address {
                        type inet:ipv4-address-no-zone;
                        description
                          "VRRP Secondary IPv4 address";
                      }
                    }
                  }
                  container tracked-objects {
                    description
                      "Track an object, reducing priority if it
                       goes down";
                    list tracked-object {
                      key "object-name";
                      description
                        "Object to be tracked";
                      leaf object-name {
                        type xr:Cisco-ios-xr-string;
                        description
                          "Object to be tracked, interface name for
                           interfaces";
                      }
                      leaf priority-decrement {
                        type uint32 {
                          range "1..254";
                        }
                        mandatory true;
                        description
                          "Priority decrement";
                      }
                    }
                  }
                  container tracks {
                    description
                      "Track an item, reducing priority if it
                       goes down";
                    list track {
                      key "interface-name";
                      description
                        "Object to be tracked";
                      leaf interface-name {
                        type xr:Interface-name;
                        description
                          "Object to be tracked, interface name for
                           interfaces";
                      }
                      leaf priority {
                        type uint32 {
                          range "1..254";
                        }
                        mandatory true;
                        description
                          "Priority decrement";
                      }
                    }
                  }
                  leaf session-name {
                    type xr:Cisco-ios-xr-string {
                      length "1..16";
                    }
                    description
                      "VRRP Session Name";
                  }
                  leaf bfd {
                    type inet:ipv4-address-no-zone;
                    description
                      "Enable use of Bidirectional Forwarding
                       Detection for this IP";
                  }
                  leaf primary-ipv4-address {
                    type inet:ipv4-address-no-zone;
                    description
                      "The Primary VRRP IPv4 address";
                  }
                  leaf preempt {
                    type uint32 {
                      range "0..3600";
                    }
                    default "0";
                    description
                      "Preempt Master router if higher priority";
                  }
                  leaf accept-mode-disable {
                    type empty;
                    description
                      "Disable Accept Mode for this virtual
                       IPAddress";
                  }
                  leaf priority {
                    type uint32 {
                      range "1..254";
                    }
                    default "100";
                    description
                      "Priority value";
                  }
                  leaf vr-id {
                    type uint32 {
                      range "1..255";
                    }
                    description
                      "VRID Virtual Router Identifier";
                  }
                }
              }
            }
            container slave-virtual-routers {
              description
                "The VRRP slave group configuration table";
              list slave-virtual-router {
                key "slave-virtual-router-id";
                description
                  "The VRRP slave being configured";
                container secondary-ipv4-addresses {
                  description
                    "The table of VRRP secondary IPv4 addresses";
                  list secondary-ipv4-address {
                    key "ip-address";
                    description
                      "A VRRP secondary IPv4 address";
                    leaf ip-address {
                      type inet:ipv4-address-no-zone;
                      description
                        "VRRP Secondary IPv4 address";
                    }
                  }
                }
                leaf follow {
                  type string;
                  description
                    "VRRP Session name for this slave to follow";
                }
                leaf accept-mode-disable {
                  type empty;
                  description
                    "Disable Accept Mode for this virtual
                     IPAddress";
                }
                leaf primary-ipv4-address {
                  type inet:ipv4-address-no-zone;
                  description
                    "The Primary VRRP IPv4 address";
                }
                leaf slave-virtual-router-id {
                  type uint32 {
                    range "1..255";
                  }
                  description
                    "Virtual Router ID";
                }
              }
            }
            container version2 {
              description
                "Version 2 VRRP configuration";
              container virtual-routers {
                description
                  "The VRRP virtual router configuration table";
                list virtual-router {
                  key "vr-id";
                  description
                    "The VRRP virtual router being configured";
                  container timer {
                    description
                      "Set advertisement timer";
                    leaf advertisement-time-in-msec {
                      type uint32 {
                        range "100..40950";
                      }
                      units "millisecond";
                      description
                        "Advertisement time in milliseconds";
                    }
                    leaf advertisement-time-in-sec {
                      type uint32 {
                        range "1..255";
                      }
                      units "second";
                      description
                        "Advertisement time in seconds";
                    }
                    leaf forced {
                      type empty;
                      units "millisecond";
                      description
                        "TRUE - Force configured timer values to
                         be used, required when configured in
                         milliseconds";
                    }
                  }
                  container secondary-ipv4-addresses {
                    description
                      "The table of VRRP secondary IPv4 addresses";
                    list secondary-ipv4-address {
                      key "ip-address";
                      description
                        "A VRRP secondary IPv4 address";
                      leaf ip-address {
                        type inet:ipv4-address-no-zone;
                        description
                          "VRRP Secondary IPv4 address";
                      }
                    }
                  }
                  container tracks {
                    description
                      "Track an item, reducing priority if it
                       goes down";
                    list track {
                      key "interface-name";
                      description
                        "Object to be tracked";
                      leaf interface-name {
                        type xr:Interface-name;
                        description
                          "Object to be tracked, interface name for
                           interfaces";
                      }
                      leaf priority {
                        type uint32 {
                          range "1..254";
                        }
                        mandatory true;
                        description
                          "Priority decrement";
                      }
                    }
                  }
                  container tracked-objects {
                    description
                      "Track an object, reducing priority if it
                       goes down";
                    list tracked-object {
                      key "object-name";
                      description
                        "Object to be tracked";
                      leaf object-name {
                        type xr:Cisco-ios-xr-string;
                        description
                          "Object to be tracked, interface name for
                           interfaces";
                      }
                      leaf priority-decrement {
                        type uint32 {
                          range "1..254";
                        }
                        mandatory true;
                        description
                          "Priority decrement";
                      }
                    }
                  }
                  leaf priority {
                    type uint32 {
                      range "1..254";
                    }
                    default "100";
                    description
                      "Priority value";
                  }
                  leaf primary-ipv4-address {
                    type inet:ipv4-address-no-zone;
                    description
                      "The Primary VRRP IPv4 address";
                  }
                  leaf preempt {
                    type uint32 {
                      range "0..3600";
                    }
                    default "0";
                    description
                      "Preempt Master router if higher priority";
                  }
                  leaf text-password {
                    type string;
                    description
                      "Authentication password, 8 chars max";
                  }
                  leaf bfd {
                    type inet:ipv4-address-no-zone;
                    description
                      "Enable use of Bidirectional Forwarding
                       Detection for this IP";
                  }
                  leaf session-name {
                    type xr:Cisco-ios-xr-string {
                      length "1..16";
                    }
                    description
                      "VRRP Session Name";
                  }
                  leaf accept-mode-disable {
                    type empty;
                    description
                      "Disable Accept Mode for this virtual
                       IPAddress";
                  }
                  leaf vr-id {
                    type uint32 {
                      range "1..255";
                    }
                    description
                      "VRID Virtual Router Identifier";
                  }
                }
              }
            }
          }
          container bfd {
            description
              "BFD configuration";
            leaf interval {
              type uint32 {
                range "3..30000";
              }
              units "millisecond";
              description
                "Hello interval for BFD sessions created by
                 vrrp";
            }
            leaf detection-multiplier {
              type uint32 {
                range "2..50";
              }
              description
                "Detection multiplier for BFD sessions created
                 by vrrp";
            }
          }
          leaf mac-refresh {
            type uint32 {
              range "0..10000";
            }
            units "second";
            default "60";
            description
              "VRRP Slave MAC-refresh rate in seconds";
          }
          leaf interface-name {
            type xr:Interface-name;
            description
              "Interface name to configure";
          }
        }
      }
      leaf enable {
        type empty;
        description
          "Enable vrrp process";
      }
    }
  }
  augment "/ncs:devices/ncs:device/ncs:live-status" {
    container vrrp {
      tailf:ncs-device-type "netconf";
      tailf:display-when "not(../../ncs:module) or ../../ncs:module[ncs:name='Cisco-IOS-XR-ipv4-vrrp-cfg'] or (../../ncs:live-status-protocol[not(ncs:capability)]) or (../../ncs:live-status-protocol/ncs:capability/ncs:module[.='Cisco-IOS-XR-ipv4-vrrp-cfg'])";
      description
        "VRRP configuration";
      container logging {
        description
          "VRRP logging options";
        leaf state-change-disable {
          type empty;
          description
            "VRRP state change IOS messages disable";
        }
      }
      container interfaces {
        description
          "Interface configuration table";
        list interface {
          key "interface-name";
          description
            "The interface being configured";
          container ipv6 {
            description
              "IPv6 VRRP configuration";
            container version3 {
              description
                "Version 3 VRRP configuration";
              container virtual-routers {
                description
                  "The VRRP virtual router configuration table";
                list virtual-router {
                  key "vr-id";
                  description
                    "The VRRP virtual router being configured";
                  container global-ipv6-addresses {
                    description
                      "The table of VRRP virtual global IPv6
                       addresses";
                    list global-ipv6-address {
                      key "ip-address";
                      description
                        "A VRRP virtual global IPv6 IP address";
                      leaf ip-address {
                        type inet:ip-address-no-zone;
                        description
                          "VRRP virtual global IPv6 address";
                      }
                    }
                  }
                  container tracks {
                    description
                      "Track an item, reducing priority if it
                       goes down";
                    list track {
                      key "interface-name";
                      description
                        "Object to be tracked";
                      leaf interface-name {
                        type xr:Interface-name;
                        description
                          "Object to be tracked, interface name for
                           interfaces";
                      }
                      leaf priority {
                        type uint32 {
                          range "1..254";
                        }
                        // NCS drop mandatory statement
                        description
                          "Priority decrement";
                      }
                    }
                  }
                  container timer {
                    description
                      "Set advertisement timer";
                    leaf advertisement-time-in-msec {
                      type uint32 {
                        range "100..40950";
                      }
                      units "millisecond";
                      description
                        "Advertisement time in milliseconds";
                    }
                    leaf advertisement-time-in-sec {
                      type uint32 {
                        range "1..40";
                      }
                      units "second";
                      description
                        "Advertisement time in seconds";
                    }
                    leaf forced {
                      type empty;
                      units "millisecond";
                      description
                        "TRUE - Force configured timer values to
                         be used, required when configured in
                         milliseconds";
                    }
                  }
                  container tracked-objects {
                    description
                      "Track an object, reducing priority if it
                       goes down";
                    list tracked-object {
                      key "object-name";
                      description
                        "Object to be tracked";
                      leaf object-name {
                        type xr:Cisco-ios-xr-string;
                        description
                          "Object to be tracked, interface name for
                           interfaces";
                      }
                      leaf priority-decrement {
                        type uint32 {
                          range "1..254";
                        }
                        // NCS drop mandatory statement
                        description
                          "Priority decrement";
                      }
                    }
                  }
                  container link-local-ipv6-address {
                    description
                      "The VRRP IPv6 virtual linklocal address";
                    leaf ip-address {
                      // NCS drop when statement
                      type inet:ip-address-no-zone;
                      description
                        "VRRP IPv6 virtual linklocal address";
                    }
                    leaf auto-configure {
                      type boolean;
                      // NCS drop default statement
                      description
                        "TRUE if the virtual linklocal address is
                         to be autoconfigured FALSE if an IPv6
                         virtual linklocal address is configured";
                    }
                  }
                  leaf bfd {
                    type inet:ip-address-no-zone;
                    description
                      "Enable use of Bidirectional Forwarding
                       Detection for this IP";
                  }
                  leaf priority {
                    type uint32 {
                      range "1..254";
                    }
                    // NCS drop default statement
                    description
                      "Priority value";
                  }
                  leaf accept-mode-disable {
                    type empty;
                    description
                      "Disable Accept Mode for this virtual
                       IPAddress";
                  }
                  leaf preempt {
                    type uint32 {
                      range "0..3600";
                    }
                    // NCS drop default statement
                    description
                      "Preempt Master router if higher priority";
                  }
                  leaf session-name {
                    type xr:Cisco-ios-xr-string {
                      length "1..16";
                    }
                    description
                      "VRRP Session Name";
                  }
                  leaf vr-id {
                    type uint32 {
                      range "1..255";
                    }
                    description
                      "VRID Virtual Router Identifier";
                  }
                }
              }
            }
            container slave-virtual-routers {
              description
                "The VRRP slave group configuration table";
              list slave-virtual-router {
                key "slave-virtual-router-id";
                description
                  "The VRRP slave being configured";
                container link-local-ipv6-address {
                  description
                    "The VRRP IPv6 virtual linklocal address";
                  leaf ip-address {
                    // NCS drop when statement
                    type inet:ip-address-no-zone;
                    description
                      "VRRP IPv6 virtual linklocal address";
                  }
                  leaf auto-configure {
                    type boolean;
                    // NCS drop default statement
                    description
                      "TRUE if the virtual linklocal address is
                       to be autoconfigured FALSE if an IPv6
                       virtual linklocal address is configured";
                  }
                }
                container global-ipv6-addresses {
                  description
                    "The table of VRRP virtual global IPv6
                     addresses";
                  list global-ipv6-address {
                    key "ip-address";
                    description
                      "A VRRP virtual global IPv6 IP address";
                    leaf ip-address {
                      type inet:ip-address-no-zone;
                      description
                        "VRRP virtual global IPv6 address";
                    }
                  }
                }
                leaf follow {
                  type string;
                  description
                    "VRRP Session name for this slave to follow";
                }
                leaf accept-mode-disable {
                  type empty;
                  description
                    "Disable Accept Mode for this virtual
                     IPAddress";
                }
                leaf slave-virtual-router-id {
                  type uint32 {
                    range "1..255";
                  }
                  description
                    "Virtual Router ID";
                }
              }
            }
          }
          container delay {
            presence "Indicates a delay node is configured.";
            description
              "Minimum and Reload Delay";
            leaf min-delay {
              type uint32 {
                range "0..10000";
              }
              units "second";
              // NCS drop mandatory statement
              description
                "Minimum delay in seconds";
            }
            leaf reload-delay {
              type uint32 {
                range "0..10000";
              }
              units "second";
              // NCS drop mandatory statement
              description
                "Reload delay in seconds";
            }
          }
          container ipv4 {
            description
              "IPv4 VRRP configuration";
            container version3 {
              description
                "Version 3 VRRP configuration";
              container virtual-routers {
                description
                  "The VRRP virtual router configuration table";
                list virtual-router {
                  key "vr-id";
                  description
                    "The VRRP virtual router being configured";
                  container timer {
                    description
                      "Set advertisement timer";
                    leaf advertisement-time-in-msec {
                      type uint32 {
                        range "100..40950";
                      }
                      units "millisecond";
                      description
                        "Advertisement time in milliseconds";
                    }
                    leaf advertisement-time-in-sec {
                      type uint32 {
                        range "1..40";
                      }
                      units "second";
                      description
                        "Advertisement time in seconds";
                    }
                    leaf forced {
                      type empty;
                      units "millisecond";
                      description
                        "TRUE - Force configured timer values to
                         be used, required when configured in
                         milliseconds";
                    }
                  }
                  container secondary-ipv4-addresses {
                    description
                      "The table of VRRP secondary IPv4 addresses";
                    list secondary-ipv4-address {
                      key "ip-address";
                      description
                        "A VRRP secondary IPv4 address";
                      leaf ip-address {
                        type inet:ipv4-address-no-zone;
                        description
                          "VRRP Secondary IPv4 address";
                      }
                    }
                  }
                  container tracked-objects {
                    description
                      "Track an object, reducing priority if it
                       goes down";
                    list tracked-object {
                      key "object-name";
                      description
                        "Object to be tracked";
                      leaf object-name {
                        type xr:Cisco-ios-xr-string;
                        description
                          "Object to be tracked, interface name for
                           interfaces";
                      }
                      leaf priority-decrement {
                        type uint32 {
                          range "1..254";
                        }
                        // NCS drop mandatory statement
                        description
                          "Priority decrement";
                      }
                    }
                  }
                  container tracks {
                    description
                      "Track an item, reducing priority if it
                       goes down";
                    list track {
                      key "interface-name";
                      description
                        "Object to be tracked";
                      leaf interface-name {
                        type xr:Interface-name;
                        description
                          "Object to be tracked, interface name for
                           interfaces";
                      }
                      leaf priority {
                        type uint32 {
                          range "1..254";
                        }
                        // NCS drop mandatory statement
                        description
                          "Priority decrement";
                      }
                    }
                  }
                  leaf session-name {
                    type xr:Cisco-ios-xr-string {
                      length "1..16";
                    }
                    description
                      "VRRP Session Name";
                  }
                  leaf bfd {
                    type inet:ipv4-address-no-zone;
                    description
                      "Enable use of Bidirectional Forwarding
                       Detection for this IP";
                  }
                  leaf primary-ipv4-address {
                    type inet:ipv4-address-no-zone;
                    description
                      "The Primary VRRP IPv4 address";
                  }
                  leaf preempt {
                    type uint32 {
                      range "0..3600";
                    }
                    // NCS drop default statement
                    description
                      "Preempt Master router if higher priority";
                  }
                  leaf accept-mode-disable {
                    type empty;
                    description
                      "Disable Accept Mode for this virtual
                       IPAddress";
                  }
                  leaf priority {
                    type uint32 {
                      range "1..254";
                    }
                    // NCS drop default statement
                    description
                      "Priority value";
                  }
                  leaf vr-id {
                    type uint32 {
                      range "1..255";
                    }
                    description
                      "VRID Virtual Router Identifier";
                  }
                }
              }
            }
            container slave-virtual-routers {
              description
                "The VRRP slave group configuration table";
              list slave-virtual-router {
                key "slave-virtual-router-id";
                description
                  "The VRRP slave being configured";
                container secondary-ipv4-addresses {
                  description
                    "The table of VRRP secondary IPv4 addresses";
                  list secondary-ipv4-address {
                    key "ip-address";
                    description
                      "A VRRP secondary IPv4 address";
                    leaf ip-address {
                      type inet:ipv4-address-no-zone;
                      description
                        "VRRP Secondary IPv4 address";
                    }
                  }
                }
                leaf follow {
                  type string;
                  description
                    "VRRP Session name for this slave to follow";
                }
                leaf accept-mode-disable {
                  type empty;
                  description
                    "Disable Accept Mode for this virtual
                     IPAddress";
                }
                leaf primary-ipv4-address {
                  type inet:ipv4-address-no-zone;
                  description
                    "The Primary VRRP IPv4 address";
                }
                leaf slave-virtual-router-id {
                  type uint32 {
                    range "1..255";
                  }
                  description
                    "Virtual Router ID";
                }
              }
            }
            container version2 {
              description
                "Version 2 VRRP configuration";
              container virtual-routers {
                description
                  "The VRRP virtual router configuration table";
                list virtual-router {
                  key "vr-id";
                  description
                    "The VRRP virtual router being configured";
                  container timer {
                    description
                      "Set advertisement timer";
                    leaf advertisement-time-in-msec {
                      type uint32 {
                        range "100..40950";
                      }
                      units "millisecond";
                      description
                        "Advertisement time in milliseconds";
                    }
                    leaf advertisement-time-in-sec {
                      type uint32 {
                        range "1..255";
                      }
                      units "second";
                      description
                        "Advertisement time in seconds";
                    }
                    leaf forced {
                      type empty;
                      units "millisecond";
                      description
                        "TRUE - Force configured timer values to
                         be used, required when configured in
                         milliseconds";
                    }
                  }
                  container secondary-ipv4-addresses {
                    description
                      "The table of VRRP secondary IPv4 addresses";
                    list secondary-ipv4-address {
                      key "ip-address";
                      description
                        "A VRRP secondary IPv4 address";
                      leaf ip-address {
                        type inet:ipv4-address-no-zone;
                        description
                          "VRRP Secondary IPv4 address";
                      }
                    }
                  }
                  container tracks {
                    description
                      "Track an item, reducing priority if it
                       goes down";
                    list track {
                      key "interface-name";
                      description
                        "Object to be tracked";
                      leaf interface-name {
                        type xr:Interface-name;
                        description
                          "Object to be tracked, interface name for
                           interfaces";
                      }
                      leaf priority {
                        type uint32 {
                          range "1..254";
                        }
                        // NCS drop mandatory statement
                        description
                          "Priority decrement";
                      }
                    }
                  }
                  container tracked-objects {
                    description
                      "Track an object, reducing priority if it
                       goes down";
                    list tracked-object {
                      key "object-name";
                      description
                        "Object to be tracked";
                      leaf object-name {
                        type xr:Cisco-ios-xr-string;
                        description
                          "Object to be tracked, interface name for
                           interfaces";
                      }
                      leaf priority-decrement {
                        type uint32 {
                          range "1..254";
                        }
                        // NCS drop mandatory statement
                        description
                          "Priority decrement";
                      }
                    }
                  }
                  leaf priority {
                    type uint32 {
                      range "1..254";
                    }
                    // NCS drop default statement
                    description
                      "Priority value";
                  }
                  leaf primary-ipv4-address {
                    type inet:ipv4-address-no-zone;
                    description
                      "The Primary VRRP IPv4 address";
                  }
                  leaf preempt {
                    type uint32 {
                      range "0..3600";
                    }
                    // NCS drop default statement
                    description
                      "Preempt Master router if higher priority";
                  }
                  leaf text-password {
                    type string;
                    description
                      "Authentication password, 8 chars max";
                  }
                  leaf bfd {
                    type inet:ipv4-address-no-zone;
                    description
                      "Enable use of Bidirectional Forwarding
                       Detection for this IP";
                  }
                  leaf session-name {
                    type xr:Cisco-ios-xr-string {
                      length "1..16";
                    }
                    description
                      "VRRP Session Name";
                  }
                  leaf accept-mode-disable {
                    type empty;
                    description
                      "Disable Accept Mode for this virtual
                       IPAddress";
                  }
                  leaf vr-id {
                    type uint32 {
                      range "1..255";
                    }
                    description
                      "VRID Virtual Router Identifier";
                  }
                }
              }
            }
          }
          container bfd {
            description
              "BFD configuration";
            leaf interval {
              type uint32 {
                range "3..30000";
              }
              units "millisecond";
              description
                "Hello interval for BFD sessions created by
                 vrrp";
            }
            leaf detection-multiplier {
              type uint32 {
                range "2..50";
              }
              description
                "Detection multiplier for BFD sessions created
                 by vrrp";
            }
          }
          leaf mac-refresh {
            type uint32 {
              range "0..10000";
            }
            units "second";
            // NCS drop default statement
            description
              "VRRP Slave MAC-refresh rate in seconds";
          }
          leaf interface-name {
            type xr:Interface-name;
            description
              "Interface name to configure";
          }
        }
      }
      leaf enable {
        type empty;
        description
          "Enable vrrp process";
      }
    }
  }
  augment "/ncs:devices/ncs:template/ncs:ned-id/ncs:config" {
    container vrrp {
      description
        "VRRP configuration";
      container logging {
        description
          "VRRP logging options";
        leaf state-change-disable {
          type empty;
          description
            "VRRP state change IOS messages disable";
        }
      }
      container interfaces {
        description
          "Interface configuration table";
        list interface {
          // NCS patched for predictable order
          ordered-by user;
          key "interface-name";
          description
            "The interface being configured";
          container ipv6 {
            description
              "IPv6 VRRP configuration";
            container version3 {
              description
                "Version 3 VRRP configuration";
              container virtual-routers {
                description
                  "The VRRP virtual router configuration table";
                list virtual-router {
                  // NCS patched for predictable order
                  ordered-by user;
                  key "vr-id";
                  description
                    "The VRRP virtual router being configured";
                  container global-ipv6-addresses {
                    description
                      "The table of VRRP virtual global IPv6
                       addresses";
                    list global-ipv6-address {
                      // NCS patched for predictable order
                      ordered-by user;
                      key "ip-address";
                      description
                        "A VRRP virtual global IPv6 IP address";
                      leaf ip-address {
                        type string;
                        description
                          "VRRP virtual global IPv6 address";
                      }
                    }
                  }
                  container tracks {
                    description
                      "Track an item, reducing priority if it
                       goes down";
                    list track {
                      // NCS patched for predictable order
                      ordered-by user;
                      key "interface-name";
                      description
                        "Object to be tracked";
                      leaf interface-name {
                        type string;
                        description
                          "Object to be tracked, interface name for
                           interfaces";
                      }
                      leaf priority {
                        type string;
                        // NCS drop mandatory statement
                        description
                          "Priority decrement";
                      }
                    }
                  }
                  container timer {
                    description
                      "Set advertisement timer";
                    leaf advertisement-time-in-msec {
                      type string;
                      units "millisecond";
                      description
                        "Advertisement time in milliseconds";
                    }
                    leaf advertisement-time-in-sec {
                      type string;
                      units "second";
                      description
                        "Advertisement time in seconds";
                    }
                    leaf forced {
                      type empty;
                      units "millisecond";
                      description
                        "TRUE - Force configured timer values to
                         be used, required when configured in
                         milliseconds";
                    }
                  }
                  container tracked-objects {
                    description
                      "Track an object, reducing priority if it
                       goes down";
                    list tracked-object {
                      // NCS patched for predictable order
                      ordered-by user;
                      key "object-name";
                      description
                        "Object to be tracked";
                      leaf object-name {
                        type string;
                        description
                          "Object to be tracked, interface name for
                           interfaces";
                      }
                      leaf priority-decrement {
                        type string;
                        // NCS drop mandatory statement
                        description
                          "Priority decrement";
                      }
                    }
                  }
                  container link-local-ipv6-address {
                    description
                      "The VRRP IPv6 virtual linklocal address";
                    leaf ip-address {
                      // NCS drop when statement
                      type string;
                      description
                        "VRRP IPv6 virtual linklocal address";
                    }
                    leaf auto-configure {
                      type string;
                      // NCS drop default statement
                      description
                        "TRUE if the virtual linklocal address is
                         to be autoconfigured FALSE if an IPv6
                         virtual linklocal address is configured";
                    }
                  }
                  leaf bfd {
                    type string;
                    description
                      "Enable use of Bidirectional Forwarding
                       Detection for this IP";
                  }
                  leaf priority {
                    type string;
                    // NCS drop default statement
                    description
                      "Priority value";
                  }
                  leaf accept-mode-disable {
                    type empty;
                    description
                      "Disable Accept Mode for this virtual
                       IPAddress";
                  }
                  leaf preempt {
                    type string;
                    // NCS drop default statement
                    description
                      "Preempt Master router if higher priority";
                  }
                  leaf session-name {
                    type string;
                    description
                      "VRRP Session Name";
                  }
                  leaf vr-id {
                    type string;
                    description
                      "VRID Virtual Router Identifier";
                  }
                }
              }
            }
            container slave-virtual-routers {
              description
                "The VRRP slave group configuration table";
              list slave-virtual-router {
                // NCS patched for predictable order
                ordered-by user;
                key "slave-virtual-router-id";
                description
                  "The VRRP slave being configured";
                container link-local-ipv6-address {
                  description
                    "The VRRP IPv6 virtual linklocal address";
                  leaf ip-address {
                    // NCS drop when statement
                    type string;
                    description
                      "VRRP IPv6 virtual linklocal address";
                  }
                  leaf auto-configure {
                    type string;
                    // NCS drop default statement
                    description
                      "TRUE if the virtual linklocal address is
                       to be autoconfigured FALSE if an IPv6
                       virtual linklocal address is configured";
                  }
                }
                container global-ipv6-addresses {
                  description
                    "The table of VRRP virtual global IPv6
                     addresses";
                  list global-ipv6-address {
                    // NCS patched for predictable order
                    ordered-by user;
                    key "ip-address";
                    description
                      "A VRRP virtual global IPv6 IP address";
                    leaf ip-address {
                      type string;
                      description
                        "VRRP virtual global IPv6 address";
                    }
                  }
                }
                leaf follow {
                  type string;
                  description
                    "VRRP Session name for this slave to follow";
                }
                leaf accept-mode-disable {
                  type empty;
                  description
                    "Disable Accept Mode for this virtual
                     IPAddress";
                }
                leaf slave-virtual-router-id {
                  type string;
                  description
                    "Virtual Router ID";
                }
              }
            }
          }
          container delay {
            presence "Indicates a delay node is configured.";
            description
              "Minimum and Reload Delay";
            leaf min-delay {
              type string;
              units "second";
              // NCS drop mandatory statement
              description
                "Minimum delay in seconds";
            }
            leaf reload-delay {
              type string;
              units "second";
              // NCS drop mandatory statement
              description
                "Reload delay in seconds";
            }
          }
          container ipv4 {
            description
              "IPv4 VRRP configuration";
            container version3 {
              description
                "Version 3 VRRP configuration";
              container virtual-routers {
                description
                  "The VRRP virtual router configuration table";
                list virtual-router {
                  // NCS patched for predictable order
                  ordered-by user;
                  key "vr-id";
                  description
                    "The VRRP virtual router being configured";
                  container timer {
                    description
                      "Set advertisement timer";
                    leaf advertisement-time-in-msec {
                      type string;
                      units "millisecond";
                      description
                        "Advertisement time in milliseconds";
                    }
                    leaf advertisement-time-in-sec {
                      type string;
                      units "second";
                      description
                        "Advertisement time in seconds";
                    }
                    leaf forced {
                      type empty;
                      units "millisecond";
                      description
                        "TRUE - Force configured timer values to
                         be used, required when configured in
                         milliseconds";
                    }
                  }
                  container secondary-ipv4-addresses {
                    description
                      "The table of VRRP secondary IPv4 addresses";
                    list secondary-ipv4-address {
                      // NCS patched for predictable order
                      ordered-by user;
                      key "ip-address";
                      description
                        "A VRRP secondary IPv4 address";
                      leaf ip-address {
                        type string;
                        description
                          "VRRP Secondary IPv4 address";
                      }
                    }
                  }
                  container tracked-objects {
                    description
                      "Track an object, reducing priority if it
                       goes down";
                    list tracked-object {
                      // NCS patched for predictable order
                      ordered-by user;
                      key "object-name";
                      description
                        "Object to be tracked";
                      leaf object-name {
                        type string;
                        description
                          "Object to be tracked, interface name for
                           interfaces";
                      }
                      leaf priority-decrement {
                        type string;
                        // NCS drop mandatory statement
                        description
                          "Priority decrement";
                      }
                    }
                  }
                  container tracks {
                    description
                      "Track an item, reducing priority if it
                       goes down";
                    list track {
                      // NCS patched for predictable order
                      ordered-by user;
                      key "interface-name";
                      description
                        "Object to be tracked";
                      leaf interface-name {
                        type string;
                        description
                          "Object to be tracked, interface name for
                           interfaces";
                      }
                      leaf priority {
                        type string;
                        // NCS drop mandatory statement
                        description
                          "Priority decrement";
                      }
                    }
                  }
                  leaf session-name {
                    type string;
                    description
                      "VRRP Session Name";
                  }
                  leaf bfd {
                    type string;
                    description
                      "Enable use of Bidirectional Forwarding
                       Detection for this IP";
                  }
                  leaf primary-ipv4-address {
                    type string;
                    description
                      "The Primary VRRP IPv4 address";
                  }
                  leaf preempt {
                    type string;
                    // NCS drop default statement
                    description
                      "Preempt Master router if higher priority";
                  }
                  leaf accept-mode-disable {
                    type empty;
                    description
                      "Disable Accept Mode for this virtual
                       IPAddress";
                  }
                  leaf priority {
                    type string;
                    // NCS drop default statement
                    description
                      "Priority value";
                  }
                  leaf vr-id {
                    type string;
                    description
                      "VRID Virtual Router Identifier";
                  }
                }
              }
            }
            container slave-virtual-routers {
              description
                "The VRRP slave group configuration table";
              list slave-virtual-router {
                // NCS patched for predictable order
                ordered-by user;
                key "slave-virtual-router-id";
                description
                  "The VRRP slave being configured";
                container secondary-ipv4-addresses {
                  description
                    "The table of VRRP secondary IPv4 addresses";
                  list secondary-ipv4-address {
                    // NCS patched for predictable order
                    ordered-by user;
                    key "ip-address";
                    description
                      "A VRRP secondary IPv4 address";
                    leaf ip-address {
                      type string;
                      description
                        "VRRP Secondary IPv4 address";
                    }
                  }
                }
                leaf follow {
                  type string;
                  description
                    "VRRP Session name for this slave to follow";
                }
                leaf accept-mode-disable {
                  type empty;
                  description
                    "Disable Accept Mode for this virtual
                     IPAddress";
                }
                leaf primary-ipv4-address {
                  type string;
                  description
                    "The Primary VRRP IPv4 address";
                }
                leaf slave-virtual-router-id {
                  type string;
                  description
                    "Virtual Router ID";
                }
              }
            }
            container version2 {
              description
                "Version 2 VRRP configuration";
              container virtual-routers {
                description
                  "The VRRP virtual router configuration table";
                list virtual-router {
                  // NCS patched for predictable order
                  ordered-by user;
                  key "vr-id";
                  description
                    "The VRRP virtual router being configured";
                  container timer {
                    description
                      "Set advertisement timer";
                    leaf advertisement-time-in-msec {
                      type string;
                      units "millisecond";
                      description
                        "Advertisement time in milliseconds";
                    }
                    leaf advertisement-time-in-sec {
                      type string;
                      units "second";
                      description
                        "Advertisement time in seconds";
                    }
                    leaf forced {
                      type empty;
                      units "millisecond";
                      description
                        "TRUE - Force configured timer values to
                         be used, required when configured in
                         milliseconds";
                    }
                  }
                  container secondary-ipv4-addresses {
                    description
                      "The table of VRRP secondary IPv4 addresses";
                    list secondary-ipv4-address {
                      // NCS patched for predictable order
                      ordered-by user;
                      key "ip-address";
                      description
                        "A VRRP secondary IPv4 address";
                      leaf ip-address {
                        type string;
                        description
                          "VRRP Secondary IPv4 address";
                      }
                    }
                  }
                  container tracks {
                    description
                      "Track an item, reducing priority if it
                       goes down";
                    list track {
                      // NCS patched for predictable order
                      ordered-by user;
                      key "interface-name";
                      description
                        "Object to be tracked";
                      leaf interface-name {
                        type string;
                        description
                          "Object to be tracked, interface name for
                           interfaces";
                      }
                      leaf priority {
                        type string;
                        // NCS drop mandatory statement
                        description
                          "Priority decrement";
                      }
                    }
                  }
                  container tracked-objects {
                    description
                      "Track an object, reducing priority if it
                       goes down";
                    list tracked-object {
                      // NCS patched for predictable order
                      ordered-by user;
                      key "object-name";
                      description
                        "Object to be tracked";
                      leaf object-name {
                        type string;
                        description
                          "Object to be tracked, interface name for
                           interfaces";
                      }
                      leaf priority-decrement {
                        type string;
                        // NCS drop mandatory statement
                        description
                          "Priority decrement";
                      }
                    }
                  }
                  leaf priority {
                    type string;
                    // NCS drop default statement
                    description
                      "Priority value";
                  }
                  leaf primary-ipv4-address {
                    type string;
                    description
                      "The Primary VRRP IPv4 address";
                  }
                  leaf preempt {
                    type string;
                    // NCS drop default statement
                    description
                      "Preempt Master router if higher priority";
                  }
                  leaf text-password {
                    type string;
                    description
                      "Authentication password, 8 chars max";
                  }
                  leaf bfd {
                    type string;
                    description
                      "Enable use of Bidirectional Forwarding
                       Detection for this IP";
                  }
                  leaf session-name {
                    type string;
                    description
                      "VRRP Session Name";
                  }
                  leaf accept-mode-disable {
                    type empty;
                    description
                      "Disable Accept Mode for this virtual
                       IPAddress";
                  }
                  leaf vr-id {
                    type string;
                    description
                      "VRID Virtual Router Identifier";
                  }
                }
              }
            }
          }
          container bfd {
            description
              "BFD configuration";
            leaf interval {
              type string;
              units "millisecond";
              description
                "Hello interval for BFD sessions created by
                 vrrp";
            }
            leaf detection-multiplier {
              type string;
              description
                "Detection multiplier for BFD sessions created
                 by vrrp";
            }
          }
          leaf mac-refresh {
            type string;
            units "second";
            // NCS drop default statement
            description
              "VRRP Slave MAC-refresh rate in seconds";
          }
          leaf interface-name {
            type string;
            description
              "Interface name to configure";
          }
        }
      }
      leaf enable {
        type empty;
        description
          "Enable vrrp process";
      }
    }
  }
  augment "/ncs:devices/ncs:template/ncs:ned-id/ncs:config/a1:snmp/a1:notification" {
    container vrrp {
      description
        "VRRP-MIB notification configuration";
      leaf enable {
        type empty;
        description
          "Enable VRRP-MIB notifications";
      }
    }
    description
      "This augment extends the configuration data of
       'Cisco-IOS-XR-snmp-agent-cfg'";
  }
  augment "/ncs:devices/ncs:device/ncs:live-status/a1:snmp/a1:notification" {
    container vrrp {
      tailf:ncs-device-type "netconf";
      tailf:display-when "not(../../../../ncs:module) or ../../../../ncs:module[ncs:name='Cisco-IOS-XR-ipv4-vrrp-cfg'] or (../../../../ncs:live-status-protocol[not(ncs:capability)]) or (../../../../ncs:live-status-protocol/ncs:capability/ncs:module[.='Cisco-IOS-XR-ipv4-vrrp-cfg'])";
      description
        "VRRP-MIB notification configuration";
      leaf enable {
        type empty;
        description
          "Enable VRRP-MIB notifications";
      }
    }
    description
      "This augment extends the configuration data of
       'Cisco-IOS-XR-snmp-agent-cfg'";
  }
  augment "/ncs:devices/ncs:device/ncs:config/a1:snmp/a1:notification" {
    container vrrp {
      tailf:ncs-device-type "netconf";
      tailf:display-when "not(../../../../ncs:module) or ../../../../ncs:module[ncs:name='Cisco-IOS-XR-ipv4-vrrp-cfg']";
      description
        "VRRP-MIB notification configuration";
      leaf enable {
        type empty;
        description
          "Enable VRRP-MIB notifications";
      }
    }
    description
      "This augment extends the configuration data of
       'Cisco-IOS-XR-snmp-agent-cfg'";
  }
}
