module Cisco-IOS-XR-ipv4-ma-cfg {
  // Generated by yanger -t ncs
  tailf:mount-id f5500-nc-1.0:f5500-nc-1.0;
  tailf:ncs-device-type "netconf";

  namespace "http://cisco.com/ns/yang/Cisco-IOS-XR-ipv4-ma-cfg";
  prefix Cisco-IOS-XR-ipv4-ma-cfg;

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ipv4-ma package configuration.

     This module contains definitions
     for the following management objects:
       ipv4-network-global: IPv4 network global configuration data
       subscriber-pta: subscriber pta

     Copyright (c) 2013-2018 by Cisco Systems, Inc.
     All rights reserved.";

  revision 2015-07-30 {
    description
      "Descriptions updated.";
  }
  revision 2015-01-07 {
    description
      "IOS XR 5.3.1 revision.";
  }

  typedef Ipv4-qppb {
    type enumeration {
      enum "none" {
        value 0;
        description
          "No QPPB configuration";
      }
      enum "ip-prec" {
        value 1;
        description
          "Enable ip-precedence based QPPB";
      }
      enum "qos-grp" {
        value 2;
        description
          "Enable qos-group based QPPB";
      }
      enum "both" {
        value 3;
        description
          "Enable both ip-precedence and qos-group based
           QPPB";
      }
    }
    description
      "Ipv4 qppb";
  }

  augment "/ncs:devices/ncs:device/ncs:config" {
    container ipv4-network-global {
      tailf:ncs-device-type "netconf";
      tailf:display-when "not(../../ncs:module) or ../../ncs:module[ncs:name='Cisco-IOS-XR-ipv4-ma-cfg']";
      description
        "IPv4 network global configuration data";
      container unnumbered {
        description
          "Enable IPv4 processing without an explicit
           address";
        container mpls {
          description
            "Configure MPLS routing protocol parameters";
          container te {
            description
              "IPv4 commands for MPLS Traffic Engineering";
            leaf interface {
              type string;
              description
                "Enable IP processing without an explicit
                 address on MPLS Traffic-Eng";
            }
          }
        }
      }
      container qppb {
        description
          "QPPB";
        leaf source {
          type Ipv4-qppb;
          description
            "QPPB configuration on source";
        }
        leaf destination {
          type Ipv4-qppb;
          description
            "QPPB configuration on destination";
        }
      }
      leaf source-route {
        type boolean;
        default "true";
        description
          "The flag for enabling whether to process packets
           with source routing header options";
      }
      leaf reassemble-max-packets {
        type uint32 {
          range "1..50";
        }
        units "percentage";
        description
          "Percentage of total packets available in the
           system";
      }
      leaf reassemble-time-out {
        type uint32 {
          range "1..120";
        }
        units "second";
        description
          "Number of seconds a reassembly queue will hold
           before timeout";
      }
    }
    container subscriber-pta {
      tailf:ncs-device-type "netconf";
      tailf:display-when "not(../../ncs:module) or ../../ncs:module[ncs:name='Cisco-IOS-XR-ipv4-ma-cfg']";
      description
        "subscriber pta";
      leaf tcp-mss-adjust {
        type uint32 {
          range "1280..1536";
        }
        units "byte";
        description
          "TCP MSS Adjust (bytes)";
      }
    }
  }
  augment "/ncs:devices/ncs:device/ncs:live-status" {
    container ipv4-network-global {
      tailf:ncs-device-type "netconf";
      tailf:display-when "not(../../ncs:module) or ../../ncs:module[ncs:name='Cisco-IOS-XR-ipv4-ma-cfg'] or (../../ncs:live-status-protocol[not(ncs:capability)]) or (../../ncs:live-status-protocol/ncs:capability/ncs:module[.='Cisco-IOS-XR-ipv4-ma-cfg'])";
      description
        "IPv4 network global configuration data";
      container unnumbered {
        description
          "Enable IPv4 processing without an explicit
           address";
        container mpls {
          description
            "Configure MPLS routing protocol parameters";
          container te {
            description
              "IPv4 commands for MPLS Traffic Engineering";
            leaf interface {
              type string;
              description
                "Enable IP processing without an explicit
                 address on MPLS Traffic-Eng";
            }
          }
        }
      }
      container qppb {
        description
          "QPPB";
        leaf source {
          type Ipv4-qppb;
          description
            "QPPB configuration on source";
        }
        leaf destination {
          type Ipv4-qppb;
          description
            "QPPB configuration on destination";
        }
      }
      leaf source-route {
        type boolean;
        // NCS drop default statement
        description
          "The flag for enabling whether to process packets
           with source routing header options";
      }
      leaf reassemble-max-packets {
        type uint32 {
          range "1..50";
        }
        units "percentage";
        description
          "Percentage of total packets available in the
           system";
      }
      leaf reassemble-time-out {
        type uint32 {
          range "1..120";
        }
        units "second";
        description
          "Number of seconds a reassembly queue will hold
           before timeout";
      }
    }
    container subscriber-pta {
      tailf:ncs-device-type "netconf";
      tailf:display-when "not(../../ncs:module) or ../../ncs:module[ncs:name='Cisco-IOS-XR-ipv4-ma-cfg'] or (../../ncs:live-status-protocol[not(ncs:capability)]) or (../../ncs:live-status-protocol/ncs:capability/ncs:module[.='Cisco-IOS-XR-ipv4-ma-cfg'])";
      description
        "subscriber pta";
      leaf tcp-mss-adjust {
        type uint32 {
          range "1280..1536";
        }
        units "byte";
        description
          "TCP MSS Adjust (bytes)";
      }
    }
  }
  augment "/ncs:devices/ncs:template/ncs:ned-id/ncs:config" {
    container ipv4-network-global {
      description
        "IPv4 network global configuration data";
      container unnumbered {
        description
          "Enable IPv4 processing without an explicit
           address";
        container mpls {
          description
            "Configure MPLS routing protocol parameters";
          container te {
            description
              "IPv4 commands for MPLS Traffic Engineering";
            leaf interface {
              type string;
              description
                "Enable IP processing without an explicit
                 address on MPLS Traffic-Eng";
            }
          }
        }
      }
      container qppb {
        description
          "QPPB";
        leaf source {
          type string;
          description
            "QPPB configuration on source";
        }
        leaf destination {
          type string;
          description
            "QPPB configuration on destination";
        }
      }
      leaf source-route {
        type string;
        // NCS drop default statement
        description
          "The flag for enabling whether to process packets
           with source routing header options";
      }
      leaf reassemble-max-packets {
        type string;
        units "percentage";
        description
          "Percentage of total packets available in the
           system";
      }
      leaf reassemble-time-out {
        type string;
        units "second";
        description
          "Number of seconds a reassembly queue will hold
           before timeout";
      }
    }
    container subscriber-pta {
      description
        "subscriber pta";
      leaf tcp-mss-adjust {
        type string;
        units "byte";
        description
          "TCP MSS Adjust (bytes)";
      }
    }
  }
}
