module Cisco-IOS-XR-snmp-ifmib-oper {
  // Generated by yanger -t ncs
  tailf:mount-id f5500-nc-1.0:f5500-nc-1.0;
  tailf:ncs-device-type "netconf";

  namespace "http://cisco.com/ns/yang/Cisco-IOS-XR-snmp-ifmib-oper";
  prefix Cisco-IOS-XR-snmp-ifmib-oper;

  import Cisco-IOS-XR-types {
    prefix xr;
  }
  import Cisco-IOS-XR-snmp-agent-oper {
    prefix a1;
  }
  include Cisco-IOS-XR-snmp-ifmib-oper-sub1 {
    revision-date 2015-01-07;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR snmp-ifmib package operational data.

     This YANG module augments the
       Cisco-IOS-XR-snmp-agent-oper
     module with state data.

     Copyright (c) 2013-2018 by Cisco Systems, Inc.
     All rights reserved.";

  revision 2015-01-07 {
    description
      "IOS XR 5.3.1 revision.";
  }

  augment "/ncs:devices/ncs:device/ncs:live-status/a1:snmp" {
    container interface-mib {
      tailf:ncs-device-type "netconf";
      tailf:display-when "not(../../../ncs:module) or ../../../ncs:module[ncs:name='Cisco-IOS-XR-snmp-ifmib-oper'] or (../../../ncs:live-status-protocol[not(ncs:capability)]) or (../../../ncs:live-status-protocol/ncs:capability/ncs:module[.='Cisco-IOS-XR-snmp-ifmib-oper'])";
      description
        "SNMP IF-MIB information";
      container interfaces {
        description
          "Interfaces ifIndex information";
        list interface {
          key "interface-name";
          description
            "ifIndex for a specific Interface Name";
          leaf interface-name {
            type xr:Interface-name;
            description
              "Interface Name";
          }
          uses live_ncs_IFMIB-IFNAME-IFINDEX-ENTRY;
        }
      }
      container interface-connectors {
        description
          "Interfaces ifConnectorPresent information";
        list interface-connector {
          key "interface-name";
          description
            "ifConnectorPresent for a specific Interface
             Name";
          leaf interface-name {
            type xr:Interface-name;
            description
              "Interface Name";
          }
          uses live_ncs_IFMIB-IFCONNECTORPRESENT-ENTRY;
        }
      }
      container interface-aliases {
        description
          "Interfaces ifAlias information";
        list interface-alias {
          key "interface-name";
          description
            "ifAlias for a specific Interface Name";
          leaf interface-name {
            type xr:Interface-name;
            description
              "Interface Name";
          }
          uses live_ncs_IFMIB-IFALIAS-ENTRY;
        }
      }
      container notification-interfaces {
        description
          "Interfaces Notification information";
        list notification-interface {
          key "interface-name";
          description
            "Notification for specific Interface Name";
          leaf interface-name {
            type xr:Interface-name;
            description
              "Interface Name";
          }
          uses live_ncs_IFMIB-NOTIF-STATUS-ENTRY;
        }
      }
      container interface-stack-statuses {
        description
          "Interfaces ifstackstatus information";
        list interface-stack-status {
          key "interface-stack-status";
          description
            "ifstatus for a pair of Interface";
          leaf interface-stack-status {
            type xr:Cisco-ios-xr-string;
            description
              "StackHigherLayer.StackLowerLayer";
          }
          uses live_ncs_IFMIB-IFSTACKSTATUS-ENTRY;
        }
      }
    }
    description
      "This augment extends the operational data of
       'Cisco-IOS-XR-snmp-agent-oper'";
  }
}
