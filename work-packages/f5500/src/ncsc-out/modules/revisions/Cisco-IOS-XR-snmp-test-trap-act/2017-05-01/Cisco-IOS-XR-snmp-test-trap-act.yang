module Cisco-IOS-XR-snmp-test-trap-act {
  // Generated by yanger -t ncs
  tailf:mount-id f5500-nc-1.0:f5500-nc-1.0;
  tailf:ncs-device-type "netconf";

  namespace "http://cisco.com/ns/yang/Cisco-IOS-XR-snmp-test-trap-act";
  prefix Cisco-IOS-XR-snmp-test-trap-act;

  import ietf-inet-types {
    prefix inet;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2017 by Cisco Systems, Inc.
     All rights reserved.";

  revision 2017-05-01 {
    description
      "Fixing backward compatibility error in module.";
  }
  revision 2016-10-25 {
    description
      "IOS XR 6.2.1 revision.";
  }

  augment "/ncs:devices/ncs:device/ncs:rpc" {
    container rpc-all {
      tailf:ncs-device-type "netconf";
      tailf:display-when "not(../../ncs:module) or ../../ncs:module[ncs:name='Cisco-IOS-XR-snmp-test-trap-act']";
      tailf:action all {
        tailf:actionpoint ncsproxy {
          tailf:internal;
        }
        description
          "generate all the supported traps";
      }
    }
  }
  augment "/ncs:devices/ncs:device-group/ncs:ned-id/ncs:rpc" {
    container rpc-all {
      tailf:ncs-device-type "netconf";
      tailf:display-when "/ncs:devices/ncs:device[ncs:name=current()/../../../ncs:member]/ncs:module[ncs:name='Cisco-IOS-XR-snmp-test-trap-act']";
      tailf:action all {
        tailf:actionpoint ncsproxy {
          tailf:internal;
        }
        description
          "generate all the supported traps";
      }
    }
  }
  augment "/ncs:devices/ncs:device/ncs:rpc" {
    container rpc-routing-mpls-tunnel-down-index {
      tailf:ncs-device-type "netconf";
      tailf:display-when "not(../../ncs:module) or ../../ncs:module[ncs:name='Cisco-IOS-XR-snmp-test-trap-act']";
      tailf:action routing-mpls-tunnel-down-index {
        tailf:actionpoint ncsproxy {
          tailf:internal;
        }
        description
          "Generate MPLS-TE-STD-MIB::mplsTunnelDown index";
        input {
          leaf index {
            description
              "tunnel index for which to generate the trap";
            mandatory true;
            type uint32 {
              range "0..65535";
            }
          }
          leaf instance {
            description
              "tunnel instance for which to generate the trap";
            mandatory true;
            type uint32 {
              range "0..65535";
            }
          }
          leaf source {
            description
              "src address";
            mandatory true;
            type inet:ipv4-address-no-zone;
          }
          leaf destination {
            description
              "destination address for which to generate the trap";
            mandatory true;
            type inet:ipv4-address-no-zone;
          }
        }
      }
    }
  }
  augment "/ncs:devices/ncs:device-group/ncs:ned-id/ncs:rpc" {
    container rpc-routing-mpls-tunnel-down-index {
      tailf:ncs-device-type "netconf";
      tailf:display-when "/ncs:devices/ncs:device[ncs:name=current()/../../../ncs:member]/ncs:module[ncs:name='Cisco-IOS-XR-snmp-test-trap-act']";
      tailf:action routing-mpls-tunnel-down-index {
        tailf:actionpoint ncsproxy {
          tailf:internal;
        }
        description
          "Generate MPLS-TE-STD-MIB::mplsTunnelDown index";
        input {
          leaf index {
            description
              "tunnel index for which to generate the trap";
            mandatory true;
            type uint32 {
              range "0..65535";
            }
          }
          leaf instance {
            description
              "tunnel instance for which to generate the trap";
            mandatory true;
            type uint32 {
              range "0..65535";
            }
          }
          leaf source {
            description
              "src address";
            mandatory true;
            type inet:ipv4-address-no-zone;
          }
          leaf destination {
            description
              "destination address for which to generate the trap";
            mandatory true;
            type inet:ipv4-address-no-zone;
          }
        }
      }
    }
  }
  augment "/ncs:devices/ncs:device/ncs:rpc" {
    container rpc-routing-mpls-tunnel-down {
      tailf:ncs-device-type "netconf";
      tailf:display-when "not(../../ncs:module) or ../../ncs:module[ncs:name='Cisco-IOS-XR-snmp-test-trap-act']";
      tailf:action routing-mpls-tunnel-down {
        tailf:actionpoint ncsproxy {
          tailf:internal;
        }
        description
          "Generate MPLS-TE-STD-MIB::mplsTunnelDown";
      }
    }
  }
  augment "/ncs:devices/ncs:device-group/ncs:ned-id/ncs:rpc" {
    container rpc-routing-mpls-tunnel-down {
      tailf:ncs-device-type "netconf";
      tailf:display-when "/ncs:devices/ncs:device[ncs:name=current()/../../../ncs:member]/ncs:module[ncs:name='Cisco-IOS-XR-snmp-test-trap-act']";
      tailf:action routing-mpls-tunnel-down {
        tailf:actionpoint ncsproxy {
          tailf:internal;
        }
        description
          "Generate MPLS-TE-STD-MIB::mplsTunnelDown";
      }
    }
  }
  augment "/ncs:devices/ncs:device/ncs:rpc" {
    container rpc-routing-mpls-tunnel-re-optimized-index {
      tailf:ncs-device-type "netconf";
      tailf:display-when "not(../../ncs:module) or ../../ncs:module[ncs:name='Cisco-IOS-XR-snmp-test-trap-act']";
      tailf:action routing-mpls-tunnel-re-optimized-index {
        tailf:actionpoint ncsproxy {
          tailf:internal;
        }
        description
          "Generate MPLS-TE-STD-MIB::mplsTunnelReoptimized index";
        input {
          leaf index {
            description
              "tunnel index for which to generate the trap";
            mandatory true;
            type uint32 {
              range "0..65535";
            }
          }
          leaf instance {
            description
              "tunnel instance for which to generate the trap";
            mandatory true;
            type uint32 {
              range "0..65535";
            }
          }
          leaf source {
            description
              "source address for which to generate the trap";
            mandatory true;
            type inet:ipv4-address-no-zone;
          }
          leaf destination {
            description
              "destination address for which to generate the trap";
            mandatory true;
            type inet:ipv4-address-no-zone;
          }
        }
      }
    }
  }
  augment "/ncs:devices/ncs:device-group/ncs:ned-id/ncs:rpc" {
    container rpc-routing-mpls-tunnel-re-optimized-index {
      tailf:ncs-device-type "netconf";
      tailf:display-when "/ncs:devices/ncs:device[ncs:name=current()/../../../ncs:member]/ncs:module[ncs:name='Cisco-IOS-XR-snmp-test-trap-act']";
      tailf:action routing-mpls-tunnel-re-optimized-index {
        tailf:actionpoint ncsproxy {
          tailf:internal;
        }
        description
          "Generate MPLS-TE-STD-MIB::mplsTunnelReoptimized index";
        input {
          leaf index {
            description
              "tunnel index for which to generate the trap";
            mandatory true;
            type uint32 {
              range "0..65535";
            }
          }
          leaf instance {
            description
              "tunnel instance for which to generate the trap";
            mandatory true;
            type uint32 {
              range "0..65535";
            }
          }
          leaf source {
            description
              "source address for which to generate the trap";
            mandatory true;
            type inet:ipv4-address-no-zone;
          }
          leaf destination {
            description
              "destination address for which to generate the trap";
            mandatory true;
            type inet:ipv4-address-no-zone;
          }
        }
      }
    }
  }
  augment "/ncs:devices/ncs:device/ncs:rpc" {
    container rpc-routing-mpls-tunnel-re-optimized {
      tailf:ncs-device-type "netconf";
      tailf:display-when "not(../../ncs:module) or ../../ncs:module[ncs:name='Cisco-IOS-XR-snmp-test-trap-act']";
      tailf:action routing-mpls-tunnel-re-optimized {
        tailf:actionpoint ncsproxy {
          tailf:internal;
        }
        description
          "Generate MPLS-TE-STD-MIB::mplsTunnelReoptimized";
      }
    }
  }
  augment "/ncs:devices/ncs:device-group/ncs:ned-id/ncs:rpc" {
    container rpc-routing-mpls-tunnel-re-optimized {
      tailf:ncs-device-type "netconf";
      tailf:display-when "/ncs:devices/ncs:device[ncs:name=current()/../../../ncs:member]/ncs:module[ncs:name='Cisco-IOS-XR-snmp-test-trap-act']";
      tailf:action routing-mpls-tunnel-re-optimized {
        tailf:actionpoint ncsproxy {
          tailf:internal;
        }
        description
          "Generate MPLS-TE-STD-MIB::mplsTunnelReoptimized";
      }
    }
  }
  augment "/ncs:devices/ncs:device/ncs:rpc" {
    container rpc-routing-mpls-tunnel-re-routed-index {
      tailf:ncs-device-type "netconf";
      tailf:display-when "not(../../ncs:module) or ../../ncs:module[ncs:name='Cisco-IOS-XR-snmp-test-trap-act']";
      tailf:action routing-mpls-tunnel-re-routed-index {
        tailf:actionpoint ncsproxy {
          tailf:internal;
        }
        description
          "Generate MPLS-TE-STD-MIB::mplsTunnelRerouted index";
        input {
          leaf index {
            description
              "tunnel index for which to generate the trap";
            mandatory true;
            type uint32 {
              range "0..65535";
            }
          }
          leaf instance {
            description
              "tunnel instance for which to generate the trap";
            mandatory true;
            type uint32 {
              range "0..65535";
            }
          }
          leaf source {
            description
              "source address for which to generate the trap";
            mandatory true;
            type inet:ipv4-address-no-zone;
          }
          leaf destination {
            description
              "destination address for which to generate the trap";
            mandatory true;
            type inet:ipv4-address-no-zone;
          }
        }
      }
    }
  }
  augment "/ncs:devices/ncs:device-group/ncs:ned-id/ncs:rpc" {
    container rpc-routing-mpls-tunnel-re-routed-index {
      tailf:ncs-device-type "netconf";
      tailf:display-when "/ncs:devices/ncs:device[ncs:name=current()/../../../ncs:member]/ncs:module[ncs:name='Cisco-IOS-XR-snmp-test-trap-act']";
      tailf:action routing-mpls-tunnel-re-routed-index {
        tailf:actionpoint ncsproxy {
          tailf:internal;
        }
        description
          "Generate MPLS-TE-STD-MIB::mplsTunnelRerouted index";
        input {
          leaf index {
            description
              "tunnel index for which to generate the trap";
            mandatory true;
            type uint32 {
              range "0..65535";
            }
          }
          leaf instance {
            description
              "tunnel instance for which to generate the trap";
            mandatory true;
            type uint32 {
              range "0..65535";
            }
          }
          leaf source {
            description
              "source address for which to generate the trap";
            mandatory true;
            type inet:ipv4-address-no-zone;
          }
          leaf destination {
            description
              "destination address for which to generate the trap";
            mandatory true;
            type inet:ipv4-address-no-zone;
          }
        }
      }
    }
  }
  augment "/ncs:devices/ncs:device/ncs:rpc" {
    container rpc-routing-mpls-tunnel-re-routed {
      tailf:ncs-device-type "netconf";
      tailf:display-when "not(../../ncs:module) or ../../ncs:module[ncs:name='Cisco-IOS-XR-snmp-test-trap-act']";
      tailf:action routing-mpls-tunnel-re-routed {
        tailf:actionpoint ncsproxy {
          tailf:internal;
        }
        description
          "Generate MPLS-TE-STD-MIB::mplsTunnelRerouted";
      }
    }
  }
  augment "/ncs:devices/ncs:device-group/ncs:ned-id/ncs:rpc" {
    container rpc-routing-mpls-tunnel-re-routed {
      tailf:ncs-device-type "netconf";
      tailf:display-when "/ncs:devices/ncs:device[ncs:name=current()/../../../ncs:member]/ncs:module[ncs:name='Cisco-IOS-XR-snmp-test-trap-act']";
      tailf:action routing-mpls-tunnel-re-routed {
        tailf:actionpoint ncsproxy {
          tailf:internal;
        }
        description
          "Generate MPLS-TE-STD-MIB::mplsTunnelRerouted";
      }
    }
  }
  augment "/ncs:devices/ncs:device/ncs:rpc" {
    container rpc-routing-mpls-ldp-session-down-entity-id {
      tailf:ncs-device-type "netconf";
      tailf:display-when "not(../../ncs:module) or ../../ncs:module[ncs:name='Cisco-IOS-XR-snmp-test-trap-act']";
      tailf:action routing-mpls-ldp-session-down-entity-id {
        tailf:actionpoint ncsproxy {
          tailf:internal;
        }
        description
          "Generate MPLS-LDP-STD-MIB::mplsLdpSessionDown entity-id";
        input {
          leaf entity-id {
            description
              "entity ldp-id in x.x.x.x.y.y format where x.x.x.x is the entity IP address and y.y is the label space";
            mandatory true;
            type string {
              length "23";
            }
          }
          leaf entity-index {
            description
              "entity index for which to generate the trap";
            mandatory true;
            type uint32 {
              range "1..4294967295";
            }
          }
          leaf peer-id {
            description
              "peer ldp-id in x.x.x.x.y.y format where x.x.x.x is the entity IP address and y.y is the label space";
            mandatory true;
            type string {
              length "23";
            }
          }
        }
      }
    }
  }
  augment "/ncs:devices/ncs:device-group/ncs:ned-id/ncs:rpc" {
    container rpc-routing-mpls-ldp-session-down-entity-id {
      tailf:ncs-device-type "netconf";
      tailf:display-when "/ncs:devices/ncs:device[ncs:name=current()/../../../ncs:member]/ncs:module[ncs:name='Cisco-IOS-XR-snmp-test-trap-act']";
      tailf:action routing-mpls-ldp-session-down-entity-id {
        tailf:actionpoint ncsproxy {
          tailf:internal;
        }
        description
          "Generate MPLS-LDP-STD-MIB::mplsLdpSessionDown entity-id";
        input {
          leaf entity-id {
            description
              "entity ldp-id in x.x.x.x.y.y format where x.x.x.x is the entity IP address and y.y is the label space";
            mandatory true;
            type string {
              length "23";
            }
          }
          leaf entity-index {
            description
              "entity index for which to generate the trap";
            mandatory true;
            type uint32 {
              range "1..4294967295";
            }
          }
          leaf peer-id {
            description
              "peer ldp-id in x.x.x.x.y.y format where x.x.x.x is the entity IP address and y.y is the label space";
            mandatory true;
            type string {
              length "23";
            }
          }
        }
      }
    }
  }
  augment "/ncs:devices/ncs:device/ncs:rpc" {
    container rpc-routing-mpls-ldp-session-down {
      tailf:ncs-device-type "netconf";
      tailf:display-when "not(../../ncs:module) or ../../ncs:module[ncs:name='Cisco-IOS-XR-snmp-test-trap-act']";
      tailf:action routing-mpls-ldp-session-down {
        tailf:actionpoint ncsproxy {
          tailf:internal;
        }
        description
          "Generate MPLS-LDP-STD-MIB::mplsLdpSessionDown";
      }
    }
  }
  augment "/ncs:devices/ncs:device-group/ncs:ned-id/ncs:rpc" {
    container rpc-routing-mpls-ldp-session-down {
      tailf:ncs-device-type "netconf";
      tailf:display-when "/ncs:devices/ncs:device[ncs:name=current()/../../../ncs:member]/ncs:module[ncs:name='Cisco-IOS-XR-snmp-test-trap-act']";
      tailf:action routing-mpls-ldp-session-down {
        tailf:actionpoint ncsproxy {
          tailf:internal;
        }
        description
          "Generate MPLS-LDP-STD-MIB::mplsLdpSessionDown";
      }
    }
  }
  augment "/ncs:devices/ncs:device/ncs:rpc" {
    container rpc-routing-ospf-neighbor-state-change-address {
      tailf:ncs-device-type "netconf";
      tailf:display-when "not(../../ncs:module) or ../../ncs:module[ncs:name='Cisco-IOS-XR-snmp-test-trap-act']";
      tailf:action routing-ospf-neighbor-state-change-address {
        tailf:actionpoint ncsproxy {
          tailf:internal;
        }
        description
          "Generate OSPF-TRAP-MIB::ospfNbrStateChange address";
        input {
          leaf address {
            description
              "neighbor's IP source address for which to generate the trap";
            mandatory true;
            type inet:ipv4-address-no-zone;
          }
          leaf ifindex {
            description
              "0 for interfaces having IP addresses or IF-MIB ifindex of addressless interface";
            mandatory true;
            type uint32 {
              range "0..2147483647";
            }
          }
        }
      }
    }
  }
  augment "/ncs:devices/ncs:device-group/ncs:ned-id/ncs:rpc" {
    container rpc-routing-ospf-neighbor-state-change-address {
      tailf:ncs-device-type "netconf";
      tailf:display-when "/ncs:devices/ncs:device[ncs:name=current()/../../../ncs:member]/ncs:module[ncs:name='Cisco-IOS-XR-snmp-test-trap-act']";
      tailf:action routing-ospf-neighbor-state-change-address {
        tailf:actionpoint ncsproxy {
          tailf:internal;
        }
        description
          "Generate OSPF-TRAP-MIB::ospfNbrStateChange address";
        input {
          leaf address {
            description
              "neighbor's IP source address for which to generate the trap";
            mandatory true;
            type inet:ipv4-address-no-zone;
          }
          leaf ifindex {
            description
              "0 for interfaces having IP addresses or IF-MIB ifindex of addressless interface";
            mandatory true;
            type uint32 {
              range "0..2147483647";
            }
          }
        }
      }
    }
  }
  augment "/ncs:devices/ncs:device/ncs:rpc" {
    container rpc-routing-ospf-neighbor-state-change {
      tailf:ncs-device-type "netconf";
      tailf:display-when "not(../../ncs:module) or ../../ncs:module[ncs:name='Cisco-IOS-XR-snmp-test-trap-act']";
      tailf:action routing-ospf-neighbor-state-change {
        tailf:actionpoint ncsproxy {
          tailf:internal;
        }
        description
          "Generate OSPF-TRAP-MIB::ospfNbrStateChange";
      }
    }
  }
  augment "/ncs:devices/ncs:device-group/ncs:ned-id/ncs:rpc" {
    container rpc-routing-ospf-neighbor-state-change {
      tailf:ncs-device-type "netconf";
      tailf:display-when "/ncs:devices/ncs:device[ncs:name=current()/../../../ncs:member]/ncs:module[ncs:name='Cisco-IOS-XR-snmp-test-trap-act']";
      tailf:action routing-ospf-neighbor-state-change {
        tailf:actionpoint ncsproxy {
          tailf:internal;
        }
        description
          "Generate OSPF-TRAP-MIB::ospfNbrStateChange";
      }
    }
  }
  augment "/ncs:devices/ncs:device/ncs:rpc" {
    container rpc-routing-bgp-state-change-remote-peer {
      tailf:ncs-device-type "netconf";
      tailf:display-when "not(../../ncs:module) or ../../ncs:module[ncs:name='Cisco-IOS-XR-snmp-test-trap-act']";
      tailf:action routing-bgp-state-change-remote-peer {
        tailf:actionpoint ncsproxy {
          tailf:internal;
        }
        description
          "Generate CISCO-BGP-MIB::cbgpBackwardTransition remote peer";
        input {
          leaf address {
            description
              "BGP remote peer IP address for which to generate the trap";
            mandatory true;
            type inet:ipv4-address-no-zone;
          }
        }
      }
    }
  }
  augment "/ncs:devices/ncs:device-group/ncs:ned-id/ncs:rpc" {
    container rpc-routing-bgp-state-change-remote-peer {
      tailf:ncs-device-type "netconf";
      tailf:display-when "/ncs:devices/ncs:device[ncs:name=current()/../../../ncs:member]/ncs:module[ncs:name='Cisco-IOS-XR-snmp-test-trap-act']";
      tailf:action routing-bgp-state-change-remote-peer {
        tailf:actionpoint ncsproxy {
          tailf:internal;
        }
        description
          "Generate CISCO-BGP-MIB::cbgpBackwardTransition remote peer";
        input {
          leaf address {
            description
              "BGP remote peer IP address for which to generate the trap";
            mandatory true;
            type inet:ipv4-address-no-zone;
          }
        }
      }
    }
  }
  augment "/ncs:devices/ncs:device/ncs:rpc" {
    container rpc-routing-bgp-state-change {
      tailf:ncs-device-type "netconf";
      tailf:display-when "not(../../ncs:module) or ../../ncs:module[ncs:name='Cisco-IOS-XR-snmp-test-trap-act']";
      tailf:action routing-bgp-state-change {
        tailf:actionpoint ncsproxy {
          tailf:internal;
        }
        description
          "Generate CISCO-BGP-MIB::cbgpBackwardTransition";
      }
    }
  }
  augment "/ncs:devices/ncs:device-group/ncs:ned-id/ncs:rpc" {
    container rpc-routing-bgp-state-change {
      tailf:ncs-device-type "netconf";
      tailf:display-when "/ncs:devices/ncs:device[ncs:name=current()/../../../ncs:member]/ncs:module[ncs:name='Cisco-IOS-XR-snmp-test-trap-act']";
      tailf:action routing-bgp-state-change {
        tailf:actionpoint ncsproxy {
          tailf:internal;
        }
        description
          "Generate CISCO-BGP-MIB::cbgpBackwardTransition";
      }
    }
  }
  augment "/ncs:devices/ncs:device/ncs:rpc" {
    container rpc-routing-bgp-established-remote-peer {
      tailf:ncs-device-type "netconf";
      tailf:display-when "not(../../ncs:module) or ../../ncs:module[ncs:name='Cisco-IOS-XR-snmp-test-trap-act']";
      tailf:action routing-bgp-established-remote-peer {
        tailf:actionpoint ncsproxy {
          tailf:internal;
        }
        description
          "Generate BGP4-MIB::bglEstablishedNotification remote peer";
        input {
          leaf address {
            description
              "BGP remote peer IP address for which to generate the trap";
            mandatory true;
            type inet:ipv4-address-no-zone;
          }
        }
      }
    }
  }
  augment "/ncs:devices/ncs:device-group/ncs:ned-id/ncs:rpc" {
    container rpc-routing-bgp-established-remote-peer {
      tailf:ncs-device-type "netconf";
      tailf:display-when "/ncs:devices/ncs:device[ncs:name=current()/../../../ncs:member]/ncs:module[ncs:name='Cisco-IOS-XR-snmp-test-trap-act']";
      tailf:action routing-bgp-established-remote-peer {
        tailf:actionpoint ncsproxy {
          tailf:internal;
        }
        description
          "Generate BGP4-MIB::bglEstablishedNotification remote peer";
        input {
          leaf address {
            description
              "BGP remote peer IP address for which to generate the trap";
            mandatory true;
            type inet:ipv4-address-no-zone;
          }
        }
      }
    }
  }
  augment "/ncs:devices/ncs:device/ncs:rpc" {
    container rpc-routing-bgp-established {
      tailf:ncs-device-type "netconf";
      tailf:display-when "not(../../ncs:module) or ../../ncs:module[ncs:name='Cisco-IOS-XR-snmp-test-trap-act']";
      tailf:action routing-bgp-established {
        tailf:actionpoint ncsproxy {
          tailf:internal;
        }
        description
          "Generate BGP4-MIB::bglEstablishedNotification";
      }
    }
  }
  augment "/ncs:devices/ncs:device-group/ncs:ned-id/ncs:rpc" {
    container rpc-routing-bgp-established {
      tailf:ncs-device-type "netconf";
      tailf:display-when "/ncs:devices/ncs:device[ncs:name=current()/../../../ncs:member]/ncs:module[ncs:name='Cisco-IOS-XR-snmp-test-trap-act']";
      tailf:action routing-bgp-established {
        tailf:actionpoint ncsproxy {
          tailf:internal;
        }
        description
          "Generate BGP4-MIB::bglEstablishedNotification";
      }
    }
  }
  augment "/ncs:devices/ncs:device/ncs:rpc" {
    container rpc-platform-hfr-plane-state {
      tailf:ncs-device-type "netconf";
      tailf:display-when "not(../../ncs:module) or ../../ncs:module[ncs:name='Cisco-IOS-XR-snmp-test-trap-act']";
      tailf:action platform-hfr-plane-state {
        tailf:actionpoint ncsproxy {
          tailf:internal;
        }
        description
          "Generate CISCO-FABRIC-HFR-MIB::cfhPlaneStateNotification";
        input {
          leaf plane-id {
            description
              "plane identifier for which to generate the trap";
            type uint32;
          }
        }
      }
    }
  }
  augment "/ncs:devices/ncs:device-group/ncs:ned-id/ncs:rpc" {
    container rpc-platform-hfr-plane-state {
      tailf:ncs-device-type "netconf";
      tailf:display-when "/ncs:devices/ncs:device[ncs:name=current()/../../../ncs:member]/ncs:module[ncs:name='Cisco-IOS-XR-snmp-test-trap-act']";
      tailf:action platform-hfr-plane-state {
        tailf:actionpoint ncsproxy {
          tailf:internal;
        }
        description
          "Generate CISCO-FABRIC-HFR-MIB::cfhPlaneStateNotification";
        input {
          leaf plane-id {
            description
              "plane identifier for which to generate the trap";
            type uint32;
          }
        }
      }
    }
  }
  augment "/ncs:devices/ncs:device/ncs:rpc" {
    container rpc-platform-hfr-bundle-state {
      tailf:ncs-device-type "netconf";
      tailf:display-when "not(../../ncs:module) or ../../ncs:module[ncs:name='Cisco-IOS-XR-snmp-test-trap-act']";
      tailf:action platform-hfr-bundle-state {
        tailf:actionpoint ncsproxy {
          tailf:internal;
        }
        description
          "Generate CISCO-FABRIC-HFR-MIB::cfhBundleStateNotification";
        input {
          leaf bundle-name {
            description
              "bundle name for which to generate the trap";
            type string;
          }
        }
      }
    }
  }
  augment "/ncs:devices/ncs:device-group/ncs:ned-id/ncs:rpc" {
    container rpc-platform-hfr-bundle-state {
      tailf:ncs-device-type "netconf";
      tailf:display-when "/ncs:devices/ncs:device[ncs:name=current()/../../../ncs:member]/ncs:module[ncs:name='Cisco-IOS-XR-snmp-test-trap-act']";
      tailf:action platform-hfr-bundle-state {
        tailf:actionpoint ncsproxy {
          tailf:internal;
        }
        description
          "Generate CISCO-FABRIC-HFR-MIB::cfhBundleStateNotification";
        input {
          leaf bundle-name {
            description
              "bundle name for which to generate the trap";
            type string;
          }
        }
      }
    }
  }
  augment "/ncs:devices/ncs:device/ncs:rpc" {
    container rpc-platform-hfr-bundle-downed-link {
      tailf:ncs-device-type "netconf";
      tailf:display-when "not(../../ncs:module) or ../../ncs:module[ncs:name='Cisco-IOS-XR-snmp-test-trap-act']";
      tailf:action platform-hfr-bundle-downed-link {
        tailf:actionpoint ncsproxy {
          tailf:internal;
        }
        description
          "Generate CISCO-FABRIC-HFR-MIB::cfhBundleDownedLinkNotification";
        input {
          leaf bundle-name {
            description
              "bundle name for which to generate the trap";
            type string;
          }
        }
      }
    }
  }
  augment "/ncs:devices/ncs:device-group/ncs:ned-id/ncs:rpc" {
    container rpc-platform-hfr-bundle-downed-link {
      tailf:ncs-device-type "netconf";
      tailf:display-when "/ncs:devices/ncs:device[ncs:name=current()/../../../ncs:member]/ncs:module[ncs:name='Cisco-IOS-XR-snmp-test-trap-act']";
      tailf:action platform-hfr-bundle-downed-link {
        tailf:actionpoint ncsproxy {
          tailf:internal;
        }
        description
          "Generate CISCO-FABRIC-HFR-MIB::cfhBundleDownedLinkNotification";
        input {
          leaf bundle-name {
            description
              "bundle name for which to generate the trap";
            type string;
          }
        }
      }
    }
  }
  augment "/ncs:devices/ncs:device/ncs:rpc" {
    container rpc-entity-fru-fan-tray-removed {
      tailf:ncs-device-type "netconf";
      tailf:display-when "not(../../ncs:module) or ../../ncs:module[ncs:name='Cisco-IOS-XR-snmp-test-trap-act']";
      tailf:action entity-fru-fan-tray-removed {
        tailf:actionpoint ncsproxy {
          tailf:internal;
        }
        description
          "Generate CISCO-ENTITY-FRU-CONTROL-MIB::cefcFRURemoved";
        input {
          leaf entindex {
            description
              "entity Physical Index for which to generate trap";
            type uint32 {
              range "1..2147483647";
            }
          }
        }
      }
    }
  }
  augment "/ncs:devices/ncs:device-group/ncs:ned-id/ncs:rpc" {
    container rpc-entity-fru-fan-tray-removed {
      tailf:ncs-device-type "netconf";
      tailf:display-when "/ncs:devices/ncs:device[ncs:name=current()/../../../ncs:member]/ncs:module[ncs:name='Cisco-IOS-XR-snmp-test-trap-act']";
      tailf:action entity-fru-fan-tray-removed {
        tailf:actionpoint ncsproxy {
          tailf:internal;
        }
        description
          "Generate CISCO-ENTITY-FRU-CONTROL-MIB::cefcFRURemoved";
        input {
          leaf entindex {
            description
              "entity Physical Index for which to generate trap";
            type uint32 {
              range "1..2147483647";
            }
          }
        }
      }
    }
  }
  augment "/ncs:devices/ncs:device/ncs:rpc" {
    container rpc-entity-fru-fan-tray-inserted {
      tailf:ncs-device-type "netconf";
      tailf:display-when "not(../../ncs:module) or ../../ncs:module[ncs:name='Cisco-IOS-XR-snmp-test-trap-act']";
      tailf:action entity-fru-fan-tray-inserted {
        tailf:actionpoint ncsproxy {
          tailf:internal;
        }
        description
          "Generate CISCO-ENTITY-FRU-CONTROL-MIB::cefcFRUInserted";
        input {
          leaf entindex {
            description
              "entity Physical Index for which to generate trap";
            type uint32 {
              range "1..2147483647";
            }
          }
        }
      }
    }
  }
  augment "/ncs:devices/ncs:device-group/ncs:ned-id/ncs:rpc" {
    container rpc-entity-fru-fan-tray-inserted {
      tailf:ncs-device-type "netconf";
      tailf:display-when "/ncs:devices/ncs:device[ncs:name=current()/../../../ncs:member]/ncs:module[ncs:name='Cisco-IOS-XR-snmp-test-trap-act']";
      tailf:action entity-fru-fan-tray-inserted {
        tailf:actionpoint ncsproxy {
          tailf:internal;
        }
        description
          "Generate CISCO-ENTITY-FRU-CONTROL-MIB::cefcFRUInserted";
        input {
          leaf entindex {
            description
              "entity Physical Index for which to generate trap";
            type uint32 {
              range "1..2147483647";
            }
          }
        }
      }
    }
  }
  augment "/ncs:devices/ncs:device/ncs:rpc" {
    container rpc-entity-fru-fan-tray-oper-status-up {
      tailf:ncs-device-type "netconf";
      tailf:display-when "not(../../ncs:module) or ../../ncs:module[ncs:name='Cisco-IOS-XR-snmp-test-trap-act']";
      tailf:action entity-fru-fan-tray-oper-status-up {
        tailf:actionpoint ncsproxy {
          tailf:internal;
        }
        description
          "Generate CISCO-ENTITY-FRU-CONTROL-MIB::cefcFanTrayStatusChange";
        input {
          leaf entindex {
            description
              "entity Physical Index for which to generate trap";
            type uint32 {
              range "1..2147483647";
            }
          }
        }
      }
    }
  }
  augment "/ncs:devices/ncs:device-group/ncs:ned-id/ncs:rpc" {
    container rpc-entity-fru-fan-tray-oper-status-up {
      tailf:ncs-device-type "netconf";
      tailf:display-when "/ncs:devices/ncs:device[ncs:name=current()/../../../ncs:member]/ncs:module[ncs:name='Cisco-IOS-XR-snmp-test-trap-act']";
      tailf:action entity-fru-fan-tray-oper-status-up {
        tailf:actionpoint ncsproxy {
          tailf:internal;
        }
        description
          "Generate CISCO-ENTITY-FRU-CONTROL-MIB::cefcFanTrayStatusChange";
        input {
          leaf entindex {
            description
              "entity Physical Index for which to generate trap";
            type uint32 {
              range "1..2147483647";
            }
          }
        }
      }
    }
  }
  augment "/ncs:devices/ncs:device/ncs:rpc" {
    container rpc-entity-fru-module-status-change-down {
      tailf:ncs-device-type "netconf";
      tailf:display-when "not(../../ncs:module) or ../../ncs:module[ncs:name='Cisco-IOS-XR-snmp-test-trap-act']";
      tailf:action entity-fru-module-status-change-down {
        tailf:actionpoint ncsproxy {
          tailf:internal;
        }
        description
          "fu trap module status changed as failed";
        input {
          leaf entindex {
            description
              "entity Physical Index for which to generate trap";
            type uint32 {
              range "1..2147483647";
            }
          }
        }
      }
    }
  }
  augment "/ncs:devices/ncs:device-group/ncs:ned-id/ncs:rpc" {
    container rpc-entity-fru-module-status-change-down {
      tailf:ncs-device-type "netconf";
      tailf:display-when "/ncs:devices/ncs:device[ncs:name=current()/../../../ncs:member]/ncs:module[ncs:name='Cisco-IOS-XR-snmp-test-trap-act']";
      tailf:action entity-fru-module-status-change-down {
        tailf:actionpoint ncsproxy {
          tailf:internal;
        }
        description
          "fu trap module status changed as failed";
        input {
          leaf entindex {
            description
              "entity Physical Index for which to generate trap";
            type uint32 {
              range "1..2147483647";
            }
          }
        }
      }
    }
  }
  augment "/ncs:devices/ncs:device/ncs:rpc" {
    container rpc-entity-fru-module-status-change-up {
      tailf:ncs-device-type "netconf";
      tailf:display-when "not(../../ncs:module) or ../../ncs:module[ncs:name='Cisco-IOS-XR-snmp-test-trap-act']";
      tailf:action entity-fru-module-status-change-up {
        tailf:actionpoint ncsproxy {
          tailf:internal;
        }
        description
          "fu trap module status changed as ok";
        input {
          leaf entindex {
            description
              "entity Physical Index for which to generate trap";
            type uint32 {
              range "1..2147483647";
            }
          }
        }
      }
    }
  }
  augment "/ncs:devices/ncs:device-group/ncs:ned-id/ncs:rpc" {
    container rpc-entity-fru-module-status-change-up {
      tailf:ncs-device-type "netconf";
      tailf:display-when "/ncs:devices/ncs:device[ncs:name=current()/../../../ncs:member]/ncs:module[ncs:name='Cisco-IOS-XR-snmp-test-trap-act']";
      tailf:action entity-fru-module-status-change-up {
        tailf:actionpoint ncsproxy {
          tailf:internal;
        }
        description
          "fu trap module status changed as ok";
        input {
          leaf entindex {
            description
              "entity Physical Index for which to generate trap";
            type uint32 {
              range "1..2147483647";
            }
          }
        }
      }
    }
  }
  augment "/ncs:devices/ncs:device/ncs:rpc" {
    container rpc-entity-fru-power-status-change-failed {
      tailf:ncs-device-type "netconf";
      tailf:display-when "not(../../ncs:module) or ../../ncs:module[ncs:name='Cisco-IOS-XR-snmp-test-trap-act']";
      tailf:action entity-fru-power-status-change-failed {
        tailf:actionpoint ncsproxy {
          tailf:internal;
        }
        description
          "oper status changed to failed";
        input {
          leaf entindex {
            description
              "entity Physical Index for which to generate trap";
            type uint32 {
              range "1..2147483647";
            }
          }
        }
      }
    }
  }
  augment "/ncs:devices/ncs:device-group/ncs:ned-id/ncs:rpc" {
    container rpc-entity-fru-power-status-change-failed {
      tailf:ncs-device-type "netconf";
      tailf:display-when "/ncs:devices/ncs:device[ncs:name=current()/../../../ncs:member]/ncs:module[ncs:name='Cisco-IOS-XR-snmp-test-trap-act']";
      tailf:action entity-fru-power-status-change-failed {
        tailf:actionpoint ncsproxy {
          tailf:internal;
        }
        description
          "oper status changed to failed";
        input {
          leaf entindex {
            description
              "entity Physical Index for which to generate trap";
            type uint32 {
              range "1..2147483647";
            }
          }
        }
      }
    }
  }
  augment "/ncs:devices/ncs:device/ncs:rpc" {
    container rpc-entity-sensor-threshold-notification {
      tailf:ncs-device-type "netconf";
      tailf:display-when "not(../../ncs:module) or ../../ncs:module[ncs:name='Cisco-IOS-XR-snmp-test-trap-act']";
      tailf:action entity-sensor-threshold-notification {
        tailf:actionpoint ncsproxy {
          tailf:internal;
        }
        description
          "Generate CISCO-ENTITY-SENSOR-MIB::entSensorThresholdNotification";
        input {
          leaf entindex {
            description
              "entity Physical Index for which to generate trap";
            type uint32 {
              range "1..2147483647";
            }
          }
        }
      }
    }
  }
  augment "/ncs:devices/ncs:device-group/ncs:ned-id/ncs:rpc" {
    container rpc-entity-sensor-threshold-notification {
      tailf:ncs-device-type "netconf";
      tailf:display-when "/ncs:devices/ncs:device[ncs:name=current()/../../../ncs:member]/ncs:module[ncs:name='Cisco-IOS-XR-snmp-test-trap-act']";
      tailf:action entity-sensor-threshold-notification {
        tailf:actionpoint ncsproxy {
          tailf:internal;
        }
        description
          "Generate CISCO-ENTITY-SENSOR-MIB::entSensorThresholdNotification";
        input {
          leaf entindex {
            description
              "entity Physical Index for which to generate trap";
            type uint32 {
              range "1..2147483647";
            }
          }
        }
      }
    }
  }
  augment "/ncs:devices/ncs:device/ncs:rpc" {
    container rpc-infra-config-event {
      tailf:ncs-device-type "netconf";
      tailf:display-when "not(../../ncs:module) or ../../ncs:module[ncs:name='Cisco-IOS-XR-snmp-test-trap-act']";
      tailf:action infra-config-event {
        tailf:actionpoint ncsproxy {
          tailf:internal;
        }
        description
          "Generate CISCO-CONFIG-MAN-MIB::ciscoConfigManEvent";
      }
    }
  }
  augment "/ncs:devices/ncs:device-group/ncs:ned-id/ncs:rpc" {
    container rpc-infra-config-event {
      tailf:ncs-device-type "netconf";
      tailf:display-when "/ncs:devices/ncs:device[ncs:name=current()/../../../ncs:member]/ncs:module[ncs:name='Cisco-IOS-XR-snmp-test-trap-act']";
      tailf:action infra-config-event {
        tailf:actionpoint ncsproxy {
          tailf:internal;
        }
        description
          "Generate CISCO-CONFIG-MAN-MIB::ciscoConfigManEvent";
      }
    }
  }
  augment "/ncs:devices/ncs:device/ncs:rpc" {
    container rpc-infra-bridge-topology-change {
      tailf:ncs-device-type "netconf";
      tailf:display-when "not(../../ncs:module) or ../../ncs:module[ncs:name='Cisco-IOS-XR-snmp-test-trap-act']";
      tailf:action infra-bridge-topology-change {
        tailf:actionpoint ncsproxy {
          tailf:internal;
        }
        description
          "Generate BRIDGE-MIB::topologyChange";
      }
    }
  }
  augment "/ncs:devices/ncs:device-group/ncs:ned-id/ncs:rpc" {
    container rpc-infra-bridge-topology-change {
      tailf:ncs-device-type "netconf";
      tailf:display-when "/ncs:devices/ncs:device[ncs:name=current()/../../../ncs:member]/ncs:module[ncs:name='Cisco-IOS-XR-snmp-test-trap-act']";
      tailf:action infra-bridge-topology-change {
        tailf:actionpoint ncsproxy {
          tailf:internal;
        }
        description
          "Generate BRIDGE-MIB::topologyChange";
      }
    }
  }
  augment "/ncs:devices/ncs:device/ncs:rpc" {
    container rpc-infra-bridge-new-root {
      tailf:ncs-device-type "netconf";
      tailf:display-when "not(../../ncs:module) or ../../ncs:module[ncs:name='Cisco-IOS-XR-snmp-test-trap-act']";
      tailf:action infra-bridge-new-root {
        tailf:actionpoint ncsproxy {
          tailf:internal;
        }
        description
          "Generate BRIDGE-MIB::newRoot";
      }
    }
  }
  augment "/ncs:devices/ncs:device-group/ncs:ned-id/ncs:rpc" {
    container rpc-infra-bridge-new-root {
      tailf:ncs-device-type "netconf";
      tailf:display-when "/ncs:devices/ncs:device[ncs:name=current()/../../../ncs:member]/ncs:module[ncs:name='Cisco-IOS-XR-snmp-test-trap-act']";
      tailf:action infra-bridge-new-root {
        tailf:actionpoint ncsproxy {
          tailf:internal;
        }
        description
          "Generate BRIDGE-MIB::newRoot";
      }
    }
  }
  augment "/ncs:devices/ncs:device/ncs:rpc" {
    container rpc-infra-redundancy-switch {
      tailf:ncs-device-type "netconf";
      tailf:display-when "not(../../ncs:module) or ../../ncs:module[ncs:name='Cisco-IOS-XR-snmp-test-trap-act']";
      tailf:action infra-redundancy-switch {
        tailf:actionpoint ncsproxy {
          tailf:internal;
        }
        description
          "Generate CISCO-RF-MIB::ciscoRFSwactNotif";
      }
    }
  }
  augment "/ncs:devices/ncs:device-group/ncs:ned-id/ncs:rpc" {
    container rpc-infra-redundancy-switch {
      tailf:ncs-device-type "netconf";
      tailf:display-when "/ncs:devices/ncs:device[ncs:name=current()/../../../ncs:member]/ncs:module[ncs:name='Cisco-IOS-XR-snmp-test-trap-act']";
      tailf:action infra-redundancy-switch {
        tailf:actionpoint ncsproxy {
          tailf:internal;
        }
        description
          "Generate CISCO-RF-MIB::ciscoRFSwactNotif";
      }
    }
  }
  augment "/ncs:devices/ncs:device/ncs:rpc" {
    container rpc-infra-redundancy-progression {
      tailf:ncs-device-type "netconf";
      tailf:display-when "not(../../ncs:module) or ../../ncs:module[ncs:name='Cisco-IOS-XR-snmp-test-trap-act']";
      tailf:action infra-redundancy-progression {
        tailf:actionpoint ncsproxy {
          tailf:internal;
        }
        description
          "Generate CISCO-RF-MIB::ciscoRFProgressionNotif";
      }
    }
  }
  augment "/ncs:devices/ncs:device-group/ncs:ned-id/ncs:rpc" {
    container rpc-infra-redundancy-progression {
      tailf:ncs-device-type "netconf";
      tailf:display-when "/ncs:devices/ncs:device[ncs:name=current()/../../../ncs:member]/ncs:module[ncs:name='Cisco-IOS-XR-snmp-test-trap-act']";
      tailf:action infra-redundancy-progression {
        tailf:actionpoint ncsproxy {
          tailf:internal;
        }
        description
          "Generate CISCO-RF-MIB::ciscoRFProgressionNotif";
      }
    }
  }
  augment "/ncs:devices/ncs:device/ncs:rpc" {
    container rpc-infra-flash-device-removed {
      tailf:ncs-device-type "netconf";
      tailf:display-when "not(../../ncs:module) or ../../ncs:module[ncs:name='Cisco-IOS-XR-snmp-test-trap-act']";
      tailf:action infra-flash-device-removed {
        tailf:actionpoint ncsproxy {
          tailf:internal;
        }
        description
          "Generate CISCO-FLASH-MIB::ciscoFlashDeviceRemovedNotif";
      }
    }
  }
  augment "/ncs:devices/ncs:device-group/ncs:ned-id/ncs:rpc" {
    container rpc-infra-flash-device-removed {
      tailf:ncs-device-type "netconf";
      tailf:display-when "/ncs:devices/ncs:device[ncs:name=current()/../../../ncs:member]/ncs:module[ncs:name='Cisco-IOS-XR-snmp-test-trap-act']";
      tailf:action infra-flash-device-removed {
        tailf:actionpoint ncsproxy {
          tailf:internal;
        }
        description
          "Generate CISCO-FLASH-MIB::ciscoFlashDeviceRemovedNotif";
      }
    }
  }
  augment "/ncs:devices/ncs:device/ncs:rpc" {
    container rpc-infra-flash-device-inserted {
      tailf:ncs-device-type "netconf";
      tailf:display-when "not(../../ncs:module) or ../../ncs:module[ncs:name='Cisco-IOS-XR-snmp-test-trap-act']";
      tailf:action infra-flash-device-inserted {
        tailf:actionpoint ncsproxy {
          tailf:internal;
        }
        description
          "Generate CISCO-FLASH-MIB::ciscoFlashDeviceInsertedNotif";
      }
    }
  }
  augment "/ncs:devices/ncs:device-group/ncs:ned-id/ncs:rpc" {
    container rpc-infra-flash-device-inserted {
      tailf:ncs-device-type "netconf";
      tailf:display-when "/ncs:devices/ncs:device[ncs:name=current()/../../../ncs:member]/ncs:module[ncs:name='Cisco-IOS-XR-snmp-test-trap-act']";
      tailf:action infra-flash-device-inserted {
        tailf:actionpoint ncsproxy {
          tailf:internal;
        }
        description
          "Generate CISCO-FLASH-MIB::ciscoFlashDeviceInsertedNotif";
      }
    }
  }
  augment "/ncs:devices/ncs:device/ncs:rpc" {
    container rpc-infra-syslog-message-generated {
      tailf:ncs-device-type "netconf";
      tailf:display-when "not(../../ncs:module) or ../../ncs:module[ncs:name='Cisco-IOS-XR-snmp-test-trap-act']";
      tailf:action infra-syslog-message-generated {
        tailf:actionpoint ncsproxy {
          tailf:internal;
        }
        description
          "Generate CISCO-SYSLOG-MIB::clogMessageGenerated";
      }
    }
  }
  augment "/ncs:devices/ncs:device-group/ncs:ned-id/ncs:rpc" {
    container rpc-infra-syslog-message-generated {
      tailf:ncs-device-type "netconf";
      tailf:display-when "/ncs:devices/ncs:device[ncs:name=current()/../../../ncs:member]/ncs:module[ncs:name='Cisco-IOS-XR-snmp-test-trap-act']";
      tailf:action infra-syslog-message-generated {
        tailf:actionpoint ncsproxy {
          tailf:internal;
        }
        description
          "Generate CISCO-SYSLOG-MIB::clogMessageGenerated";
      }
    }
  }
  augment "/ncs:devices/ncs:device/ncs:rpc" {
    container rpc-sonet-path-status {
      tailf:ncs-device-type "netconf";
      tailf:display-when "not(../../ncs:module) or ../../ncs:module[ncs:name='Cisco-IOS-XR-snmp-test-trap-act']";
      tailf:action sonet-path-status {
        tailf:actionpoint ncsproxy {
          tailf:internal;
        }
        description
          "Generate CISCO-SONET-MIB::ciscoSonetPathStatusChange";
        input {
          leaf ifindex {
            description
              "interface index for which to generate ciscoSonetPathStatusChange trap";
            type uint32 {
              range "1..2147483647";
            }
          }
        }
      }
    }
  }
  augment "/ncs:devices/ncs:device-group/ncs:ned-id/ncs:rpc" {
    container rpc-sonet-path-status {
      tailf:ncs-device-type "netconf";
      tailf:display-when "/ncs:devices/ncs:device[ncs:name=current()/../../../ncs:member]/ncs:module[ncs:name='Cisco-IOS-XR-snmp-test-trap-act']";
      tailf:action sonet-path-status {
        tailf:actionpoint ncsproxy {
          tailf:internal;
        }
        description
          "Generate CISCO-SONET-MIB::ciscoSonetPathStatusChange";
        input {
          leaf ifindex {
            description
              "interface index for which to generate ciscoSonetPathStatusChange trap";
            type uint32 {
              range "1..2147483647";
            }
          }
        }
      }
    }
  }
  augment "/ncs:devices/ncs:device/ncs:rpc" {
    container rpc-sonet-line-status {
      tailf:ncs-device-type "netconf";
      tailf:display-when "not(../../ncs:module) or ../../ncs:module[ncs:name='Cisco-IOS-XR-snmp-test-trap-act']";
      tailf:action sonet-line-status {
        tailf:actionpoint ncsproxy {
          tailf:internal;
        }
        description
          "Generate CISCO-SONET-MIB::ciscoSonetLineStatusChange";
        input {
          leaf ifindex {
            description
              "interface index for which to generate ciscoSonetLineStatusChange trap";
            type uint32 {
              range "1..2147483647";
            }
          }
        }
      }
    }
  }
  augment "/ncs:devices/ncs:device-group/ncs:ned-id/ncs:rpc" {
    container rpc-sonet-line-status {
      tailf:ncs-device-type "netconf";
      tailf:display-when "/ncs:devices/ncs:device[ncs:name=current()/../../../ncs:member]/ncs:module[ncs:name='Cisco-IOS-XR-snmp-test-trap-act']";
      tailf:action sonet-line-status {
        tailf:actionpoint ncsproxy {
          tailf:internal;
        }
        description
          "Generate CISCO-SONET-MIB::ciscoSonetLineStatusChange";
        input {
          leaf ifindex {
            description
              "interface index for which to generate ciscoSonetLineStatusChange trap";
            type uint32 {
              range "1..2147483647";
            }
          }
        }
      }
    }
  }
  augment "/ncs:devices/ncs:device/ncs:rpc" {
    container rpc-sonet-section-status {
      tailf:ncs-device-type "netconf";
      tailf:display-when "not(../../ncs:module) or ../../ncs:module[ncs:name='Cisco-IOS-XR-snmp-test-trap-act']";
      tailf:action sonet-section-status {
        tailf:actionpoint ncsproxy {
          tailf:internal;
        }
        description
          "Generate CISCO-SONET-MIB::ciscoSonetSectionStatusChange";
        input {
          leaf ifindex {
            description
              "interface index for which to generate ciscoSonetSectionStatusChange trap";
            type uint32 {
              range "1..2147483647";
            }
          }
        }
      }
    }
  }
  augment "/ncs:devices/ncs:device-group/ncs:ned-id/ncs:rpc" {
    container rpc-sonet-section-status {
      tailf:ncs-device-type "netconf";
      tailf:display-when "/ncs:devices/ncs:device[ncs:name=current()/../../../ncs:member]/ncs:module[ncs:name='Cisco-IOS-XR-snmp-test-trap-act']";
      tailf:action sonet-section-status {
        tailf:actionpoint ncsproxy {
          tailf:internal;
        }
        description
          "Generate CISCO-SONET-MIB::ciscoSonetSectionStatusChange";
        input {
          leaf ifindex {
            description
              "interface index for which to generate ciscoSonetSectionStatusChange trap";
            type uint32 {
              range "1..2147483647";
            }
          }
        }
      }
    }
  }
  augment "/ncs:devices/ncs:device/ncs:rpc" {
    container rpc-interface-link-down {
      tailf:ncs-device-type "netconf";
      tailf:display-when "not(../../ncs:module) or ../../ncs:module[ncs:name='Cisco-IOS-XR-snmp-test-trap-act']";
      tailf:action interface-link-down {
        tailf:actionpoint ncsproxy {
          tailf:internal;
        }
        description
          "Generate IF-MIB::linkDown";
        input {
          leaf ifindex {
            description
              "interface index for which to generate LinkDown trap";
            type uint32 {
              range "1..2147483647";
            }
          }
        }
      }
    }
  }
  augment "/ncs:devices/ncs:device-group/ncs:ned-id/ncs:rpc" {
    container rpc-interface-link-down {
      tailf:ncs-device-type "netconf";
      tailf:display-when "/ncs:devices/ncs:device[ncs:name=current()/../../../ncs:member]/ncs:module[ncs:name='Cisco-IOS-XR-snmp-test-trap-act']";
      tailf:action interface-link-down {
        tailf:actionpoint ncsproxy {
          tailf:internal;
        }
        description
          "Generate IF-MIB::linkDown";
        input {
          leaf ifindex {
            description
              "interface index for which to generate LinkDown trap";
            type uint32 {
              range "1..2147483647";
            }
          }
        }
      }
    }
  }
  augment "/ncs:devices/ncs:device/ncs:rpc" {
    container rpc-interface-link-up {
      tailf:ncs-device-type "netconf";
      tailf:display-when "not(../../ncs:module) or ../../ncs:module[ncs:name='Cisco-IOS-XR-snmp-test-trap-act']";
      tailf:action interface-link-up {
        tailf:actionpoint ncsproxy {
          tailf:internal;
        }
        description
          "Generate IF-MIB::linkUp";
        input {
          leaf ifindex {
            description
              "interface index for which to generate LinkUp trap";
            type uint32 {
              range "1..2147483647";
            }
          }
        }
      }
    }
  }
  augment "/ncs:devices/ncs:device-group/ncs:ned-id/ncs:rpc" {
    container rpc-interface-link-up {
      tailf:ncs-device-type "netconf";
      tailf:display-when "/ncs:devices/ncs:device[ncs:name=current()/../../../ncs:member]/ncs:module[ncs:name='Cisco-IOS-XR-snmp-test-trap-act']";
      tailf:action interface-link-up {
        tailf:actionpoint ncsproxy {
          tailf:internal;
        }
        description
          "Generate IF-MIB::linkUp";
        input {
          leaf ifindex {
            description
              "interface index for which to generate LinkUp trap";
            type uint32 {
              range "1..2147483647";
            }
          }
        }
      }
    }
  }
  augment "/ncs:devices/ncs:device/ncs:rpc" {
    container rpc-snmp-warm-start {
      tailf:ncs-device-type "netconf";
      tailf:display-when "not(../../ncs:module) or ../../ncs:module[ncs:name='Cisco-IOS-XR-snmp-test-trap-act']";
      tailf:action snmp-warm-start {
        tailf:actionpoint ncsproxy {
          tailf:internal;
        }
        description
          "Generate SNMPv2-MIB::warmStart";
      }
    }
  }
  augment "/ncs:devices/ncs:device-group/ncs:ned-id/ncs:rpc" {
    container rpc-snmp-warm-start {
      tailf:ncs-device-type "netconf";
      tailf:display-when "/ncs:devices/ncs:device[ncs:name=current()/../../../ncs:member]/ncs:module[ncs:name='Cisco-IOS-XR-snmp-test-trap-act']";
      tailf:action snmp-warm-start {
        tailf:actionpoint ncsproxy {
          tailf:internal;
        }
        description
          "Generate SNMPv2-MIB::warmStart";
      }
    }
  }
  augment "/ncs:devices/ncs:device/ncs:rpc" {
    container rpc-snmp-cold-start {
      tailf:ncs-device-type "netconf";
      tailf:display-when "not(../../ncs:module) or ../../ncs:module[ncs:name='Cisco-IOS-XR-snmp-test-trap-act']";
      tailf:action snmp-cold-start {
        tailf:actionpoint ncsproxy {
          tailf:internal;
        }
        description
          "Generate SNMPv2-MIB::coldStart";
      }
    }
  }
  augment "/ncs:devices/ncs:device-group/ncs:ned-id/ncs:rpc" {
    container rpc-snmp-cold-start {
      tailf:ncs-device-type "netconf";
      tailf:display-when "/ncs:devices/ncs:device[ncs:name=current()/../../../ncs:member]/ncs:module[ncs:name='Cisco-IOS-XR-snmp-test-trap-act']";
      tailf:action snmp-cold-start {
        tailf:actionpoint ncsproxy {
          tailf:internal;
        }
        description
          "Generate SNMPv2-MIB::coldStart";
      }
    }
  }
}
