module Cisco-IOS-XR-tunnel-l2tun-oper {
  // Generated by yanger -t ncs
  tailf:mount-id f5500-nc-1.0:f5500-nc-1.0;
  tailf:ncs-device-type "netconf";

  namespace "http://cisco.com/ns/yang/Cisco-IOS-XR-tunnel-l2tun-oper";
  prefix Cisco-IOS-XR-tunnel-l2tun-oper;

  import Cisco-IOS-XR-types {
    prefix xr;
  }
  include Cisco-IOS-XR-tunnel-l2tun-oper-sub1 {
    revision-date 2018-11-01;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR tunnel-l2tun package operational data.

     This module contains definitions
     for the following management objects:
       l2tp: L2TP operational data
       l2tpv2: l2tpv2

     Copyright (c) 2013-2018 by Cisco Systems, Inc.
     All rights reserved.";

  revision 2018-11-01 {
    description
      "Added Yang support show l2tpv2 internal.";
  }
  revision 2017-09-07 {
    description
      "Fixed type translation error.";
  }
  revision 2015-11-09 {
    description
      "IOS XR 6.0 revision.";
  }

  grouping ncs_template_CONTROL {
    description
      "Common node of counters, counters";
    container control {
      description
        "L2TP control messages counters";
      container tunnel-xr {
        description
          "L2TP control tunnel messages counters";
        container authentication {
          description
            "Tunnel authentication counters";
          uses ncs_template_L2TP-AUTHEN-STATS-DATA;
        }
        container global {
          description
            "Tunnel counters";
          uses ncs_template_L2TP-CTRL-MSG-STATS-GLOBAL-DATA;
        }
      }
      container tunnels {
        description
          "Table of tunnel IDs of control message counters";
        list tunnel {
          // NCS patched for predictable order
          ordered-by user;
          key "tunnel-id";
          description
            "L2TP tunnel control message counters";
          leaf tunnel-id {
            type string;
            description
              "L2TP tunnel ID";
          }
          uses ncs_template_L2TP-CTRL-MSG-STATS-DATA;
        }
      }
    }
  }

  grouping ncs_template_SESSION-TABLE {
    description
      "Common node of node, node";
    container sessions {
      description
        "List of session IDs";
      list session {
        // NCS patched for predictable order
        ordered-by user;
        key "local-tunnel-id local-session-id";
        description
          "L2TP information for a particular session";
        leaf local-tunnel-id {
          type string;
          description
            "Local tunnel ID";
        }
        leaf local-session-id {
          type string;
          description
            "Local session ID";
        }
        uses ncs_template_L2TP-SESSION-INFO;
      }
    }
  }

  grouping ncs_template_SESSION {
    description
      "Common node of node, node";
    container session {
      description
        "L2TP control messages counters";
      container unavailable {
        description
          "L2TP session unavailable  information";
        uses ncs_template_L2TP-SESSION-ID-HOLD-DB-DATA;
      }
    }
  }

  grouping ncs_template_TUNNEL-CONFIGURATION-TABLE {
    description
      "Common node of node, node";
    container tunnel-configurations {
      description
        "List of tunnel IDs";
      list tunnel-configuration {
        // NCS patched for predictable order
        ordered-by user;
        key "local-tunnel-id";
        description
          "L2TP tunnel information";
        leaf local-tunnel-id {
          type string;
          description
            "Local tunnel ID";
        }
        uses ncs_template_L2TP-CC-CFG-DATA;
      }
    }
  }

  grouping ncs_template_TUNNEL-TABLE {
    description
      "Common node of node, node";
    container tunnels {
      description
        "List of tunnel IDs";
      list tunnel {
        // NCS patched for predictable order
        ordered-by user;
        key "local-tunnel-id";
        description
          "L2TP tunnel  information";
        leaf local-tunnel-id {
          type string;
          description
            "Local tunnel ID";
        }
        uses ncs_template_L2TP-CC-INFO;
      }
    }
  }

  grouping ncs_template_INTERNAL {
    description
      "Common node of node, node";
    container internal {
      description
        "L2TP v2/v3 internal information";
      uses ncs_template_L2TP-INTERNAL-STATS-BAG-DATA;
    }
  }

  grouping ncs_template_COUNTER-HIST-FAIL {
    description
      "Common node of node, node";
    container counter-hist-fail {
      description
        "Failure events leading to disconnection";
      uses ncs_template_L2TP-HIST-FAIL-STATS-BAG-DATA;
    }
  }

  grouping ncs_template_CLASS-TABLE {
    description
      "Common node of node, node";
    container classes {
      description
        "List of L2TP class names";
      list class {
        // NCS patched for predictable order
        ordered-by user;
        key "class-name";
        description
          "L2TP class name";
        leaf class-name {
          type string;
          description
            "L2TP class name";
        }
        uses ncs_template_L2TP-CC-CLASS-DATA;
      }
    }
  }

  grouping ncs_rpc_notif_CONTROL {
    description
      "Common node of counters, counters";
    container control {
      description
        "L2TP control messages counters";
      container tunnel-xr {
        description
          "L2TP control tunnel messages counters";
        container authentication {
          description
            "Tunnel authentication counters";
          uses ncs_rpc_notif_L2TP-AUTHEN-STATS-DATA;
        }
        container global {
          description
            "Tunnel counters";
          uses ncs_rpc_notif_L2TP-CTRL-MSG-STATS-GLOBAL-DATA;
        }
      }
      container tunnels {
        description
          "Table of tunnel IDs of control message counters";
        list tunnel {
          key "tunnel-id";
          description
            "L2TP tunnel control message counters";
          leaf tunnel-id {
            type uint32;
            description
              "L2TP tunnel ID";
          }
          uses ncs_rpc_notif_L2TP-CTRL-MSG-STATS-DATA;
        }
      }
    }
  }

  grouping ncs_rpc_notif_SESSION-TABLE {
    description
      "Common node of node, node";
    container sessions {
      description
        "List of session IDs";
      list session {
        key "local-tunnel-id local-session-id";
        description
          "L2TP information for a particular session";
        leaf local-tunnel-id {
          type uint32;
          description
            "Local tunnel ID";
        }
        leaf local-session-id {
          type uint32;
          description
            "Local session ID";
        }
        uses ncs_rpc_notif_L2TP-SESSION-INFO;
      }
    }
  }

  grouping ncs_rpc_notif_SESSION {
    description
      "Common node of node, node";
    container session {
      description
        "L2TP control messages counters";
      container unavailable {
        description
          "L2TP session unavailable  information";
        uses ncs_rpc_notif_L2TP-SESSION-ID-HOLD-DB-DATA;
      }
    }
  }

  grouping ncs_rpc_notif_TUNNEL-CONFIGURATION-TABLE {
    description
      "Common node of node, node";
    container tunnel-configurations {
      description
        "List of tunnel IDs";
      list tunnel-configuration {
        key "local-tunnel-id";
        description
          "L2TP tunnel information";
        leaf local-tunnel-id {
          type uint32;
          description
            "Local tunnel ID";
        }
        uses ncs_rpc_notif_L2TP-CC-CFG-DATA;
      }
    }
  }

  grouping ncs_rpc_notif_TUNNEL-TABLE {
    description
      "Common node of node, node";
    container tunnels {
      description
        "List of tunnel IDs";
      list tunnel {
        key "local-tunnel-id";
        description
          "L2TP tunnel  information";
        leaf local-tunnel-id {
          type uint32;
          description
            "Local tunnel ID";
        }
        uses ncs_rpc_notif_L2TP-CC-INFO;
      }
    }
  }

  grouping ncs_rpc_notif_INTERNAL {
    description
      "Common node of node, node";
    container internal {
      description
        "L2TP v2/v3 internal information";
      uses ncs_rpc_notif_L2TP-INTERNAL-STATS-BAG-DATA;
    }
  }

  grouping ncs_rpc_notif_COUNTER-HIST-FAIL {
    description
      "Common node of node, node";
    container counter-hist-fail {
      description
        "Failure events leading to disconnection";
      uses ncs_rpc_notif_L2TP-HIST-FAIL-STATS-BAG-DATA;
    }
  }

  grouping ncs_rpc_notif_CLASS-TABLE {
    description
      "Common node of node, node";
    container classes {
      description
        "List of L2TP class names";
      list class {
        key "class-name";
        description
          "L2TP class name";
        leaf class-name {
          type xr:Cisco-ios-xr-string {
            length "1..31";
          }
          description
            "L2TP class name";
        }
        uses ncs_rpc_notif_L2TP-CC-CLASS-DATA;
      }
    }
  }

  grouping live_ncs_CONTROL {
    description
      "Common node of counters, counters";
    container control {
      description
        "L2TP control messages counters";
      container tunnel-xr {
        description
          "L2TP control tunnel messages counters";
        container authentication {
          description
            "Tunnel authentication counters";
          uses live_ncs_L2TP-AUTHEN-STATS-DATA;
        }
        container global {
          description
            "Tunnel counters";
          uses live_ncs_L2TP-CTRL-MSG-STATS-GLOBAL-DATA;
        }
      }
      container tunnels {
        description
          "Table of tunnel IDs of control message counters";
        list tunnel {
          key "tunnel-id";
          description
            "L2TP tunnel control message counters";
          leaf tunnel-id {
            type uint32;
            description
              "L2TP tunnel ID";
          }
          uses live_ncs_L2TP-CTRL-MSG-STATS-DATA;
        }
      }
    }
  }

  grouping live_ncs_SESSION-TABLE {
    description
      "Common node of node, node";
    container sessions {
      description
        "List of session IDs";
      list session {
        key "local-tunnel-id local-session-id";
        description
          "L2TP information for a particular session";
        leaf local-tunnel-id {
          type uint32;
          description
            "Local tunnel ID";
        }
        leaf local-session-id {
          type uint32;
          description
            "Local session ID";
        }
        uses live_ncs_L2TP-SESSION-INFO;
      }
    }
  }

  grouping live_ncs_SESSION {
    description
      "Common node of node, node";
    container session {
      description
        "L2TP control messages counters";
      container unavailable {
        description
          "L2TP session unavailable  information";
        uses live_ncs_L2TP-SESSION-ID-HOLD-DB-DATA;
      }
    }
  }

  grouping live_ncs_TUNNEL-CONFIGURATION-TABLE {
    description
      "Common node of node, node";
    container tunnel-configurations {
      description
        "List of tunnel IDs";
      list tunnel-configuration {
        key "local-tunnel-id";
        description
          "L2TP tunnel information";
        leaf local-tunnel-id {
          type uint32;
          description
            "Local tunnel ID";
        }
        uses live_ncs_L2TP-CC-CFG-DATA;
      }
    }
  }

  grouping live_ncs_TUNNEL-TABLE {
    description
      "Common node of node, node";
    container tunnels {
      description
        "List of tunnel IDs";
      list tunnel {
        key "local-tunnel-id";
        description
          "L2TP tunnel  information";
        leaf local-tunnel-id {
          type uint32;
          description
            "Local tunnel ID";
        }
        uses live_ncs_L2TP-CC-INFO;
      }
    }
  }

  grouping live_ncs_INTERNAL {
    description
      "Common node of node, node";
    container internal {
      description
        "L2TP v2/v3 internal information";
      uses live_ncs_L2TP-INTERNAL-STATS-BAG-DATA;
    }
  }

  grouping live_ncs_COUNTER-HIST-FAIL {
    description
      "Common node of node, node";
    container counter-hist-fail {
      description
        "Failure events leading to disconnection";
      uses live_ncs_L2TP-HIST-FAIL-STATS-BAG-DATA;
    }
  }

  grouping live_ncs_CLASS-TABLE {
    description
      "Common node of node, node";
    container classes {
      description
        "List of L2TP class names";
      list class {
        key "class-name";
        description
          "L2TP class name";
        leaf class-name {
          type xr:Cisco-ios-xr-string {
            length "1..31";
          }
          description
            "L2TP class name";
        }
        uses live_ncs_L2TP-CC-CLASS-DATA;
      }
    }
  }

  grouping CONTROL {
    description
      "Common node of counters, counters";
    container control {
      description
        "L2TP control messages counters";
      container tunnel-xr {
        description
          "L2TP control tunnel messages counters";
        container authentication {
          description
            "Tunnel authentication counters";
          uses L2TP-AUTHEN-STATS-DATA;
        }
        container global {
          description
            "Tunnel counters";
          uses L2TP-CTRL-MSG-STATS-GLOBAL-DATA;
        }
      }
      container tunnels {
        description
          "Table of tunnel IDs of control message counters";
        list tunnel {
          key "tunnel-id";
          description
            "L2TP tunnel control message counters";
          leaf tunnel-id {
            type uint32;
            description
              "L2TP tunnel ID";
          }
          uses L2TP-CTRL-MSG-STATS-DATA;
        }
      }
    }
  }

  grouping SESSION-TABLE {
    description
      "Common node of node, node";
    container sessions {
      description
        "List of session IDs";
      list session {
        key "local-tunnel-id local-session-id";
        description
          "L2TP information for a particular session";
        leaf local-tunnel-id {
          type uint32;
          description
            "Local tunnel ID";
        }
        leaf local-session-id {
          type uint32;
          description
            "Local session ID";
        }
        uses L2TP-SESSION-INFO;
      }
    }
  }

  grouping SESSION {
    description
      "Common node of node, node";
    container session {
      description
        "L2TP control messages counters";
      container unavailable {
        description
          "L2TP session unavailable  information";
        uses L2TP-SESSION-ID-HOLD-DB-DATA;
      }
    }
  }

  grouping TUNNEL-CONFIGURATION-TABLE {
    description
      "Common node of node, node";
    container tunnel-configurations {
      description
        "List of tunnel IDs";
      list tunnel-configuration {
        key "local-tunnel-id";
        description
          "L2TP tunnel information";
        leaf local-tunnel-id {
          type uint32;
          description
            "Local tunnel ID";
        }
        uses L2TP-CC-CFG-DATA;
      }
    }
  }

  grouping TUNNEL-TABLE {
    description
      "Common node of node, node";
    container tunnels {
      description
        "List of tunnel IDs";
      list tunnel {
        key "local-tunnel-id";
        description
          "L2TP tunnel  information";
        leaf local-tunnel-id {
          type uint32;
          description
            "Local tunnel ID";
        }
        uses L2TP-CC-INFO;
      }
    }
  }

  grouping INTERNAL {
    description
      "Common node of node, node";
    container internal {
      description
        "L2TP v2/v3 internal information";
      uses L2TP-INTERNAL-STATS-BAG-DATA;
    }
  }

  grouping COUNTER-HIST-FAIL {
    description
      "Common node of node, node";
    container counter-hist-fail {
      description
        "Failure events leading to disconnection";
      uses L2TP-HIST-FAIL-STATS-BAG-DATA;
    }
  }

  grouping CLASS-TABLE {
    description
      "Common node of node, node";
    container classes {
      description
        "List of L2TP class names";
      list class {
        key "class-name";
        description
          "L2TP class name";
        leaf class-name {
          type xr:Cisco-ios-xr-string {
            length "1..31";
          }
          description
            "L2TP class name";
        }
        uses L2TP-CC-CLASS-DATA;
      }
    }
  }

  augment "/ncs:devices/ncs:device/ncs:config" {
    // NCS drop config false container l2tp
    // NCS drop config false container l2tpv2
  }
  augment "/ncs:devices/ncs:device/ncs:live-status" {
    container l2tp {
      tailf:ncs-device-type "netconf";
      tailf:display-when "not(../../ncs:module) or ../../ncs:module[ncs:name='Cisco-IOS-XR-tunnel-l2tun-oper'] or (../../ncs:live-status-protocol[not(ncs:capability)]) or (../../ncs:live-status-protocol/ncs:capability/ncs:module[.='Cisco-IOS-XR-tunnel-l2tun-oper'])";
      description
        "L2TP operational data";
      container nodes {
        description
          "List of nodes for which subscriber data is
           collected";
        list node {
          key "node-name";
          description
            "Subscriber data for a particular node";
          container counters {
            description
              "L2TP control messages counters";
            uses live_ncs_CONTROL;
          }
          leaf node-name {
            type xr:Node-id;
            description
              "Node name";
          }
          uses live_ncs_TUNNEL-CONFIGURATION-TABLE;
          uses live_ncs_COUNTER-HIST-FAIL;
          uses live_ncs_CLASS-TABLE;
          uses live_ncs_TUNNEL-TABLE;
          uses live_ncs_SESSION-TABLE;
          uses live_ncs_SESSION;
          uses live_ncs_INTERNAL;
        }
      }
    }
    container l2tpv2 {
      tailf:ncs-device-type "netconf";
      tailf:display-when "not(../../ncs:module) or ../../ncs:module[ncs:name='Cisco-IOS-XR-tunnel-l2tun-oper'] or (../../ncs:live-status-protocol[not(ncs:capability)]) or (../../ncs:live-status-protocol/ncs:capability/ncs:module[.='Cisco-IOS-XR-tunnel-l2tun-oper'])";
      description
        "l2tpv2";
      container nodes {
        description
          "List of nodes for which subscriber data is
           collected";
        list node {
          key "node-name";
          description
            "Subscriber data for a particular node";
          container counters {
            description
              "L2TP control messages counters";
            container forwarding {
              description
                "L2TP forwarding messages counters";
              container sessions {
                description
                  "List of class and session IDs";
                list session {
                  key "tunnel-id session-id";
                  description
                    "L2TP information for a particular session";
                  leaf tunnel-id {
                    type uint32;
                    description
                      "Local tunnel ID";
                  }
                  leaf session-id {
                    type uint32;
                    description
                      "Local session ID";
                  }
                  uses live_ncs_L2TP-SESS-FWD-STATS;
                }
              }
            }
            uses live_ncs_CONTROL;
          }
          container statistics {
            description
              "L2TP v2 statistics information";
            uses live_ncs_L2TPV2-STATS-DATA;
          }
          container tunnel {
            description
              "L2TPv2 tunnel ";
            container accounting {
              description
                "Tunnel accounting counters";
              container statistics {
                description
                  "Tunnel accounting statistics";
                uses live_ncs_L2TPV2-CC-ACCT-STATS-DATA;
              }
            }
          }
          leaf node-name {
            type xr:Node-id;
            description
              "Node name";
          }
          uses live_ncs_TUNNEL-CONFIGURATION-TABLE;
          uses live_ncs_COUNTER-HIST-FAIL;
          uses live_ncs_CLASS-TABLE;
          uses live_ncs_TUNNEL-TABLE;
          uses live_ncs_SESSION-TABLE;
          uses live_ncs_SESSION;
          uses live_ncs_INTERNAL;
        }
      }
    }
  }
  augment "/ncs:devices/ncs:template/ncs:ned-id/ncs:config" {
    // NCS drop config false container l2tp
    // NCS drop config false container l2tpv2
  }
}
