module Cisco-IOS-XR-manageability-perfmgmt-oper {
  // Generated by yanger -t ncs
  tailf:mount-id f5500-nc-1.0:f5500-nc-1.0;
  tailf:ncs-device-type "netconf";

  namespace "http://cisco.com/ns/yang/Cisco-IOS-XR-manageability-perfmgmt-oper";
  prefix Cisco-IOS-XR-manageability-perfmgmt-oper;

  import ietf-inet-types {
    prefix inet;
  }
  import Cisco-IOS-XR-types {
    prefix xr;
  }
  include Cisco-IOS-XR-manageability-perfmgmt-oper-sub1 {
    revision-date 2017-09-07;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR manageability-perfmgmt package operational data.

     This module contains definitions
     for the following management objects:
       perf-mgmt: Performance Management agent operational data

     Copyright (c) 2013-2018 by Cisco Systems, Inc.
     All rights reserved.";

  revision 2017-09-07 {
    description
      "Fixed type translation error.";
  }
  revision 2015-11-09 {
    description
      "IOS XR 6.0 revision.";
  }

  typedef Pm-sample-id {
    type uint32;
    description
      "Pm sample id";
  }

  typedef Pm-process-id {
    type uint32;
    description
      "Pm process id";
  }

  grouping ncs_template_MPLS {
    description
      "Common node of periodic, monitor";
    container mpls {
      description
        "Collected MPLS data";
      container ldp-neighbors {
        description
          "LDP neighbors for which statistics are
           collected";
        list ldp-neighbor {
          // NCS patched for predictable order
          ordered-by user;
          key "nbr";
          description
            "Samples for a particular LDP neighbor";
          container samples {
            description
              "Samples for a particular LDP neighbor";
            list sample {
              // NCS patched for predictable order
              ordered-by user;
              key "sample-id";
              description
                "LDP neighbor statistics sample";
              leaf sample-id {
                type string;
                description
                  "Sample ID";
              }
              uses ncs_template_PM-MPLS-LDP-BAG;
            }
          }
          leaf nbr {
            type string;
            description
              "Neighbor Address";
          }
        }
      }
    }
  }

  grouping ncs_template_INTERFACE {
    description
      "Common node of periodic, monitor";
    container interface {
      description
        "Collected Interface data";
      container generic-counter-interfaces {
        description
          "Interfaces for which Generic Counters are
           collected";
        list generic-counter-interface {
          // NCS patched for predictable order
          ordered-by user;
          key "interface-name";
          description
            "Samples for a particular interface";
          container samples {
            description
              "Generic Counter samples for an interface";
            list sample {
              // NCS patched for predictable order
              ordered-by user;
              key "sample-id";
              description
                "Generic Counters sample";
              leaf sample-id {
                type string;
                description
                  "Sample ID";
              }
              uses ncs_template_PM-INTERFACE-GENERIC-BAG;
            }
          }
          leaf interface-name {
            type string;
            description
              "Interface Name";
          }
        }
      }
      container basic-counter-interfaces {
        description
          "Interfaces for which Basic Counters are
           collected";
        list basic-counter-interface {
          // NCS patched for predictable order
          ordered-by user;
          key "interface-name";
          description
            "Samples for a particular interface";
          container samples {
            description
              "Basic Counter samples for an interface";
            list sample {
              // NCS patched for predictable order
              ordered-by user;
              key "sample-id";
              description
                "Basic Counters sample";
              leaf sample-id {
                type string;
                description
                  "Sample ID";
              }
              uses ncs_template_PM-INTERFACE-BASIC-STATS;
            }
          }
          leaf interface-name {
            type string;
            description
              "Interface Name";
          }
        }
      }
      container data-rate-interfaces {
        description
          "Interfaces for which Data Rates are collected";
        list data-rate-interface {
          // NCS patched for predictable order
          ordered-by user;
          key "interface-name";
          description
            "Samples for a particular interface";
          container samples {
            description
              "Data Rate samples for an interface";
            list sample {
              // NCS patched for predictable order
              ordered-by user;
              key "sample-id";
              description
                "Data Rates sample";
              leaf sample-id {
                type string;
                description
                  "Sample ID";
              }
              uses ncs_template_PM-INTERFACE-DATARATE-BAG;
            }
          }
          leaf interface-name {
            type string;
            description
              "Interface Name";
          }
        }
      }
    }
  }

  grouping ncs_template_NODE-TABLE {
    description
      "Common node of periodic, monitor";
    container nodes {
      description
        "Nodes for which data is collected";
      list node {
        // NCS patched for predictable order
        ordered-by user;
        key "node-id";
        description
          "Node Instance";
        container sample-xr {
          description
            "Node CPU data";
          list sample {
            // NCS patched for predictable order
            ordered-by user;
            key "sample-id";
            description
              "Node CPU data sample";
            leaf sample-id {
              type string;
              description
                "Sample ID";
            }
            uses ncs_template_PM-NODE-CPU-BAG;
          }
        }
        container processes {
          description
            "Processes data";
          list process {
            // NCS patched for predictable order
            ordered-by user;
            key "process-id";
            description
              "Process data";
            container samples {
              description
                "Process data";
              list sample {
                // NCS patched for predictable order
                ordered-by user;
                key "sample-id";
                description
                  "Process data sample";
                leaf sample-id {
                  type string;
                  description
                    "Sample ID";
                }
                uses ncs_template_PM-NODE-PROCESS-BAG;
              }
            }
            leaf process-id {
              type string;
              description
                "Process ID";
            }
          }
        }
        container samples {
          description
            "Node Memory data";
          list sample {
            // NCS patched for predictable order
            ordered-by user;
            key "sample-id";
            description
              "Node Memory data sample";
            leaf sample-id {
              type string;
              description
                "Sample ID";
            }
            uses ncs_template_PM-NODE-MEM-BAG;
          }
        }
        leaf node-id {
          type string;
          description
            "Node ID";
        }
      }
    }
  }

  grouping ncs_template_OSPF {
    description
      "Common node of periodic, monitor";
    container ospf {
      description
        "Collected OSPF data";
      container ospfv2-protocol-instances {
        description
          "OSPF v2 instances for which protocol statistics
           are collected";
        list ospfv2-protocol-instance {
          // NCS patched for predictable order
          ordered-by user;
          key "instance-name";
          description
            "Protocol samples for a particular OSPF v2
             instance";
          container samples {
            description
              "Sample Table for an OSPV v2 instance";
            list sample {
              // NCS patched for predictable order
              ordered-by user;
              key "sample-id";
              description
                "Generic Counters sample";
              leaf sample-id {
                type string;
                description
                  "Sample ID";
              }
              uses ncs_template_PM-OSPF-V2PROTO-BAG;
            }
          }
          leaf instance-name {
            type string;
            description
              "OSPF Instance Name";
          }
        }
      }
      container ospfv3-protocol-instances {
        description
          "OSPF v3 instances for which protocol statistics
           are collected";
        list ospfv3-protocol-instance {
          // NCS patched for predictable order
          ordered-by user;
          key "instance-name";
          description
            "Protocol samples for a particular OSPF v3
             instance";
          container samples {
            description
              "Sample Table for an OSPV v3 instance";
            list sample {
              // NCS patched for predictable order
              ordered-by user;
              key "sample-id";
              description
                "Generic Counters sample";
              leaf sample-id {
                type string;
                description
                  "Sample ID";
              }
              uses ncs_template_PM-OSPF-V3PROTO-BAG;
            }
          }
          leaf instance-name {
            type string;
            description
              "OSPF Instance Name";
          }
        }
      }
    }
  }

  grouping ncs_template_BGP {
    description
      "Common node of periodic, monitor";
    container bgp {
      description
        "Collected BGP data";
      container bgp-neighbors {
        description
          "Neighbors for which statistics are collected";
        list bgp-neighbor {
          // NCS patched for predictable order
          ordered-by user;
          key "ip-address";
          description
            "Samples for particular neighbor";
          container samples {
            description
              "Sample Table for a BGP neighbor";
            list sample {
              // NCS patched for predictable order
              ordered-by user;
              key "sample-id";
              description
                "Neighbor statistics sample";
              leaf sample-id {
                type string;
                description
                  "Sample ID";
              }
              uses ncs_template_PM-BGP-NBR-BAG;
            }
          }
          leaf ip-address {
            type string;
            description
              "BGP Neighbor Identifier";
          }
        }
      }
    }
  }

  grouping ncs_rpc_notif_MPLS {
    description
      "Common node of periodic, monitor";
    container mpls {
      description
        "Collected MPLS data";
      container ldp-neighbors {
        description
          "LDP neighbors for which statistics are
           collected";
        list ldp-neighbor {
          key "nbr";
          description
            "Samples for a particular LDP neighbor";
          container samples {
            description
              "Samples for a particular LDP neighbor";
            list sample {
              key "sample-id";
              description
                "LDP neighbor statistics sample";
              leaf sample-id {
                type Pm-sample-id;
                description
                  "Sample ID";
              }
              uses ncs_rpc_notif_PM-MPLS-LDP-BAG;
            }
          }
          leaf nbr {
            type inet:ipv4-address-no-zone;
            description
              "Neighbor Address";
          }
        }
      }
    }
  }

  grouping ncs_rpc_notif_INTERFACE {
    description
      "Common node of periodic, monitor";
    container interface {
      description
        "Collected Interface data";
      container generic-counter-interfaces {
        description
          "Interfaces for which Generic Counters are
           collected";
        list generic-counter-interface {
          key "interface-name";
          description
            "Samples for a particular interface";
          container samples {
            description
              "Generic Counter samples for an interface";
            list sample {
              key "sample-id";
              description
                "Generic Counters sample";
              leaf sample-id {
                type Pm-sample-id;
                description
                  "Sample ID";
              }
              uses ncs_rpc_notif_PM-INTERFACE-GENERIC-BAG;
            }
          }
          leaf interface-name {
            type xr:Interface-name;
            description
              "Interface Name";
          }
        }
      }
      container basic-counter-interfaces {
        description
          "Interfaces for which Basic Counters are
           collected";
        list basic-counter-interface {
          key "interface-name";
          description
            "Samples for a particular interface";
          container samples {
            description
              "Basic Counter samples for an interface";
            list sample {
              key "sample-id";
              description
                "Basic Counters sample";
              leaf sample-id {
                type Pm-sample-id;
                description
                  "Sample ID";
              }
              uses ncs_rpc_notif_PM-INTERFACE-BASIC-STATS;
            }
          }
          leaf interface-name {
            type xr:Interface-name;
            description
              "Interface Name";
          }
        }
      }
      container data-rate-interfaces {
        description
          "Interfaces for which Data Rates are collected";
        list data-rate-interface {
          key "interface-name";
          description
            "Samples for a particular interface";
          container samples {
            description
              "Data Rate samples for an interface";
            list sample {
              key "sample-id";
              description
                "Data Rates sample";
              leaf sample-id {
                type Pm-sample-id;
                description
                  "Sample ID";
              }
              uses ncs_rpc_notif_PM-INTERFACE-DATARATE-BAG;
            }
          }
          leaf interface-name {
            type xr:Interface-name;
            description
              "Interface Name";
          }
        }
      }
    }
  }

  grouping ncs_rpc_notif_NODE-TABLE {
    description
      "Common node of periodic, monitor";
    container nodes {
      description
        "Nodes for which data is collected";
      list node {
        key "node-id";
        description
          "Node Instance";
        container sample-xr {
          description
            "Node CPU data";
          list sample {
            key "sample-id";
            description
              "Node CPU data sample";
            leaf sample-id {
              type Pm-sample-id;
              description
                "Sample ID";
            }
            uses ncs_rpc_notif_PM-NODE-CPU-BAG;
          }
        }
        container processes {
          description
            "Processes data";
          list process {
            key "process-id";
            description
              "Process data";
            container samples {
              description
                "Process data";
              list sample {
                key "sample-id";
                description
                  "Process data sample";
                leaf sample-id {
                  type Pm-sample-id;
                  description
                    "Sample ID";
                }
                uses ncs_rpc_notif_PM-NODE-PROCESS-BAG;
              }
            }
            leaf process-id {
              type Pm-process-id;
              description
                "Process ID";
            }
          }
        }
        container samples {
          description
            "Node Memory data";
          list sample {
            key "sample-id";
            description
              "Node Memory data sample";
            leaf sample-id {
              type Pm-sample-id;
              description
                "Sample ID";
            }
            uses ncs_rpc_notif_PM-NODE-MEM-BAG;
          }
        }
        leaf node-id {
          type xr:Node-id;
          description
            "Node ID";
        }
      }
    }
  }

  grouping ncs_rpc_notif_OSPF {
    description
      "Common node of periodic, monitor";
    container ospf {
      description
        "Collected OSPF data";
      container ospfv2-protocol-instances {
        description
          "OSPF v2 instances for which protocol statistics
           are collected";
        list ospfv2-protocol-instance {
          key "instance-name";
          description
            "Protocol samples for a particular OSPF v2
             instance";
          container samples {
            description
              "Sample Table for an OSPV v2 instance";
            list sample {
              key "sample-id";
              description
                "Generic Counters sample";
              leaf sample-id {
                type Pm-sample-id;
                description
                  "Sample ID";
              }
              uses ncs_rpc_notif_PM-OSPF-V2PROTO-BAG;
            }
          }
          leaf instance-name {
            type xr:Cisco-ios-xr-string;
            description
              "OSPF Instance Name";
          }
        }
      }
      container ospfv3-protocol-instances {
        description
          "OSPF v3 instances for which protocol statistics
           are collected";
        list ospfv3-protocol-instance {
          key "instance-name";
          description
            "Protocol samples for a particular OSPF v3
             instance";
          container samples {
            description
              "Sample Table for an OSPV v3 instance";
            list sample {
              key "sample-id";
              description
                "Generic Counters sample";
              leaf sample-id {
                type Pm-sample-id;
                description
                  "Sample ID";
              }
              uses ncs_rpc_notif_PM-OSPF-V3PROTO-BAG;
            }
          }
          leaf instance-name {
            type xr:Cisco-ios-xr-string;
            description
              "OSPF Instance Name";
          }
        }
      }
    }
  }

  grouping ncs_rpc_notif_BGP {
    description
      "Common node of periodic, monitor";
    container bgp {
      description
        "Collected BGP data";
      container bgp-neighbors {
        description
          "Neighbors for which statistics are collected";
        list bgp-neighbor {
          key "ip-address";
          description
            "Samples for particular neighbor";
          container samples {
            description
              "Sample Table for a BGP neighbor";
            list sample {
              key "sample-id";
              description
                "Neighbor statistics sample";
              leaf sample-id {
                type Pm-sample-id;
                description
                  "Sample ID";
              }
              uses ncs_rpc_notif_PM-BGP-NBR-BAG;
            }
          }
          leaf ip-address {
            type inet:ipv4-address-no-zone;
            description
              "BGP Neighbor Identifier";
          }
        }
      }
    }
  }

  grouping live_ncs_MPLS {
    description
      "Common node of periodic, monitor";
    container mpls {
      description
        "Collected MPLS data";
      container ldp-neighbors {
        description
          "LDP neighbors for which statistics are
           collected";
        list ldp-neighbor {
          key "nbr";
          description
            "Samples for a particular LDP neighbor";
          container samples {
            description
              "Samples for a particular LDP neighbor";
            list sample {
              key "sample-id";
              description
                "LDP neighbor statistics sample";
              leaf sample-id {
                type Pm-sample-id;
                description
                  "Sample ID";
              }
              uses live_ncs_PM-MPLS-LDP-BAG;
            }
          }
          leaf nbr {
            type inet:ipv4-address-no-zone;
            description
              "Neighbor Address";
          }
        }
      }
    }
  }

  grouping live_ncs_INTERFACE {
    description
      "Common node of periodic, monitor";
    container interface {
      description
        "Collected Interface data";
      container generic-counter-interfaces {
        description
          "Interfaces for which Generic Counters are
           collected";
        list generic-counter-interface {
          key "interface-name";
          description
            "Samples for a particular interface";
          container samples {
            description
              "Generic Counter samples for an interface";
            list sample {
              key "sample-id";
              description
                "Generic Counters sample";
              leaf sample-id {
                type Pm-sample-id;
                description
                  "Sample ID";
              }
              uses live_ncs_PM-INTERFACE-GENERIC-BAG;
            }
          }
          leaf interface-name {
            type xr:Interface-name;
            description
              "Interface Name";
          }
        }
      }
      container basic-counter-interfaces {
        description
          "Interfaces for which Basic Counters are
           collected";
        list basic-counter-interface {
          key "interface-name";
          description
            "Samples for a particular interface";
          container samples {
            description
              "Basic Counter samples for an interface";
            list sample {
              key "sample-id";
              description
                "Basic Counters sample";
              leaf sample-id {
                type Pm-sample-id;
                description
                  "Sample ID";
              }
              uses live_ncs_PM-INTERFACE-BASIC-STATS;
            }
          }
          leaf interface-name {
            type xr:Interface-name;
            description
              "Interface Name";
          }
        }
      }
      container data-rate-interfaces {
        description
          "Interfaces for which Data Rates are collected";
        list data-rate-interface {
          key "interface-name";
          description
            "Samples for a particular interface";
          container samples {
            description
              "Data Rate samples for an interface";
            list sample {
              key "sample-id";
              description
                "Data Rates sample";
              leaf sample-id {
                type Pm-sample-id;
                description
                  "Sample ID";
              }
              uses live_ncs_PM-INTERFACE-DATARATE-BAG;
            }
          }
          leaf interface-name {
            type xr:Interface-name;
            description
              "Interface Name";
          }
        }
      }
    }
  }

  grouping live_ncs_NODE-TABLE {
    description
      "Common node of periodic, monitor";
    container nodes {
      description
        "Nodes for which data is collected";
      list node {
        key "node-id";
        description
          "Node Instance";
        container sample-xr {
          description
            "Node CPU data";
          list sample {
            key "sample-id";
            description
              "Node CPU data sample";
            leaf sample-id {
              type Pm-sample-id;
              description
                "Sample ID";
            }
            uses live_ncs_PM-NODE-CPU-BAG;
          }
        }
        container processes {
          description
            "Processes data";
          list process {
            key "process-id";
            description
              "Process data";
            container samples {
              description
                "Process data";
              list sample {
                key "sample-id";
                description
                  "Process data sample";
                leaf sample-id {
                  type Pm-sample-id;
                  description
                    "Sample ID";
                }
                uses live_ncs_PM-NODE-PROCESS-BAG;
              }
            }
            leaf process-id {
              type Pm-process-id;
              description
                "Process ID";
            }
          }
        }
        container samples {
          description
            "Node Memory data";
          list sample {
            key "sample-id";
            description
              "Node Memory data sample";
            leaf sample-id {
              type Pm-sample-id;
              description
                "Sample ID";
            }
            uses live_ncs_PM-NODE-MEM-BAG;
          }
        }
        leaf node-id {
          type xr:Node-id;
          description
            "Node ID";
        }
      }
    }
  }

  grouping live_ncs_OSPF {
    description
      "Common node of periodic, monitor";
    container ospf {
      description
        "Collected OSPF data";
      container ospfv2-protocol-instances {
        description
          "OSPF v2 instances for which protocol statistics
           are collected";
        list ospfv2-protocol-instance {
          key "instance-name";
          description
            "Protocol samples for a particular OSPF v2
             instance";
          container samples {
            description
              "Sample Table for an OSPV v2 instance";
            list sample {
              key "sample-id";
              description
                "Generic Counters sample";
              leaf sample-id {
                type Pm-sample-id;
                description
                  "Sample ID";
              }
              uses live_ncs_PM-OSPF-V2PROTO-BAG;
            }
          }
          leaf instance-name {
            type xr:Cisco-ios-xr-string;
            description
              "OSPF Instance Name";
          }
        }
      }
      container ospfv3-protocol-instances {
        description
          "OSPF v3 instances for which protocol statistics
           are collected";
        list ospfv3-protocol-instance {
          key "instance-name";
          description
            "Protocol samples for a particular OSPF v3
             instance";
          container samples {
            description
              "Sample Table for an OSPV v3 instance";
            list sample {
              key "sample-id";
              description
                "Generic Counters sample";
              leaf sample-id {
                type Pm-sample-id;
                description
                  "Sample ID";
              }
              uses live_ncs_PM-OSPF-V3PROTO-BAG;
            }
          }
          leaf instance-name {
            type xr:Cisco-ios-xr-string;
            description
              "OSPF Instance Name";
          }
        }
      }
    }
  }

  grouping live_ncs_BGP {
    description
      "Common node of periodic, monitor";
    container bgp {
      description
        "Collected BGP data";
      container bgp-neighbors {
        description
          "Neighbors for which statistics are collected";
        list bgp-neighbor {
          key "ip-address";
          description
            "Samples for particular neighbor";
          container samples {
            description
              "Sample Table for a BGP neighbor";
            list sample {
              key "sample-id";
              description
                "Neighbor statistics sample";
              leaf sample-id {
                type Pm-sample-id;
                description
                  "Sample ID";
              }
              uses live_ncs_PM-BGP-NBR-BAG;
            }
          }
          leaf ip-address {
            type inet:ipv4-address-no-zone;
            description
              "BGP Neighbor Identifier";
          }
        }
      }
    }
  }

  grouping MPLS {
    description
      "Common node of periodic, monitor";
    container mpls {
      description
        "Collected MPLS data";
      container ldp-neighbors {
        description
          "LDP neighbors for which statistics are
           collected";
        list ldp-neighbor {
          key "nbr";
          description
            "Samples for a particular LDP neighbor";
          container samples {
            description
              "Samples for a particular LDP neighbor";
            list sample {
              key "sample-id";
              description
                "LDP neighbor statistics sample";
              leaf sample-id {
                type Pm-sample-id;
                description
                  "Sample ID";
              }
              uses PM-MPLS-LDP-BAG;
            }
          }
          leaf nbr {
            type inet:ipv4-address-no-zone;
            description
              "Neighbor Address";
          }
        }
      }
    }
  }

  grouping INTERFACE {
    description
      "Common node of periodic, monitor";
    container interface {
      description
        "Collected Interface data";
      container generic-counter-interfaces {
        description
          "Interfaces for which Generic Counters are
           collected";
        list generic-counter-interface {
          key "interface-name";
          description
            "Samples for a particular interface";
          container samples {
            description
              "Generic Counter samples for an interface";
            list sample {
              key "sample-id";
              description
                "Generic Counters sample";
              leaf sample-id {
                type Pm-sample-id;
                description
                  "Sample ID";
              }
              uses PM-INTERFACE-GENERIC-BAG;
            }
          }
          leaf interface-name {
            type xr:Interface-name;
            description
              "Interface Name";
          }
        }
      }
      container basic-counter-interfaces {
        description
          "Interfaces for which Basic Counters are
           collected";
        list basic-counter-interface {
          key "interface-name";
          description
            "Samples for a particular interface";
          container samples {
            description
              "Basic Counter samples for an interface";
            list sample {
              key "sample-id";
              description
                "Basic Counters sample";
              leaf sample-id {
                type Pm-sample-id;
                description
                  "Sample ID";
              }
              uses PM-INTERFACE-BASIC-STATS;
            }
          }
          leaf interface-name {
            type xr:Interface-name;
            description
              "Interface Name";
          }
        }
      }
      container data-rate-interfaces {
        description
          "Interfaces for which Data Rates are collected";
        list data-rate-interface {
          key "interface-name";
          description
            "Samples for a particular interface";
          container samples {
            description
              "Data Rate samples for an interface";
            list sample {
              key "sample-id";
              description
                "Data Rates sample";
              leaf sample-id {
                type Pm-sample-id;
                description
                  "Sample ID";
              }
              uses PM-INTERFACE-DATARATE-BAG;
            }
          }
          leaf interface-name {
            type xr:Interface-name;
            description
              "Interface Name";
          }
        }
      }
    }
  }

  grouping NODE-TABLE {
    description
      "Common node of periodic, monitor";
    container nodes {
      description
        "Nodes for which data is collected";
      list node {
        key "node-id";
        description
          "Node Instance";
        container sample-xr {
          description
            "Node CPU data";
          list sample {
            key "sample-id";
            description
              "Node CPU data sample";
            leaf sample-id {
              type Pm-sample-id;
              description
                "Sample ID";
            }
            uses PM-NODE-CPU-BAG;
          }
        }
        container processes {
          description
            "Processes data";
          list process {
            key "process-id";
            description
              "Process data";
            container samples {
              description
                "Process data";
              list sample {
                key "sample-id";
                description
                  "Process data sample";
                leaf sample-id {
                  type Pm-sample-id;
                  description
                    "Sample ID";
                }
                uses PM-NODE-PROCESS-BAG;
              }
            }
            leaf process-id {
              type Pm-process-id;
              description
                "Process ID";
            }
          }
        }
        container samples {
          description
            "Node Memory data";
          list sample {
            key "sample-id";
            description
              "Node Memory data sample";
            leaf sample-id {
              type Pm-sample-id;
              description
                "Sample ID";
            }
            uses PM-NODE-MEM-BAG;
          }
        }
        leaf node-id {
          type xr:Node-id;
          description
            "Node ID";
        }
      }
    }
  }

  grouping OSPF {
    description
      "Common node of periodic, monitor";
    container ospf {
      description
        "Collected OSPF data";
      container ospfv2-protocol-instances {
        description
          "OSPF v2 instances for which protocol statistics
           are collected";
        list ospfv2-protocol-instance {
          key "instance-name";
          description
            "Protocol samples for a particular OSPF v2
             instance";
          container samples {
            description
              "Sample Table for an OSPV v2 instance";
            list sample {
              key "sample-id";
              description
                "Generic Counters sample";
              leaf sample-id {
                type Pm-sample-id;
                description
                  "Sample ID";
              }
              uses PM-OSPF-V2PROTO-BAG;
            }
          }
          leaf instance-name {
            type xr:Cisco-ios-xr-string;
            description
              "OSPF Instance Name";
          }
        }
      }
      container ospfv3-protocol-instances {
        description
          "OSPF v3 instances for which protocol statistics
           are collected";
        list ospfv3-protocol-instance {
          key "instance-name";
          description
            "Protocol samples for a particular OSPF v3
             instance";
          container samples {
            description
              "Sample Table for an OSPV v3 instance";
            list sample {
              key "sample-id";
              description
                "Generic Counters sample";
              leaf sample-id {
                type Pm-sample-id;
                description
                  "Sample ID";
              }
              uses PM-OSPF-V3PROTO-BAG;
            }
          }
          leaf instance-name {
            type xr:Cisco-ios-xr-string;
            description
              "OSPF Instance Name";
          }
        }
      }
    }
  }

  grouping BGP {
    description
      "Common node of periodic, monitor";
    container bgp {
      description
        "Collected BGP data";
      container bgp-neighbors {
        description
          "Neighbors for which statistics are collected";
        list bgp-neighbor {
          key "ip-address";
          description
            "Samples for particular neighbor";
          container samples {
            description
              "Sample Table for a BGP neighbor";
            list sample {
              key "sample-id";
              description
                "Neighbor statistics sample";
              leaf sample-id {
                type Pm-sample-id;
                description
                  "Sample ID";
              }
              uses PM-BGP-NBR-BAG;
            }
          }
          leaf ip-address {
            type inet:ipv4-address-no-zone;
            description
              "BGP Neighbor Identifier";
          }
        }
      }
    }
  }

  augment "/ncs:devices/ncs:device/ncs:config" {
    // NCS drop config false container 'perf-mgmt'
  }
  augment "/ncs:devices/ncs:device/ncs:live-status" {
    container perf-mgmt {
      tailf:ncs-device-type "netconf";
      tailf:display-when "not(../../ncs:module) or ../../ncs:module[ncs:name='Cisco-IOS-XR-manageability-perfmgmt-oper'] or (../../ncs:live-status-protocol[not(ncs:capability)]) or (../../ncs:live-status-protocol/ncs:capability/ncs:module[.='Cisco-IOS-XR-manageability-perfmgmt-oper'])";
      description
        "Performance Management agent operational data";
      container periodic {
        description
          "Data from periodic requests";
        uses live_ncs_OSPF;
        uses live_ncs_MPLS;
        uses live_ncs_NODE-TABLE;
        uses live_ncs_BGP;
        uses live_ncs_INTERFACE;
      }
      container monitor {
        description
          "Data from monitor (one history period) requests";
        uses live_ncs_OSPF;
        uses live_ncs_MPLS;
        uses live_ncs_NODE-TABLE;
        uses live_ncs_BGP;
        uses live_ncs_INTERFACE;
      }
    }
  }
  augment "/ncs:devices/ncs:template/ncs:ned-id/ncs:config" {
    // NCS drop config false container 'perf-mgmt'
  }
}
