module Cisco-IOS-XR-mpls-oam-oper {
  // Generated by yanger -t ncs
  tailf:mount-id f5500-nc-1.0:f5500-nc-1.0;
  tailf:ncs-device-type "netconf";

  namespace "http://cisco.com/ns/yang/Cisco-IOS-XR-mpls-oam-oper";
  prefix Cisco-IOS-XR-mpls-oam-oper;

  import Cisco-IOS-XR-types {
    prefix xr;
  }
  include Cisco-IOS-XR-mpls-oam-oper-sub1 {
    revision-date 2015-11-09;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR mpls-oam package operational data.

     This module contains definitions
     for the following management objects:
       mpls-oam: MPLS OAM operational data

     Copyright (c) 2013-2018 by Cisco Systems, Inc.
     All rights reserved.";

  revision 2015-11-09 {
    description
      "IOS XR 6.0 revision.";
  }

  augment "/ncs:devices/ncs:device/ncs:config" {
    // NCS drop config false container 'mpls-oam'
  }
  augment "/ncs:devices/ncs:device/ncs:live-status" {
    container mpls-oam {
      tailf:ncs-device-type "netconf";
      tailf:display-when "not(../../ncs:module) or ../../ncs:module[ncs:name='Cisco-IOS-XR-mpls-oam-oper'] or (../../ncs:live-status-protocol[not(ncs:capability)]) or (../../ncs:live-status-protocol/ncs:capability/ncs:module[.='Cisco-IOS-XR-mpls-oam-oper'])";
      description
        "MPLS OAM operational data";
      container interface {
        description
          "MPLS OAM interface operational data";
        container briefs {
          description
            "MPLS OAM interface detail data";
          list brief {
            key "interface-name";
            description
              "MPLS OAM interface operational data";
            leaf interface-name {
              type xr:Interface-name;
              description
                "Interface name";
            }
            uses live_ncs_LSPV-INTERFACE-INFO-BRIEF;
          }
        }
        container details {
          description
            "MPLS OAM interface detail data";
          list detail {
            key "interface-name";
            description
              "MPLS OAM interface operational data";
            leaf interface-name {
              type xr:Interface-name;
              description
                "Interface name";
            }
            uses live_ncs_LSPV-INTERFACE-INFO;
          }
        }
      }
      container packet {
        description
          "LSPV packet counters operational data";
        uses live_ncs_LSPV-PACKET-STATISTICS;
      }
      container global {
        description
          "LSPV global counters operational data";
        uses live_ncs_LSPV-GLOBAL-TYPE;
      }
    }
  }
  augment "/ncs:devices/ncs:template/ncs:ned-id/ncs:config" {
    // NCS drop config false container 'mpls-oam'
  }
}
