module Cisco-IOS-XR-infra-rsi-oper {
  // Generated by yanger -t ncs
  tailf:mount-id f5500-nc-1.0:f5500-nc-1.0;
  tailf:ncs-device-type "netconf";

  namespace "http://cisco.com/ns/yang/Cisco-IOS-XR-infra-rsi-oper";
  prefix Cisco-IOS-XR-infra-rsi-oper;

  import Cisco-IOS-XR-types {
    prefix xr;
  }
  include Cisco-IOS-XR-infra-rsi-oper-sub2 {
    revision-date 2017-09-07;
  }
  include Cisco-IOS-XR-infra-rsi-oper-sub1 {
    revision-date 2017-09-07;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR infra-rsi package operational data.

     This module contains definitions
     for the following management objects:
       vrf-group: VRF group operational data
       srlg: srlg
       selective-vrf-download: selective vrf download

     Copyright (c) 2013-2018 by Cisco Systems, Inc.
     All rights reserved.";

  revision 2017-09-07 {
    description
      "Fixed type translation error.";
  }
  revision 2017-05-01 {
    description
      "Fixing backward compatibility error in module.";
  }
  revision 2015-01-07 {
    description
      "IOS XR 5.3.1 revision.";
  }

  augment "/ncs:devices/ncs:device/ncs:config" {
    // NCS drop config false container 'vrf-group'
    // NCS drop config false container srlg
    // NCS drop config false container 'selective-vrf-download'
  }
  augment "/ncs:devices/ncs:device/ncs:live-status" {
    container vrf-group {
      tailf:ncs-device-type "netconf";
      tailf:display-when "not(../../ncs:module) or ../../ncs:module[ncs:name='Cisco-IOS-XR-infra-rsi-oper'] or (../../ncs:live-status-protocol[not(ncs:capability)]) or (../../ncs:live-status-protocol/ncs:capability/ncs:module[.='Cisco-IOS-XR-infra-rsi-oper'])";
      description
        "VRF group operational data";
      container nodes {
        description
          "Node operational data";
        list node {
          key "node-name";
          description
            "Node details";
          container groups {
            description
              "Group operational data";
            list group {
              key "group-name";
              description
                "Group details";
              leaf group-name {
                type xr:Cisco-ios-xr-string {
                  length "1..32";
                }
                description
                  "Group name";
              }
              uses live_ncs_RSI-VRFGROUP-GROUP-SHOW;
            }
          }
          leaf node-name {
            type xr:Node-id;
            description
              "Node";
          }
        }
      }
    }
    container srlg {
      tailf:ncs-device-type "netconf";
      tailf:display-when "not(../../ncs:module) or ../../ncs:module[ncs:name='Cisco-IOS-XR-infra-rsi-oper'] or (../../ncs:live-status-protocol[not(ncs:capability)]) or (../../ncs:live-status-protocol/ncs:capability/ncs:module[.='Cisco-IOS-XR-infra-rsi-oper'])";
      description
        "srlg";
      container groups {
        description
          "Set of Groups configured for SRLG";
        list group {
          key "group-name";
          description
            "SRLG group details";
          leaf group-name {
            type xr:Cisco-ios-xr-string;
            description
              "Group name";
          }
          uses live_ncs_RSI-SRLG-GROUP-SHOW;
        }
      }
      container interfaces {
        description
          "Set of interfaces configured for SRLG";
        list interface {
          key "interface-name";
          description
            "SRLG interface summary";
          leaf interface-name {
            type xr:Interface-name;
            description
              "Interface name";
          }
          uses live_ncs_RSI-SRLG-INTF-BRIEF-SHOW;
        }
      }
      container rsips {
        description
          "Set of rsip configured for SRLG";
        list rsip {
          key "rsip-name";
          description
            "SRLG rsip details";
          leaf rsip-name {
            type xr:Interface-name;
            description
              "Interface name";
          }
          uses live_ncs_RSI-SRLG-RSIP-SHOW;
        }
      }
      container srlg-maps {
        description
          "Set of SRLG name, value maps configured";
        list srlg-map {
          key "srlg-name";
          description
            "Configured SRLG name details ";
          leaf srlg-name {
            type xr:Cisco-ios-xr-string {
              length "1..64";
            }
            description
              "SRLG name";
          }
          uses live_ncs_RSI-SRLG-NAME-VALUE-SHOW;
        }
      }
      container nodes {
        description
          "RSI SRLG operational data";
        list node {
          key "node-name";
          description
            "RSI SRLG operational data";
          container srlg-maps {
            description
              "Set of SRLG name, value maps configured";
            list srlg-map {
              key "srlg-name";
              description
                "Configured SRLG name details ";
              leaf srlg-name {
                type xr:Cisco-ios-xr-string {
                  length "1..64";
                }
                description
                  "SRLG name";
              }
              uses live_ncs_RSI-SRLG-NAME-VALUE-SHOW;
            }
          }
          container groups {
            description
              "Set of Groups configured for SRLG";
            list group {
              key "group-name";
              description
                "SRLG group details";
              leaf group-name {
                type xr:Cisco-ios-xr-string;
                description
                  "Group name";
              }
              uses live_ncs_RSI-SRLG-GROUP-SHOW;
            }
          }
          container inherit-nodes {
            description
              "Set of inherit locations configured for SRLG";
            list inherit-node {
              key "inherit-node-name";
              description
                "SRLG inherit location details";
              leaf inherit-node-name {
                type xr:Pq-node-id;
                description
                  "Inherit node";
              }
              uses live_ncs_RSI-SRLG-INHLOC-SHOW;
            }
          }
          container interfaces {
            description
              "Set of interfaces configured for SRLG";
            list interface {
              key "interface-name";
              description
                "SRLG interface summary";
              leaf interface-name {
                type xr:Interface-name;
                description
                  "Interface name";
              }
              uses live_ncs_RSI-SRLG-INTF-BRIEF-SHOW;
            }
          }
          container interface-details {
            description
              "Set of interfaces configured for SRLG";
            list interface-detail {
              key "interface-name";
              description
                "SRLG interface details";
              leaf interface-name {
                type xr:Interface-name;
                description
                  "Interface name";
              }
              uses live_ncs_RSI-SRLG-INTF-DETAIL-SHOW;
            }
          }
          container srlg-values {
            description
              "Set of SRLG values configured";
            list srlg-value {
              key "value";
              description
                "Configured SRLG value details ";
              leaf value {
                type uint32;
                description
                  "SRLG value";
              }
              uses live_ncs_RSI-SRLG-INTF-SHOW;
            }
          }
          container interface-srlg-names {
            description
              "Set of SRLG names configured";
            list interface-srlg-name {
              key "srlg-name";
              description
                "Configured SRLG name details ";
              leaf srlg-name {
                type xr:Cisco-ios-xr-string {
                  length "1..64";
                }
                description
                  "SRLG name";
              }
              uses live_ncs_RSI-SRLG-NAME-INTF-SHOW;
            }
          }
          leaf node-name {
            type xr:Node-id;
            description
              "Node";
          }
        }
      }
      container interface-srlg-names {
        description
          "Set of SRLG names configured";
        list interface-srlg-name {
          key "srlg-name";
          description
            "Configured SRLG name details ";
          leaf srlg-name {
            type xr:Cisco-ios-xr-string {
              length "1..64";
            }
            description
              "SRLG name";
          }
          uses live_ncs_RSI-SRLG-NAME-INTF-SHOW;
        }
      }
      container inherit-nodes {
        description
          "Set of inherit locations configured for SRLG";
        list inherit-node {
          key "inherit-node-name";
          description
            "SRLG inherit location details";
          leaf inherit-node-name {
            type xr:Pq-node-id;
            description
              "Inherit Locatio";
          }
          uses live_ncs_RSI-SRLG-INHLOC-SHOW;
        }
      }
      container srlg-values {
        description
          "Set of SRLG values configured";
        list srlg-value {
          key "value";
          description
            "Configured SRLG value details ";
          leaf value {
            type uint32;
            description
              "SRLG value";
          }
          uses live_ncs_RSI-SRLG-INTF-SHOW;
        }
      }
      container interface-details {
        description
          "Set of interfaces configured for SRLG";
        list interface-detail {
          key "interface-name";
          description
            "SRLG interface details";
          leaf interface-name {
            type xr:Interface-name;
            description
              "Interface name";
          }
          uses live_ncs_RSI-SRLG-INTF-DETAIL-SHOW;
        }
      }
    }
    container selective-vrf-download {
      tailf:ncs-device-type "netconf";
      tailf:display-when "not(../../ncs:module) or ../../ncs:module[ncs:name='Cisco-IOS-XR-infra-rsi-oper'] or (../../ncs:live-status-protocol[not(ncs:capability)]) or (../../ncs:live-status-protocol/ncs:capability/ncs:module[.='Cisco-IOS-XR-infra-rsi-oper'])";
      description
        "selective vrf download";
      container state {
        description
          "Selective VRF Download feature state details";
        uses live_ncs_RSI-MASTER-STATE;
      }
    }
  }
  augment "/ncs:devices/ncs:template/ncs:ned-id/ncs:config" {
    // NCS drop config false container 'vrf-group'
    // NCS drop config false container srlg
    // NCS drop config false container 'selective-vrf-download'
  }
}
