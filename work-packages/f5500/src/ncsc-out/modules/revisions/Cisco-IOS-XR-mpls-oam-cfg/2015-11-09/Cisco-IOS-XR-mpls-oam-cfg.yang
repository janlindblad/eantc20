module Cisco-IOS-XR-mpls-oam-cfg {
  // Generated by yanger -t ncs
  tailf:mount-id f5500-nc-1.0:f5500-nc-1.0;
  tailf:ncs-device-type "netconf";

  namespace "http://cisco.com/ns/yang/Cisco-IOS-XR-mpls-oam-cfg";
  prefix Cisco-IOS-XR-mpls-oam-cfg;

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR mpls-oam package configuration.

     This module contains definitions
     for the following management objects:
       mpls-oam: MPLS LSP verification configuration

     Copyright (c) 2013-2018 by Cisco Systems, Inc.
     All rights reserved.";

  revision 2015-11-09 {
    description
      "IOS XR 6.0 revision.";
  }

  augment "/ncs:devices/ncs:device/ncs:config" {
    container mpls-oam {
      tailf:ncs-device-type "netconf";
      tailf:display-when "not(../../ncs:module) or ../../ncs:module[ncs:name='Cisco-IOS-XR-mpls-oam-cfg']";
      description
        "MPLS LSP verification configuration";
      container reply-mode {
        description
          "Echo request reply mode attributes";
        container control-channel {
          description
            "Configure control channel reply mode";
          leaf allow-reverse-lsp {
            type empty;
            description
              "Use Reverse LSP as the control channel";
          }
        }
      }
      leaf enable-oam {
        type empty;
        description
          "Enable/Disable MPLS OAM globally.Without
           creating this object the MPLS OAM feature will
           not be enabled. Deleting this object will stop
           the MPLS OAM feature.";
      }
      leaf disable-vendor-extension {
        type empty;
        description
          "Disable vendor extension";
      }
    }
  }
  augment "/ncs:devices/ncs:device/ncs:live-status" {
    container mpls-oam {
      tailf:ncs-device-type "netconf";
      tailf:display-when "not(../../ncs:module) or ../../ncs:module[ncs:name='Cisco-IOS-XR-mpls-oam-cfg'] or (../../ncs:live-status-protocol[not(ncs:capability)]) or (../../ncs:live-status-protocol/ncs:capability/ncs:module[.='Cisco-IOS-XR-mpls-oam-cfg'])";
      description
        "MPLS LSP verification configuration";
      container reply-mode {
        description
          "Echo request reply mode attributes";
        container control-channel {
          description
            "Configure control channel reply mode";
          leaf allow-reverse-lsp {
            type empty;
            description
              "Use Reverse LSP as the control channel";
          }
        }
      }
      leaf enable-oam {
        type empty;
        description
          "Enable/Disable MPLS OAM globally.Without
           creating this object the MPLS OAM feature will
           not be enabled. Deleting this object will stop
           the MPLS OAM feature.";
      }
      leaf disable-vendor-extension {
        type empty;
        description
          "Disable vendor extension";
      }
    }
  }
  augment "/ncs:devices/ncs:template/ncs:ned-id/ncs:config" {
    container mpls-oam {
      description
        "MPLS LSP verification configuration";
      container reply-mode {
        description
          "Echo request reply mode attributes";
        container control-channel {
          description
            "Configure control channel reply mode";
          leaf allow-reverse-lsp {
            type empty;
            description
              "Use Reverse LSP as the control channel";
          }
        }
      }
      leaf enable-oam {
        type empty;
        description
          "Enable/Disable MPLS OAM globally.Without
           creating this object the MPLS OAM feature will
           not be enabled. Deleting this object will stop
           the MPLS OAM feature.";
      }
      leaf disable-vendor-extension {
        type empty;
        description
          "Disable vendor extension";
      }
    }
  }
}
