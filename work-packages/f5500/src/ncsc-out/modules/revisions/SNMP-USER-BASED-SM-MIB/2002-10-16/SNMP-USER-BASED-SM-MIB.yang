module SNMP-USER-BASED-SM-MIB {
  // Generated by yanger -t ncs
  tailf:mount-id f5500-nc-1.0:f5500-nc-1.0;
  tailf:ncs-device-type "netconf";

  namespace "http://tail-f.com/ns/mibs/SNMP-USER-BASED-SM-MIB/200210160000Z";
  prefix SNMP-USER-BASED-SM-MIB;
  // NCS drop tailf:id
  tailf:snmp-mib-module-name SNMP-USER-BASED-SM-MIB;

  import ietf-yang-types {
    prefix yang;
  }
  import tailf-common {
    prefix tailf;
  }
  import SNMPv2-TC {
    prefix SNMPv2_TC;
  }
  import SNMP-FRAMEWORK-MIB {
    prefix SNMP_FRAMEWORK_MIB;
  }
  import "f5500-nc-1.0" {
    prefix "f5500-nc-1.0";
  }
  import tailf-ncs {
    prefix ncs;
  }

  revision 2002-10-16 {
    description
      "";
  }

  typedef usmUserPublicType {
    type tailf:hex-list {
      pattern '(((([0-9A-Fa-f]{2}):){0,31}([0-9A-Fa-f]{2}))){0,1}';
      tailf:value-length "min .. 32";
    }
  }

  typedef usmUserNameType {
    type string {
      length "1 .. 32";
    }
  }

  typedef KeyChange {
    type tailf:hex-list {
      pattern '(((([0-9A-Fa-f]{2}):)*([0-9A-Fa-f]{2}))){0,1}';
    }
  }

  augment "/ncs:devices/ncs:device/ncs:config" {
    container SNMP-USER-BASED-SM-MIB {
      tailf:ncs-device-type "netconf";
      tailf:display-when "not(../../ncs:module) or ../../ncs:module[ncs:name='SNMP-USER-BASED-SM-MIB']";
      // NCS drop config false container usmStats
      container usmUserTable {
        list usmUserEntry {
          key "usmUserEngineID usmUserName";
          unique "usmUserEngineID usmUserSecurityName";
          tailf:sort-order snmp;
          tailf:snmp-oid "1.3.6.1.6.3.15.1.2.2";
          leaf usmUserEngineID {
            type SNMP_FRAMEWORK_MIB:SnmpEngineID;
            tailf:snmp-oid "1.3.6.1.6.3.15.1.2.2.1.1";
          }
          leaf usmUserName {
            type usmUserNameType;
            tailf:snmp-oid "1.3.6.1.6.3.15.1.2.2.1.2";
          }
          leaf usmUserSecurityName {
            type SNMP_FRAMEWORK_MIB:SnmpAdminString;
            mandatory true;
            tailf:snmp-oid "1.3.6.1.6.3.15.1.2.2.1.3";
          }
          leaf usmUserCloneFrom {
            type SNMPv2_TC:RowPointer;
            tailf:snmp-oid "1.3.6.1.6.3.15.1.2.2.1.4";
          }
          leaf usmUserAuthProtocol {
            type SNMPv2_TC:AutonomousType;
            tailf:snmp-oid "1.3.6.1.6.3.15.1.2.2.1.5";
            default "1.3.6.1.6.3.10.1.1.1";
          }
          leaf usmUserAuthKeyChange {
            type KeyChange;
            tailf:snmp-oid "1.3.6.1.6.3.15.1.2.2.1.6";
          }
          leaf usmUserOwnAuthKeyChange {
            type KeyChange;
            tailf:snmp-oid "1.3.6.1.6.3.15.1.2.2.1.7";
          }
          leaf usmUserPrivProtocol {
            type SNMPv2_TC:AutonomousType;
            tailf:snmp-oid "1.3.6.1.6.3.15.1.2.2.1.8";
            default "1.3.6.1.6.3.10.1.2.1";
          }
          leaf usmUserPrivKeyChange {
            type KeyChange;
            tailf:snmp-oid "1.3.6.1.6.3.15.1.2.2.1.9";
          }
          leaf usmUserOwnPrivKeyChange {
            type KeyChange;
            tailf:snmp-oid "1.3.6.1.6.3.15.1.2.2.1.10";
          }
          leaf usmUserPublic {
            type usmUserPublicType;
            tailf:snmp-oid "1.3.6.1.6.3.15.1.2.2.1.11";
          }
          leaf usmUserStorageType {
            type SNMPv2_TC:StorageType;
            tailf:snmp-oid "1.3.6.1.6.3.15.1.2.2.1.12";
            default "nonVolatile";
          }
          leaf usmUserAuthKey {
            type KeyChange;
          }
          leaf usmUserPrivKey {
            type KeyChange;
          }
        }
      }
    }
  }
  augment "/ncs:devices/ncs:device/ncs:live-status" {
    container SNMP-USER-BASED-SM-MIB {
      tailf:ncs-device-type "netconf";
      tailf:display-when "not(../../ncs:module) or ../../ncs:module[ncs:name='SNMP-USER-BASED-SM-MIB'] or (../../ncs:live-status-protocol[not(ncs:capability)]) or (../../ncs:live-status-protocol/ncs:capability/ncs:module[.='SNMP-USER-BASED-SM-MIB'])";
      container usmStats {
        tailf:snmp-oid "1.3.6.1.6.3.15.1.1";
        leaf usmStatsUnsupportedSecLevels {
          type yang:counter32;
          tailf:snmp-oid "1.3.6.1.6.3.15.1.1.1";
        }
        leaf usmStatsNotInTimeWindows {
          type yang:counter32;
          tailf:snmp-oid "1.3.6.1.6.3.15.1.1.2";
        }
        leaf usmStatsUnknownUserNames {
          type yang:counter32;
          tailf:snmp-oid "1.3.6.1.6.3.15.1.1.3";
        }
        leaf usmStatsUnknownEngineIDs {
          type yang:counter32;
          tailf:snmp-oid "1.3.6.1.6.3.15.1.1.4";
        }
        leaf usmStatsWrongDigests {
          type yang:counter32;
          tailf:snmp-oid "1.3.6.1.6.3.15.1.1.5";
        }
        leaf usmStatsDecryptionErrors {
          type yang:counter32;
          tailf:snmp-oid "1.3.6.1.6.3.15.1.1.6";
        }
      }
      container usmUserTable {
        list usmUserEntry {
          key "usmUserEngineID usmUserName";
          unique "usmUserEngineID usmUserSecurityName";
          tailf:sort-order snmp;
          tailf:snmp-oid "1.3.6.1.6.3.15.1.2.2";
          leaf usmUserEngineID {
            type SNMP_FRAMEWORK_MIB:SnmpEngineID;
            tailf:snmp-oid "1.3.6.1.6.3.15.1.2.2.1.1";
          }
          leaf usmUserName {
            type usmUserNameType;
            tailf:snmp-oid "1.3.6.1.6.3.15.1.2.2.1.2";
          }
          leaf usmUserSecurityName {
            type SNMP_FRAMEWORK_MIB:SnmpAdminString;
            // NCS drop mandatory statement
            tailf:snmp-oid "1.3.6.1.6.3.15.1.2.2.1.3";
          }
          leaf usmUserCloneFrom {
            type SNMPv2_TC:RowPointer;
            tailf:snmp-oid "1.3.6.1.6.3.15.1.2.2.1.4";
          }
          leaf usmUserAuthProtocol {
            type SNMPv2_TC:AutonomousType;
            tailf:snmp-oid "1.3.6.1.6.3.15.1.2.2.1.5";
            // NCS drop default statement
          }
          leaf usmUserAuthKeyChange {
            type KeyChange;
            tailf:snmp-oid "1.3.6.1.6.3.15.1.2.2.1.6";
          }
          leaf usmUserOwnAuthKeyChange {
            type KeyChange;
            tailf:snmp-oid "1.3.6.1.6.3.15.1.2.2.1.7";
          }
          leaf usmUserPrivProtocol {
            type SNMPv2_TC:AutonomousType;
            tailf:snmp-oid "1.3.6.1.6.3.15.1.2.2.1.8";
            // NCS drop default statement
          }
          leaf usmUserPrivKeyChange {
            type KeyChange;
            tailf:snmp-oid "1.3.6.1.6.3.15.1.2.2.1.9";
          }
          leaf usmUserOwnPrivKeyChange {
            type KeyChange;
            tailf:snmp-oid "1.3.6.1.6.3.15.1.2.2.1.10";
          }
          leaf usmUserPublic {
            type usmUserPublicType;
            tailf:snmp-oid "1.3.6.1.6.3.15.1.2.2.1.11";
          }
          leaf usmUserStorageType {
            type SNMPv2_TC:StorageType;
            tailf:snmp-oid "1.3.6.1.6.3.15.1.2.2.1.12";
            // NCS drop default statement
          }
          leaf usmUserAuthKey {
            type KeyChange;
          }
          leaf usmUserPrivKey {
            type KeyChange;
          }
        }
      }
    }
  }
  augment "/ncs:devices/ncs:template/ncs:ned-id/ncs:config" {
    container SNMP-USER-BASED-SM-MIB {
      // NCS drop config false container usmStats
      container usmUserTable {
        list usmUserEntry {
          // NCS patched for predictable order
          ordered-by user;
          key "usmUserEngineID usmUserName";
          unique "usmUserEngineID usmUserSecurityName";
          leaf usmUserEngineID {
            type string;
          }
          leaf usmUserName {
            type string;
          }
          leaf usmUserSecurityName {
            type string;
            // NCS drop mandatory statement
          }
          leaf usmUserCloneFrom {
            type string;
          }
          leaf usmUserAuthProtocol {
            type string;
            // NCS drop default statement
          }
          leaf usmUserAuthKeyChange {
            type string;
          }
          leaf usmUserOwnAuthKeyChange {
            type string;
          }
          leaf usmUserPrivProtocol {
            type string;
            // NCS drop default statement
          }
          leaf usmUserPrivKeyChange {
            type string;
          }
          leaf usmUserOwnPrivKeyChange {
            type string;
          }
          leaf usmUserPublic {
            type string;
          }
          leaf usmUserStorageType {
            type string;
            // NCS drop default statement
          }
          leaf usmUserAuthKey {
            type string;
          }
          leaf usmUserPrivKey {
            type string;
          }
        }
      }
    }
  }
}
