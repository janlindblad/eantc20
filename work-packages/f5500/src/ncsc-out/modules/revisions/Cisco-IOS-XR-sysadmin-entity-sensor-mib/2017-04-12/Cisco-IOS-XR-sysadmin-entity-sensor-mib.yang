module Cisco-IOS-XR-sysadmin-entity-sensor-mib {
  // Generated by yanger -t ncs
  tailf:mount-id f5500-nc-1.0:f5500-nc-1.0;
  tailf:ncs-device-type "netconf";

  namespace "http://www.cisco.com/ns/yang/Cisco-IOS-XR-sysadmin-entity-sensor-mib";
  prefix Cisco-IOS-XR-sysadmin-entity-sensor-mib;

  import ietf-yang-types {
    prefix yang;
  }
  import SNMPv2-TC {
    prefix SNMPv2-TC;
  }
  import Cisco-IOS-XR-sysadmin-entity-mib {
    prefix ENTITY-MIB;
  }
  import "f5500-nc-1.0" {
    prefix "f5500-nc-1.0";
  }
  import tailf-ncs {
    prefix ncs;
  }
  import tailf-common {
    prefix tailf;
  }

  organization
    "Cisco Systems Inc.";
  contact
    "Cisco Systems, Inc.
     Customer Service

     Postal: 170 West Tasman Drive
     San Jose, CA 95134

     Tel: +1 800 553-NETS

     E-mail: cs-yang@cisco.com";
  description
    "This module contains definitions
     for the Calvados model objects.

     This module contains a collection of YANG
     definitions for Cisco IOS-XR SysAdmin configuration.

     Copyright(c) 2015-2017 by Cisco Systems, Inc.
     All rights reserved.

     Copyright (c) 2012-2018 by Cisco Systems, Inc.
     All rights reserved.";

  revision 2017-04-12 {
    description
      "Changed namespace and module name";
  }

  typedef entSensorThresholdIndexType {
    type int32 {
      range "1 .. 99999999";
    }
  }

  typedef entSensorMeasuredEntityType {
    type int32 {
      range "0 .. 2147483647";
    }
  }

  typedef SensorThresholdRelation {
    type enumeration {
      enum "lessThan" {
        value 1;
      }
      enum "lessOrEqual" {
        value 2;
      }
      enum "greaterThan" {
        value 3;
      }
      enum "greaterOrEqual" {
        value 4;
      }
      enum "equalTo" {
        value 5;
      }
      enum "notEqualTo" {
        value 6;
      }
    }
  }

  typedef SensorThresholdSeverity {
    type enumeration {
      enum "other" {
        value 1;
      }
      enum "minor" {
        value 10;
      }
      enum "major" {
        value 20;
      }
      enum "critical" {
        value 30;
      }
    }
  }

  typedef SensorValueUpdateRate {
    type int32 {
      range "0 .. 999999999";
    }
  }

  typedef SensorStatus {
    type enumeration {
      enum "ok" {
        value 1;
      }
      enum "unavailable" {
        value 2;
      }
      enum "nonoperational" {
        value 3;
      }
    }
  }

  typedef SensorValue {
    type int32 {
      range "-1000000000 .. 1000000000";
    }
  }

  typedef SensorPrecision {
    type int32 {
      range "-8 .. 9";
    }
  }

  typedef SensorDataScale {
    type enumeration {
      enum "yocto" {
        value 1;
      }
      enum "zepto" {
        value 2;
      }
      enum "atto" {
        value 3;
      }
      enum "femto" {
        value 4;
      }
      enum "pico" {
        value 5;
      }
      enum "nano" {
        value 6;
      }
      enum "micro" {
        value 7;
      }
      enum "milli" {
        value 8;
      }
      enum "units" {
        value 9;
      }
      enum "kilo" {
        value 10;
      }
      enum "mega" {
        value 11;
      }
      enum "giga" {
        value 12;
      }
      enum "tera" {
        value 13;
      }
      enum "exa" {
        value 14;
      }
      enum "peta" {
        value 15;
      }
      enum "zetta" {
        value 16;
      }
      enum "yotta" {
        value 17;
      }
    }
  }

  typedef SensorDataType {
    type enumeration {
      enum "other" {
        value 1;
      }
      enum "unknown" {
        value 2;
      }
      enum "voltsAC" {
        value 3;
      }
      enum "voltsDC" {
        value 4;
      }
      enum "amperes" {
        value 5;
      }
      enum "watts" {
        value 6;
      }
      enum "hertz" {
        value 7;
      }
      enum "celsius" {
        value 8;
      }
      enum "percentRH" {
        value 9;
      }
      enum "rpm" {
        value 10;
      }
      enum "cmm" {
        value 11;
      }
      enum "truthvalue" {
        value 12;
      }
      enum "specialEnum" {
        value 13;
      }
    }
  }

  augment "/ncs:devices/ncs:device/ncs:config" {
    container CISCO-ENTITY-SENSOR-MIB {
      tailf:ncs-device-type "netconf";
      tailf:display-when "not(../../ncs:module) or ../../ncs:module[ncs:name='Cisco-IOS-XR-sysadmin-entity-sensor-mib']";
      // NCS drop config false container entSensorValueTable
      // NCS drop config false container entSensorThresholdTable
    }
  }
  augment "/ncs:devices/ncs:device/ncs:live-status" {
    container CISCO-ENTITY-SENSOR-MIB {
      tailf:ncs-device-type "netconf";
      tailf:display-when "not(../../ncs:module) or ../../ncs:module[ncs:name='Cisco-IOS-XR-sysadmin-entity-sensor-mib'] or (../../ncs:live-status-protocol[not(ncs:capability)]) or (../../ncs:live-status-protocol/ncs:capability/ncs:module[.='Cisco-IOS-XR-sysadmin-entity-sensor-mib'])";
      container entSensorValueTable {
        list entSensorValueEntry {
          key "entPhysicalIndex";
          leaf entPhysicalIndex {
            type ENTITY-MIB:PhysicalIndex;
          }
          leaf entSensorType {
            type SensorDataType;
          }
          leaf entSensorScale {
            type SensorDataScale;
          }
          leaf entSensorPrecision {
            type SensorPrecision;
          }
          leaf entSensorValue {
            type SensorValue;
          }
          leaf entSensorStatus {
            type SensorStatus;
          }
          leaf entSensorValueTimeStamp {
            type yang:timestamp;
          }
          leaf entSensorValueUpdateRate {
            type SensorValueUpdateRate;
          }
          leaf entSensorMeasuredEntity {
            type entSensorMeasuredEntityType;
          }
        }
      }
      container entSensorThresholdTable {
        list entSensorThresholdEntry {
          key "entPhysicalIndex entSensorThresholdIndex";
          leaf entPhysicalIndex {
            type ENTITY-MIB:PhysicalIndex;
          }
          leaf entSensorThresholdIndex {
            type entSensorThresholdIndexType;
          }
          leaf entSensorThresholdSeverity {
            type SensorThresholdSeverity;
          }
          leaf entSensorThresholdRelation {
            type SensorThresholdRelation;
          }
          leaf entSensorThresholdValue {
            type SensorValue;
          }
          leaf entSensorThresholdEvaluation {
            type SNMPv2-TC:TruthValue;
          }
          leaf entSensorThresholdNotificationEnable {
            type SNMPv2-TC:TruthValue;
          }
        }
      }
    }
  }
  augment "/ncs:devices/ncs:template/ncs:ned-id/ncs:config" {
    container CISCO-ENTITY-SENSOR-MIB {
      // NCS drop config false container entSensorValueTable
      // NCS drop config false container entSensorThresholdTable
    }
  }
}
