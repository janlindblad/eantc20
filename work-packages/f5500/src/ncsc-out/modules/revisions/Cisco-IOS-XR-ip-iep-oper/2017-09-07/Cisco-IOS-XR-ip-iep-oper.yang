module Cisco-IOS-XR-ip-iep-oper {
  // Generated by yanger -t ncs
  tailf:mount-id f5500-nc-1.0:f5500-nc-1.0;
  tailf:ncs-device-type "netconf";

  namespace "http://cisco.com/ns/yang/Cisco-IOS-XR-ip-iep-oper";
  prefix Cisco-IOS-XR-ip-iep-oper;

  import Cisco-IOS-XR-types {
    prefix xr;
  }
  include Cisco-IOS-XR-ip-iep-oper-sub1 {
    revision-date 2017-09-07;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ip-iep package operational data.

     This module contains definitions
     for the following management objects:
       explicit-paths: Configured IP explicit paths

     Copyright (c) 2013-2018 by Cisco Systems, Inc.
     All rights reserved.";

  revision 2017-09-07 {
    description
      "Fixed type translation error.";
  }
  revision 2015-11-09 {
    description
      "IOS XR 6.0 revision.";
  }

  augment "/ncs:devices/ncs:device/ncs:config" {
    // NCS drop config false container 'explicit-paths'
  }
  augment "/ncs:devices/ncs:device/ncs:live-status" {
    container explicit-paths {
      tailf:ncs-device-type "netconf";
      tailf:display-when "not(../../ncs:module) or ../../ncs:module[ncs:name='Cisco-IOS-XR-ip-iep-oper'] or (../../ncs:live-status-protocol[not(ncs:capability)]) or (../../ncs:live-status-protocol/ncs:capability/ncs:module[.='Cisco-IOS-XR-ip-iep-oper'])";
      description
        "Configured IP explicit paths";
      container identifiers {
        description
          "List of configured IP explicit path identifiers,
           this corresponds to mplsTunnelHopTable in TE MIB";
        list identifier {
          key "identifier-id";
          description
            "IP explicit path configured for a particular
             identifier";
          leaf identifier-id {
            type uint32;
            description
              "Identifier ID";
          }
          uses live_ncs_IEP-EXPLICIT-PATH;
        }
      }
      container names {
        description
          "List of configured IP explicit path names, this
           corresponds to mplsTunnelHopTable in TE MIB";
        list name {
          key "path-name";
          description
            "IP explicit path configured for a particular
             path name";
          leaf path-name {
            type xr:Cisco-ios-xr-string;
            description
              "Path name";
          }
          uses live_ncs_IEP-EXPLICIT-PATH;
        }
      }
    }
  }
  augment "/ncs:devices/ncs:template/ncs:ned-id/ncs:config" {
    // NCS drop config false container 'explicit-paths'
  }
}
