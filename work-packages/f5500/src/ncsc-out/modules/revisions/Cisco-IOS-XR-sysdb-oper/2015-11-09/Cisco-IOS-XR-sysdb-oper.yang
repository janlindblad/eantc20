module Cisco-IOS-XR-sysdb-oper {
  // Generated by yanger -t ncs
  tailf:mount-id f5500-nc-1.0:f5500-nc-1.0;
  tailf:ncs-device-type "netconf";

  namespace "http://cisco.com/ns/yang/Cisco-IOS-XR-sysdb-oper";
  prefix Cisco-IOS-XR-sysdb-oper;

  import Cisco-IOS-XR-types {
    prefix xr;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR sysdb package operational data.

     This module contains definitions
     for the following management objects:
       sysdb-connections: Sysdb health on client connections
       sysdb: sysdb

     Copyright (c) 2013-2018 by Cisco Systems, Inc.
     All rights reserved.";

  revision 2015-11-09 {
    description
      "IOS XR 6.0 revision.";
  }

  augment "/ncs:devices/ncs:device/ncs:config" {
    // NCS drop config false container 'sysdb-connections'
    // NCS drop config false container sysdb
  }
  augment "/ncs:devices/ncs:device/ncs:live-status" {
    container sysdb-connections {
      tailf:ncs-device-type "netconf";
      tailf:display-when "not(../../ncs:module) or ../../ncs:module[ncs:name='Cisco-IOS-XR-sysdb-oper'] or (../../ncs:live-status-protocol[not(ncs:capability)]) or (../../ncs:live-status-protocol/ncs:capability/ncs:module[.='Cisco-IOS-XR-sysdb-oper'])";
      description
        "Sysdb health on client connections";
      container nodes {
        description
          "Node operational data";
        list node {
          key "node-name";
          description
            "Per-node Sysdb health on connection";
          leaf connections {
            type string;
            description
              "Per-node Sysdb Client Connections";
          }
          leaf node-name {
            type xr:Node-id;
            description
              "Node name";
          }
        }
      }
    }
    container sysdb {
      tailf:ncs-device-type "netconf";
      tailf:display-when "not(../../ncs:module) or ../../ncs:module[ncs:name='Cisco-IOS-XR-sysdb-oper'] or (../../ncs:live-status-protocol[not(ncs:capability)]) or (../../ncs:live-status-protocol/ncs:capability/ncs:module[.='Cisco-IOS-XR-sysdb-oper'])";
      description
        "sysdb";
      leaf configuration-space {
        type string;
        description
          "Sysdb health for configuration space";
      }
      leaf memory {
        type string;
        description
          "Sysdb health on memory consumption";
      }
      leaf ipc-space {
        type string;
        description
          "Sysdb health for operational space";
      }
      leaf cpu {
        type string;
        description
          "Sysdb health on cpu consumption";
      }
    }
  }
  augment "/ncs:devices/ncs:template/ncs:ned-id/ncs:config" {
    // NCS drop config false container 'sysdb-connections'
    // NCS drop config false container sysdb
  }
}
