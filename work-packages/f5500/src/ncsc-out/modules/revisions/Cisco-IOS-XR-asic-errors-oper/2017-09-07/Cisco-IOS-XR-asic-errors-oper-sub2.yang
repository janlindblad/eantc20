submodule Cisco-IOS-XR-asic-errors-oper-sub2 {
  // Generated by yanger -t ncs
  tailf:mount-id f5500-nc-1.0:f5500-nc-1.0;

  belongs-to Cisco-IOS-XR-asic-errors-oper {
    prefix Cisco-IOS-XR-asic-errors-oper-sub2;
  }

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR asic-errors package operational data.

     Copyright (c) 2013-2018 by Cisco Systems, Inc.
     All rights reserved.";

  revision 2017-09-07 {
    description
      "Fixed type translation error.";
  }
  revision 2015-11-09 {
    description
      "IOS XR 6.0 revision.";
  }

  grouping ncs_template_COUNT-INFO-BG {
    description
      "COUNT INFO BG";
    leaf name {
      type string;
      description
        "name";
    }
    leaf count {
      type string;
      description
        "count";
    }
  }

  grouping ncs_template_SUMMARY-DATA-BG {
    description
      "SUMMARY DATA BG";
    leaf num-nodes {
      type string;
      description
        "num nodes";
    }
    leaf crc-err-count {
      type string;
      description
        "crc err count";
    }
    leaf sbe-err-count {
      type string;
      description
        "sbe err count";
    }
    leaf mbe-err-count {
      type string;
      description
        "mbe err count";
    }
    leaf par-err-count {
      type string;
      description
        "par err count";
    }
    leaf gen-err-count {
      type string;
      description
        "gen err count";
    }
    leaf reset-err-count {
      type string;
      description
        "reset err count";
    }
    leaf-list node-key {
      // NCS patched for predictable order
      ordered-by user;
      type string;
      description
        "node key";
    }
    list err-count {
      // NCS patched for predictable order
      ordered-by user;
      description
        "err count";
      uses ncs_template_COUNT-INFO-BG;
    }
    list pcie-err-count {
      // NCS patched for predictable order
      ordered-by user;
      description
        "pcie err count";
      uses ncs_template_COUNT-INFO-BG;
    }
  }

  grouping ncs_template_ASIC-SUMMARY-BG {
    description
      "ASIC SUMMARY BG";
    leaf legacy-client {
      type string;
      description
        "legacy client";
    }
    leaf cih-client {
      type string;
      description
        "cih client";
    }
    list sum-data {
      // NCS patched for predictable order
      ordered-by user;
      description
        "sum data";
      uses ncs_template_SUMMARY-DATA-BG;
    }
  }

  grouping ncs_rpc_notif_COUNT-INFO-BG {
    description
      "COUNT INFO BG";
    leaf name {
      type string;
      description
        "name";
    }
    leaf count {
      type uint32;
      description
        "count";
    }
  }

  grouping ncs_rpc_notif_SUMMARY-DATA-BG {
    description
      "SUMMARY DATA BG";
    leaf num-nodes {
      type uint32;
      description
        "num nodes";
    }
    leaf crc-err-count {
      type uint32;
      description
        "crc err count";
    }
    leaf sbe-err-count {
      type uint32;
      description
        "sbe err count";
    }
    leaf mbe-err-count {
      type uint32;
      description
        "mbe err count";
    }
    leaf par-err-count {
      type uint32;
      description
        "par err count";
    }
    leaf gen-err-count {
      type uint32;
      description
        "gen err count";
    }
    leaf reset-err-count {
      type uint32;
      description
        "reset err count";
    }
    leaf-list node-key {
      type uint32;
      description
        "node key";
    }
    list err-count {
      description
        "err count";
      uses ncs_rpc_notif_COUNT-INFO-BG;
    }
    list pcie-err-count {
      description
        "pcie err count";
      uses ncs_rpc_notif_COUNT-INFO-BG;
    }
  }

  grouping ncs_rpc_notif_ASIC-SUMMARY-BG {
    description
      "ASIC SUMMARY BG";
    leaf legacy-client {
      type boolean;
      description
        "legacy client";
    }
    leaf cih-client {
      type boolean;
      description
        "cih client";
    }
    list sum-data {
      description
        "sum data";
      uses ncs_rpc_notif_SUMMARY-DATA-BG;
    }
  }

  grouping live_ncs_COUNT-INFO-BG {
    description
      "COUNT INFO BG";
    leaf name {
      type string;
      description
        "name";
    }
    leaf count {
      type uint32;
      description
        "count";
    }
  }

  grouping live_ncs_SUMMARY-DATA-BG {
    description
      "SUMMARY DATA BG";
    leaf num-nodes {
      type uint32;
      description
        "num nodes";
    }
    leaf crc-err-count {
      type uint32;
      description
        "crc err count";
    }
    leaf sbe-err-count {
      type uint32;
      description
        "sbe err count";
    }
    leaf mbe-err-count {
      type uint32;
      description
        "mbe err count";
    }
    leaf par-err-count {
      type uint32;
      description
        "par err count";
    }
    leaf gen-err-count {
      type uint32;
      description
        "gen err count";
    }
    leaf reset-err-count {
      type uint32;
      description
        "reset err count";
    }
    leaf-list node-key {
      type uint32;
      description
        "node key";
    }
    list err-count {
      description
        "err count";
      uses live_ncs_COUNT-INFO-BG;
    }
    list pcie-err-count {
      description
        "pcie err count";
      uses live_ncs_COUNT-INFO-BG;
    }
  }

  grouping live_ncs_ASIC-SUMMARY-BG {
    description
      "ASIC SUMMARY BG";
    leaf legacy-client {
      type boolean;
      description
        "legacy client";
    }
    leaf cih-client {
      type boolean;
      description
        "cih client";
    }
    list sum-data {
      description
        "sum data";
      uses live_ncs_SUMMARY-DATA-BG;
    }
  }

  grouping COUNT-INFO-BG {
    description
      "COUNT INFO BG";
    leaf name {
      type string;
      description
        "name";
    }
    leaf count {
      type uint32;
      description
        "count";
    }
  }

  grouping SUMMARY-DATA-BG {
    description
      "SUMMARY DATA BG";
    leaf num-nodes {
      type uint32;
      description
        "num nodes";
    }
    leaf crc-err-count {
      type uint32;
      description
        "crc err count";
    }
    leaf sbe-err-count {
      type uint32;
      description
        "sbe err count";
    }
    leaf mbe-err-count {
      type uint32;
      description
        "mbe err count";
    }
    leaf par-err-count {
      type uint32;
      description
        "par err count";
    }
    leaf gen-err-count {
      type uint32;
      description
        "gen err count";
    }
    leaf reset-err-count {
      type uint32;
      description
        "reset err count";
    }
    leaf-list node-key {
      type uint32;
      description
        "node key";
    }
    list err-count {
      description
        "err count";
      uses COUNT-INFO-BG;
    }
    list pcie-err-count {
      description
        "pcie err count";
      uses COUNT-INFO-BG;
    }
  }

  grouping ASIC-SUMMARY-BG {
    description
      "ASIC SUMMARY BG";
    leaf legacy-client {
      type boolean;
      description
        "legacy client";
    }
    leaf cih-client {
      type boolean;
      description
        "cih client";
    }
    list sum-data {
      description
        "sum data";
      uses SUMMARY-DATA-BG;
    }
  }
}
