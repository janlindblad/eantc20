submodule Cisco-IOS-XR-asic-errors-oper-sub1 {
  // Generated by yanger -t ncs
  tailf:mount-id f5500-nc-1.0:f5500-nc-1.0;

  belongs-to Cisco-IOS-XR-asic-errors-oper {
    prefix Cisco-IOS-XR-asic-errors-oper-sub1;
  }

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR asic-errors package operational data.

     Copyright (c) 2013-2018 by Cisco Systems, Inc.
     All rights reserved.";

  revision 2017-09-07 {
    description
      "Fixed type translation error.";
  }
  revision 2015-11-09 {
    description
      "IOS XR 6.0 revision.";
  }

  grouping ncs_template_CIHERR-ERROR-DATA-BG {
    description
      "CIHERR ERROR DATA BG";
    leaf at-time {
      type string;
      description
        "at time";
    }
    leaf at-time-nsec {
      type string;
      description
        "at time nsec";
    }
    leaf counter-val {
      type string;
      description
        "counter val";
    }
    leaf error-desc {
      type string;
      description
        "error desc";
    }
    leaf-list error-regval {
      // NCS patched for predictable order
      ordered-by user;
      type string;
      description
        "error regval";
    }
  }

  grouping ncs_template_CSRS-INFO-BG {
    description
      "CSRS INFO BG";
    leaf name {
      type string;
      description
        "name";
    }
    leaf address {
      type string;
      description
        "address";
    }
    leaf width {
      type string;
      description
        "width";
    }
  }

  grouping ncs_template_CIHERR-NODE-BG {
    description
      "CIHERR NODE BG";
    leaf name {
      type string;
      description
        "Name assigned to mem";
    }
    leaf asic-info {
      type string;
      description
        "Name of rack/board/asic";
    }
    leaf node-key {
      type string;
      description
        "32 bit key";
    }
    leaf alarm-on {
      type string;
      description
        "High threshold crossed";
    }
    leaf thresh-hi {
      type string;
      description
        "High threshold value";
    }
    leaf period-hi {
      type string;
      description
        "High period value";
    }
    leaf thresh-lo {
      type string;
      description
        "High threshold value";
    }
    leaf period-lo {
      type string;
      description
        "High period value";
    }
    leaf count {
      type string;
      description
        "Accumulated count";
    }
    leaf intr-type {
      type string;
      description
        "Type of error";
    }
    leaf leaf-id {
      type string;
      description
        "Leaf ID defined in user data";
    }
    leaf last-cleared {
      type string;
      description
        "Time  cleared";
    }
    list csrs-info {
      // NCS patched for predictable order
      ordered-by user;
      description
        "List of csrs_info";
      uses ncs_template_CSRS-INFO-BG;
    }
    list last-err {
      // NCS patched for predictable order
      ordered-by user;
      description
        "Last Printable error information";
      uses ncs_template_CIHERR-ERROR-DATA-BG;
    }
  }

  grouping ncs_template_CIHERR-NODES-BG {
    description
      "CIHERR NODES BG";
    list error {
      // NCS patched for predictable order
      ordered-by user;
      description
        "Collection of errors";
      uses ncs_template_CIHERR-NODE-BG;
    }
  }

  grouping ncs_rpc_notif_CIHERR-ERROR-DATA-BG {
    description
      "CIHERR ERROR DATA BG";
    leaf at-time {
      type uint64;
      description
        "at time";
    }
    leaf at-time-nsec {
      type uint64;
      description
        "at time nsec";
    }
    leaf counter-val {
      type uint32;
      description
        "counter val";
    }
    leaf error-desc {
      type string;
      description
        "error desc";
    }
    leaf-list error-regval {
      type uint8;
      description
        "error regval";
    }
  }

  grouping ncs_rpc_notif_CSRS-INFO-BG {
    description
      "CSRS INFO BG";
    leaf name {
      type string;
      description
        "name";
    }
    leaf address {
      type uint64;
      description
        "address";
    }
    leaf width {
      type uint32;
      description
        "width";
    }
  }

  grouping ncs_rpc_notif_CIHERR-NODE-BG {
    description
      "CIHERR NODE BG";
    leaf name {
      type string;
      description
        "Name assigned to mem";
    }
    leaf asic-info {
      type string;
      description
        "Name of rack/board/asic";
    }
    leaf node-key {
      type uint32;
      description
        "32 bit key";
    }
    leaf alarm-on {
      type boolean;
      description
        "High threshold crossed";
    }
    leaf thresh-hi {
      type uint32;
      description
        "High threshold value";
    }
    leaf period-hi {
      type uint32;
      description
        "High period value";
    }
    leaf thresh-lo {
      type uint32;
      description
        "High threshold value";
    }
    leaf period-lo {
      type uint32;
      description
        "High period value";
    }
    leaf count {
      type uint32;
      description
        "Accumulated count";
    }
    leaf intr-type {
      type uint32;
      description
        "Type of error";
    }
    leaf leaf-id {
      type uint32;
      description
        "Leaf ID defined in user data";
    }
    leaf last-cleared {
      type uint64;
      description
        "Time  cleared";
    }
    list csrs-info {
      description
        "List of csrs_info";
      uses ncs_rpc_notif_CSRS-INFO-BG;
    }
    list last-err {
      description
        "Last Printable error information";
      uses ncs_rpc_notif_CIHERR-ERROR-DATA-BG;
    }
  }

  grouping ncs_rpc_notif_CIHERR-NODES-BG {
    description
      "CIHERR NODES BG";
    list error {
      description
        "Collection of errors";
      uses ncs_rpc_notif_CIHERR-NODE-BG;
    }
  }

  grouping live_ncs_CIHERR-ERROR-DATA-BG {
    description
      "CIHERR ERROR DATA BG";
    leaf at-time {
      type uint64;
      description
        "at time";
    }
    leaf at-time-nsec {
      type uint64;
      description
        "at time nsec";
    }
    leaf counter-val {
      type uint32;
      description
        "counter val";
    }
    leaf error-desc {
      type string;
      description
        "error desc";
    }
    leaf-list error-regval {
      type uint8;
      description
        "error regval";
    }
  }

  grouping live_ncs_CSRS-INFO-BG {
    description
      "CSRS INFO BG";
    leaf name {
      type string;
      description
        "name";
    }
    leaf address {
      type uint64;
      description
        "address";
    }
    leaf width {
      type uint32;
      description
        "width";
    }
  }

  grouping live_ncs_CIHERR-NODE-BG {
    description
      "CIHERR NODE BG";
    leaf name {
      type string;
      description
        "Name assigned to mem";
    }
    leaf asic-info {
      type string;
      description
        "Name of rack/board/asic";
    }
    leaf node-key {
      type uint32;
      description
        "32 bit key";
    }
    leaf alarm-on {
      type boolean;
      description
        "High threshold crossed";
    }
    leaf thresh-hi {
      type uint32;
      description
        "High threshold value";
    }
    leaf period-hi {
      type uint32;
      description
        "High period value";
    }
    leaf thresh-lo {
      type uint32;
      description
        "High threshold value";
    }
    leaf period-lo {
      type uint32;
      description
        "High period value";
    }
    leaf count {
      type uint32;
      description
        "Accumulated count";
    }
    leaf intr-type {
      type uint32;
      description
        "Type of error";
    }
    leaf leaf-id {
      type uint32;
      description
        "Leaf ID defined in user data";
    }
    leaf last-cleared {
      type uint64;
      description
        "Time  cleared";
    }
    list csrs-info {
      description
        "List of csrs_info";
      uses live_ncs_CSRS-INFO-BG;
    }
    list last-err {
      description
        "Last Printable error information";
      uses live_ncs_CIHERR-ERROR-DATA-BG;
    }
  }

  grouping live_ncs_CIHERR-NODES-BG {
    description
      "CIHERR NODES BG";
    list error {
      description
        "Collection of errors";
      uses live_ncs_CIHERR-NODE-BG;
    }
  }

  grouping CIHERR-ERROR-DATA-BG {
    description
      "CIHERR ERROR DATA BG";
    leaf at-time {
      type uint64;
      description
        "at time";
    }
    leaf at-time-nsec {
      type uint64;
      description
        "at time nsec";
    }
    leaf counter-val {
      type uint32;
      description
        "counter val";
    }
    leaf error-desc {
      type string;
      description
        "error desc";
    }
    leaf-list error-regval {
      type uint8;
      description
        "error regval";
    }
  }

  grouping CSRS-INFO-BG {
    description
      "CSRS INFO BG";
    leaf name {
      type string;
      description
        "name";
    }
    leaf address {
      type uint64;
      description
        "address";
    }
    leaf width {
      type uint32;
      description
        "width";
    }
  }

  grouping CIHERR-NODE-BG {
    description
      "CIHERR NODE BG";
    leaf name {
      type string;
      description
        "Name assigned to mem";
    }
    leaf asic-info {
      type string;
      description
        "Name of rack/board/asic";
    }
    leaf node-key {
      type uint32;
      description
        "32 bit key";
    }
    leaf alarm-on {
      type boolean;
      description
        "High threshold crossed";
    }
    leaf thresh-hi {
      type uint32;
      description
        "High threshold value";
    }
    leaf period-hi {
      type uint32;
      description
        "High period value";
    }
    leaf thresh-lo {
      type uint32;
      description
        "High threshold value";
    }
    leaf period-lo {
      type uint32;
      description
        "High period value";
    }
    leaf count {
      type uint32;
      description
        "Accumulated count";
    }
    leaf intr-type {
      type uint32;
      description
        "Type of error";
    }
    leaf leaf-id {
      type uint32;
      description
        "Leaf ID defined in user data";
    }
    leaf last-cleared {
      type uint64;
      description
        "Time  cleared";
    }
    list csrs-info {
      description
        "List of csrs_info";
      uses CSRS-INFO-BG;
    }
    list last-err {
      description
        "Last Printable error information";
      uses CIHERR-ERROR-DATA-BG;
    }
  }

  grouping CIHERR-NODES-BG {
    description
      "CIHERR NODES BG";
    list error {
      description
        "Collection of errors";
      uses CIHERR-NODE-BG;
    }
  }
}
