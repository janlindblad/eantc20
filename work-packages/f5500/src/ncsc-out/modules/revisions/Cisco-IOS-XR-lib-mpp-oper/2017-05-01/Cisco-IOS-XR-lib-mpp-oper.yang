module Cisco-IOS-XR-lib-mpp-oper {
  // Generated by yanger -t ncs
  tailf:mount-id f5500-nc-1.0:f5500-nc-1.0;
  tailf:ncs-device-type "netconf";

  namespace "http://cisco.com/ns/yang/Cisco-IOS-XR-lib-mpp-oper";
  prefix Cisco-IOS-XR-lib-mpp-oper;

  include Cisco-IOS-XR-lib-mpp-oper-sub1 {
    revision-date 2017-05-01;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR lib-mpp package operational data.

     This module contains definitions
     for the following management objects:
       management-plane-protection: Management Plane Protection (MPP)
         operational data

     Copyright (c) 2013-2018 by Cisco Systems, Inc.
     All rights reserved.";

  revision 2017-05-01 {
    description
      "Fixing backward compatibility error in module.";
  }
  revision 2015-01-07 {
    description
      "IOS XR 5.3.1 revision.";
  }

  grouping ncs_template_INTERFACE-TABLE {
    description
      "Common node of inband, outband";
    container interfaces {
      description
        "List of inband/outband interfaces";
      list interface {
        // NCS patched for predictable order
        ordered-by user;
        key "interface-name";
        description
          "MPP interface information";
        leaf interface-name {
          type string;
          description
            "Interface name, specify 'all' for all
             interfaces";
        }
        uses ncs_template_MPP-PROTO;
      }
    }
  }

  grouping ncs_rpc_notif_INTERFACE-TABLE {
    description
      "Common node of inband, outband";
    container interfaces {
      description
        "List of inband/outband interfaces";
      list interface {
        key "interface-name";
        description
          "MPP interface information";
        leaf interface-name {
          type string;
          description
            "Interface name, specify 'all' for all
             interfaces";
        }
        uses ncs_rpc_notif_MPP-PROTO;
      }
    }
  }

  grouping live_ncs_INTERFACE-TABLE {
    description
      "Common node of inband, outband";
    container interfaces {
      description
        "List of inband/outband interfaces";
      list interface {
        key "interface-name";
        description
          "MPP interface information";
        leaf interface-name {
          type string;
          description
            "Interface name, specify 'all' for all
             interfaces";
        }
        uses live_ncs_MPP-PROTO;
      }
    }
  }

  grouping INTERFACE-TABLE {
    description
      "Common node of inband, outband";
    container interfaces {
      description
        "List of inband/outband interfaces";
      list interface {
        key "interface-name";
        description
          "MPP interface information";
        leaf interface-name {
          type string;
          description
            "Interface name, specify 'all' for all
             interfaces";
        }
        uses MPP-PROTO;
      }
    }
  }

  augment "/ncs:devices/ncs:device/ncs:config" {
    // NCS drop config false container 'management-plane-protection'
  }
  augment "/ncs:devices/ncs:device/ncs:live-status" {
    container management-plane-protection {
      tailf:ncs-device-type "netconf";
      tailf:display-when "not(../../ncs:module) or ../../ncs:module[ncs:name='Cisco-IOS-XR-lib-mpp-oper'] or (../../ncs:live-status-protocol[not(ncs:capability)]) or (../../ncs:live-status-protocol/ncs:capability/ncs:module[.='Cisco-IOS-XR-lib-mpp-oper'])";
      description
        "Management Plane Protection (MPP) operational
         data";
      container outband {
        description
          "Management Plane Protection (MPP) outband
           interface data";
        container vrf {
          description
            "Outband VRF information";
          uses live_ncs_VRF-INFO;
        }
        uses live_ncs_INTERFACE-TABLE;
      }
      container inband {
        description
          "Management Plane Protection (MPP) inband
           interface data";
        uses live_ncs_INTERFACE-TABLE;
      }
    }
  }
  augment "/ncs:devices/ncs:template/ncs:ned-id/ncs:config" {
    // NCS drop config false container 'management-plane-protection'
  }
}
