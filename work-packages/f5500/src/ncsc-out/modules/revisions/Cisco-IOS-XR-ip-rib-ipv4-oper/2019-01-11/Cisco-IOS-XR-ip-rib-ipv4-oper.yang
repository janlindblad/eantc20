module Cisco-IOS-XR-ip-rib-ipv4-oper {
  // Generated by yanger -t ncs
  tailf:mount-id f5500-nc-1.0:f5500-nc-1.0;
  tailf:ncs-device-type "netconf";

  namespace "http://cisco.com/ns/yang/Cisco-IOS-XR-ip-rib-ipv4-oper";
  prefix Cisco-IOS-XR-ip-rib-ipv4-oper;

  import ietf-inet-types {
    prefix inet;
  }
  import Cisco-IOS-XR-types {
    prefix xr;
  }
  include Cisco-IOS-XR-ip-rib-ipv4-oper-sub1 {
    revision-date 2019-01-11;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ip-rib-ipv4 package operational data.

     This module contains definitions
     for the following management objects:
       rib-stdby: RIB standby node operational data
       rib: rib

     Copyright (c) 2013-2018 by Cisco Systems, Inc.
     All rights reserved.";

  revision 2019-01-11 {
    description
      "Route lookup key is limited to Prefix and Prefix Length";
  }
  revision 2018-11-20 {
    description
      "Add keys for route lookup via resconf.";
  }
  revision 2015-11-09 {
    description
      "IOS XR 6.0 revision.";
  }

  typedef Rib-af-name {
    type string {
      pattern '(IPv4)|(IPv6)';
    }
    description
      "IPv4: Comment: v4 string for <afi_name>, IPv6:
       Comment: v6 string for <afi_name>";
  }

  typedef Rib-saf-name {
    type string {
      pattern '(Unicast)|(Multicast)';
    }
    description
      "Unicast:   Comment: Ucast string for <safi_name>,
       Multicast: Comment: Mcast string for <safi_name>";
  }

  grouping ncs_template_VRF-TABLE {
    description
      "Common node of rib, rib-stdby";
    container vrfs {
      description
        "VRF table";
      list vrf {
        // NCS patched for predictable order
        ordered-by user;
        key "vrf-name";
        description
          "Specific VRF";
        container afs {
          description
            "Address Family (AF) table";
          list af {
            // NCS patched for predictable order
            ordered-by user;
            key "af-name";
            description
              "Specific AF information";
            container safs {
              description
                "Subsequent Address Family (SAF) table";
              list saf {
                // NCS patched for predictable order
                ordered-by user;
                key "saf-name";
                description
                  "Specific SAF information";
                container ip-rib-route-table-names {
                  description
                    "Global container of routes";
                  list ip-rib-route-table-name {
                    // NCS patched for predictable order
                    ordered-by user;
                    key "route-table-name";
                    description
                      "IP RIB Route table name for a topology";
                    container routes {
                      description
                        "Route information ";
                      list route {
                        // NCS patched for predictable order
                        ordered-by user;
                        key "address prefix-length";
                        description
                          "Route information of a specific Network
                           Address ";
                        leaf address {
                          type string;
                          description
                            "Network Address";
                        }
                        leaf prefix-length {
                          type string;
                          description
                            "Prefix Length";
                        }
                        uses ncs_template_IPV4-RIB-EDM-ROUTE;
                      }
                    }
                    container deleted-routes {
                      description
                        "Deleted";
                      list deleted-route {
                        // NCS patched for predictable order
                        ordered-by user;
                        key "address prefix-length";
                        description
                          "Route information for a specific
                           deleted address ";
                        leaf address {
                          type string;
                          description
                            "Network Address";
                        }
                        leaf prefix-length {
                          type string;
                          description
                            "Prefix Length";
                        }
                        uses ncs_template_IPV4-RIB-EDM-ROUTE;
                      }
                    }
                    container destination-kw {
                      description
                        "Destination KW";
                      container dest-best-routes {
                        description
                          "Best Local";
                        list dest-best-route {
                          // NCS patched for predictable order
                          ordered-by user;
                          key "address";
                          description
                            "Best local route information for a
                             specific Address ";
                          leaf address {
                            type string;
                            description
                              "Network Address";
                          }
                          uses ncs_template_IPV4-RIB-EDM-ROUTE;
                        }
                      }
                      container dest-q-routes {
                        description
                          "Quarantine";
                        list dest-q-route {
                          // NCS patched for predictable order
                          ordered-by user;
                          key "address prefix-length";
                          description
                            "Route information of a specific Backup
                             Address ";
                          leaf address {
                            type string;
                            description
                              "Network Address";
                          }
                          leaf prefix-length {
                            type string;
                            description
                              "Prefix Length";
                          }
                          uses ncs_template_IPV4-RIB-EDM-ROUTE;
                        }
                      }
                      container dest-backup-routes {
                        description
                          "Backup";
                        list dest-backup-route {
                          // NCS patched for predictable order
                          ordered-by user;
                          key "address prefix-length";
                          description
                            "Route information of a specific Backup
                             Address ";
                          leaf address {
                            type string;
                            description
                              "Network Address";
                          }
                          leaf prefix-length {
                            type string;
                            description
                              "Prefix Length";
                          }
                          uses ncs_template_IPV4-RIB-EDM-ROUTE;
                        }
                      }
                      container dest-next-hop-routes {
                        description
                          "Resolving next hop";
                        list dest-next-hop-route {
                          // NCS patched for predictable order
                          ordered-by user;
                          key "address";
                          description
                            "Nexthop information for a specific
                             address";
                          leaf address {
                            type string;
                            description
                              "Network Address";
                          }
                          uses ncs_template_IPV4-RIB-EDM-ROUTE;
                        }
                      }
                    }
                    container opaques {
                      description
                        "Opaque information ";
                      list opaque {
                        // NCS patched for predictable order
                        ordered-by user;
                        description
                          "Opaque item ";
                        leaf opaque-clientid {
                          type string;
                          description
                            "Opaque Client ID";
                        }
                        leaf opaque-protoid {
                          type string;
                          description
                            "Opaque Proto ID";
                        }
                        leaf opaque-key-type {
                          type string;
                          description
                            "Opaque key type";
                        }
                        leaf opaque-key-size {
                          type string;
                          description
                            "Opaque key size";
                        }
                        leaf opaque-data-size {
                          type string;
                          description
                            "Opaque data size";
                        }
                        leaf opaque-string {
                          type string;
                          description
                            "Opaque string";
                        }
                        uses ncs_template_RIB-EDM-OPAQUE-OBJ;
                      }
                    }
                    container protocol {
                      description
                        "Contains the classification of routes by
                         protocol";
                      container mobile {
                        description
                          "Mobile Protocol";
                        uses ncs_template_NON-AS;
                      }
                      container subscriber {
                        description
                          "Subscriber Protocol";
                        uses ncs_template_NON-AS;
                      }
                      container connected {
                        description
                          "Connected Protocol";
                        uses ncs_template_NON-AS;
                      }
                      container dagr {
                        description
                          "DAGR Protocol(Direct-Attached Gateway
                           Redundancy) Protocol";
                        uses ncs_template_NON-AS;
                      }
                      container rip {
                        description
                          "RIP Protocol";
                        uses ncs_template_NON-AS;
                      }
                      container ospf {
                        description
                          "OSPF Protocol";
                        uses ncs_template_AS;
                      }
                      container srv6-local {
                        description
                          "SRv6-Local Protocol";
                        uses ncs_template_NON-AS;
                      }
                      container static {
                        description
                          "Static Protocol";
                        uses ncs_template_NON-AS;
                      }
                      container rpl {
                        description
                          "RPL Protocol";
                        uses ncs_template_AS;
                      }
                      container application {
                        description
                          "Application Protocol";
                        uses ncs_template_NON-AS;
                      }
                      container te-client {
                        description
                          "TEClient Protocol";
                        uses ncs_template_NON-AS;
                      }
                      container eigrp {
                        description
                          "EIGRP Protocol";
                        uses ncs_template_AS;
                      }
                      container local {
                        description
                          "Local Protocol";
                        container smiap {
                          description
                            "SMIAP";
                          uses ncs_template_PROTOCOL-ROUTE-TABLE;
                          uses ncs_template_INFORMATION;
                        }
                        container lspv {
                          description
                            "LSPV(Label Switched Path Verification)
                             Protocol";
                          uses ncs_template_PROTOCOL-ROUTE-TABLE;
                          uses ncs_template_INFORMATION;
                        }
                        uses ncs_template_NON-AS;
                      }
                      container bgp {
                        description
                          "BGP Protocol";
                        uses ncs_template_AS;
                      }
                      container isis {
                        description
                          "ISIS Protocol";
                        uses ncs_template_AS;
                      }
                    }
                    container q-routes {
                      description
                        "Quarantine";
                      list q-route {
                        // NCS patched for predictable order
                        ordered-by user;
                        key "address prefix-length";
                        description
                          "Route information for a specific
                           quarantined address ";
                        leaf address {
                          type string;
                          description
                            "Network Address";
                        }
                        leaf prefix-length {
                          type string;
                          description
                            "Prefix Length";
                        }
                        uses ncs_template_IPV4-RIB-EDM-ROUTE;
                      }
                    }
                    container backup-routes {
                      description
                        "Backup route information for the given
                         table";
                      list backup-route {
                        // NCS patched for predictable order
                        ordered-by user;
                        key "address prefix-length protoid";
                        description
                          "Route information for a specific backup
                           address ";
                        leaf address {
                          type string;
                          description
                            "Network Address";
                        }
                        leaf prefix-length {
                          type string;
                          description
                            "Prefix Length";
                        }
                        leaf protoid {
                          type string;
                          description
                            "Proto ID";
                        }
                        uses ncs_template_IPV4-RIB-EDM-ROUTE;
                      }
                    }
                    container adverts {
                      description
                        "Route advertiser information ";
                      list advert {
                        // NCS patched for predictable order
                        ordered-by user;
                        key "address prefix-length";
                        description
                          "Route information of a specific Network
                           Address ";
                        leaf address {
                          type string;
                          description
                            "Network Address";
                        }
                        leaf prefix-length {
                          type string;
                          description
                            "Prefix Length";
                        }
                        uses ncs_template_IPV4-RIB-EDM-ADVERT;
                      }
                    }
                    leaf route-table-name {
                      type string;
                      description
                        "Name of the route table";
                    }
                  }
                }
                leaf saf-name {
                  type string;
                  description
                    "Name of the SAF";
                }
              }
            }
            leaf af-name {
              type string;
              description
                "Name of the AF";
            }
          }
        }
        leaf vrf-name {
          type string;
          description
            "Name of the VRF";
        }
      }
    }
  }

  grouping ncs_template_AS {
    description
      "Common node of bgp, ospf, isis, eigrp, rpl";
    list as {
      // NCS patched for predictable order
      ordered-by user;
      key "as";
      description
        "Autonomous System of protocol";
      leaf as {
        type string;
        description
          "Autonomous system";
      }
      uses ncs_template_PROTOCOL-ROUTE-TABLE;
      uses ncs_template_INFORMATION;
    }
  }

  grouping ncs_template_INFORMATION {
    description
      "Common node of as, non-as, smiap, lspv";
    container information {
      description
        "Protocol related Information";
      uses ncs_template_IPV4-RIB-EDM-PROTO;
    }
  }

  grouping ncs_template_RIB-TABLE {
    description
      "Common node of rib, rib-stdby";
    container rib-table-ids {
      description
        "RIB table";
      list rib-table-id {
        // NCS patched for predictable order
        ordered-by user;
        key "tableid";
        description
          "Specific Table";
        container summary-protos {
          description
            "RIB table summary";
          list summary-proto {
            // NCS patched for predictable order
            ordered-by user;
            key "protoid";
            description
              "Route summary information for a specific
               table/protocol ";
            leaf protoid {
              type string;
              description
                "Proto ID";
            }
            uses ncs_template_RIB-EDM-PROTO-ROUTE-SUMM-DETAIL;
          }
        }
        container rib-table-itf-hndls {
          description
            "RIB table interface";
          list rib-table-itf-hndl {
            // NCS patched for predictable order
            ordered-by user;
            key "handle";
            description
              "Interface handle";
            leaf handle {
              type string;
              description
                "Itf Handle";
            }
            list itf-route {
              // NCS patched for predictable order
              ordered-by user;
              key "address";
              description
                "Route information for a specific
                 table/interface ";
              leaf address {
                type string;
                description
                  "Network Address";
              }
              uses ncs_template_IPV4-RIB-EDM-ROUTE;
            }
          }
        }
        container information {
          description
            "Table related Information";
          uses ncs_template_IPV4-RIB-EDM-TABLE;
        }
        leaf tableid {
          type string;
          description
            "Table ID";
        }
      }
    }
  }

  grouping ncs_template_NON-AS {
    description
      "Common node of local, srv6-local, connected, rip,
       static, subscriber, mobile, dagr, application,
       te-client";
    container non-as {
      description
        "Non Autonomous System of protocol";
      uses ncs_template_PROTOCOL-ROUTE-TABLE;
      uses ncs_template_INFORMATION;
    }
  }

  grouping ncs_template_PROTOCOL-ROUTE-TABLE {
    description
      "Common node of as, non-as, smiap, lspv";
    container protocol-routes {
      description
        "Protocol specific Route";
      list protocol-route {
        // NCS patched for predictable order
        ordered-by user;
        key "address prefix-length";
        description
          " Route information of a specific Network
           Address ";
        leaf address {
          type string;
          description
            "Network Address";
        }
        leaf prefix-length {
          type string;
          description
            "Prefix Length";
        }
        uses ncs_template_IPV4-RIB-EDM-ROUTE;
      }
    }
  }

  grouping ncs_rpc_notif_VRF-TABLE {
    description
      "Common node of rib, rib-stdby";
    container vrfs {
      description
        "VRF table";
      list vrf {
        key "vrf-name";
        description
          "Specific VRF";
        container afs {
          description
            "Address Family (AF) table";
          list af {
            key "af-name";
            description
              "Specific AF information";
            container safs {
              description
                "Subsequent Address Family (SAF) table";
              list saf {
                key "saf-name";
                description
                  "Specific SAF information";
                container ip-rib-route-table-names {
                  description
                    "Global container of routes";
                  list ip-rib-route-table-name {
                    key "route-table-name";
                    description
                      "IP RIB Route table name for a topology";
                    container routes {
                      description
                        "Route information ";
                      list route {
                        key "address prefix-length";
                        description
                          "Route information of a specific Network
                           Address ";
                        leaf address {
                          type inet:ipv4-address-no-zone;
                          description
                            "Network Address";
                        }
                        leaf prefix-length {
                          type xr:Ipv4-prefix-length;
                          description
                            "Prefix Length";
                        }
                        uses ncs_rpc_notif_IPV4-RIB-EDM-ROUTE;
                      }
                    }
                    container deleted-routes {
                      description
                        "Deleted";
                      list deleted-route {
                        key "address prefix-length";
                        description
                          "Route information for a specific
                           deleted address ";
                        leaf address {
                          type inet:ipv4-address-no-zone;
                          description
                            "Network Address";
                        }
                        leaf prefix-length {
                          type xr:Ipv4-prefix-length;
                          description
                            "Prefix Length";
                        }
                        uses ncs_rpc_notif_IPV4-RIB-EDM-ROUTE;
                      }
                    }
                    container destination-kw {
                      description
                        "Destination KW";
                      container dest-best-routes {
                        description
                          "Best Local";
                        list dest-best-route {
                          key "address";
                          description
                            "Best local route information for a
                             specific Address ";
                          leaf address {
                            type inet:ipv4-address-no-zone;
                            description
                              "Network Address";
                          }
                          uses ncs_rpc_notif_IPV4-RIB-EDM-ROUTE;
                        }
                      }
                      container dest-q-routes {
                        description
                          "Quarantine";
                        list dest-q-route {
                          key "address prefix-length";
                          description
                            "Route information of a specific Backup
                             Address ";
                          leaf address {
                            type inet:ipv4-address-no-zone;
                            description
                              "Network Address";
                          }
                          leaf prefix-length {
                            type xr:Ipv4-prefix-length;
                            description
                              "Prefix Length";
                          }
                          uses ncs_rpc_notif_IPV4-RIB-EDM-ROUTE;
                        }
                      }
                      container dest-backup-routes {
                        description
                          "Backup";
                        list dest-backup-route {
                          key "address prefix-length";
                          description
                            "Route information of a specific Backup
                             Address ";
                          leaf address {
                            type inet:ipv4-address-no-zone;
                            description
                              "Network Address";
                          }
                          leaf prefix-length {
                            type xr:Ipv4-prefix-length;
                            description
                              "Prefix Length";
                          }
                          uses ncs_rpc_notif_IPV4-RIB-EDM-ROUTE;
                        }
                      }
                      container dest-next-hop-routes {
                        description
                          "Resolving next hop";
                        list dest-next-hop-route {
                          key "address";
                          description
                            "Nexthop information for a specific
                             address";
                          leaf address {
                            type inet:ipv4-address-no-zone;
                            description
                              "Network Address";
                          }
                          uses ncs_rpc_notif_IPV4-RIB-EDM-ROUTE;
                        }
                      }
                    }
                    container opaques {
                      description
                        "Opaque information ";
                      list opaque {
                        description
                          "Opaque item ";
                        leaf opaque-clientid {
                          type uint32;
                          description
                            "Opaque Client ID";
                        }
                        leaf opaque-protoid {
                          type uint32;
                          description
                            "Opaque Proto ID";
                        }
                        leaf opaque-key-type {
                          type uint32;
                          description
                            "Opaque key type";
                        }
                        leaf opaque-key-size {
                          type uint32;
                          description
                            "Opaque key size";
                        }
                        leaf opaque-data-size {
                          type uint32;
                          description
                            "Opaque data size";
                        }
                        leaf opaque-string {
                          type xr:Cisco-ios-xr-string;
                          description
                            "Opaque string";
                        }
                        uses ncs_rpc_notif_RIB-EDM-OPAQUE-OBJ;
                      }
                    }
                    container protocol {
                      description
                        "Contains the classification of routes by
                         protocol";
                      container mobile {
                        description
                          "Mobile Protocol";
                        uses ncs_rpc_notif_NON-AS;
                      }
                      container subscriber {
                        description
                          "Subscriber Protocol";
                        uses ncs_rpc_notif_NON-AS;
                      }
                      container connected {
                        description
                          "Connected Protocol";
                        uses ncs_rpc_notif_NON-AS;
                      }
                      container dagr {
                        description
                          "DAGR Protocol(Direct-Attached Gateway
                           Redundancy) Protocol";
                        uses ncs_rpc_notif_NON-AS;
                      }
                      container rip {
                        description
                          "RIP Protocol";
                        uses ncs_rpc_notif_NON-AS;
                      }
                      container ospf {
                        description
                          "OSPF Protocol";
                        uses ncs_rpc_notif_AS;
                      }
                      container srv6-local {
                        description
                          "SRv6-Local Protocol";
                        uses ncs_rpc_notif_NON-AS;
                      }
                      container static {
                        description
                          "Static Protocol";
                        uses ncs_rpc_notif_NON-AS;
                      }
                      container rpl {
                        description
                          "RPL Protocol";
                        uses ncs_rpc_notif_AS;
                      }
                      container application {
                        description
                          "Application Protocol";
                        uses ncs_rpc_notif_NON-AS;
                      }
                      container te-client {
                        description
                          "TEClient Protocol";
                        uses ncs_rpc_notif_NON-AS;
                      }
                      container eigrp {
                        description
                          "EIGRP Protocol";
                        uses ncs_rpc_notif_AS;
                      }
                      container local {
                        description
                          "Local Protocol";
                        container smiap {
                          description
                            "SMIAP";
                          uses ncs_rpc_notif_PROTOCOL-ROUTE-TABLE;
                          uses ncs_rpc_notif_INFORMATION;
                        }
                        container lspv {
                          description
                            "LSPV(Label Switched Path Verification)
                             Protocol";
                          uses ncs_rpc_notif_PROTOCOL-ROUTE-TABLE;
                          uses ncs_rpc_notif_INFORMATION;
                        }
                        uses ncs_rpc_notif_NON-AS;
                      }
                      container bgp {
                        description
                          "BGP Protocol";
                        uses ncs_rpc_notif_AS;
                      }
                      container isis {
                        description
                          "ISIS Protocol";
                        uses ncs_rpc_notif_AS;
                      }
                    }
                    container q-routes {
                      description
                        "Quarantine";
                      list q-route {
                        key "address prefix-length";
                        description
                          "Route information for a specific
                           quarantined address ";
                        leaf address {
                          type inet:ipv4-address-no-zone;
                          description
                            "Network Address";
                        }
                        leaf prefix-length {
                          type xr:Ipv4-prefix-length;
                          description
                            "Prefix Length";
                        }
                        uses ncs_rpc_notif_IPV4-RIB-EDM-ROUTE;
                      }
                    }
                    container backup-routes {
                      description
                        "Backup route information for the given
                         table";
                      list backup-route {
                        key "address prefix-length protoid";
                        description
                          "Route information for a specific backup
                           address ";
                        leaf address {
                          type inet:ipv4-address-no-zone;
                          description
                            "Network Address";
                        }
                        leaf prefix-length {
                          type xr:Ipv4-prefix-length;
                          description
                            "Prefix Length";
                        }
                        leaf protoid {
                          type uint32;
                          description
                            "Proto ID";
                        }
                        uses ncs_rpc_notif_IPV4-RIB-EDM-ROUTE;
                      }
                    }
                    container adverts {
                      description
                        "Route advertiser information ";
                      list advert {
                        key "address prefix-length";
                        description
                          "Route information of a specific Network
                           Address ";
                        leaf address {
                          type inet:ipv4-address-no-zone;
                          description
                            "Network Address";
                        }
                        leaf prefix-length {
                          type xr:Ipv4-prefix-length;
                          description
                            "Prefix Length";
                        }
                        uses ncs_rpc_notif_IPV4-RIB-EDM-ADVERT;
                      }
                    }
                    leaf route-table-name {
                      type xr:Cisco-ios-xr-string;
                      description
                        "Name of the route table";
                    }
                  }
                }
                leaf saf-name {
                  type Rib-saf-name;
                  description
                    "Name of the SAF";
                }
              }
            }
            leaf af-name {
              type Rib-af-name;
              description
                "Name of the AF";
            }
          }
        }
        leaf vrf-name {
          type xr:Cisco-ios-xr-string;
          description
            "Name of the VRF";
        }
      }
    }
  }

  grouping ncs_rpc_notif_AS {
    description
      "Common node of bgp, ospf, isis, eigrp, rpl";
    list as {
      key "as";
      description
        "Autonomous System of protocol";
      leaf as {
        type xr:Cisco-ios-xr-string;
        description
          "Autonomous system";
      }
      uses ncs_rpc_notif_PROTOCOL-ROUTE-TABLE;
      uses ncs_rpc_notif_INFORMATION;
    }
  }

  grouping ncs_rpc_notif_INFORMATION {
    description
      "Common node of as, non-as, smiap, lspv";
    container information {
      description
        "Protocol related Information";
      uses ncs_rpc_notif_IPV4-RIB-EDM-PROTO;
    }
  }

  grouping ncs_rpc_notif_RIB-TABLE {
    description
      "Common node of rib, rib-stdby";
    container rib-table-ids {
      description
        "RIB table";
      list rib-table-id {
        key "tableid";
        description
          "Specific Table";
        container summary-protos {
          description
            "RIB table summary";
          list summary-proto {
            key "protoid";
            description
              "Route summary information for a specific
               table/protocol ";
            leaf protoid {
              type uint32;
              description
                "Proto ID";
            }
            uses ncs_rpc_notif_RIB-EDM-PROTO-ROUTE-SUMM-DETAIL;
          }
        }
        container rib-table-itf-hndls {
          description
            "RIB table interface";
          list rib-table-itf-hndl {
            key "handle";
            description
              "Interface handle";
            leaf handle {
              type uint32;
              description
                "Itf Handle";
            }
            list itf-route {
              key "address";
              description
                "Route information for a specific
                 table/interface ";
              leaf address {
                type inet:ipv4-address-no-zone;
                description
                  "Network Address";
              }
              uses ncs_rpc_notif_IPV4-RIB-EDM-ROUTE;
            }
          }
        }
        container information {
          description
            "Table related Information";
          uses ncs_rpc_notif_IPV4-RIB-EDM-TABLE;
        }
        leaf tableid {
          type xr:Hex-integer;
          description
            "Table ID";
        }
      }
    }
  }

  grouping ncs_rpc_notif_NON-AS {
    description
      "Common node of local, srv6-local, connected, rip,
       static, subscriber, mobile, dagr, application,
       te-client";
    container non-as {
      description
        "Non Autonomous System of protocol";
      uses ncs_rpc_notif_PROTOCOL-ROUTE-TABLE;
      uses ncs_rpc_notif_INFORMATION;
    }
  }

  grouping ncs_rpc_notif_PROTOCOL-ROUTE-TABLE {
    description
      "Common node of as, non-as, smiap, lspv";
    container protocol-routes {
      description
        "Protocol specific Route";
      list protocol-route {
        key "address prefix-length";
        description
          " Route information of a specific Network
           Address ";
        leaf address {
          type inet:ipv4-address-no-zone;
          description
            "Network Address";
        }
        leaf prefix-length {
          type xr:Ipv4-prefix-length;
          description
            "Prefix Length";
        }
        uses ncs_rpc_notif_IPV4-RIB-EDM-ROUTE;
      }
    }
  }

  grouping live_ncs_VRF-TABLE {
    description
      "Common node of rib, rib-stdby";
    container vrfs {
      description
        "VRF table";
      list vrf {
        key "vrf-name";
        description
          "Specific VRF";
        container afs {
          description
            "Address Family (AF) table";
          list af {
            key "af-name";
            description
              "Specific AF information";
            container safs {
              description
                "Subsequent Address Family (SAF) table";
              list saf {
                key "saf-name";
                description
                  "Specific SAF information";
                container ip-rib-route-table-names {
                  description
                    "Global container of routes";
                  list ip-rib-route-table-name {
                    key "route-table-name";
                    description
                      "IP RIB Route table name for a topology";
                    container routes {
                      description
                        "Route information ";
                      list route {
                        key "address prefix-length";
                        description
                          "Route information of a specific Network
                           Address ";
                        leaf address {
                          type inet:ipv4-address-no-zone;
                          description
                            "Network Address";
                        }
                        leaf prefix-length {
                          type xr:Ipv4-prefix-length;
                          description
                            "Prefix Length";
                        }
                        uses live_ncs_IPV4-RIB-EDM-ROUTE;
                      }
                    }
                    container deleted-routes {
                      description
                        "Deleted";
                      list deleted-route {
                        key "address prefix-length";
                        description
                          "Route information for a specific
                           deleted address ";
                        leaf address {
                          type inet:ipv4-address-no-zone;
                          description
                            "Network Address";
                        }
                        leaf prefix-length {
                          type xr:Ipv4-prefix-length;
                          description
                            "Prefix Length";
                        }
                        uses live_ncs_IPV4-RIB-EDM-ROUTE;
                      }
                    }
                    container destination-kw {
                      description
                        "Destination KW";
                      container dest-best-routes {
                        description
                          "Best Local";
                        list dest-best-route {
                          key "address";
                          description
                            "Best local route information for a
                             specific Address ";
                          leaf address {
                            type inet:ipv4-address-no-zone;
                            description
                              "Network Address";
                          }
                          uses live_ncs_IPV4-RIB-EDM-ROUTE;
                        }
                      }
                      container dest-q-routes {
                        description
                          "Quarantine";
                        list dest-q-route {
                          key "address prefix-length";
                          description
                            "Route information of a specific Backup
                             Address ";
                          leaf address {
                            type inet:ipv4-address-no-zone;
                            description
                              "Network Address";
                          }
                          leaf prefix-length {
                            type xr:Ipv4-prefix-length;
                            description
                              "Prefix Length";
                          }
                          uses live_ncs_IPV4-RIB-EDM-ROUTE;
                        }
                      }
                      container dest-backup-routes {
                        description
                          "Backup";
                        list dest-backup-route {
                          key "address prefix-length";
                          description
                            "Route information of a specific Backup
                             Address ";
                          leaf address {
                            type inet:ipv4-address-no-zone;
                            description
                              "Network Address";
                          }
                          leaf prefix-length {
                            type xr:Ipv4-prefix-length;
                            description
                              "Prefix Length";
                          }
                          uses live_ncs_IPV4-RIB-EDM-ROUTE;
                        }
                      }
                      container dest-next-hop-routes {
                        description
                          "Resolving next hop";
                        list dest-next-hop-route {
                          key "address";
                          description
                            "Nexthop information for a specific
                             address";
                          leaf address {
                            type inet:ipv4-address-no-zone;
                            description
                              "Network Address";
                          }
                          uses live_ncs_IPV4-RIB-EDM-ROUTE;
                        }
                      }
                    }
                    container opaques {
                      description
                        "Opaque information ";
                      list opaque {
                        description
                          "Opaque item ";
                        leaf opaque-clientid {
                          type uint32;
                          description
                            "Opaque Client ID";
                        }
                        leaf opaque-protoid {
                          type uint32;
                          description
                            "Opaque Proto ID";
                        }
                        leaf opaque-key-type {
                          type uint32;
                          description
                            "Opaque key type";
                        }
                        leaf opaque-key-size {
                          type uint32;
                          description
                            "Opaque key size";
                        }
                        leaf opaque-data-size {
                          type uint32;
                          description
                            "Opaque data size";
                        }
                        leaf opaque-string {
                          type xr:Cisco-ios-xr-string;
                          description
                            "Opaque string";
                        }
                        uses live_ncs_RIB-EDM-OPAQUE-OBJ;
                      }
                    }
                    container protocol {
                      description
                        "Contains the classification of routes by
                         protocol";
                      container mobile {
                        description
                          "Mobile Protocol";
                        uses live_ncs_NON-AS;
                      }
                      container subscriber {
                        description
                          "Subscriber Protocol";
                        uses live_ncs_NON-AS;
                      }
                      container connected {
                        description
                          "Connected Protocol";
                        uses live_ncs_NON-AS;
                      }
                      container dagr {
                        description
                          "DAGR Protocol(Direct-Attached Gateway
                           Redundancy) Protocol";
                        uses live_ncs_NON-AS;
                      }
                      container rip {
                        description
                          "RIP Protocol";
                        uses live_ncs_NON-AS;
                      }
                      container ospf {
                        description
                          "OSPF Protocol";
                        uses live_ncs_AS;
                      }
                      container srv6-local {
                        description
                          "SRv6-Local Protocol";
                        uses live_ncs_NON-AS;
                      }
                      container static {
                        description
                          "Static Protocol";
                        uses live_ncs_NON-AS;
                      }
                      container rpl {
                        description
                          "RPL Protocol";
                        uses live_ncs_AS;
                      }
                      container application {
                        description
                          "Application Protocol";
                        uses live_ncs_NON-AS;
                      }
                      container te-client {
                        description
                          "TEClient Protocol";
                        uses live_ncs_NON-AS;
                      }
                      container eigrp {
                        description
                          "EIGRP Protocol";
                        uses live_ncs_AS;
                      }
                      container local {
                        description
                          "Local Protocol";
                        container smiap {
                          description
                            "SMIAP";
                          uses live_ncs_PROTOCOL-ROUTE-TABLE;
                          uses live_ncs_INFORMATION;
                        }
                        container lspv {
                          description
                            "LSPV(Label Switched Path Verification)
                             Protocol";
                          uses live_ncs_PROTOCOL-ROUTE-TABLE;
                          uses live_ncs_INFORMATION;
                        }
                        uses live_ncs_NON-AS;
                      }
                      container bgp {
                        description
                          "BGP Protocol";
                        uses live_ncs_AS;
                      }
                      container isis {
                        description
                          "ISIS Protocol";
                        uses live_ncs_AS;
                      }
                    }
                    container q-routes {
                      description
                        "Quarantine";
                      list q-route {
                        key "address prefix-length";
                        description
                          "Route information for a specific
                           quarantined address ";
                        leaf address {
                          type inet:ipv4-address-no-zone;
                          description
                            "Network Address";
                        }
                        leaf prefix-length {
                          type xr:Ipv4-prefix-length;
                          description
                            "Prefix Length";
                        }
                        uses live_ncs_IPV4-RIB-EDM-ROUTE;
                      }
                    }
                    container backup-routes {
                      description
                        "Backup route information for the given
                         table";
                      list backup-route {
                        key "address prefix-length protoid";
                        description
                          "Route information for a specific backup
                           address ";
                        leaf address {
                          type inet:ipv4-address-no-zone;
                          description
                            "Network Address";
                        }
                        leaf prefix-length {
                          type xr:Ipv4-prefix-length;
                          description
                            "Prefix Length";
                        }
                        leaf protoid {
                          type uint32;
                          description
                            "Proto ID";
                        }
                        uses live_ncs_IPV4-RIB-EDM-ROUTE;
                      }
                    }
                    container adverts {
                      description
                        "Route advertiser information ";
                      list advert {
                        key "address prefix-length";
                        description
                          "Route information of a specific Network
                           Address ";
                        leaf address {
                          type inet:ipv4-address-no-zone;
                          description
                            "Network Address";
                        }
                        leaf prefix-length {
                          type xr:Ipv4-prefix-length;
                          description
                            "Prefix Length";
                        }
                        uses live_ncs_IPV4-RIB-EDM-ADVERT;
                      }
                    }
                    leaf route-table-name {
                      type xr:Cisco-ios-xr-string;
                      description
                        "Name of the route table";
                    }
                  }
                }
                leaf saf-name {
                  type Rib-saf-name;
                  description
                    "Name of the SAF";
                }
              }
            }
            leaf af-name {
              type Rib-af-name;
              description
                "Name of the AF";
            }
          }
        }
        leaf vrf-name {
          type xr:Cisco-ios-xr-string;
          description
            "Name of the VRF";
        }
      }
    }
  }

  grouping live_ncs_AS {
    description
      "Common node of bgp, ospf, isis, eigrp, rpl";
    list as {
      key "as";
      description
        "Autonomous System of protocol";
      leaf as {
        type xr:Cisco-ios-xr-string;
        description
          "Autonomous system";
      }
      uses live_ncs_PROTOCOL-ROUTE-TABLE;
      uses live_ncs_INFORMATION;
    }
  }

  grouping live_ncs_INFORMATION {
    description
      "Common node of as, non-as, smiap, lspv";
    container information {
      description
        "Protocol related Information";
      uses live_ncs_IPV4-RIB-EDM-PROTO;
    }
  }

  grouping live_ncs_RIB-TABLE {
    description
      "Common node of rib, rib-stdby";
    container rib-table-ids {
      description
        "RIB table";
      list rib-table-id {
        key "tableid";
        description
          "Specific Table";
        container summary-protos {
          description
            "RIB table summary";
          list summary-proto {
            key "protoid";
            description
              "Route summary information for a specific
               table/protocol ";
            leaf protoid {
              type uint32;
              description
                "Proto ID";
            }
            uses live_ncs_RIB-EDM-PROTO-ROUTE-SUMM-DETAIL;
          }
        }
        container rib-table-itf-hndls {
          description
            "RIB table interface";
          list rib-table-itf-hndl {
            key "handle";
            description
              "Interface handle";
            leaf handle {
              type uint32;
              description
                "Itf Handle";
            }
            list itf-route {
              key "address";
              description
                "Route information for a specific
                 table/interface ";
              leaf address {
                type inet:ipv4-address-no-zone;
                description
                  "Network Address";
              }
              uses live_ncs_IPV4-RIB-EDM-ROUTE;
            }
          }
        }
        container information {
          description
            "Table related Information";
          uses live_ncs_IPV4-RIB-EDM-TABLE;
        }
        leaf tableid {
          type xr:Hex-integer;
          description
            "Table ID";
        }
      }
    }
  }

  grouping live_ncs_NON-AS {
    description
      "Common node of local, srv6-local, connected, rip,
       static, subscriber, mobile, dagr, application,
       te-client";
    container non-as {
      description
        "Non Autonomous System of protocol";
      uses live_ncs_PROTOCOL-ROUTE-TABLE;
      uses live_ncs_INFORMATION;
    }
  }

  grouping live_ncs_PROTOCOL-ROUTE-TABLE {
    description
      "Common node of as, non-as, smiap, lspv";
    container protocol-routes {
      description
        "Protocol specific Route";
      list protocol-route {
        key "address prefix-length";
        description
          " Route information of a specific Network
           Address ";
        leaf address {
          type inet:ipv4-address-no-zone;
          description
            "Network Address";
        }
        leaf prefix-length {
          type xr:Ipv4-prefix-length;
          description
            "Prefix Length";
        }
        uses live_ncs_IPV4-RIB-EDM-ROUTE;
      }
    }
  }

  grouping VRF-TABLE {
    description
      "Common node of rib, rib-stdby";
    container vrfs {
      description
        "VRF table";
      list vrf {
        key "vrf-name";
        description
          "Specific VRF";
        container afs {
          description
            "Address Family (AF) table";
          list af {
            key "af-name";
            description
              "Specific AF information";
            container safs {
              description
                "Subsequent Address Family (SAF) table";
              list saf {
                key "saf-name";
                description
                  "Specific SAF information";
                container ip-rib-route-table-names {
                  description
                    "Global container of routes";
                  list ip-rib-route-table-name {
                    key "route-table-name";
                    description
                      "IP RIB Route table name for a topology";
                    container routes {
                      description
                        "Route information ";
                      list route {
                        key "address prefix-length";
                        description
                          "Route information of a specific Network
                           Address ";
                        leaf address {
                          type inet:ipv4-address-no-zone;
                          description
                            "Network Address";
                        }
                        leaf prefix-length {
                          type xr:Ipv4-prefix-length;
                          description
                            "Prefix Length";
                        }
                        uses IPV4-RIB-EDM-ROUTE;
                      }
                    }
                    container deleted-routes {
                      description
                        "Deleted";
                      list deleted-route {
                        key "address prefix-length";
                        description
                          "Route information for a specific
                           deleted address ";
                        leaf address {
                          type inet:ipv4-address-no-zone;
                          description
                            "Network Address";
                        }
                        leaf prefix-length {
                          type xr:Ipv4-prefix-length;
                          description
                            "Prefix Length";
                        }
                        uses IPV4-RIB-EDM-ROUTE;
                      }
                    }
                    container destination-kw {
                      description
                        "Destination KW";
                      container dest-best-routes {
                        description
                          "Best Local";
                        list dest-best-route {
                          key "address";
                          description
                            "Best local route information for a
                             specific Address ";
                          leaf address {
                            type inet:ipv4-address-no-zone;
                            description
                              "Network Address";
                          }
                          uses IPV4-RIB-EDM-ROUTE;
                        }
                      }
                      container dest-q-routes {
                        description
                          "Quarantine";
                        list dest-q-route {
                          key "address prefix-length";
                          description
                            "Route information of a specific Backup
                             Address ";
                          leaf address {
                            type inet:ipv4-address-no-zone;
                            description
                              "Network Address";
                          }
                          leaf prefix-length {
                            type xr:Ipv4-prefix-length;
                            description
                              "Prefix Length";
                          }
                          uses IPV4-RIB-EDM-ROUTE;
                        }
                      }
                      container dest-backup-routes {
                        description
                          "Backup";
                        list dest-backup-route {
                          key "address prefix-length";
                          description
                            "Route information of a specific Backup
                             Address ";
                          leaf address {
                            type inet:ipv4-address-no-zone;
                            description
                              "Network Address";
                          }
                          leaf prefix-length {
                            type xr:Ipv4-prefix-length;
                            description
                              "Prefix Length";
                          }
                          uses IPV4-RIB-EDM-ROUTE;
                        }
                      }
                      container dest-next-hop-routes {
                        description
                          "Resolving next hop";
                        list dest-next-hop-route {
                          key "address";
                          description
                            "Nexthop information for a specific
                             address";
                          leaf address {
                            type inet:ipv4-address-no-zone;
                            description
                              "Network Address";
                          }
                          uses IPV4-RIB-EDM-ROUTE;
                        }
                      }
                    }
                    container opaques {
                      description
                        "Opaque information ";
                      list opaque {
                        description
                          "Opaque item ";
                        leaf opaque-clientid {
                          type uint32;
                          description
                            "Opaque Client ID";
                        }
                        leaf opaque-protoid {
                          type uint32;
                          description
                            "Opaque Proto ID";
                        }
                        leaf opaque-key-type {
                          type uint32;
                          description
                            "Opaque key type";
                        }
                        leaf opaque-key-size {
                          type uint32;
                          description
                            "Opaque key size";
                        }
                        leaf opaque-data-size {
                          type uint32;
                          description
                            "Opaque data size";
                        }
                        leaf opaque-string {
                          type xr:Cisco-ios-xr-string;
                          description
                            "Opaque string";
                        }
                        uses RIB-EDM-OPAQUE-OBJ;
                      }
                    }
                    container protocol {
                      description
                        "Contains the classification of routes by
                         protocol";
                      container mobile {
                        description
                          "Mobile Protocol";
                        uses NON-AS;
                      }
                      container subscriber {
                        description
                          "Subscriber Protocol";
                        uses NON-AS;
                      }
                      container connected {
                        description
                          "Connected Protocol";
                        uses NON-AS;
                      }
                      container dagr {
                        description
                          "DAGR Protocol(Direct-Attached Gateway
                           Redundancy) Protocol";
                        uses NON-AS;
                      }
                      container rip {
                        description
                          "RIP Protocol";
                        uses NON-AS;
                      }
                      container ospf {
                        description
                          "OSPF Protocol";
                        uses AS;
                      }
                      container srv6-local {
                        description
                          "SRv6-Local Protocol";
                        uses NON-AS;
                      }
                      container static {
                        description
                          "Static Protocol";
                        uses NON-AS;
                      }
                      container rpl {
                        description
                          "RPL Protocol";
                        uses AS;
                      }
                      container application {
                        description
                          "Application Protocol";
                        uses NON-AS;
                      }
                      container te-client {
                        description
                          "TEClient Protocol";
                        uses NON-AS;
                      }
                      container eigrp {
                        description
                          "EIGRP Protocol";
                        uses AS;
                      }
                      container local {
                        description
                          "Local Protocol";
                        container smiap {
                          description
                            "SMIAP";
                          uses PROTOCOL-ROUTE-TABLE;
                          uses INFORMATION;
                        }
                        container lspv {
                          description
                            "LSPV(Label Switched Path Verification)
                             Protocol";
                          uses PROTOCOL-ROUTE-TABLE;
                          uses INFORMATION;
                        }
                        uses NON-AS;
                      }
                      container bgp {
                        description
                          "BGP Protocol";
                        uses AS;
                      }
                      container isis {
                        description
                          "ISIS Protocol";
                        uses AS;
                      }
                    }
                    container q-routes {
                      description
                        "Quarantine";
                      list q-route {
                        key "address prefix-length";
                        description
                          "Route information for a specific
                           quarantined address ";
                        leaf address {
                          type inet:ipv4-address-no-zone;
                          description
                            "Network Address";
                        }
                        leaf prefix-length {
                          type xr:Ipv4-prefix-length;
                          description
                            "Prefix Length";
                        }
                        uses IPV4-RIB-EDM-ROUTE;
                      }
                    }
                    container backup-routes {
                      description
                        "Backup route information for the given
                         table";
                      list backup-route {
                        key "address prefix-length protoid";
                        description
                          "Route information for a specific backup
                           address ";
                        leaf address {
                          type inet:ipv4-address-no-zone;
                          description
                            "Network Address";
                        }
                        leaf prefix-length {
                          type xr:Ipv4-prefix-length;
                          description
                            "Prefix Length";
                        }
                        leaf protoid {
                          type uint32;
                          description
                            "Proto ID";
                        }
                        uses IPV4-RIB-EDM-ROUTE;
                      }
                    }
                    container adverts {
                      description
                        "Route advertiser information ";
                      list advert {
                        key "address prefix-length";
                        description
                          "Route information of a specific Network
                           Address ";
                        leaf address {
                          type inet:ipv4-address-no-zone;
                          description
                            "Network Address";
                        }
                        leaf prefix-length {
                          type xr:Ipv4-prefix-length;
                          description
                            "Prefix Length";
                        }
                        uses IPV4-RIB-EDM-ADVERT;
                      }
                    }
                    leaf route-table-name {
                      type xr:Cisco-ios-xr-string;
                      description
                        "Name of the route table";
                    }
                  }
                }
                leaf saf-name {
                  type Rib-saf-name;
                  description
                    "Name of the SAF";
                }
              }
            }
            leaf af-name {
              type Rib-af-name;
              description
                "Name of the AF";
            }
          }
        }
        leaf vrf-name {
          type xr:Cisco-ios-xr-string;
          description
            "Name of the VRF";
        }
      }
    }
  }

  grouping AS {
    description
      "Common node of bgp, ospf, isis, eigrp, rpl";
    list as {
      key "as";
      description
        "Autonomous System of protocol";
      leaf as {
        type xr:Cisco-ios-xr-string;
        description
          "Autonomous system";
      }
      uses PROTOCOL-ROUTE-TABLE;
      uses INFORMATION;
    }
  }

  grouping INFORMATION {
    description
      "Common node of as, non-as, smiap, lspv";
    container information {
      description
        "Protocol related Information";
      uses IPV4-RIB-EDM-PROTO;
    }
  }

  grouping RIB-TABLE {
    description
      "Common node of rib, rib-stdby";
    container rib-table-ids {
      description
        "RIB table";
      list rib-table-id {
        key "tableid";
        description
          "Specific Table";
        container summary-protos {
          description
            "RIB table summary";
          list summary-proto {
            key "protoid";
            description
              "Route summary information for a specific
               table/protocol ";
            leaf protoid {
              type uint32;
              description
                "Proto ID";
            }
            uses RIB-EDM-PROTO-ROUTE-SUMM-DETAIL;
          }
        }
        container rib-table-itf-hndls {
          description
            "RIB table interface";
          list rib-table-itf-hndl {
            key "handle";
            description
              "Interface handle";
            leaf handle {
              type uint32;
              description
                "Itf Handle";
            }
            list itf-route {
              key "address";
              description
                "Route information for a specific
                 table/interface ";
              leaf address {
                type inet:ipv4-address-no-zone;
                description
                  "Network Address";
              }
              uses IPV4-RIB-EDM-ROUTE;
            }
          }
        }
        container information {
          description
            "Table related Information";
          uses IPV4-RIB-EDM-TABLE;
        }
        leaf tableid {
          type xr:Hex-integer;
          description
            "Table ID";
        }
      }
    }
  }

  grouping NON-AS {
    description
      "Common node of local, srv6-local, connected, rip,
       static, subscriber, mobile, dagr, application,
       te-client";
    container non-as {
      description
        "Non Autonomous System of protocol";
      uses PROTOCOL-ROUTE-TABLE;
      uses INFORMATION;
    }
  }

  grouping PROTOCOL-ROUTE-TABLE {
    description
      "Common node of as, non-as, smiap, lspv";
    container protocol-routes {
      description
        "Protocol specific Route";
      list protocol-route {
        key "address prefix-length";
        description
          " Route information of a specific Network
           Address ";
        leaf address {
          type inet:ipv4-address-no-zone;
          description
            "Network Address";
        }
        leaf prefix-length {
          type xr:Ipv4-prefix-length;
          description
            "Prefix Length";
        }
        uses IPV4-RIB-EDM-ROUTE;
      }
    }
  }

  augment "/ncs:devices/ncs:device/ncs:config" {
    // NCS drop config false container 'rib-stdby'
    // NCS drop config false container rib
  }
  augment "/ncs:devices/ncs:device/ncs:live-status" {
    container rib-stdby {
      tailf:ncs-device-type "netconf";
      tailf:display-when "not(../../ncs:module) or ../../ncs:module[ncs:name='Cisco-IOS-XR-ip-rib-ipv4-oper'] or (../../ncs:live-status-protocol[not(ncs:capability)]) or (../../ncs:live-status-protocol/ncs:capability/ncs:module[.='Cisco-IOS-XR-ip-rib-ipv4-oper'])";
      description
        "RIB standby node operational data";
      uses live_ncs_VRF-TABLE;
      uses live_ncs_RIB-TABLE;
    }
    container rib {
      tailf:ncs-device-type "netconf";
      tailf:display-when "not(../../ncs:module) or ../../ncs:module[ncs:name='Cisco-IOS-XR-ip-rib-ipv4-oper'] or (../../ncs:live-status-protocol[not(ncs:capability)]) or (../../ncs:live-status-protocol/ncs:capability/ncs:module[.='Cisco-IOS-XR-ip-rib-ipv4-oper'])";
      description
        "rib";
      uses live_ncs_VRF-TABLE;
      uses live_ncs_RIB-TABLE;
    }
  }
  augment "/ncs:devices/ncs:template/ncs:ned-id/ncs:config" {
    // NCS drop config false container 'rib-stdby'
    // NCS drop config false container rib
  }
}
