submodule Cisco-IOS-XR-ipv4-ping-act {
  // Generated by yanger -t ncs
  tailf:mount-id f5500-nc-1.0:f5500-nc-1.0;

  belongs-to Cisco-IOS-XR-ping-act {
    prefix Cisco-IOS-XR-ipv4-ping-act;
  }

  import Cisco-IOS-XR-types {
    prefix xr;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR IPv4 ping action package configuration.

     Copyright (c) 2016-2017 by Cisco Systems, Inc.
     All rights reserved.";

  revision 2016-08-20 {
    description
      "IOS XR 6.2.1 revision.";
  }

  grouping ncs_template_PING-COMMON-INPUT-OUTPUT-OPTIONS {
    leaf destination {
      description
        "Ping destination address or hostname";
      type string;
      // NCS drop mandatory statement
    }
    leaf repeat-count {
      description
        "Number of ping packets to be sent out";
      type string;
      // NCS drop default statement
    }
    leaf data-size {
      description
        "Size of ping packet";
      type string;
      // NCS drop default statement
    }
    leaf timeout {
      description
        "Timeout in seconds";
      type string;
      // NCS drop default statement
    }
    leaf interval {
      description
        "Ping interval in milli seconds";
      type string;
      // NCS drop default statement
    }
    leaf pattern {
      description
        "Pattern of payload data";
      type string;
    }
    leaf sweep {
      description
        "Sweep is enabled";
      type string;
    }
  }

  grouping ncs_template_PING-OPTIONS {
    uses ncs_template_PING-COMMON-INPUT-OUTPUT-OPTIONS;
    leaf vrf-name {
      description
        "VRF name";
      type string;
    }
    leaf source {
      description
        "Source address or interface";
      type string;
    }
    leaf verbose {
      description
        "Validate return packet";
      type string;
    }
  }

  grouping ncs_template_IPV4-SPECIFIC-OPTIONS {
    leaf type-of-service {
      description
        "Type of Service";
      type string;
    }
    leaf do-not-frag {
      description
        "Do Not Fragment";
      type string;
    }
    leaf validate {
      description
        "Validate return packet";
      type string;
    }
  }

  grouping ncs_template_IPV4-PING-OPTIONS {
    uses ncs_template_PING-OPTIONS;
    uses ncs_template_IPV4-SPECIFIC-OPTIONS;
  }

  grouping ncs_template_IPV4-PING-INPUT {
    uses ncs_template_IPV4-PING-OPTIONS;
  }

  grouping ncs_template_IPV4-PING-OUTPUT {
    uses ncs_template_PING-COMMON-INPUT-OUTPUT-OPTIONS;
    container replies {
      list reply {
        // NCS patched for predictable order
        ordered-by user;
        key "reply-index";
        leaf reply-index {
          description
            "Index of the reply list";
          type string;
        }
        leaf result {
          description
            "Response for each packet";
          type string;
        }
        container broadcast-reply-addresses {
          list broadcast-reply-address {
            // NCS patched for predictable order
            ordered-by user;
            key "reply-address";
            leaf reply-address {
              description
                "Broadcast reply address";
              type string;
            }
            leaf result {
              description
                "Sign for each reply packet";
              type string;
            }
          }
        }
      }
    }
    leaf hits {
      description
        "Number of packets reach to destination and get reply back";
      type string;
    }
    leaf total {
      description
        "Total number of packets sent out";
      type string;
    }
    leaf success-rate {
      description
        "Successful rate of ping";
      type string;
    }
    leaf rtt-min {
      description
        "Minimum value of Round Trip Time";
      type string;
    }
    leaf rtt-avg {
      description
        "Average value of Round Trip Time";
      type string;
    }
    leaf rtt-max {
      description
        "Maximum value of Round Trip Time";
      type string;
    }
    leaf sweep-min {
      description
        "Minimum value of sweep size";
      type string;
    }
    leaf sweep-max {
      description
        "Maximum value of sweep size";
      type string;
    }
    leaf rotate-pattern {
      description
        "Rotate Pattern is enabled";
      type string;
    }
    leaf ping-error-response {
      description
        "Error response for each ping, in case of bulk ping";
      type string;
    }
  }

  grouping ncs_rpc_notif_PING-COMMON-INPUT-OUTPUT-OPTIONS {
    leaf destination {
      description
        "Ping destination address or hostname";
      type string;
      mandatory true;
    }
    leaf repeat-count {
      description
        "Number of ping packets to be sent out";
      type uint64 {
        range "1..64";
      }
      default "5";
    }
    leaf data-size {
      description
        "Size of ping packet";
      type uint64 {
        range "36..18024";
      }
      default "100";
    }
    leaf timeout {
      description
        "Timeout in seconds";
      type uint64 {
        range "0..36";
      }
      default "2";
    }
    leaf interval {
      description
        "Ping interval in milli seconds";
      type uint32 {
        range "0..3600";
      }
      default "10";
    }
    leaf pattern {
      description
        "Pattern of payload data";
      type xr:Hex-integer;
    }
    leaf sweep {
      description
        "Sweep is enabled";
      type boolean;
    }
  }

  grouping ncs_rpc_notif_PING-OPTIONS {
    uses ncs_rpc_notif_PING-COMMON-INPUT-OUTPUT-OPTIONS;
    leaf vrf-name {
      description
        "VRF name";
      type string;
    }
    leaf source {
      description
        "Source address or interface";
      type string;
    }
    leaf verbose {
      description
        "Validate return packet";
      type boolean;
    }
  }

  grouping ncs_rpc_notif_IPV4-SPECIFIC-OPTIONS {
    leaf type-of-service {
      description
        "Type of Service";
      type uint8 {
        range "0..255";
      }
    }
    leaf do-not-frag {
      description
        "Do Not Fragment";
      type boolean;
    }
    leaf validate {
      description
        "Validate return packet";
      type boolean;
    }
  }

  grouping ncs_rpc_notif_IPV4-PING-OPTIONS {
    uses ncs_rpc_notif_PING-OPTIONS;
    uses ncs_rpc_notif_IPV4-SPECIFIC-OPTIONS;
  }

  grouping ncs_rpc_notif_IPV4-PING-INPUT {
    uses ncs_rpc_notif_IPV4-PING-OPTIONS;
  }

  grouping ncs_rpc_notif_IPV4-PING-OUTPUT {
    uses ncs_rpc_notif_PING-COMMON-INPUT-OUTPUT-OPTIONS;
    container replies {
      list reply {
        key "reply-index";
        leaf reply-index {
          description
            "Index of the reply list";
          type uint64 {
            range "1..2147483647";
          }
        }
        leaf result {
          description
            "Response for each packet";
          type string;
        }
        container broadcast-reply-addresses {
          list broadcast-reply-address {
            key "reply-address";
            leaf reply-address {
              description
                "Broadcast reply address";
              type string;
            }
            leaf result {
              description
                "Sign for each reply packet";
              type string;
            }
          }
        }
      }
    }
    leaf hits {
      description
        "Number of packets reach to destination and get reply back";
      type uint64;
    }
    leaf total {
      description
        "Total number of packets sent out";
      type uint64;
    }
    leaf success-rate {
      description
        "Successful rate of ping";
      type uint64;
    }
    leaf rtt-min {
      description
        "Minimum value of Round Trip Time";
      type uint64;
    }
    leaf rtt-avg {
      description
        "Average value of Round Trip Time";
      type uint64;
    }
    leaf rtt-max {
      description
        "Maximum value of Round Trip Time";
      type uint64;
    }
    leaf sweep-min {
      description
        "Minimum value of sweep size";
      type uint32;
    }
    leaf sweep-max {
      description
        "Maximum value of sweep size";
      type uint64;
    }
    leaf rotate-pattern {
      description
        "Rotate Pattern is enabled";
      type boolean;
    }
    leaf ping-error-response {
      description
        "Error response for each ping, in case of bulk ping";
      type string;
    }
  }

  grouping live_ncs_PING-COMMON-INPUT-OUTPUT-OPTIONS {
    leaf destination {
      description
        "Ping destination address or hostname";
      type string;
      // NCS drop mandatory statement
    }
    leaf repeat-count {
      description
        "Number of ping packets to be sent out";
      type uint64 {
        range "1..64";
      }
      // NCS drop default statement
    }
    leaf data-size {
      description
        "Size of ping packet";
      type uint64 {
        range "36..18024";
      }
      // NCS drop default statement
    }
    leaf timeout {
      description
        "Timeout in seconds";
      type uint64 {
        range "0..36";
      }
      // NCS drop default statement
    }
    leaf interval {
      description
        "Ping interval in milli seconds";
      type uint32 {
        range "0..3600";
      }
      // NCS drop default statement
    }
    leaf pattern {
      description
        "Pattern of payload data";
      type xr:Hex-integer;
    }
    leaf sweep {
      description
        "Sweep is enabled";
      type boolean;
    }
  }

  grouping live_ncs_PING-OPTIONS {
    uses live_ncs_PING-COMMON-INPUT-OUTPUT-OPTIONS;
    leaf vrf-name {
      description
        "VRF name";
      type string;
    }
    leaf source {
      description
        "Source address or interface";
      type string;
    }
    leaf verbose {
      description
        "Validate return packet";
      type boolean;
    }
  }

  grouping live_ncs_IPV4-SPECIFIC-OPTIONS {
    leaf type-of-service {
      description
        "Type of Service";
      type uint8 {
        range "0..255";
      }
    }
    leaf do-not-frag {
      description
        "Do Not Fragment";
      type boolean;
    }
    leaf validate {
      description
        "Validate return packet";
      type boolean;
    }
  }

  grouping live_ncs_IPV4-PING-OPTIONS {
    uses live_ncs_PING-OPTIONS;
    uses live_ncs_IPV4-SPECIFIC-OPTIONS;
  }

  grouping live_ncs_IPV4-PING-INPUT {
    uses live_ncs_IPV4-PING-OPTIONS;
  }

  grouping live_ncs_IPV4-PING-OUTPUT {
    uses live_ncs_PING-COMMON-INPUT-OUTPUT-OPTIONS;
    container replies {
      list reply {
        key "reply-index";
        leaf reply-index {
          description
            "Index of the reply list";
          type uint64 {
            range "1..2147483647";
          }
        }
        leaf result {
          description
            "Response for each packet";
          type string;
        }
        container broadcast-reply-addresses {
          list broadcast-reply-address {
            key "reply-address";
            leaf reply-address {
              description
                "Broadcast reply address";
              type string;
            }
            leaf result {
              description
                "Sign for each reply packet";
              type string;
            }
          }
        }
      }
    }
    leaf hits {
      description
        "Number of packets reach to destination and get reply back";
      type uint64;
    }
    leaf total {
      description
        "Total number of packets sent out";
      type uint64;
    }
    leaf success-rate {
      description
        "Successful rate of ping";
      type uint64;
    }
    leaf rtt-min {
      description
        "Minimum value of Round Trip Time";
      type uint64;
    }
    leaf rtt-avg {
      description
        "Average value of Round Trip Time";
      type uint64;
    }
    leaf rtt-max {
      description
        "Maximum value of Round Trip Time";
      type uint64;
    }
    leaf sweep-min {
      description
        "Minimum value of sweep size";
      type uint32;
    }
    leaf sweep-max {
      description
        "Maximum value of sweep size";
      type uint64;
    }
    leaf rotate-pattern {
      description
        "Rotate Pattern is enabled";
      type boolean;
    }
    leaf ping-error-response {
      description
        "Error response for each ping, in case of bulk ping";
      type string;
    }
  }

  grouping PING-COMMON-INPUT-OUTPUT-OPTIONS {
    leaf destination {
      description
        "Ping destination address or hostname";
      type string;
      mandatory true;
    }
    leaf repeat-count {
      description
        "Number of ping packets to be sent out";
      type uint64 {
        range "1..64";
      }
      default "5";
    }
    leaf data-size {
      description
        "Size of ping packet";
      type uint64 {
        range "36..18024";
      }
      default "100";
    }
    leaf timeout {
      description
        "Timeout in seconds";
      type uint64 {
        range "0..36";
      }
      default "2";
    }
    leaf interval {
      description
        "Ping interval in milli seconds";
      type uint32 {
        range "0..3600";
      }
      default "10";
    }
    leaf pattern {
      description
        "Pattern of payload data";
      type xr:Hex-integer;
    }
    leaf sweep {
      description
        "Sweep is enabled";
      type boolean;
    }
  }

  grouping PING-OPTIONS {
    uses PING-COMMON-INPUT-OUTPUT-OPTIONS;
    leaf vrf-name {
      description
        "VRF name";
      type string;
    }
    leaf source {
      description
        "Source address or interface";
      type string;
    }
    leaf verbose {
      description
        "Validate return packet";
      type boolean;
    }
  }

  grouping IPV4-SPECIFIC-OPTIONS {
    leaf type-of-service {
      description
        "Type of Service";
      type uint8 {
        range "0..255";
      }
    }
    leaf do-not-frag {
      description
        "Do Not Fragment";
      type boolean;
    }
    leaf validate {
      description
        "Validate return packet";
      type boolean;
    }
  }

  grouping IPV4-PING-OPTIONS {
    uses PING-OPTIONS;
    uses IPV4-SPECIFIC-OPTIONS;
  }

  grouping IPV4-PING-INPUT {
    uses IPV4-PING-OPTIONS;
  }

  grouping IPV4-PING-OUTPUT {
    uses PING-COMMON-INPUT-OUTPUT-OPTIONS;
    container replies {
      list reply {
        key "reply-index";
        leaf reply-index {
          description
            "Index of the reply list";
          type uint64 {
            range "1..2147483647";
          }
        }
        leaf result {
          description
            "Response for each packet";
          type string;
        }
        container broadcast-reply-addresses {
          list broadcast-reply-address {
            key "reply-address";
            leaf reply-address {
              description
                "Broadcast reply address";
              type string;
            }
            leaf result {
              description
                "Sign for each reply packet";
              type string;
            }
          }
        }
      }
    }
    leaf hits {
      description
        "Number of packets reach to destination and get reply back";
      type uint64;
    }
    leaf total {
      description
        "Total number of packets sent out";
      type uint64;
    }
    leaf success-rate {
      description
        "Successful rate of ping";
      type uint64;
    }
    leaf rtt-min {
      description
        "Minimum value of Round Trip Time";
      type uint64;
    }
    leaf rtt-avg {
      description
        "Average value of Round Trip Time";
      type uint64;
    }
    leaf rtt-max {
      description
        "Maximum value of Round Trip Time";
      type uint64;
    }
    leaf sweep-min {
      description
        "Minimum value of sweep size";
      type uint32;
    }
    leaf sweep-max {
      description
        "Maximum value of sweep size";
      type uint64;
    }
    leaf rotate-pattern {
      description
        "Rotate Pattern is enabled";
      type boolean;
    }
    leaf ping-error-response {
      description
        "Error response for each ping, in case of bulk ping";
      type string;
    }
  }
}
