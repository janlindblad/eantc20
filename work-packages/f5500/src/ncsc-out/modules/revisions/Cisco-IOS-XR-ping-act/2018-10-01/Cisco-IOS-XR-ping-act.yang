module Cisco-IOS-XR-ping-act {
  // Generated by yanger -t ncs
  tailf:mount-id f5500-nc-1.0:f5500-nc-1.0;
  tailf:ncs-device-type "netconf";

  namespace "http://cisco.com/ns/yang/Cisco-IOS-XR-ping-act";
  prefix Cisco-IOS-XR-ping-act;

  include Cisco-IOS-XR-ipv4-ping-act;
  include Cisco-IOS-XR-ipv6-ping-act;
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ping action package configuration.

     Copyright (c) 2016, 2018 by Cisco Systems, Inc.
     All rights reserved.";

  revision 2018-10-01 {
    description
      "IOS XR 6.2.1 revision.";
  }

  augment "/ncs:devices/ncs:device/ncs:rpc" {
    container rpc-ping {
      tailf:ncs-device-type "netconf";
      tailf:display-when "not(../../ncs:module) or ../../ncs:module[ncs:name='Cisco-IOS-XR-ping-act']";
      tailf:action ping {
        tailf:actionpoint ncsproxy {
          tailf:internal;
        }
        description
          "Send echo messages";
        input {
          container destination {
            presence "ping input";
            uses ncs_rpc_notif_PING-OPTIONS;
            uses ncs_rpc_notif_IPV4-SPECIFIC-OPTIONS;
            uses ncs_rpc_notif_IPV6-SPECIFIC-OPTIONS;
          }
          list ipv4 {
            key "destination";
            uses ncs_rpc_notif_IPV4-PING-INPUT;
          }
          container ipv6 {
            presence "ipv6 ping input";
            uses ncs_rpc_notif_IPV6-PING-INPUT;
          }
        }
        output {
          container ping-response {
            list ipv4 {
              key "destination";
              uses ncs_rpc_notif_IPV4-PING-OUTPUT;
            }
            container ipv6 {
              presence "ipv6 ping output";
              uses ncs_rpc_notif_IPV6-PING-OUTPUT;
            }
          }
        }
      }
    }
  }
  augment "/ncs:devices/ncs:device-group/ncs:ned-id/ncs:rpc" {
    container rpc-ping {
      tailf:ncs-device-type "netconf";
      tailf:display-when "/ncs:devices/ncs:device[ncs:name=current()/../../../ncs:member]/ncs:module[ncs:name='Cisco-IOS-XR-ping-act']";
      tailf:action ping {
        tailf:actionpoint ncsproxy {
          tailf:internal;
        }
        description
          "Send echo messages";
        input {
          container destination {
            presence "ping input";
            uses ncs_rpc_notif_PING-OPTIONS;
            uses ncs_rpc_notif_IPV4-SPECIFIC-OPTIONS;
            uses ncs_rpc_notif_IPV6-SPECIFIC-OPTIONS;
          }
          list ipv4 {
            key "destination";
            uses ncs_rpc_notif_IPV4-PING-INPUT;
          }
          container ipv6 {
            presence "ipv6 ping input";
            uses ncs_rpc_notif_IPV6-PING-INPUT;
          }
        }
        output {
          container "device" {
            leaf "name" {
              type string;
            }
            leaf "info" {
              type string;
            }
            container "result" {
              container ping-response {
                list ipv4 {
                  key "destination";
                  uses ncs_rpc_notif_IPV4-PING-OUTPUT;
                }
                container ipv6 {
                  presence "ipv6 ping output";
                  uses ncs_rpc_notif_IPV6-PING-OUTPUT;
                }
              }
            }
          }
        }
      }
    }
  }
}
