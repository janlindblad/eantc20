submodule Cisco-IOS-XR-ipv6-ping-act {
  // Generated by yanger -t ncs
  tailf:mount-id f5500-nc-1.0:f5500-nc-1.0;

  belongs-to Cisco-IOS-XR-ping-act {
    prefix Cisco-IOS-XR-ipv6-ping-act;
  }

  include Cisco-IOS-XR-ipv4-ping-act;
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR IPv6 ping action package configuration.

     Copyright (c) 2016 by Cisco Systems, Inc.
     All rights reserved.";

  revision 2016-09-13 {
    description
      "IOS XR 6.2.1 revision.";
  }

  grouping ncs_template_IPV6-SPECIFIC-OPTIONS {
    leaf priority {
      description
        "Priority of the packet";
      type string;
    }
    leaf outgoing-interface {
      description
        "Outgoing interface, needed in case of ping to link local address";
      type string;
    }
  }

  grouping ncs_template_IPV6-PING-INPUT {
    uses ncs_template_PING-OPTIONS;
    uses ncs_template_IPV6-SPECIFIC-OPTIONS;
  }

  grouping ncs_template_IPV6-PING-OUTPUT {
    uses ncs_template_PING-COMMON-INPUT-OUTPUT-OPTIONS;
    leaf sweep-min {
      description
        "Minimum value of sweep size";
      type string;
    }
    leaf sweep-max {
      description
        "Maximum value of sweep size";
      type string;
    }
    leaf rotate-pattern {
      description
        "Rotate Pattern is enabled";
      type string;
    }
    container replies {
      list reply {
        // NCS patched for predictable order
        ordered-by user;
        key "reply-index";
        leaf reply-index {
          description
            "Index of the reply list";
          type string;
        }
        leaf result {
          description
            "Response for each packet";
          type string;
        }
      }
    }
    leaf hits {
      description
        "Number of packets reach to destination and get reply back";
      type string;
    }
    leaf total {
      description
        "Total number of packets sent out";
      type string;
    }
    leaf success-rate {
      description
        "Successful rate of ping";
      type string;
    }
    leaf rtt-min {
      description
        "Minimum value of Round Trip Time";
      type string;
    }
    leaf rtt-avg {
      description
        "Average value of Round Trip Time";
      type string;
    }
    leaf rtt-max {
      description
        "Maximum value of Round Trip Time";
      type string;
    }
  }

  grouping ncs_rpc_notif_IPV6-SPECIFIC-OPTIONS {
    leaf priority {
      description
        "Priority of the packet";
      type uint8 {
        range "0..15";
      }
    }
    leaf outgoing-interface {
      description
        "Outgoing interface, needed in case of ping to link local address";
      type string;
    }
  }

  grouping ncs_rpc_notif_IPV6-PING-INPUT {
    uses ncs_rpc_notif_PING-OPTIONS;
    uses ncs_rpc_notif_IPV6-SPECIFIC-OPTIONS;
  }

  grouping ncs_rpc_notif_IPV6-PING-OUTPUT {
    uses ncs_rpc_notif_PING-COMMON-INPUT-OUTPUT-OPTIONS;
    leaf sweep-min {
      description
        "Minimum value of sweep size";
      type uint32;
    }
    leaf sweep-max {
      description
        "Maximum value of sweep size";
      type uint64;
    }
    leaf rotate-pattern {
      description
        "Rotate Pattern is enabled";
      type boolean;
    }
    container replies {
      list reply {
        key "reply-index";
        leaf reply-index {
          description
            "Index of the reply list";
          type uint64 {
            range "1..2147483647";
          }
        }
        leaf result {
          description
            "Response for each packet";
          type string;
        }
      }
    }
    leaf hits {
      description
        "Number of packets reach to destination and get reply back";
      type uint64;
    }
    leaf total {
      description
        "Total number of packets sent out";
      type uint64;
    }
    leaf success-rate {
      description
        "Successful rate of ping";
      type uint64;
    }
    leaf rtt-min {
      description
        "Minimum value of Round Trip Time";
      type uint64;
    }
    leaf rtt-avg {
      description
        "Average value of Round Trip Time";
      type uint64;
    }
    leaf rtt-max {
      description
        "Maximum value of Round Trip Time";
      type uint64;
    }
  }

  grouping live_ncs_IPV6-SPECIFIC-OPTIONS {
    leaf priority {
      description
        "Priority of the packet";
      type uint8 {
        range "0..15";
      }
    }
    leaf outgoing-interface {
      description
        "Outgoing interface, needed in case of ping to link local address";
      type string;
    }
  }

  grouping live_ncs_IPV6-PING-INPUT {
    uses live_ncs_PING-OPTIONS;
    uses live_ncs_IPV6-SPECIFIC-OPTIONS;
  }

  grouping live_ncs_IPV6-PING-OUTPUT {
    uses live_ncs_PING-COMMON-INPUT-OUTPUT-OPTIONS;
    leaf sweep-min {
      description
        "Minimum value of sweep size";
      type uint32;
    }
    leaf sweep-max {
      description
        "Maximum value of sweep size";
      type uint64;
    }
    leaf rotate-pattern {
      description
        "Rotate Pattern is enabled";
      type boolean;
    }
    container replies {
      list reply {
        key "reply-index";
        leaf reply-index {
          description
            "Index of the reply list";
          type uint64 {
            range "1..2147483647";
          }
        }
        leaf result {
          description
            "Response for each packet";
          type string;
        }
      }
    }
    leaf hits {
      description
        "Number of packets reach to destination and get reply back";
      type uint64;
    }
    leaf total {
      description
        "Total number of packets sent out";
      type uint64;
    }
    leaf success-rate {
      description
        "Successful rate of ping";
      type uint64;
    }
    leaf rtt-min {
      description
        "Minimum value of Round Trip Time";
      type uint64;
    }
    leaf rtt-avg {
      description
        "Average value of Round Trip Time";
      type uint64;
    }
    leaf rtt-max {
      description
        "Maximum value of Round Trip Time";
      type uint64;
    }
  }

  grouping IPV6-SPECIFIC-OPTIONS {
    leaf priority {
      description
        "Priority of the packet";
      type uint8 {
        range "0..15";
      }
    }
    leaf outgoing-interface {
      description
        "Outgoing interface, needed in case of ping to link local address";
      type string;
    }
  }

  grouping IPV6-PING-INPUT {
    uses PING-OPTIONS;
    uses IPV6-SPECIFIC-OPTIONS;
  }

  grouping IPV6-PING-OUTPUT {
    uses PING-COMMON-INPUT-OUTPUT-OPTIONS;
    leaf sweep-min {
      description
        "Minimum value of sweep size";
      type uint32;
    }
    leaf sweep-max {
      description
        "Maximum value of sweep size";
      type uint64;
    }
    leaf rotate-pattern {
      description
        "Rotate Pattern is enabled";
      type boolean;
    }
    container replies {
      list reply {
        key "reply-index";
        leaf reply-index {
          description
            "Index of the reply list";
          type uint64 {
            range "1..2147483647";
          }
        }
        leaf result {
          description
            "Response for each packet";
          type string;
        }
      }
    }
    leaf hits {
      description
        "Number of packets reach to destination and get reply back";
      type uint64;
    }
    leaf total {
      description
        "Total number of packets sent out";
      type uint64;
    }
    leaf success-rate {
      description
        "Successful rate of ping";
      type uint64;
    }
    leaf rtt-min {
      description
        "Minimum value of Round Trip Time";
      type uint64;
    }
    leaf rtt-avg {
      description
        "Average value of Round Trip Time";
      type uint64;
    }
    leaf rtt-max {
      description
        "Maximum value of Round Trip Time";
      type uint64;
    }
  }
}
