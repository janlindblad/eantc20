module Cisco-IOS-XR-infra-alarm-logger-cfg {
  // Generated by yanger -t ncs
  tailf:mount-id f5500-nc-1.0:f5500-nc-1.0;
  tailf:ncs-device-type "netconf";

  namespace "http://cisco.com/ns/yang/Cisco-IOS-XR-infra-alarm-logger-cfg";
  prefix Cisco-IOS-XR-infra-alarm-logger-cfg;

  import Cisco-IOS-XR-types {
    prefix xr;
  }
  import Cisco-IOS-XR-infra-alarm-logger-datatypes {
    prefix dt1;
  }
  import Cisco-IOS-XR-infra-syslog-cfg {
    prefix a1;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR infra-alarm-logger package configuration.

     This YANG module augments the
       Cisco-IOS-XR-infra-syslog-cfg
     module with configuration data.

     Copyright (c) 2013-2018 by Cisco Systems, Inc.
     All rights reserved.";

  revision 2017-02-23 {
    description
      "Added pre-config suppression feature";
  }
  revision 2015-01-07 {
    description
      "IOS XR 5.3.1 revision.";
  }

  augment "/ncs:devices/ncs:template/ncs:ned-id/ncs:config/a1:syslog" {
    container alarm-logger {
      description
        "Alarm Logger Properties";
      container alarm-filter-strings {
        description
          "List of filter strings";
        list alarm-filter-string {
          // NCS patched for predictable order
          ordered-by user;
          key "filter-string";
          description
            "Match string to filter alarms";
          leaf filter-string {
            type string;
            description
              "Filter String";
          }
        }
      }
      leaf pre-config-suppression {
        type empty;
        description
          "Suppress events from a card/VM till its
           configuration is complete";
      }
      leaf severity-level {
        type string;
        description
          "Log all events with equal or higher (lower
           level) severity than this";
      }
      leaf pre-config-suppression-timeout {
        type string;
        units "minute";
        // NCS drop default statement
        description
          "Timeout (in minutes) for pre-config events
           suppression (default 15)";
      }
      leaf buffer-size {
        type string;
        description
          "Set size of the local event buffer";
      }
      leaf source-location {
        type empty;
        description
          "Enable alarm source location in message text";
      }
      leaf threshold {
        type string;
        // NCS drop default statement
        description
          "Configure threshold (%) for capacity alarm";
      }
    }
    description
      "This augment extends the configuration data of
       'Cisco-IOS-XR-infra-syslog-cfg'";
  }
  augment "/ncs:devices/ncs:device/ncs:live-status/a1:syslog" {
    container alarm-logger {
      tailf:ncs-device-type "netconf";
      tailf:display-when "not(../../../ncs:module) or ../../../ncs:module[ncs:name='Cisco-IOS-XR-infra-alarm-logger-cfg'] or (../../../ncs:live-status-protocol[not(ncs:capability)]) or (../../../ncs:live-status-protocol/ncs:capability/ncs:module[.='Cisco-IOS-XR-infra-alarm-logger-cfg'])";
      description
        "Alarm Logger Properties";
      container alarm-filter-strings {
        description
          "List of filter strings";
        list alarm-filter-string {
          key "filter-string";
          description
            "Match string to filter alarms";
          leaf filter-string {
            type xr:Cisco-ios-xr-string;
            description
              "Filter String";
          }
        }
      }
      leaf pre-config-suppression {
        type empty;
        description
          "Suppress events from a card/VM till its
           configuration is complete";
      }
      leaf severity-level {
        type dt1:Alarm-logger-severity-level;
        description
          "Log all events with equal or higher (lower
           level) severity than this";
      }
      leaf pre-config-suppression-timeout {
        type uint32 {
          range "1..60";
        }
        units "minute";
        // NCS drop default statement
        description
          "Timeout (in minutes) for pre-config events
           suppression (default 15)";
      }
      leaf buffer-size {
        type uint32 {
          range "1024..1024000";
        }
        description
          "Set size of the local event buffer";
      }
      leaf source-location {
        type empty;
        description
          "Enable alarm source location in message text";
      }
      leaf threshold {
        type uint32 {
          range "10..100";
        }
        // NCS drop default statement
        description
          "Configure threshold (%) for capacity alarm";
      }
    }
    description
      "This augment extends the configuration data of
       'Cisco-IOS-XR-infra-syslog-cfg'";
  }
  augment "/ncs:devices/ncs:device/ncs:config/a1:syslog" {
    container alarm-logger {
      tailf:ncs-device-type "netconf";
      tailf:display-when "not(../../../ncs:module) or ../../../ncs:module[ncs:name='Cisco-IOS-XR-infra-alarm-logger-cfg']";
      description
        "Alarm Logger Properties";
      container alarm-filter-strings {
        description
          "List of filter strings";
        list alarm-filter-string {
          key "filter-string";
          description
            "Match string to filter alarms";
          leaf filter-string {
            type xr:Cisco-ios-xr-string;
            description
              "Filter String";
          }
        }
      }
      leaf pre-config-suppression {
        type empty;
        description
          "Suppress events from a card/VM till its
           configuration is complete";
      }
      leaf severity-level {
        type dt1:Alarm-logger-severity-level;
        description
          "Log all events with equal or higher (lower
           level) severity than this";
      }
      leaf pre-config-suppression-timeout {
        type uint32 {
          range "1..60";
        }
        units "minute";
        default "15";
        description
          "Timeout (in minutes) for pre-config events
           suppression (default 15)";
      }
      leaf buffer-size {
        type uint32 {
          range "1024..1024000";
        }
        description
          "Set size of the local event buffer";
      }
      leaf source-location {
        type empty;
        description
          "Enable alarm source location in message text";
      }
      leaf threshold {
        type uint32 {
          range "10..100";
        }
        default "90";
        description
          "Configure threshold (%) for capacity alarm";
      }
    }
    description
      "This augment extends the configuration data of
       'Cisco-IOS-XR-infra-syslog-cfg'";
  }
}
