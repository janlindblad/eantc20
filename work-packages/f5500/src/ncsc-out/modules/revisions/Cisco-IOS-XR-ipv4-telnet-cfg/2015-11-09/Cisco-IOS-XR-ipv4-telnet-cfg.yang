module Cisco-IOS-XR-ipv4-telnet-cfg {
  // Generated by yanger -t ncs
  tailf:mount-id f5500-nc-1.0:f5500-nc-1.0;
  tailf:ncs-device-type "netconf";

  namespace "http://cisco.com/ns/yang/Cisco-IOS-XR-ipv4-telnet-cfg";
  prefix Cisco-IOS-XR-ipv4-telnet-cfg;

  import Cisco-IOS-XR-types {
    prefix xr;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ipv4-telnet package configuration.

     This module contains definitions
     for the following management objects:
       ipv6-telnet: IPv6 telnet configuration
       ipv4-telnet: ipv4 telnet

     Copyright (c) 2013-2018 by Cisco Systems, Inc.
     All rights reserved.";

  revision 2015-11-09 {
    description
      "IOS XR 6.0 revision.";
  }

  grouping ncs_template_CLIENT {
    description
      "Common node of ipv4-telnet, ipv6-telnet";
    container client {
      description
        "Telnet client configuration";
      leaf source-interface {
        type string;
        description
          "Source interface for telnet sessions";
      }
    }
  }

  grouping ncs_rpc_notif_CLIENT {
    description
      "Common node of ipv4-telnet, ipv6-telnet";
    container client {
      description
        "Telnet client configuration";
      leaf source-interface {
        type xr:Interface-name;
        description
          "Source interface for telnet sessions";
      }
    }
  }

  grouping live_ncs_CLIENT {
    description
      "Common node of ipv4-telnet, ipv6-telnet";
    container client {
      description
        "Telnet client configuration";
      leaf source-interface {
        type xr:Interface-name;
        description
          "Source interface for telnet sessions";
      }
    }
  }

  grouping CLIENT {
    description
      "Common node of ipv4-telnet, ipv6-telnet";
    container client {
      description
        "Telnet client configuration";
      leaf source-interface {
        type xr:Interface-name;
        description
          "Source interface for telnet sessions";
      }
    }
  }

  augment "/ncs:devices/ncs:device/ncs:config" {
    container ipv6-telnet {
      tailf:ncs-device-type "netconf";
      tailf:display-when "not(../../ncs:module) or ../../ncs:module[ncs:name='Cisco-IOS-XR-ipv4-telnet-cfg']";
      description
        "IPv6 telnet configuration";
      uses CLIENT;
    }
    container ipv4-telnet {
      tailf:ncs-device-type "netconf";
      tailf:display-when "not(../../ncs:module) or ../../ncs:module[ncs:name='Cisco-IOS-XR-ipv4-telnet-cfg']";
      description
        "ipv4 telnet";
      uses CLIENT;
    }
  }
  augment "/ncs:devices/ncs:device/ncs:live-status" {
    container ipv6-telnet {
      tailf:ncs-device-type "netconf";
      tailf:display-when "not(../../ncs:module) or ../../ncs:module[ncs:name='Cisco-IOS-XR-ipv4-telnet-cfg'] or (../../ncs:live-status-protocol[not(ncs:capability)]) or (../../ncs:live-status-protocol/ncs:capability/ncs:module[.='Cisco-IOS-XR-ipv4-telnet-cfg'])";
      description
        "IPv6 telnet configuration";
      uses live_ncs_CLIENT;
    }
    container ipv4-telnet {
      tailf:ncs-device-type "netconf";
      tailf:display-when "not(../../ncs:module) or ../../ncs:module[ncs:name='Cisco-IOS-XR-ipv4-telnet-cfg'] or (../../ncs:live-status-protocol[not(ncs:capability)]) or (../../ncs:live-status-protocol/ncs:capability/ncs:module[.='Cisco-IOS-XR-ipv4-telnet-cfg'])";
      description
        "ipv4 telnet";
      uses live_ncs_CLIENT;
    }
  }
  augment "/ncs:devices/ncs:template/ncs:ned-id/ncs:config" {
    container ipv6-telnet {
      description
        "IPv6 telnet configuration";
      uses ncs_template_CLIENT;
    }
    container ipv4-telnet {
      description
        "ipv4 telnet";
      uses ncs_template_CLIENT;
    }
  }
}
