submodule Cisco-IOS-XR-linux-os-reboot-history-oper-sub1 {
  // Generated by yanger -t ncs
  tailf:mount-id f5500-nc-1.0:f5500-nc-1.0;

  belongs-to Cisco-IOS-XR-linux-os-reboot-history-oper {
    prefix Cisco-IOS-XR-linux-os-reboot-history-oper-sub1;
  }

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR linux-os-reboot-history package operational data.

     Copyright (c) 2013-2018 by Cisco Systems, Inc.
     All rights reserved.";

  revision 2015-11-09 {
    description
      "IOS XR 6.0 revision.";
  }

  grouping ncs_template_HISTORY-DETAIL {
    description
      "Reboot history details";
    leaf no {
      type string;
      description
        "Number count";
    }
    leaf time {
      type string;
      description
        "Time of reboot";
    }
    leaf cause-code {
      type string;
      description
        "Cause code for reboot";
    }
    leaf reason {
      type string;
      description
        "Reason for reboot";
    }
  }

  grouping ncs_template_HISTORY {
    description
      "Reboot history information";
    list reboot-history {
      // NCS patched for predictable order
      ordered-by user;
      description
        "Last Reboots";
      uses ncs_template_HISTORY-DETAIL;
    }
  }

  grouping ncs_rpc_notif_HISTORY-DETAIL {
    description
      "Reboot history details";
    leaf no {
      type uint32;
      description
        "Number count";
    }
    leaf time {
      type string;
      description
        "Time of reboot";
    }
    leaf cause-code {
      type uint32;
      description
        "Cause code for reboot";
    }
    leaf reason {
      type string;
      description
        "Reason for reboot";
    }
  }

  grouping ncs_rpc_notif_HISTORY {
    description
      "Reboot history information";
    list reboot-history {
      description
        "Last Reboots";
      uses ncs_rpc_notif_HISTORY-DETAIL;
    }
  }

  grouping live_ncs_HISTORY-DETAIL {
    description
      "Reboot history details";
    leaf no {
      type uint32;
      description
        "Number count";
    }
    leaf time {
      type string;
      description
        "Time of reboot";
    }
    leaf cause-code {
      type uint32;
      description
        "Cause code for reboot";
    }
    leaf reason {
      type string;
      description
        "Reason for reboot";
    }
  }

  grouping live_ncs_HISTORY {
    description
      "Reboot history information";
    list reboot-history {
      description
        "Last Reboots";
      uses live_ncs_HISTORY-DETAIL;
    }
  }

  grouping HISTORY-DETAIL {
    description
      "Reboot history details";
    leaf no {
      type uint32;
      description
        "Number count";
    }
    leaf time {
      type string;
      description
        "Time of reboot";
    }
    leaf cause-code {
      type uint32;
      description
        "Cause code for reboot";
    }
    leaf reason {
      type string;
      description
        "Reason for reboot";
    }
  }

  grouping HISTORY {
    description
      "Reboot history information";
    list reboot-history {
      description
        "Last Reboots";
      uses HISTORY-DETAIL;
    }
  }
}
