submodule Cisco-IOS-XR-fia-internal-tcam-oper-sub1 {
  // Generated by yanger -t ncs
  tailf:mount-id f5500-nc-1.0:f5500-nc-1.0;

  belongs-to Cisco-IOS-XR-fia-internal-tcam-oper {
    prefix Cisco-IOS-XR-fia-internal-tcam-oper-sub1;
  }

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR fia-internal-tcam package operational data.

     Copyright (c) 2013-2018 by Cisco Systems, Inc.
     All rights reserved.";

  revision 2015-11-09 {
    description
      "IOS XR 6.0 revision.";
  }

  grouping ncs_template_FIA-TCAM-DB {
    description
      "FIA TCAM DB";
    leaf db-id {
      type string;
      description
        "db id";
    }
    leaf db-inuse-entries {
      type string;
      description
        "db inuse entries";
    }
    leaf db-prefix {
      type string;
      description
        "db prefix";
    }
  }

  grouping ncs_template_FIA-TCAM-BANK {
    description
      "FIA TCAM BANK";
    leaf bank-id {
      type string;
      description
        "bank id";
    }
    leaf bank-key-size {
      type string;
      description
        "bank key size";
    }
    leaf bank-free-entries {
      type string;
      description
        "bank free entries";
    }
    leaf bank-inuse-entries {
      type string;
      description
        "bank inuse entries";
    }
    leaf owner {
      type string;
      description
        "owner";
    }
    leaf nof-dbs {
      type string;
      description
        "nof dbs";
    }
    list bank-db {
      // NCS patched for predictable order
      ordered-by user;
      description
        "bank db";
      uses ncs_template_FIA-TCAM-DB;
    }
  }

  grouping ncs_template_FIA-NPU-TCAM {
    description
      "FIA NPU TCAM";
    leaf npu-id {
      type string;
      description
        "npu id";
    }
    list tcam-bank {
      // NCS patched for predictable order
      ordered-by user;
      description
        "tcam bank";
      uses ncs_template_FIA-TCAM-BANK;
    }
  }

  grouping ncs_template_FIA-CARD-TCAM {
    description
      "FIA CARD TCAM";
    list npu-tcam {
      // NCS patched for predictable order
      ordered-by user;
      description
        "npu tcam";
      uses ncs_template_FIA-NPU-TCAM;
    }
  }

  grouping ncs_rpc_notif_FIA-TCAM-DB {
    description
      "FIA TCAM DB";
    leaf db-id {
      type uint32;
      description
        "db id";
    }
    leaf db-inuse-entries {
      type uint32;
      description
        "db inuse entries";
    }
    leaf db-prefix {
      type string;
      description
        "db prefix";
    }
  }

  grouping ncs_rpc_notif_FIA-TCAM-BANK {
    description
      "FIA TCAM BANK";
    leaf bank-id {
      type string;
      description
        "bank id";
    }
    leaf bank-key-size {
      type string;
      description
        "bank key size";
    }
    leaf bank-free-entries {
      type uint32;
      description
        "bank free entries";
    }
    leaf bank-inuse-entries {
      type uint32;
      description
        "bank inuse entries";
    }
    leaf owner {
      type string;
      description
        "owner";
    }
    leaf nof-dbs {
      type uint32;
      description
        "nof dbs";
    }
    list bank-db {
      description
        "bank db";
      uses ncs_rpc_notif_FIA-TCAM-DB;
    }
  }

  grouping ncs_rpc_notif_FIA-NPU-TCAM {
    description
      "FIA NPU TCAM";
    leaf npu-id {
      type uint32;
      description
        "npu id";
    }
    list tcam-bank {
      description
        "tcam bank";
      uses ncs_rpc_notif_FIA-TCAM-BANK;
    }
  }

  grouping ncs_rpc_notif_FIA-CARD-TCAM {
    description
      "FIA CARD TCAM";
    list npu-tcam {
      description
        "npu tcam";
      uses ncs_rpc_notif_FIA-NPU-TCAM;
    }
  }

  grouping live_ncs_FIA-TCAM-DB {
    description
      "FIA TCAM DB";
    leaf db-id {
      type uint32;
      description
        "db id";
    }
    leaf db-inuse-entries {
      type uint32;
      description
        "db inuse entries";
    }
    leaf db-prefix {
      type string;
      description
        "db prefix";
    }
  }

  grouping live_ncs_FIA-TCAM-BANK {
    description
      "FIA TCAM BANK";
    leaf bank-id {
      type string;
      description
        "bank id";
    }
    leaf bank-key-size {
      type string;
      description
        "bank key size";
    }
    leaf bank-free-entries {
      type uint32;
      description
        "bank free entries";
    }
    leaf bank-inuse-entries {
      type uint32;
      description
        "bank inuse entries";
    }
    leaf owner {
      type string;
      description
        "owner";
    }
    leaf nof-dbs {
      type uint32;
      description
        "nof dbs";
    }
    list bank-db {
      description
        "bank db";
      uses live_ncs_FIA-TCAM-DB;
    }
  }

  grouping live_ncs_FIA-NPU-TCAM {
    description
      "FIA NPU TCAM";
    leaf npu-id {
      type uint32;
      description
        "npu id";
    }
    list tcam-bank {
      description
        "tcam bank";
      uses live_ncs_FIA-TCAM-BANK;
    }
  }

  grouping live_ncs_FIA-CARD-TCAM {
    description
      "FIA CARD TCAM";
    list npu-tcam {
      description
        "npu tcam";
      uses live_ncs_FIA-NPU-TCAM;
    }
  }

  grouping FIA-TCAM-DB {
    description
      "FIA TCAM DB";
    leaf db-id {
      type uint32;
      description
        "db id";
    }
    leaf db-inuse-entries {
      type uint32;
      description
        "db inuse entries";
    }
    leaf db-prefix {
      type string;
      description
        "db prefix";
    }
  }

  grouping FIA-TCAM-BANK {
    description
      "FIA TCAM BANK";
    leaf bank-id {
      type string;
      description
        "bank id";
    }
    leaf bank-key-size {
      type string;
      description
        "bank key size";
    }
    leaf bank-free-entries {
      type uint32;
      description
        "bank free entries";
    }
    leaf bank-inuse-entries {
      type uint32;
      description
        "bank inuse entries";
    }
    leaf owner {
      type string;
      description
        "owner";
    }
    leaf nof-dbs {
      type uint32;
      description
        "nof dbs";
    }
    list bank-db {
      description
        "bank db";
      uses FIA-TCAM-DB;
    }
  }

  grouping FIA-NPU-TCAM {
    description
      "FIA NPU TCAM";
    leaf npu-id {
      type uint32;
      description
        "npu id";
    }
    list tcam-bank {
      description
        "tcam bank";
      uses FIA-TCAM-BANK;
    }
  }

  grouping FIA-CARD-TCAM {
    description
      "FIA CARD TCAM";
    list npu-tcam {
      description
        "npu tcam";
      uses FIA-NPU-TCAM;
    }
  }
}
