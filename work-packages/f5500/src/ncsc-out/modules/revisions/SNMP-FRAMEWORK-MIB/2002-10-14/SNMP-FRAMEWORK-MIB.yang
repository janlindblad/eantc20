module SNMP-FRAMEWORK-MIB {
  // Generated by yanger -t ncs
  tailf:mount-id f5500-nc-1.0:f5500-nc-1.0;
  tailf:ncs-device-type "netconf";

  namespace "http://tail-f.com/ns/mibs/SNMP-FRAMEWORK-MIB/200210140000Z";
  prefix SNMP-FRAMEWORK-MIB;
  // NCS drop tailf:id
  tailf:snmp-mib-module-name SNMP-FRAMEWORK-MIB;

  import tailf-common {
    prefix tailf;
  }
  import "f5500-nc-1.0" {
    prefix "f5500-nc-1.0";
  }
  import tailf-ncs {
    prefix ncs;
  }

  revision 2002-10-14 {
    description
      "";
  }

  typedef snmpEngineMaxMessageSizeType {
    type int32 {
      range "484 .. 2147483647";
    }
  }

  typedef snmpEngineTimeType {
    type int32 {
      range "0 .. 2147483647";
    }
  }

  typedef snmpEngineBootsType {
    type int32 {
      range "1 .. 2147483647";
    }
  }

  typedef SnmpAdminString {
    type string {
      length "min .. 255";
    }
  }

  typedef SnmpSecurityLevel {
    type enumeration {
      enum "noAuthNoPriv" {
        value 1;
      }
      enum "authNoPriv" {
        value 2;
      }
      enum "authPriv" {
        value 3;
      }
    }
  }

  typedef SnmpMessageProcessingModel {
    type int32 {
      range "0 .. 2147483647";
    }
  }

  typedef SnmpSecurityModel {
    type int32 {
      range "0 .. 2147483647";
    }
  }

  typedef SnmpEngineID {
    type tailf:hex-list {
      pattern '(((([0-9A-Fa-f]{2}):){4,31})([0-9A-Fa-f]{2}))';
      tailf:value-length "5 .. 32";
    }
  }

  augment "/ncs:devices/ncs:device/ncs:config" {
    // NCS drop config false container 'SNMP-FRAMEWORK-MIB'
  }
  augment "/ncs:devices/ncs:device/ncs:live-status" {
    container SNMP-FRAMEWORK-MIB {
      tailf:ncs-device-type "netconf";
      tailf:display-when "not(../../ncs:module) or ../../ncs:module[ncs:name='SNMP-FRAMEWORK-MIB'] or (../../ncs:live-status-protocol[not(ncs:capability)]) or (../../ncs:live-status-protocol/ncs:capability/ncs:module[.='SNMP-FRAMEWORK-MIB'])";
      container snmpEngine {
        tailf:snmp-oid "1.3.6.1.6.3.10.2.1";
        leaf snmpEngineID {
          type SnmpEngineID;
          tailf:snmp-oid "1.3.6.1.6.3.10.2.1.1";
        }
        leaf snmpEngineBoots {
          type snmpEngineBootsType;
          tailf:snmp-oid "1.3.6.1.6.3.10.2.1.2";
        }
        leaf snmpEngineTime {
          type snmpEngineTimeType;
          tailf:snmp-oid "1.3.6.1.6.3.10.2.1.3";
        }
        leaf snmpEngineMaxMessageSize {
          type snmpEngineMaxMessageSizeType;
          tailf:snmp-oid "1.3.6.1.6.3.10.2.1.4";
        }
      }
    }
  }
  augment "/ncs:devices/ncs:template/ncs:ned-id/ncs:config" {
    // NCS drop config false container 'SNMP-FRAMEWORK-MIB'
  }
}
