module Cisco-IOS-XR-sysadmin-time-of-day-timezone {
  // Generated by yanger -t ncs
  tailf:mount-id f5500-nc-1.0:f5500-nc-1.0;
  tailf:ncs-device-type "netconf";

  namespace "http://cisco.com/calvados/Cisco-IOS-XR-sysadmin-time-of-day-timezone";
  prefix Cisco-IOS-XR-sysadmin-time-of-day-timezone;

  import Cisco-IOS-XR-sysadmin-show-trace {
    prefix show_trace;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains definitions
     for the Calvados model objects.

     This module contains a collection of YANG definitions
     for Cisco IOS-XR syadmin TOD configuration and cli.

     This module contains definitions
     for the following management objects:
     Time of the Day(TOD) Cli and configuration data

     Copyright (c) 2013-2017 by Cisco Systems, Inc.
     All rights reserved.

     Copyright (c) 2012-2018 by Cisco Systems, Inc.
     All rights reserved.";

  revision 2016-07-04 {
    description
      "Remove refine stmt";
  }

  augment "/ncs:devices/ncs:device/ncs:config" {
    container clock {
      tailf:ncs-device-type "netconf";
      tailf:display-when "not(../../ncs:module) or ../../ncs:module[ncs:name='Cisco-IOS-XR-sysadmin-time-of-day-timezone']";
      container timezone {
        leaf tzname {
          type string;
        }
        leaf area {
          type string;
        }
      }
    }
    // NCS drop config false container trace
  }
  augment "/ncs:devices/ncs:device/ncs:live-status" {
    container clock {
      tailf:ncs-device-type "netconf";
      tailf:display-when "not(../../ncs:module) or ../../ncs:module[ncs:name='Cisco-IOS-XR-sysadmin-time-of-day-timezone'] or (../../ncs:live-status-protocol[not(ncs:capability)]) or (../../ncs:live-status-protocol/ncs:capability/ncs:module[.='Cisco-IOS-XR-sysadmin-time-of-day-timezone'])";
      container timezone {
        leaf tzname {
          type string;
        }
        leaf area {
          type string;
        }
      }
    }
    container trace {
      tailf:ncs-device-type "netconf";
      tailf:display-when "not(../../ncs:module) or ../../ncs:module[ncs:name='Cisco-IOS-XR-sysadmin-time-of-day-timezone'] or (../../ncs:live-status-protocol[not(ncs:capability)]) or (../../ncs:live-status-protocol/ncs:capability/ncs:module[.='Cisco-IOS-XR-sysadmin-time-of-day-timezone'])";
      container timezone_config {
        uses show_trace:live_ncs_traceable;
      }
      container timezone_notify {
        uses show_trace:live_ncs_traceable;
      }
    }
  }
  augment "/ncs:devices/ncs:template/ncs:ned-id/ncs:config" {
    container clock {
      container timezone {
        leaf tzname {
          type string;
        }
        leaf area {
          type string;
        }
      }
    }
    // NCS drop config false container trace
  }
}
