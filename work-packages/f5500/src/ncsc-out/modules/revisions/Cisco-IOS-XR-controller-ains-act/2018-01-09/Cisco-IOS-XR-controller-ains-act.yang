module Cisco-IOS-XR-controller-ains-act {
  // Generated by yanger -t ncs
  tailf:mount-id f5500-nc-1.0:f5500-nc-1.0;
  tailf:ncs-device-type "netconf";

  namespace "http://cisco.com/ns/yang/Cisco-IOS-XR-controller-ains-act";
  prefix Cisco-IOS-XR-controller-ains-act;

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR Controller AINS configuration.

     Copyright (c) 2018 by Cisco Systems, Inc.
     All rights reserved.";

  revision 2018-01-09 {
    description
      "IOS XR 6.5.1 revision.";
  }

  augment "/ncs:devices/ncs:device/ncs:rpc" {
    container rpc-controller-ains-soak {
      tailf:ncs-device-type "netconf";
      tailf:display-when "not(../../ncs:module) or ../../ncs:module[ncs:name='Cisco-IOS-XR-controller-ains-act']";
      tailf:action controller-ains-soak {
        tailf:actionpoint ncsproxy {
          tailf:internal;
        }
        description
          "Execute ains soak configuration operations";
        input {
          leaf controller {
            description
              "Controller name in R/S/I/P format";
            type string;
          }
          leaf hours {
            description
              "Hours in range of 0-48";
            type uint32 {
              range "0..48";
            }
          }
          leaf minutes {
            description
              "Minutes in range of 0-59";
            type uint32 {
              range "0..59";
            }
          }
        }
      }
    }
  }
  augment "/ncs:devices/ncs:device-group/ncs:ned-id/ncs:rpc" {
    container rpc-controller-ains-soak {
      tailf:ncs-device-type "netconf";
      tailf:display-when "/ncs:devices/ncs:device[ncs:name=current()/../../../ncs:member]/ncs:module[ncs:name='Cisco-IOS-XR-controller-ains-act']";
      tailf:action controller-ains-soak {
        tailf:actionpoint ncsproxy {
          tailf:internal;
        }
        description
          "Execute ains soak configuration operations";
        input {
          leaf controller {
            description
              "Controller name in R/S/I/P format";
            type string;
          }
          leaf hours {
            description
              "Hours in range of 0-48";
            type uint32 {
              range "0..48";
            }
          }
          leaf minutes {
            description
              "Minutes in range of 0-59";
            type uint32 {
              range "0..59";
            }
          }
        }
      }
    }
  }
}
