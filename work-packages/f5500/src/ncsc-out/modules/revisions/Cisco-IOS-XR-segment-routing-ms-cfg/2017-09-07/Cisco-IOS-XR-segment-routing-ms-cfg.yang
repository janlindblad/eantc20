module Cisco-IOS-XR-segment-routing-ms-cfg {
  // Generated by yanger -t ncs
  tailf:mount-id f5500-nc-1.0:f5500-nc-1.0;
  tailf:ncs-device-type "netconf";

  namespace "http://cisco.com/ns/yang/Cisco-IOS-XR-segment-routing-ms-cfg";
  prefix Cisco-IOS-XR-segment-routing-ms-cfg;

  import ietf-inet-types {
    prefix inet;
  }
  import Cisco-IOS-XR-types {
    prefix xr;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR segment-routing-ms package configuration.

     This module contains definitions
     for the following management objects:
       sr: Segment Routing

     Copyright (c) 2013-2018 by Cisco Systems, Inc.
     All rights reserved.";

  revision 2017-09-07 {
    description
      "Fixed type translation error.";
  }
  revision 2015-11-09 {
    description
      "IOS XR 6.0 revision.";
  }

  typedef Sid-type-list {
    type enumeration {
      enum "absolute" {
        value 1;
        description
          "Absolute SID";
      }
      enum "index" {
        value 2;
        description
          "Index SID";
      }
    }
    description
      "Sid type list";
  }

  typedef Srlb-string {
    type string {
      pattern '(srlb_default)';
    }
    description
      "srlb_default:Default SRLB block";
  }

  typedef Srms-address-family {
    type enumeration {
      enum "ipv4" {
        value 1;
        description
          "IP version 4";
      }
      enum "ipv6" {
        value 2;
        description
          "IP version 6";
      }
    }
    description
      "Srms address family";
  }

  typedef Srms-mi-flag {
    type enumeration {
      enum "disable" {
        value 0;
        description
          "Disable flag";
      }
      enum "enable" {
        value 1;
        description
          "Enable flag";
      }
    }
    description
      "Srms mi flag";
  }

  augment "/ncs:devices/ncs:device/ncs:config" {
    container sr {
      tailf:ncs-device-type "netconf";
      tailf:display-when "not(../../ncs:module) or ../../ncs:module[ncs:name='Cisco-IOS-XR-segment-routing-ms-cfg']";
      description
        "Segment Routing";
      container local-block {
        presence "Indicates a local-block node is configured.";
        description
          "Segment Routing Local Block of Labels";
        leaf lower-bound {
          type uint32 {
            range "15000..1048574";
          }
          mandatory true;
          description
            "SRLB Lower Bound";
        }
        leaf upper-bound {
          type uint32 {
            range "15001..1048575";
          }
          mandatory true;
          description
            "SRLB Upper Bound";
        }
      }
      container mappings {
        description
          "Mapping Server";
        list mapping {
          key "af ip mask";
          description
            "IP prefix to SID mapping";
          leaf af {
            type Srms-address-family;
            description
              "Address Family";
          }
          leaf ip {
            type inet:ip-address-no-zone;
            description
              "IP prefix";
          }
          leaf mask {
            type uint32 {
              range "1..128";
            }
            description
              "Mask";
          }
          leaf sid-start {
            type uint32 {
              range "0..1048575";
            }
            description
              "Start of SID index range";
          }
          leaf sid-range {
            type uint32 {
              range "0..1048575";
            }
            description
              "Range (number of SIDs)";
          }
          leaf flag-attached {
            type Srms-mi-flag;
            description
              "Enable/Disable Attached flag";
          }
        }
      }
      container adjacency-sid {
        description
          "Segment Routing Adjacency SID";
        container interfaces {
          description
            "Segment Routing Adjacency SID Interface Table";
          list interface {
            key "interface";
            description
              "Segment Routing Adjacency SID Interface";
            container address-families {
              description
                "Segment Routing Adjacency SID Interface
                 Address Family Table";
              list address-family {
                key "address-family";
                description
                  "Segment Routing Adjacency SID Interface
                   Address Family";
                container next-hops {
                  description
                    "Segment Routing Adjacency SID Interface
                     Address Family NextHop Table";
                  list next-hop {
                    must "(count(../next-hop)=1) or ((count(../next-hop[ip-addr='0.0.0.0'])=0) and (count(../next-hop[ip-addr='::0'])=0))" {
                      tailf:xpath-root 3;
                    }
                    unique "l2-adjacency-sid/sid-type l2-adjacency-sid/index-sid l2-adjacency-sid/absolute-sid l2-adjacency-sid/srlb";
                    key "ip-addr";
                    description
                      "Segment Routing Adjacency SID Interface
                       Address Family NextHop, use a single
                       ANYADDR (0.0.0.0 or ::) NextHop for point
                       to point links";
                    container l2-adjacency-sid {
                      description
                        "L2 Adjacency SID type and value";
                      leaf sid-type {
                        type Sid-type-list;
                        description
                          "SID type";
                      }
                      leaf absolute-sid {
                        when "../sid-type = 'absolute'" {
                          tailf:xpath-root 3;
                          description
                            "../SIDType = absolute";
                        }
                        type uint32 {
                          range "15000..1048575";
                        }
                        description
                          "SID value";
                      }
                      leaf index-sid {
                        when "../sid-type = 'index'" {
                          tailf:xpath-root 3;
                          description
                            "../SIDType = index";
                        }
                        type uint32 {
                          range "0..1048575";
                        }
                        description
                          "SID value";
                      }
                      leaf srlb {
                        when "../sid-type = 'absolute' or ../sid-type = 'index'" {
                          tailf:xpath-root 3;
                          description
                            "../SIDType = absolute or ../SIDType =
                             index";
                        }
                        type Srlb-string;
                        mandatory true;
                        description
                          "SRLB block name";
                      }
                    }
                    leaf ip-addr {
                      type inet:ip-address-no-zone;
                      description
                        "NextHop IP address";
                    }
                  }
                }
                leaf address-family {
                  type Srms-address-family;
                  description
                    "Address Family";
                }
              }
            }
            leaf interface {
              type xr:Interface-name;
              description
                "Interface name";
            }
          }
        }
      }
      container global-block {
        presence "Indicates a global-block node is configured.";
        description
          "Global Block Segment Routing";
        leaf lower-bound {
          type uint32 {
            range "16000..1048574";
          }
          mandatory true;
          description
            "SRGB Lower Bound";
        }
        leaf upper-bound {
          type uint32 {
            range "16001..1048575";
          }
          mandatory true;
          description
            "SRGB Upper Bound";
        }
      }
      leaf enable {
        type empty;
        description
          "enable SR";
      }
    }
  }
  augment "/ncs:devices/ncs:device/ncs:live-status" {
    container sr {
      tailf:ncs-device-type "netconf";
      tailf:display-when "not(../../ncs:module) or ../../ncs:module[ncs:name='Cisco-IOS-XR-segment-routing-ms-cfg'] or (../../ncs:live-status-protocol[not(ncs:capability)]) or (../../ncs:live-status-protocol/ncs:capability/ncs:module[.='Cisco-IOS-XR-segment-routing-ms-cfg'])";
      description
        "Segment Routing";
      container local-block {
        presence "Indicates a local-block node is configured.";
        description
          "Segment Routing Local Block of Labels";
        leaf lower-bound {
          type uint32 {
            range "15000..1048574";
          }
          // NCS drop mandatory statement
          description
            "SRLB Lower Bound";
        }
        leaf upper-bound {
          type uint32 {
            range "15001..1048575";
          }
          // NCS drop mandatory statement
          description
            "SRLB Upper Bound";
        }
      }
      container mappings {
        description
          "Mapping Server";
        list mapping {
          key "af ip mask";
          description
            "IP prefix to SID mapping";
          leaf af {
            type Srms-address-family;
            description
              "Address Family";
          }
          leaf ip {
            type inet:ip-address-no-zone;
            description
              "IP prefix";
          }
          leaf mask {
            type uint32 {
              range "1..128";
            }
            description
              "Mask";
          }
          leaf sid-start {
            type uint32 {
              range "0..1048575";
            }
            description
              "Start of SID index range";
          }
          leaf sid-range {
            type uint32 {
              range "0..1048575";
            }
            description
              "Range (number of SIDs)";
          }
          leaf flag-attached {
            type Srms-mi-flag;
            description
              "Enable/Disable Attached flag";
          }
        }
      }
      container adjacency-sid {
        description
          "Segment Routing Adjacency SID";
        container interfaces {
          description
            "Segment Routing Adjacency SID Interface Table";
          list interface {
            key "interface";
            description
              "Segment Routing Adjacency SID Interface";
            container address-families {
              description
                "Segment Routing Adjacency SID Interface
                 Address Family Table";
              list address-family {
                key "address-family";
                description
                  "Segment Routing Adjacency SID Interface
                   Address Family";
                container next-hops {
                  description
                    "Segment Routing Adjacency SID Interface
                     Address Family NextHop Table";
                  list next-hop {
                    // NCS drop must statement
                    unique "l2-adjacency-sid/sid-type l2-adjacency-sid/index-sid l2-adjacency-sid/absolute-sid l2-adjacency-sid/srlb";
                    key "ip-addr";
                    description
                      "Segment Routing Adjacency SID Interface
                       Address Family NextHop, use a single
                       ANYADDR (0.0.0.0 or ::) NextHop for point
                       to point links";
                    container l2-adjacency-sid {
                      description
                        "L2 Adjacency SID type and value";
                      leaf sid-type {
                        type Sid-type-list;
                        description
                          "SID type";
                      }
                      leaf absolute-sid {
                        // NCS drop when statement
                        type uint32 {
                          range "15000..1048575";
                        }
                        description
                          "SID value";
                      }
                      leaf index-sid {
                        // NCS drop when statement
                        type uint32 {
                          range "0..1048575";
                        }
                        description
                          "SID value";
                      }
                      leaf srlb {
                        // NCS drop when statement
                        type Srlb-string;
                        // NCS drop mandatory statement
                        description
                          "SRLB block name";
                      }
                    }
                    leaf ip-addr {
                      type inet:ip-address-no-zone;
                      description
                        "NextHop IP address";
                    }
                  }
                }
                leaf address-family {
                  type Srms-address-family;
                  description
                    "Address Family";
                }
              }
            }
            leaf interface {
              type xr:Interface-name;
              description
                "Interface name";
            }
          }
        }
      }
      container global-block {
        presence "Indicates a global-block node is configured.";
        description
          "Global Block Segment Routing";
        leaf lower-bound {
          type uint32 {
            range "16000..1048574";
          }
          // NCS drop mandatory statement
          description
            "SRGB Lower Bound";
        }
        leaf upper-bound {
          type uint32 {
            range "16001..1048575";
          }
          // NCS drop mandatory statement
          description
            "SRGB Upper Bound";
        }
      }
      leaf enable {
        type empty;
        description
          "enable SR";
      }
    }
  }
  augment "/ncs:devices/ncs:template/ncs:ned-id/ncs:config" {
    container sr {
      description
        "Segment Routing";
      container local-block {
        presence "Indicates a local-block node is configured.";
        description
          "Segment Routing Local Block of Labels";
        leaf lower-bound {
          type string;
          // NCS drop mandatory statement
          description
            "SRLB Lower Bound";
        }
        leaf upper-bound {
          type string;
          // NCS drop mandatory statement
          description
            "SRLB Upper Bound";
        }
      }
      container mappings {
        description
          "Mapping Server";
        list mapping {
          // NCS patched for predictable order
          ordered-by user;
          key "af ip mask";
          description
            "IP prefix to SID mapping";
          leaf af {
            type string;
            description
              "Address Family";
          }
          leaf ip {
            type string;
            description
              "IP prefix";
          }
          leaf mask {
            type string;
            description
              "Mask";
          }
          leaf sid-start {
            type string;
            description
              "Start of SID index range";
          }
          leaf sid-range {
            type string;
            description
              "Range (number of SIDs)";
          }
          leaf flag-attached {
            type string;
            description
              "Enable/Disable Attached flag";
          }
        }
      }
      container adjacency-sid {
        description
          "Segment Routing Adjacency SID";
        container interfaces {
          description
            "Segment Routing Adjacency SID Interface Table";
          list interface {
            // NCS patched for predictable order
            ordered-by user;
            key "interface";
            description
              "Segment Routing Adjacency SID Interface";
            container address-families {
              description
                "Segment Routing Adjacency SID Interface
                 Address Family Table";
              list address-family {
                // NCS patched for predictable order
                ordered-by user;
                key "address-family";
                description
                  "Segment Routing Adjacency SID Interface
                   Address Family";
                container next-hops {
                  description
                    "Segment Routing Adjacency SID Interface
                     Address Family NextHop Table";
                  list next-hop {
                    // NCS patched for predictable order
                    ordered-by user;
                    // NCS drop must statement
                    unique "l2-adjacency-sid/sid-type l2-adjacency-sid/index-sid l2-adjacency-sid/absolute-sid l2-adjacency-sid/srlb";
                    key "ip-addr";
                    description
                      "Segment Routing Adjacency SID Interface
                       Address Family NextHop, use a single
                       ANYADDR (0.0.0.0 or ::) NextHop for point
                       to point links";
                    container l2-adjacency-sid {
                      description
                        "L2 Adjacency SID type and value";
                      leaf sid-type {
                        type string;
                        description
                          "SID type";
                      }
                      leaf absolute-sid {
                        // NCS drop when statement
                        type string;
                        description
                          "SID value";
                      }
                      leaf index-sid {
                        // NCS drop when statement
                        type string;
                        description
                          "SID value";
                      }
                      leaf srlb {
                        // NCS drop when statement
                        type string;
                        // NCS drop mandatory statement
                        description
                          "SRLB block name";
                      }
                    }
                    leaf ip-addr {
                      type string;
                      description
                        "NextHop IP address";
                    }
                  }
                }
                leaf address-family {
                  type string;
                  description
                    "Address Family";
                }
              }
            }
            leaf interface {
              type string;
              description
                "Interface name";
            }
          }
        }
      }
      container global-block {
        presence "Indicates a global-block node is configured.";
        description
          "Global Block Segment Routing";
        leaf lower-bound {
          type string;
          // NCS drop mandatory statement
          description
            "SRGB Lower Bound";
        }
        leaf upper-bound {
          type string;
          // NCS drop mandatory statement
          description
            "SRGB Upper Bound";
        }
      }
      leaf enable {
        type empty;
        description
          "enable SR";
      }
    }
  }
}
