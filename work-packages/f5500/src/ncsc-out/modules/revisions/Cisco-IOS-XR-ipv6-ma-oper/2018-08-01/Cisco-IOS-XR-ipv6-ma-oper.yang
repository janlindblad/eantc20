module Cisco-IOS-XR-ipv6-ma-oper {
  // Generated by yanger -t ncs
  tailf:mount-id f5500-nc-1.0:f5500-nc-1.0;
  tailf:ncs-device-type "netconf";

  namespace "http://cisco.com/ns/yang/Cisco-IOS-XR-ipv6-ma-oper";
  prefix Cisco-IOS-XR-ipv6-ma-oper;

  import Cisco-IOS-XR-types {
    prefix xr;
  }
  include Cisco-IOS-XR-ipv6-ma-oper-sub1 {
    revision-date 2018-08-01;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ipv6-ma package operational data.

     This module contains definitions
     for the following management objects:
       ipv6-network: IPv6 network operational data

     Copyright (c) 2013-2018 by Cisco Systems, Inc.
     All rights reserved.";

  revision 2018-08-01 {
    description
      "Removed empty groupings.";
  }
  revision 2018-07-02 {
    description
      "IPV6 MA added new fields to bag.";
  }
  revision 2018-05-16 {
    description
      "IPV6 MA added new fields to bag.";
  }
  revision 2017-08-09 {
    description
      "IPV6 MA schema file has all the latest changes.";
  }
  revision 2015-01-07 {
    description
      "IOS XR 5.3.1 revision.";
  }

  augment "/ncs:devices/ncs:device/ncs:config" {
    // NCS drop config false container 'ipv6-network'
  }
  augment "/ncs:devices/ncs:device/ncs:live-status" {
    container ipv6-network {
      tailf:ncs-device-type "netconf";
      tailf:display-when "not(../../ncs:module) or ../../ncs:module[ncs:name='Cisco-IOS-XR-ipv6-ma-oper'] or (../../ncs:live-status-protocol[not(ncs:capability)]) or (../../ncs:live-status-protocol/ncs:capability/ncs:module[.='Cisco-IOS-XR-ipv6-ma-oper'])";
      description
        "IPv6 network operational data";
      container nodes {
        description
          "Node-specific IPv6 network operational data";
        list node {
          key "node-name";
          description
            "IPv6 network operational data for a particular
             node";
          container interface-data {
            description
              "IPv6 network operational interface data";
            container vrfs {
              description
                "VRF specific IPv6 network operational
                 interface data";
              list vrf {
                key "vrf-name";
                description
                  "VRF ID of an interface belong to";
                container briefs {
                  description
                    "Brief interface IPv6 network operational
                     data for a node";
                  list brief {
                    key "interface-name";
                    description
                      "Brief interface IPv6 network operational
                       data for an interface";
                    leaf interface-name {
                      type xr:Interface-name;
                      description
                        "The name of the interface";
                    }
                    uses live_ncs_IPV6-IF-BRIEF;
                  }
                }
                container global-details {
                  description
                    "Detail interface IPv4 network operational
                     data for global data";
                  list global-detail {
                    key "interface-name";
                    description
                      "Detail interface IPv6 network operational
                       data for an interface";
                    leaf interface-name {
                      type xr:Interface-name;
                      description
                        "The name of the interface";
                    }
                    uses live_ncs_IPV6-IF-DETAIL;
                  }
                }
                container global-briefs {
                  description
                    "Brief interface IPv6 network operational
                     data from global data";
                  list global-brief {
                    key "interface-name";
                    description
                      "Brief interface IPv6 network operational
                       data for an interface";
                    leaf interface-name {
                      type xr:Interface-name;
                      description
                        "The name of the interface";
                    }
                    uses live_ncs_IPV6-IF-BRIEF;
                  }
                }
                container details {
                  description
                    "Detail interface IPv4 network operational
                     data for a node";
                  list detail {
                    key "interface-name";
                    description
                      "Detail interface IPv6 network operational
                       data for an interface";
                    leaf interface-name {
                      type xr:Interface-name;
                      description
                        "The name of the interface";
                    }
                    uses live_ncs_IPV6-IF-DETAIL;
                  }
                }
                leaf vrf-name {
                  type xr:Cisco-ios-xr-string;
                  description
                    "The VRF name";
                }
              }
            }
            container summary {
              description
                "Summary of IPv6 network operational interface
                 data on a node";
              uses live_ncs_IPV6-IF-SUMMARY;
            }
          }
          leaf node-name {
            type xr:Node-id;
            description
              "The node name";
          }
        }
      }
    }
  }
  augment "/ncs:devices/ncs:template/ncs:ned-id/ncs:config" {
    // NCS drop config false container 'ipv6-network'
  }
}
