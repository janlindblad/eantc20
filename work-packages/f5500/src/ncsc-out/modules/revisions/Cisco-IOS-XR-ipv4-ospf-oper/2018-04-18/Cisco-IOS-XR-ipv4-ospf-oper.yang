module Cisco-IOS-XR-ipv4-ospf-oper {
  // Generated by yanger -t ncs
  tailf:mount-id f5500-nc-1.0:f5500-nc-1.0;
  tailf:ncs-device-type "netconf";

  namespace "http://cisco.com/ns/yang/Cisco-IOS-XR-ipv4-ospf-oper";
  prefix Cisco-IOS-XR-ipv4-ospf-oper;

  import ietf-inet-types {
    prefix inet;
  }
  import Cisco-IOS-XR-types {
    prefix xr;
  }
  include Cisco-IOS-XR-ipv4-ospf-oper-sub3 {
    revision-date 2018-04-18;
  }
  include Cisco-IOS-XR-ipv4-ospf-oper-sub2 {
    revision-date 2018-04-18;
  }
  include Cisco-IOS-XR-ipv4-ospf-oper-sub1 {
    revision-date 2018-04-18;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ipv4-ospf package operational data.

     This module contains definitions
     for the following management objects:
       ospf: OSPF operational data

     Copyright (c) 2013-2018 by Cisco Systems, Inc.
     All rights reserved.";

  revision 2018-04-18 {
    description
      "Added keychain name to be displayed in show ospf interface bag";
  }
  revision 2017-10-26 {
    description
      "Fixed some field name and values for better interpretation";
  }
  revision 2017-09-07 {
    description
      "Fixed type translation error.";
  }
  revision 2017-05-01 {
    description
      "Fixing backward compatibility error in module.";
  }
  revision 2017-01-02 {
    description
      "IOS XR 6.2.1 revision.";
  }
  revision 2015-11-09 {
    description
      "IOS XR 6.0 revision.";
  }

  typedef Ospf-ls {
    type enumeration {
      enum "router" {
        value 1;
        description
          "Router LSA";
      }
      enum "network" {
        value 2;
        description
          "Network LSA";
      }
      enum "summary" {
        value 3;
        description
          "Summary LSA";
      }
      enum "asbr-summary" {
        value 4;
        description
          "ASBR-Summary LSA";
      }
      enum "external" {
        value 5;
        description
          "External LSA";
      }
      enum "nssa-external" {
        value 7;
        description
          "NSSA External LSA";
      }
      enum "opaque-link" {
        value 9;
        description
          "Opaque LSALink Scope";
      }
      enum "opaque-area" {
        value 10;
        description
          "Opaque LSA Area Scope";
      }
      enum "opaque-as" {
        value 11;
        description
          "Opaque LSA AS Scope";
      }
    }
    description
      "Ospf ls";
  }

  typedef Ospf-prefix-length {
    type uint32 {
      range "0..32";
    }
    description
      "Ospf prefix length";
  }

  grouping ncs_template_ROUTE {
    description
      "Common node of route-table,
       multicast-intact-route-table";
    list route {
      // NCS patched for predictable order
      ordered-by user;
      description
        "An OSPF route";
      leaf prefix {
        type string;
        description
          "Prefix";
      }
      leaf prefix-length {
        type string;
        description
          "Prefix Length";
      }
      uses ncs_template_OSPF-SH-TOPOLOGY;
    }
  }

  grouping ncs_template_FLOOD-LIST {
    description
      "Common node of flood-list-table,
       flood-list-area-table";
    list flood {
      // NCS patched for predictable order
      ordered-by user;
      key "interface-name";
      description
        "Flooding information for a specific interface";
      leaf interface-name {
        type string;
        description
          "Interface name";
      }
      uses ncs_template_OSPF-SH-FLOOD-LIST;
    }
  }

  grouping ncs_template_BORDER-ROUTER-TABLE {
    description
      "Common node of default-vrf, vrf";
    container border-routers {
      description
        "Border router table";
      list border-router {
        // NCS patched for predictable order
        ordered-by user;
        key "border-router-id";
        description
          "Information for a particular border router";
        leaf border-router-id {
          type string;
          description
            "Router address";
        }
        uses ncs_template_OSPF-SH-BORDER-ROUTER;
      }
    }
  }

  grouping ncs_template_SEGMENT-ROUTING {
    description
      "Common node of default-vrf, vrf";
    container segment-routing {
      description
        "Container for Segment Routing";
      container adjacency-sids {
        description
          "Container for SR Adjacency SIDs";
        list adjacency-sid {
          // NCS patched for predictable order
          ordered-by user;
          key "adj-sid";
          description
            "SR Adj SID Bag";
          leaf adj-sid {
            type string;
            description
              "Adjacency SID";
          }
          uses ncs_template_OSPF-SH-ADJ-SID;
        }
      }
      container sr-endpoint-policies {
        description
          "Container for SR Policies";
        list sr-endpoint-policy {
          // NCS patched for predictable order
          ordered-by user;
          key "endpoint-ip";
          description
            "SR Endpoint Policy Bag";
          leaf endpoint-ip {
            type string;
            description
              "Endpoint IP Address";
          }
          uses ncs_template_OSPF-SH-SR-ENDPOINT;
        }
      }
    }
  }

  grouping ncs_template_AREA-TABLE {
    description
      "Common node of default-vrf, vrf";
    container areas {
      description
        "Area table";
      list area {
        // NCS patched for predictable order
        ordered-by user;
        key "area-id";
        description
          "Container for per area data";
        container flood-list-area-table {
          description
            "Area specific flood list table";
          uses ncs_template_FLOOD-LIST;
        }
        leaf area-id {
          type string;
          description
            "Area ID";
        }
        uses ncs_template_NEIGHBOR-TABLE;
        uses ncs_template_INTERFACE-BRIEF-TABLE;
        uses ncs_template_REQUEST-LIST-TABLE;
        uses ncs_template_RETRANSMISSION-LIST-TABLE;
        uses ncs_template_AREA-STATISTICS;
        uses ncs_template_NEIGHBOR-DETAIL-TABLE;
        uses ncs_template_INTERFACE-TABLE;
      }
    }
  }

  grouping ncs_template_INTERFACE-STATS-TABLE {
    description
      "Common node of statistics, area-statistics";
    container interface-stats-entries {
      description
        "Statistics innformation Interface table";
      list interface-stats-entry {
        // NCS patched for predictable order
        ordered-by user;
        key "interface-name";
        description
          "Statistics information for a specific interface";
        leaf interface-name {
          type string;
          description
            "Interface name";
        }
        uses ncs_template_OSPF-SH-IF-STATS;
      }
    }
  }

  grouping ncs_template_STATISTICS {
    description
      "Common node of default-vrf, vrf";
    container statistics {
      description
        "Container for Statistics";
      container spf-stats {
        description
          "OSPF SPF statistics";
        uses ncs_template_OSPF-SH-STATS-SPF;
      }
      container rib-batch-stats {
        description
          "Stats concerning RIB route updates using the
           Batching API";
        uses ncs_template_OSPF-SH-RIB-BATCH-PRIORITY-QUEUES;
      }
      container issu-stats {
        description
          "OSPF ISSU statistics";
        uses ncs_template_OSPF-SH-NSR-STATS;
      }
      container rib-thread-stats {
        description
          "OSPF RIB thread statistics";
        uses ncs_template_OSPF-SH-STATS-WORK-QUEUES;
      }
      container nsr-pl-stats {
        description
          "OSPF NSR packet library statistics";
        uses ncs_template_OSPF-SH-NCD-STATS;
      }
      container nsr-stats {
        description
          "OSPF NSR thread statistics";
        uses ncs_template_OSPF-SH-NSR-STATS;
      }
      container frr-stats {
        description
          "OSPF fast-reroute statistics";
        uses ncs_template_OSPF-SH-IPFRR-STATS;
      }
      container te-stats {
        description
          "OSPF TE IO statistics";
        uses ncs_template_OSPF-SH-TE-STATS;
      }
      container protocol-stats {
        description
          "OSPF Protocol statistics";
        uses ncs_template_OSPF-SH-PROTOPKT-STATS;
      }
      container raw-io-stats {
        description
          "OSPF RAW IO statistics";
        uses ncs_template_OSPF-SH-RAW-STATS;
      }
      uses ncs_template_INTERFACE-STATS-TABLE;
    }
  }

  grouping ncs_template_OSPF-SUMMARY {
    description
      "Common node of default-vrf, vrf";
    container ospf-summary {
      description
        "Fast-reroute topology information";
      uses ncs_template_OSPF-SH-STATS-AGGT;
    }
  }

  grouping ncs_template_PROCESS-INFORMATION {
    description
      "Common node of default-vrf, vrf";
    container process-information {
      description
        "Container for OSPF Process information";
      container protocol-areas {
        description
          "Protocol Area table";
        list protocol-area {
          // NCS patched for predictable order
          ordered-by user;
          description
            "Area information";
          leaf area-id {
            type string;
            description
              "Area ID if in integer format";
          }
          leaf address {
            type string;
            description
              "Area ID if in IP address format";
          }
          uses ncs_template_OSPF-SH-PROTO-AREA;
        }
      }
      container protocol-summary {
        description
          "Basic OSPF protocol information";
        uses ncs_template_OSPF-SH-PROTOCOL;
      }
      container redistributions {
        description
          "Redistribution information table";
        list redistribution {
          // NCS patched for predictable order
          ordered-by user;
          description
            "Redistribution information";
          leaf protocol-name {
            type string;
            description
              "Protocol name";
          }
          leaf process-name {
            type string;
            description
              "Process name";
          }
          uses ncs_template_OSPF-SH-REDIST;
        }
      }
      container process-areas {
        description
          "Process Area table";
        list process-area {
          // NCS patched for predictable order
          ordered-by user;
          description
            "Detailed information for a particular area";
          leaf area-id {
            type string;
            description
              "Area ID if in integer format";
          }
          leaf address {
            type string;
            description
              "Area ID if in IP address format";
          }
          uses ncs_template_OSPF-SH-AREA;
        }
      }
      container process-summary {
        description
          "Basic OSPF summary information";
        uses ncs_template_OSPF-SH-SUMMARY;
      }
    }
  }

  grouping ncs_template_ADJACENCY-INFORMATION {
    description
      "Common node of default-vrf, vrf";
    container adjacency-information {
      description
        "Container for OSPF Interfaces";
      uses ncs_template_NEIGHBOR-TABLE;
      uses ncs_template_REQUEST-LIST-TABLE;
      uses ncs_template_RETRANSMISSION-LIST-TABLE;
      uses ncs_template_NEIGHBOR-DETAIL-TABLE;
    }
  }

  grouping ncs_template_RETRANSMISSION-LIST-TABLE {
    description
      "Common node of adjacency-information, area";
    container retransmissions {
      description
        "Retransmission list table";
      list retransmission {
        // NCS patched for predictable order
        ordered-by user;
        description
          "Retransmission list for a particular adjacency";
        leaf interface-name {
          type string;
          description
            "Interface name";
        }
        leaf neighbor-address {
          type string;
          description
            "Neighbor address";
        }
        uses ncs_template_OSPF-SH-RETRANS-LIST;
      }
    }
  }

  grouping ncs_template_LSA-SUMMARY-TABLE {
    description
      "Common node of database, database-area";
    container lsa-summaries {
      description
        "Link state advertisement summary table";
      list lsa-summary {
        // NCS patched for predictable order
        ordered-by user;
        description
          "LSA summary information";
        leaf area-id {
          type string;
          description
            "Area ID";
        }
        leaf ls-type {
          type string;
          description
            "Link state type";
        }
        leaf ls-id {
          type string;
          description
            "Link state ID";
        }
        leaf advertising-router {
          type string;
          description
            "Advertising Router ID";
        }
        leaf interface-name {
          type string;
          description
            "Interface name";
        }
        uses ncs_template_OSPF-SH-DATABASE;
      }
    }
  }

  grouping ncs_template_ROUTE-INFORMATION {
    description
      "Common node of default-vrf, vrf";
    container route-information {
      description
        "Container for OSPF routing tables";
      container backup-routes {
        description
          "OSPF Route Table Including Backup Paths";
        list backup-route {
          // NCS patched for predictable order
          ordered-by user;
          description
            "OSPF route including backup paths";
          leaf prefix {
            type string;
            description
              "Prefix";
          }
          leaf prefix-length {
            type string;
            description
              "Prefix Length";
          }
          uses ncs_template_OSPF-SH-TOPOLOGY-BACKUP;
        }
      }
      container multicast-intact-route-table {
        description
          "OSPF Route Table including multicast-intact
           routes";
        uses ncs_template_ROUTE;
      }
      container multicast-intact-backup-routes {
        description
          "OSPF Route Table Including Multicast intact
           Backup Paths";
        list multicast-intact-backup-route {
          // NCS patched for predictable order
          ordered-by user;
          description
            "OSPF route including multicast backup paths";
          leaf prefix {
            type string;
            description
              "Prefix";
          }
          leaf prefix-length {
            type string;
            description
              "Prefix Length";
          }
          uses ncs_template_OSPF-SH-TOPOLOGY-BACKUP;
        }
      }
      container summary-information {
        description
          "OSPF route summary statistics";
        uses ncs_template_OSPF-SH-ROUTE-SUMMARY;
      }
      container connected-routes {
        description
          "OSPF Connected Route Table";
        list connected-route {
          // NCS patched for predictable order
          ordered-by user;
          description
            "Connected route";
          leaf prefix {
            type string;
            description
              "Prefix";
          }
          leaf prefix-length {
            type string;
            description
              "Prefix Length";
          }
          uses ncs_template_OSPF-SH-TOPOLOGY;
        }
      }
      container local-routes {
        description
          "OSPF Local Route Table";
        list local-route {
          // NCS patched for predictable order
          ordered-by user;
          description
            "Local route";
          leaf prefix {
            type string;
            description
              "Prefix";
          }
          leaf prefix-length {
            type string;
            description
              "Prefix Length";
          }
          uses ncs_template_OSPF-SH-TOPOLOGY;
        }
      }
      container route-areas {
        description
          "OSPF Area Route Table";
        list route-area {
          // NCS patched for predictable order
          ordered-by user;
          key "area-id";
          description
            "OSPF Area Route";
          container multicast-intact-backup-route-areas {
            description
              "OSPF Route Table Including Multicast Intace
               Backup Paths in an area";
            list multicast-intact-backup-route-area {
              // NCS patched for predictable order
              ordered-by user;
              description
                "OSPF route including Multicast intact backup
                 paths";
              leaf prefix {
                type string;
                description
                  "Prefix";
              }
              leaf prefix-length {
                type string;
                description
                  "Prefix Length";
              }
              uses ncs_template_OSPF-SH-TOPOLOGY-BACKUP;
            }
          }
          container connected-route-areas {
            description
              "OSPF Connected Route Table in an area";
            list connected-route-area {
              // NCS patched for predictable order
              ordered-by user;
              description
                "Connected route";
              leaf prefix {
                type string;
                description
                  "Prefix";
              }
              leaf prefix-length {
                type string;
                description
                  "Prefix Length";
              }
              uses ncs_template_OSPF-SH-TOPOLOGY;
            }
          }
          container backup-route-areas {
            description
              "OSPF Route Table Including Backup Paths in an
               area";
            list backup-route-area {
              // NCS patched for predictable order
              ordered-by user;
              description
                "OSPF route including backup paths";
              leaf prefix {
                type string;
                description
                  "Prefix";
              }
              leaf prefix-length {
                type string;
                description
                  "Prefix Length";
              }
              uses ncs_template_OSPF-SH-TOPOLOGY-BACKUP;
            }
          }
          container route-area-informations {
            description
              "OSPF Area Route Entry";
            list route-area-information {
              // NCS patched for predictable order
              ordered-by user;
              description
                "An OSPF route";
              leaf prefix {
                type string;
                description
                  "Prefix";
              }
              leaf prefix-length {
                type string;
                description
                  "Prefix Length";
              }
              uses ncs_template_OSPF-SH-TOPOLOGY;
            }
          }
          container multicast-intact-route-areas {
            description
              "OSPF Area multicast-intact included route
               entry";
            list multicast-intact-route-area {
              // NCS patched for predictable order
              ordered-by user;
              description
                "A Muliticast OSPF route in an area";
              leaf prefix {
                type string;
                description
                  "Prefix";
              }
              leaf prefix-length {
                type string;
                description
                  "Prefix Length";
              }
              uses ncs_template_OSPF-SH-TOPOLOGY;
            }
          }
          container summary-area-information {
            description
              "OSPF route summary statistics";
            uses ncs_template_OSPF-SH-ROUTE-SUMMARY;
          }
          container local-route-areas {
            description
              "OSPF Local Route Table";
            list local-route-area {
              // NCS patched for predictable order
              ordered-by user;
              description
                "Local route";
              leaf prefix {
                type string;
                description
                  "Prefix";
              }
              leaf prefix-length {
                type string;
                description
                  "Prefix Length";
              }
              uses ncs_template_OSPF-SH-TOPOLOGY;
            }
          }
          leaf area-id {
            type string;
            description
              "Area ID";
          }
        }
      }
      container route-table {
        description
          "OSPF Route Table";
        uses ncs_template_ROUTE;
      }
      container external-routes {
        description
          "OSPF External Route Table";
        list external-route {
          // NCS patched for predictable order
          ordered-by user;
          description
            "OSPF external route";
          leaf prefix {
            type string;
            description
              "Prefix";
          }
          leaf prefix-length {
            type string;
            description
              "Prefix Length";
          }
          uses ncs_template_OSPF-SH-ROUTE-EXT;
        }
      }
    }
  }

  grouping ncs_template_FAST-REROUTE {
    description
      "Common node of default-vrf, vrf";
    container fast-reroute {
      description
        "Container for FastReroute";
      container topologies {
        description
          "Fast-reroute topology information table";
        list topology {
          // NCS patched for predictable order
          ordered-by user;
          description
            "Fast-reroute topology information";
          leaf router-id {
            type string;
            description
              "Router ID";
          }
          leaf area-id {
            type string;
            description
              "Area ID";
          }
          uses ncs_template_OSPF-SH-IPFRR-TOPO;
        }
      }
    }
  }

  grouping ncs_template_POLICY-MI {
    description
      "Common node of policy-ipv4-active,
       policy-ipv4-backup";
    list policy-mi {
      // NCS patched for predictable order
      ordered-by user;
      key "mi-id";
      description
        "Mapping Item";
      leaf mi-id {
        type string;
        description
          "Mapping Item ID (0, 1, 2, ...)";
      }
      uses ncs_template_SRMS-MI-T-B;
    }
  }

  grouping ncs_template_MPLS-TE {
    description
      "Common node of default-vrf, vrf";
    container mpls-te {
      description
        "Container for MPLS TE";
      container mpls-te-links {
        description
          "MPLS TE link information table";
        list mpls-te-link {
          // NCS patched for predictable order
          ordered-by user;
          key "area-id";
          description
            "MPLS TE link information";
          leaf area-id {
            type string;
            description
              "Area ID";
          }
          uses ncs_template_OSPF-SH-MPLS;
        }
      }
      container mpls-te-fragments {
        description
          "MPLS TE Fragment information table";
        list mpls-te-fragment {
          // NCS patched for predictable order
          ordered-by user;
          key "area-id";
          description
            "MPLS TE Fragment";
          leaf area-id {
            type string;
            description
              "Area ID";
          }
          uses ncs_template_OSPF-SH-MPLS;
        }
      }
    }
  }

  grouping ncs_template_FLOOD-LIST-TABLE {
    description
      "Common node of default-vrf, vrf";
    container flood-list-table {
      description
        "Flood list table";
      uses ncs_template_FLOOD-LIST;
    }
  }

  grouping ncs_template_SUMMARY-PREFIX-TABLE {
    description
      "Common node of default-vrf, vrf";
    container summary-prefixes {
      description
        "Summary prefix table";
      list summary-prefix {
        // NCS patched for predictable order
        ordered-by user;
        description
          "Summary prefix information";
        leaf prefix {
          type string;
          description
            "Summary Prefix";
        }
        leaf netmask {
          type string;
          description
            "Summary Mask";
        }
        uses ncs_template_OSPF-SH-SUMMARY-ADDRESS;
      }
    }
  }

  grouping ncs_template_NEIGHBOR-DETAIL-TABLE {
    description
      "Common node of adjacency-information, area";
    container neighbor-details {
      description
        "Neighbor detail table";
      list neighbor-detail {
        // NCS patched for predictable order
        ordered-by user;
        description
          "A single neighbor's detail information";
        leaf interface-name {
          type string;
          description
            "Interface name";
        }
        leaf neighbor-address {
          type string;
          description
            "Neighbor address";
        }
        uses ncs_template_OSPF-SH-NEIGHBOR-DETAIL;
      }
    }
  }

  grouping ncs_template_REQUEST-LIST-TABLE {
    description
      "Common node of adjacency-information, area";
    container requests {
      description
        "Request List table";
      list request {
        // NCS patched for predictable order
        ordered-by user;
        description
          "Request list for a particular adjacency";
        leaf interface-name {
          type string;
          description
            "Interface";
        }
        leaf neighbor-address {
          type string;
          description
            "Neighbor address";
        }
        uses ncs_template_OSPF-SH-REQUEST-LIST;
      }
    }
  }

  grouping ncs_template_AREA-STATISTICS {
    description
      "Common node of default-vrf, vrf, area";
    container area-statistics {
      description
        "Container for Statistics";
      uses ncs_template_INTERFACE-STATS-TABLE;
    }
  }

  grouping ncs_template_INTERFACE-TABLE {
    description
      "Common node of interface-information, area";
    container interfaces {
      description
        "OSPF Interface Table";
      list interface {
        // NCS patched for predictable order
        ordered-by user;
        key "interface-name";
        description
          "OSPF interface information";
        leaf interface-name {
          type string;
          description
            "Interface name";
        }
        uses ncs_template_OSPF-SH-INTERFACE;
      }
    }
  }

  grouping ncs_template_INTERFACE-BRIEF-TABLE {
    description
      "Common node of interface-information, area";
    container interface-briefs {
      description
        "OSPF Interface Brief Table";
      list interface-brief {
        // NCS patched for predictable order
        ordered-by user;
        key "interface-name";
        description
          "OSPF interface brief information";
        leaf interface-name {
          type string;
          description
            "Interface";
        }
        uses ncs_template_OSPF-SH-IF-BRIEF;
      }
    }
  }

  grouping ncs_template_DATABASE {
    description
      "Common node of default-vrf, vrf";
    container database {
      description
        "OSPF Link State Database";
      container database-areas {
        description
          "Per-Area view of Link state database";
        list database-area {
          // NCS patched for predictable order
          ordered-by user;
          key "area-id";
          description
            "Per-Area Link State Database data";
          leaf area-id {
            type string;
            description
              "Area ID";
          }
          uses ncs_template_LSA-TABLE;
          uses ncs_template_LSA-SUMMARY-TABLE;
        }
      }
      container database-summaries {
        description
          "Link State database summary table";
        list database-summary {
          // NCS patched for predictable order
          ordered-by user;
          key "area-id";
          description
            "Link State Database summary for a particular
             area";
          leaf area-id {
            type string;
            description
              "Area ID";
          }
          uses ncs_template_OSPF-SH-DB-AREA-SUM;
        }
      }
      container database-summary-as {
        description
          "Link State Database summary for the AS";
        uses ncs_template_OSPF-SH-DB-AS-SUM;
      }
      uses ncs_template_LSA-TABLE;
      uses ncs_template_LSA-SUMMARY-TABLE;
    }
  }

  grouping ncs_template_INTERFACE-INFORMATION {
    description
      "Common node of default-vrf, vrf";
    container interface-information {
      description
        "Container for OSPF Interfaces/links";
      container virtual-links {
        description
          "Virtual Link table";
        list virtual-link {
          // NCS patched for predictable order
          ordered-by user;
          key "virtual-link-name";
          description
            "Information for one Virtual link";
          leaf virtual-link-name {
            type string;
            description
              "Virtual link";
          }
          uses ncs_template_OSPF-SH-VIRTUAL-LINKS;
        }
      }
      uses ncs_template_INTERFACE-BRIEF-TABLE;
      uses ncs_template_INTERFACE-TABLE;
    }
  }

  grouping ncs_template_NEIGHBOR-TABLE {
    description
      "Common node of adjacency-information, area";
    container neighbors {
      description
        "Neighbor table";
      list neighbor {
        // NCS patched for predictable order
        ordered-by user;
        description
          "Neighbor information";
        leaf interface-name {
          type string;
          description
            "Interface name";
        }
        leaf neighbor-address {
          type string;
          description
            "Neighbor address";
        }
        uses ncs_template_OSPF-SH-NEIGHBOR;
      }
    }
  }

  grouping ncs_template_LSA-TABLE {
    description
      "Common node of database-area, database";
    container lsas {
      description
        "Link State Database Table";
      list lsa {
        // NCS patched for predictable order
        ordered-by user;
        description
          "Link State Advertisement information";
        leaf area-id {
          type string;
          description
            "Area ID";
        }
        leaf ls-type {
          type string;
          description
            "Link state type";
        }
        leaf ls-id {
          type string;
          description
            "Link state ID";
        }
        leaf advertising-router {
          type string;
          description
            "Advertising Router ID";
        }
        leaf interface-name {
          type string;
          description
            "InterfaceName";
        }
        uses ncs_template_OSPF-SH-DATABASE-DETAIL;
      }
    }
  }

  grouping ncs_rpc_notif_ROUTE {
    description
      "Common node of route-table,
       multicast-intact-route-table";
    list route {
      description
        "An OSPF route";
      leaf prefix {
        type inet:ipv4-address-no-zone;
        description
          "Prefix";
      }
      leaf prefix-length {
        type Ospf-prefix-length;
        description
          "Prefix Length";
      }
      uses ncs_rpc_notif_OSPF-SH-TOPOLOGY;
    }
  }

  grouping ncs_rpc_notif_FLOOD-LIST {
    description
      "Common node of flood-list-table,
       flood-list-area-table";
    list flood {
      key "interface-name";
      description
        "Flooding information for a specific interface";
      leaf interface-name {
        type xr:Interface-name;
        description
          "Interface name";
      }
      uses ncs_rpc_notif_OSPF-SH-FLOOD-LIST;
    }
  }

  grouping ncs_rpc_notif_BORDER-ROUTER-TABLE {
    description
      "Common node of default-vrf, vrf";
    container border-routers {
      description
        "Border router table";
      list border-router {
        key "border-router-id";
        description
          "Information for a particular border router";
        leaf border-router-id {
          type inet:ipv4-address-no-zone;
          description
            "Router address";
        }
        uses ncs_rpc_notif_OSPF-SH-BORDER-ROUTER;
      }
    }
  }

  grouping ncs_rpc_notif_SEGMENT-ROUTING {
    description
      "Common node of default-vrf, vrf";
    container segment-routing {
      description
        "Container for Segment Routing";
      container adjacency-sids {
        description
          "Container for SR Adjacency SIDs";
        list adjacency-sid {
          key "adj-sid";
          description
            "SR Adj SID Bag";
          leaf adj-sid {
            type uint32;
            description
              "Adjacency SID";
          }
          uses ncs_rpc_notif_OSPF-SH-ADJ-SID;
        }
      }
      container sr-endpoint-policies {
        description
          "Container for SR Policies";
        list sr-endpoint-policy {
          key "endpoint-ip";
          description
            "SR Endpoint Policy Bag";
          leaf endpoint-ip {
            type inet:ip-address-no-zone;
            description
              "Endpoint IP Address";
          }
          uses ncs_rpc_notif_OSPF-SH-SR-ENDPOINT;
        }
      }
    }
  }

  grouping ncs_rpc_notif_AREA-TABLE {
    description
      "Common node of default-vrf, vrf";
    container areas {
      description
        "Area table";
      list area {
        key "area-id";
        description
          "Container for per area data";
        container flood-list-area-table {
          description
            "Area specific flood list table";
          uses ncs_rpc_notif_FLOOD-LIST;
        }
        leaf area-id {
          type uint32;
          description
            "Area ID";
        }
        uses ncs_rpc_notif_NEIGHBOR-TABLE;
        uses ncs_rpc_notif_INTERFACE-BRIEF-TABLE;
        uses ncs_rpc_notif_REQUEST-LIST-TABLE;
        uses ncs_rpc_notif_RETRANSMISSION-LIST-TABLE;
        uses ncs_rpc_notif_AREA-STATISTICS;
        uses ncs_rpc_notif_NEIGHBOR-DETAIL-TABLE;
        uses ncs_rpc_notif_INTERFACE-TABLE;
      }
    }
  }

  grouping ncs_rpc_notif_INTERFACE-STATS-TABLE {
    description
      "Common node of statistics, area-statistics";
    container interface-stats-entries {
      description
        "Statistics innformation Interface table";
      list interface-stats-entry {
        key "interface-name";
        description
          "Statistics information for a specific interface";
        leaf interface-name {
          type xr:Interface-name;
          description
            "Interface name";
        }
        uses ncs_rpc_notif_OSPF-SH-IF-STATS;
      }
    }
  }

  grouping ncs_rpc_notif_STATISTICS {
    description
      "Common node of default-vrf, vrf";
    container statistics {
      description
        "Container for Statistics";
      container spf-stats {
        description
          "OSPF SPF statistics";
        uses ncs_rpc_notif_OSPF-SH-STATS-SPF;
      }
      container rib-batch-stats {
        description
          "Stats concerning RIB route updates using the
           Batching API";
        uses ncs_rpc_notif_OSPF-SH-RIB-BATCH-PRIORITY-QUEUES;
      }
      container issu-stats {
        description
          "OSPF ISSU statistics";
        uses ncs_rpc_notif_OSPF-SH-NSR-STATS;
      }
      container rib-thread-stats {
        description
          "OSPF RIB thread statistics";
        uses ncs_rpc_notif_OSPF-SH-STATS-WORK-QUEUES;
      }
      container nsr-pl-stats {
        description
          "OSPF NSR packet library statistics";
        uses ncs_rpc_notif_OSPF-SH-NCD-STATS;
      }
      container nsr-stats {
        description
          "OSPF NSR thread statistics";
        uses ncs_rpc_notif_OSPF-SH-NSR-STATS;
      }
      container frr-stats {
        description
          "OSPF fast-reroute statistics";
        uses ncs_rpc_notif_OSPF-SH-IPFRR-STATS;
      }
      container te-stats {
        description
          "OSPF TE IO statistics";
        uses ncs_rpc_notif_OSPF-SH-TE-STATS;
      }
      container protocol-stats {
        description
          "OSPF Protocol statistics";
        uses ncs_rpc_notif_OSPF-SH-PROTOPKT-STATS;
      }
      container raw-io-stats {
        description
          "OSPF RAW IO statistics";
        uses ncs_rpc_notif_OSPF-SH-RAW-STATS;
      }
      uses ncs_rpc_notif_INTERFACE-STATS-TABLE;
    }
  }

  grouping ncs_rpc_notif_OSPF-SUMMARY {
    description
      "Common node of default-vrf, vrf";
    container ospf-summary {
      description
        "Fast-reroute topology information";
      uses ncs_rpc_notif_OSPF-SH-STATS-AGGT;
    }
  }

  grouping ncs_rpc_notif_PROCESS-INFORMATION {
    description
      "Common node of default-vrf, vrf";
    container process-information {
      description
        "Container for OSPF Process information";
      container protocol-areas {
        description
          "Protocol Area table";
        list protocol-area {
          description
            "Area information";
          leaf area-id {
            type uint32;
            description
              "Area ID if in integer format";
          }
          leaf address {
            type inet:ipv4-address-no-zone;
            description
              "Area ID if in IP address format";
          }
          uses ncs_rpc_notif_OSPF-SH-PROTO-AREA;
        }
      }
      container protocol-summary {
        description
          "Basic OSPF protocol information";
        uses ncs_rpc_notif_OSPF-SH-PROTOCOL;
      }
      container redistributions {
        description
          "Redistribution information table";
        list redistribution {
          description
            "Redistribution information";
          leaf protocol-name {
            type xr:Cisco-ios-xr-string;
            description
              "Protocol name";
          }
          leaf process-name {
            type xr:Cisco-ios-xr-string;
            description
              "Process name";
          }
          uses ncs_rpc_notif_OSPF-SH-REDIST;
        }
      }
      container process-areas {
        description
          "Process Area table";
        list process-area {
          description
            "Detailed information for a particular area";
          leaf area-id {
            type uint32;
            description
              "Area ID if in integer format";
          }
          leaf address {
            type inet:ipv4-address-no-zone;
            description
              "Area ID if in IP address format";
          }
          uses ncs_rpc_notif_OSPF-SH-AREA;
        }
      }
      container process-summary {
        description
          "Basic OSPF summary information";
        uses ncs_rpc_notif_OSPF-SH-SUMMARY;
      }
    }
  }

  grouping ncs_rpc_notif_ADJACENCY-INFORMATION {
    description
      "Common node of default-vrf, vrf";
    container adjacency-information {
      description
        "Container for OSPF Interfaces";
      uses ncs_rpc_notif_NEIGHBOR-TABLE;
      uses ncs_rpc_notif_REQUEST-LIST-TABLE;
      uses ncs_rpc_notif_RETRANSMISSION-LIST-TABLE;
      uses ncs_rpc_notif_NEIGHBOR-DETAIL-TABLE;
    }
  }

  grouping ncs_rpc_notif_RETRANSMISSION-LIST-TABLE {
    description
      "Common node of adjacency-information, area";
    container retransmissions {
      description
        "Retransmission list table";
      list retransmission {
        description
          "Retransmission list for a particular adjacency";
        leaf interface-name {
          type xr:Interface-name;
          description
            "Interface name";
        }
        leaf neighbor-address {
          type inet:ipv4-address-no-zone;
          description
            "Neighbor address";
        }
        uses ncs_rpc_notif_OSPF-SH-RETRANS-LIST;
      }
    }
  }

  grouping ncs_rpc_notif_LSA-SUMMARY-TABLE {
    description
      "Common node of database, database-area";
    container lsa-summaries {
      description
        "Link state advertisement summary table";
      list lsa-summary {
        description
          "LSA summary information";
        leaf area-id {
          type uint32;
          description
            "Area ID";
        }
        leaf ls-type {
          type Ospf-ls;
          description
            "Link state type";
        }
        leaf ls-id {
          type inet:ipv4-address-no-zone;
          description
            "Link state ID";
        }
        leaf advertising-router {
          type inet:ipv4-address-no-zone;
          description
            "Advertising Router ID";
        }
        leaf interface-name {
          type xr:Interface-name;
          description
            "Interface name";
        }
        uses ncs_rpc_notif_OSPF-SH-DATABASE;
      }
    }
  }

  grouping ncs_rpc_notif_ROUTE-INFORMATION {
    description
      "Common node of default-vrf, vrf";
    container route-information {
      description
        "Container for OSPF routing tables";
      container backup-routes {
        description
          "OSPF Route Table Including Backup Paths";
        list backup-route {
          description
            "OSPF route including backup paths";
          leaf prefix {
            type inet:ipv4-address-no-zone;
            description
              "Prefix";
          }
          leaf prefix-length {
            type Ospf-prefix-length;
            description
              "Prefix Length";
          }
          uses ncs_rpc_notif_OSPF-SH-TOPOLOGY-BACKUP;
        }
      }
      container multicast-intact-route-table {
        description
          "OSPF Route Table including multicast-intact
           routes";
        uses ncs_rpc_notif_ROUTE;
      }
      container multicast-intact-backup-routes {
        description
          "OSPF Route Table Including Multicast intact
           Backup Paths";
        list multicast-intact-backup-route {
          description
            "OSPF route including multicast backup paths";
          leaf prefix {
            type inet:ipv4-address-no-zone;
            description
              "Prefix";
          }
          leaf prefix-length {
            type Ospf-prefix-length;
            description
              "Prefix Length";
          }
          uses ncs_rpc_notif_OSPF-SH-TOPOLOGY-BACKUP;
        }
      }
      container summary-information {
        description
          "OSPF route summary statistics";
        uses ncs_rpc_notif_OSPF-SH-ROUTE-SUMMARY;
      }
      container connected-routes {
        description
          "OSPF Connected Route Table";
        list connected-route {
          description
            "Connected route";
          leaf prefix {
            type inet:ipv4-address-no-zone;
            description
              "Prefix";
          }
          leaf prefix-length {
            type Ospf-prefix-length;
            description
              "Prefix Length";
          }
          uses ncs_rpc_notif_OSPF-SH-TOPOLOGY;
        }
      }
      container local-routes {
        description
          "OSPF Local Route Table";
        list local-route {
          description
            "Local route";
          leaf prefix {
            type inet:ipv4-address-no-zone;
            description
              "Prefix";
          }
          leaf prefix-length {
            type Ospf-prefix-length;
            description
              "Prefix Length";
          }
          uses ncs_rpc_notif_OSPF-SH-TOPOLOGY;
        }
      }
      container route-areas {
        description
          "OSPF Area Route Table";
        list route-area {
          key "area-id";
          description
            "OSPF Area Route";
          container multicast-intact-backup-route-areas {
            description
              "OSPF Route Table Including Multicast Intace
               Backup Paths in an area";
            list multicast-intact-backup-route-area {
              description
                "OSPF route including Multicast intact backup
                 paths";
              leaf prefix {
                type inet:ipv4-address-no-zone;
                description
                  "Prefix";
              }
              leaf prefix-length {
                type Ospf-prefix-length;
                description
                  "Prefix Length";
              }
              uses ncs_rpc_notif_OSPF-SH-TOPOLOGY-BACKUP;
            }
          }
          container connected-route-areas {
            description
              "OSPF Connected Route Table in an area";
            list connected-route-area {
              description
                "Connected route";
              leaf prefix {
                type inet:ipv4-address-no-zone;
                description
                  "Prefix";
              }
              leaf prefix-length {
                type Ospf-prefix-length;
                description
                  "Prefix Length";
              }
              uses ncs_rpc_notif_OSPF-SH-TOPOLOGY;
            }
          }
          container backup-route-areas {
            description
              "OSPF Route Table Including Backup Paths in an
               area";
            list backup-route-area {
              description
                "OSPF route including backup paths";
              leaf prefix {
                type inet:ipv4-address-no-zone;
                description
                  "Prefix";
              }
              leaf prefix-length {
                type Ospf-prefix-length;
                description
                  "Prefix Length";
              }
              uses ncs_rpc_notif_OSPF-SH-TOPOLOGY-BACKUP;
            }
          }
          container route-area-informations {
            description
              "OSPF Area Route Entry";
            list route-area-information {
              description
                "An OSPF route";
              leaf prefix {
                type inet:ipv4-address-no-zone;
                description
                  "Prefix";
              }
              leaf prefix-length {
                type Ospf-prefix-length;
                description
                  "Prefix Length";
              }
              uses ncs_rpc_notif_OSPF-SH-TOPOLOGY;
            }
          }
          container multicast-intact-route-areas {
            description
              "OSPF Area multicast-intact included route
               entry";
            list multicast-intact-route-area {
              description
                "A Muliticast OSPF route in an area";
              leaf prefix {
                type inet:ipv4-address-no-zone;
                description
                  "Prefix";
              }
              leaf prefix-length {
                type Ospf-prefix-length;
                description
                  "Prefix Length";
              }
              uses ncs_rpc_notif_OSPF-SH-TOPOLOGY;
            }
          }
          container summary-area-information {
            description
              "OSPF route summary statistics";
            uses ncs_rpc_notif_OSPF-SH-ROUTE-SUMMARY;
          }
          container local-route-areas {
            description
              "OSPF Local Route Table";
            list local-route-area {
              description
                "Local route";
              leaf prefix {
                type inet:ipv4-address-no-zone;
                description
                  "Prefix";
              }
              leaf prefix-length {
                type Ospf-prefix-length;
                description
                  "Prefix Length";
              }
              uses ncs_rpc_notif_OSPF-SH-TOPOLOGY;
            }
          }
          leaf area-id {
            type uint32;
            description
              "Area ID";
          }
        }
      }
      container route-table {
        description
          "OSPF Route Table";
        uses ncs_rpc_notif_ROUTE;
      }
      container external-routes {
        description
          "OSPF External Route Table";
        list external-route {
          description
            "OSPF external route";
          leaf prefix {
            type inet:ipv4-address-no-zone;
            description
              "Prefix";
          }
          leaf prefix-length {
            type Ospf-prefix-length;
            description
              "Prefix Length";
          }
          uses ncs_rpc_notif_OSPF-SH-ROUTE-EXT;
        }
      }
    }
  }

  grouping ncs_rpc_notif_FAST-REROUTE {
    description
      "Common node of default-vrf, vrf";
    container fast-reroute {
      description
        "Container for FastReroute";
      container topologies {
        description
          "Fast-reroute topology information table";
        list topology {
          description
            "Fast-reroute topology information";
          leaf router-id {
            type inet:ipv4-address-no-zone;
            description
              "Router ID";
          }
          leaf area-id {
            type uint32;
            description
              "Area ID";
          }
          uses ncs_rpc_notif_OSPF-SH-IPFRR-TOPO;
        }
      }
    }
  }

  grouping ncs_rpc_notif_POLICY-MI {
    description
      "Common node of policy-ipv4-active,
       policy-ipv4-backup";
    list policy-mi {
      key "mi-id";
      description
        "Mapping Item";
      leaf mi-id {
        type xr:Cisco-ios-xr-string;
        description
          "Mapping Item ID (0, 1, 2, ...)";
      }
      uses ncs_rpc_notif_SRMS-MI-T-B;
    }
  }

  grouping ncs_rpc_notif_MPLS-TE {
    description
      "Common node of default-vrf, vrf";
    container mpls-te {
      description
        "Container for MPLS TE";
      container mpls-te-links {
        description
          "MPLS TE link information table";
        list mpls-te-link {
          key "area-id";
          description
            "MPLS TE link information";
          leaf area-id {
            type uint32;
            description
              "Area ID";
          }
          uses ncs_rpc_notif_OSPF-SH-MPLS;
        }
      }
      container mpls-te-fragments {
        description
          "MPLS TE Fragment information table";
        list mpls-te-fragment {
          key "area-id";
          description
            "MPLS TE Fragment";
          leaf area-id {
            type uint32;
            description
              "Area ID";
          }
          uses ncs_rpc_notif_OSPF-SH-MPLS;
        }
      }
    }
  }

  grouping ncs_rpc_notif_FLOOD-LIST-TABLE {
    description
      "Common node of default-vrf, vrf";
    container flood-list-table {
      description
        "Flood list table";
      uses ncs_rpc_notif_FLOOD-LIST;
    }
  }

  grouping ncs_rpc_notif_SUMMARY-PREFIX-TABLE {
    description
      "Common node of default-vrf, vrf";
    container summary-prefixes {
      description
        "Summary prefix table";
      list summary-prefix {
        description
          "Summary prefix information";
        leaf prefix {
          type inet:ipv4-address-no-zone;
          description
            "Summary Prefix";
        }
        leaf netmask {
          type inet:ipv4-address-no-zone;
          description
            "Summary Mask";
        }
        uses ncs_rpc_notif_OSPF-SH-SUMMARY-ADDRESS;
      }
    }
  }

  grouping ncs_rpc_notif_NEIGHBOR-DETAIL-TABLE {
    description
      "Common node of adjacency-information, area";
    container neighbor-details {
      description
        "Neighbor detail table";
      list neighbor-detail {
        description
          "A single neighbor's detail information";
        leaf interface-name {
          type xr:Interface-name;
          description
            "Interface name";
        }
        leaf neighbor-address {
          type inet:ipv4-address-no-zone;
          description
            "Neighbor address";
        }
        uses ncs_rpc_notif_OSPF-SH-NEIGHBOR-DETAIL;
      }
    }
  }

  grouping ncs_rpc_notif_REQUEST-LIST-TABLE {
    description
      "Common node of adjacency-information, area";
    container requests {
      description
        "Request List table";
      list request {
        description
          "Request list for a particular adjacency";
        leaf interface-name {
          type xr:Interface-name;
          description
            "Interface";
        }
        leaf neighbor-address {
          type inet:ipv4-address-no-zone;
          description
            "Neighbor address";
        }
        uses ncs_rpc_notif_OSPF-SH-REQUEST-LIST;
      }
    }
  }

  grouping ncs_rpc_notif_AREA-STATISTICS {
    description
      "Common node of default-vrf, vrf, area";
    container area-statistics {
      description
        "Container for Statistics";
      uses ncs_rpc_notif_INTERFACE-STATS-TABLE;
    }
  }

  grouping ncs_rpc_notif_INTERFACE-TABLE {
    description
      "Common node of interface-information, area";
    container interfaces {
      description
        "OSPF Interface Table";
      list interface {
        key "interface-name";
        description
          "OSPF interface information";
        leaf interface-name {
          type xr:Interface-name;
          description
            "Interface name";
        }
        uses ncs_rpc_notif_OSPF-SH-INTERFACE;
      }
    }
  }

  grouping ncs_rpc_notif_INTERFACE-BRIEF-TABLE {
    description
      "Common node of interface-information, area";
    container interface-briefs {
      description
        "OSPF Interface Brief Table";
      list interface-brief {
        key "interface-name";
        description
          "OSPF interface brief information";
        leaf interface-name {
          type xr:Interface-name;
          description
            "Interface";
        }
        uses ncs_rpc_notif_OSPF-SH-IF-BRIEF;
      }
    }
  }

  grouping ncs_rpc_notif_DATABASE {
    description
      "Common node of default-vrf, vrf";
    container database {
      description
        "OSPF Link State Database";
      container database-areas {
        description
          "Per-Area view of Link state database";
        list database-area {
          key "area-id";
          description
            "Per-Area Link State Database data";
          leaf area-id {
            type uint32;
            description
              "Area ID";
          }
          uses ncs_rpc_notif_LSA-TABLE;
          uses ncs_rpc_notif_LSA-SUMMARY-TABLE;
        }
      }
      container database-summaries {
        description
          "Link State database summary table";
        list database-summary {
          key "area-id";
          description
            "Link State Database summary for a particular
             area";
          leaf area-id {
            type uint32;
            description
              "Area ID";
          }
          uses ncs_rpc_notif_OSPF-SH-DB-AREA-SUM;
        }
      }
      container database-summary-as {
        description
          "Link State Database summary for the AS";
        uses ncs_rpc_notif_OSPF-SH-DB-AS-SUM;
      }
      uses ncs_rpc_notif_LSA-TABLE;
      uses ncs_rpc_notif_LSA-SUMMARY-TABLE;
    }
  }

  grouping ncs_rpc_notif_INTERFACE-INFORMATION {
    description
      "Common node of default-vrf, vrf";
    container interface-information {
      description
        "Container for OSPF Interfaces/links";
      container virtual-links {
        description
          "Virtual Link table";
        list virtual-link {
          key "virtual-link-name";
          description
            "Information for one Virtual link";
          leaf virtual-link-name {
            type xr:Cisco-ios-xr-string;
            description
              "Virtual link";
          }
          uses ncs_rpc_notif_OSPF-SH-VIRTUAL-LINKS;
        }
      }
      uses ncs_rpc_notif_INTERFACE-BRIEF-TABLE;
      uses ncs_rpc_notif_INTERFACE-TABLE;
    }
  }

  grouping ncs_rpc_notif_NEIGHBOR-TABLE {
    description
      "Common node of adjacency-information, area";
    container neighbors {
      description
        "Neighbor table";
      list neighbor {
        description
          "Neighbor information";
        leaf interface-name {
          type xr:Interface-name;
          description
            "Interface name";
        }
        leaf neighbor-address {
          type inet:ipv4-address-no-zone;
          description
            "Neighbor address";
        }
        uses ncs_rpc_notif_OSPF-SH-NEIGHBOR;
      }
    }
  }

  grouping ncs_rpc_notif_LSA-TABLE {
    description
      "Common node of database-area, database";
    container lsas {
      description
        "Link State Database Table";
      list lsa {
        description
          "Link State Advertisement information";
        leaf area-id {
          type uint32;
          description
            "Area ID";
        }
        leaf ls-type {
          type Ospf-ls;
          description
            "Link state type";
        }
        leaf ls-id {
          type inet:ipv4-address-no-zone;
          description
            "Link state ID";
        }
        leaf advertising-router {
          type inet:ipv4-address-no-zone;
          description
            "Advertising Router ID";
        }
        leaf interface-name {
          type xr:Interface-name;
          description
            "InterfaceName";
        }
        uses ncs_rpc_notif_OSPF-SH-DATABASE-DETAIL;
      }
    }
  }

  grouping live_ncs_ROUTE {
    description
      "Common node of route-table,
       multicast-intact-route-table";
    list route {
      description
        "An OSPF route";
      leaf prefix {
        type inet:ipv4-address-no-zone;
        description
          "Prefix";
      }
      leaf prefix-length {
        type Ospf-prefix-length;
        description
          "Prefix Length";
      }
      uses live_ncs_OSPF-SH-TOPOLOGY;
    }
  }

  grouping live_ncs_FLOOD-LIST {
    description
      "Common node of flood-list-table,
       flood-list-area-table";
    list flood {
      key "interface-name";
      description
        "Flooding information for a specific interface";
      leaf interface-name {
        type xr:Interface-name;
        description
          "Interface name";
      }
      uses live_ncs_OSPF-SH-FLOOD-LIST;
    }
  }

  grouping live_ncs_BORDER-ROUTER-TABLE {
    description
      "Common node of default-vrf, vrf";
    container border-routers {
      description
        "Border router table";
      list border-router {
        key "border-router-id";
        description
          "Information for a particular border router";
        leaf border-router-id {
          type inet:ipv4-address-no-zone;
          description
            "Router address";
        }
        uses live_ncs_OSPF-SH-BORDER-ROUTER;
      }
    }
  }

  grouping live_ncs_SEGMENT-ROUTING {
    description
      "Common node of default-vrf, vrf";
    container segment-routing {
      description
        "Container for Segment Routing";
      container adjacency-sids {
        description
          "Container for SR Adjacency SIDs";
        list adjacency-sid {
          key "adj-sid";
          description
            "SR Adj SID Bag";
          leaf adj-sid {
            type uint32;
            description
              "Adjacency SID";
          }
          uses live_ncs_OSPF-SH-ADJ-SID;
        }
      }
      container sr-endpoint-policies {
        description
          "Container for SR Policies";
        list sr-endpoint-policy {
          key "endpoint-ip";
          description
            "SR Endpoint Policy Bag";
          leaf endpoint-ip {
            type inet:ip-address-no-zone;
            description
              "Endpoint IP Address";
          }
          uses live_ncs_OSPF-SH-SR-ENDPOINT;
        }
      }
    }
  }

  grouping live_ncs_AREA-TABLE {
    description
      "Common node of default-vrf, vrf";
    container areas {
      description
        "Area table";
      list area {
        key "area-id";
        description
          "Container for per area data";
        container flood-list-area-table {
          description
            "Area specific flood list table";
          uses live_ncs_FLOOD-LIST;
        }
        leaf area-id {
          type uint32;
          description
            "Area ID";
        }
        uses live_ncs_NEIGHBOR-TABLE;
        uses live_ncs_INTERFACE-BRIEF-TABLE;
        uses live_ncs_REQUEST-LIST-TABLE;
        uses live_ncs_RETRANSMISSION-LIST-TABLE;
        uses live_ncs_AREA-STATISTICS;
        uses live_ncs_NEIGHBOR-DETAIL-TABLE;
        uses live_ncs_INTERFACE-TABLE;
      }
    }
  }

  grouping live_ncs_INTERFACE-STATS-TABLE {
    description
      "Common node of statistics, area-statistics";
    container interface-stats-entries {
      description
        "Statistics innformation Interface table";
      list interface-stats-entry {
        key "interface-name";
        description
          "Statistics information for a specific interface";
        leaf interface-name {
          type xr:Interface-name;
          description
            "Interface name";
        }
        uses live_ncs_OSPF-SH-IF-STATS;
      }
    }
  }

  grouping live_ncs_STATISTICS {
    description
      "Common node of default-vrf, vrf";
    container statistics {
      description
        "Container for Statistics";
      container spf-stats {
        description
          "OSPF SPF statistics";
        uses live_ncs_OSPF-SH-STATS-SPF;
      }
      container rib-batch-stats {
        description
          "Stats concerning RIB route updates using the
           Batching API";
        uses live_ncs_OSPF-SH-RIB-BATCH-PRIORITY-QUEUES;
      }
      container issu-stats {
        description
          "OSPF ISSU statistics";
        uses live_ncs_OSPF-SH-NSR-STATS;
      }
      container rib-thread-stats {
        description
          "OSPF RIB thread statistics";
        uses live_ncs_OSPF-SH-STATS-WORK-QUEUES;
      }
      container nsr-pl-stats {
        description
          "OSPF NSR packet library statistics";
        uses live_ncs_OSPF-SH-NCD-STATS;
      }
      container nsr-stats {
        description
          "OSPF NSR thread statistics";
        uses live_ncs_OSPF-SH-NSR-STATS;
      }
      container frr-stats {
        description
          "OSPF fast-reroute statistics";
        uses live_ncs_OSPF-SH-IPFRR-STATS;
      }
      container te-stats {
        description
          "OSPF TE IO statistics";
        uses live_ncs_OSPF-SH-TE-STATS;
      }
      container protocol-stats {
        description
          "OSPF Protocol statistics";
        uses live_ncs_OSPF-SH-PROTOPKT-STATS;
      }
      container raw-io-stats {
        description
          "OSPF RAW IO statistics";
        uses live_ncs_OSPF-SH-RAW-STATS;
      }
      uses live_ncs_INTERFACE-STATS-TABLE;
    }
  }

  grouping live_ncs_OSPF-SUMMARY {
    description
      "Common node of default-vrf, vrf";
    container ospf-summary {
      description
        "Fast-reroute topology information";
      uses live_ncs_OSPF-SH-STATS-AGGT;
    }
  }

  grouping live_ncs_PROCESS-INFORMATION {
    description
      "Common node of default-vrf, vrf";
    container process-information {
      description
        "Container for OSPF Process information";
      container protocol-areas {
        description
          "Protocol Area table";
        list protocol-area {
          description
            "Area information";
          leaf area-id {
            type uint32;
            description
              "Area ID if in integer format";
          }
          leaf address {
            type inet:ipv4-address-no-zone;
            description
              "Area ID if in IP address format";
          }
          uses live_ncs_OSPF-SH-PROTO-AREA;
        }
      }
      container protocol-summary {
        description
          "Basic OSPF protocol information";
        uses live_ncs_OSPF-SH-PROTOCOL;
      }
      container redistributions {
        description
          "Redistribution information table";
        list redistribution {
          description
            "Redistribution information";
          leaf protocol-name {
            type xr:Cisco-ios-xr-string;
            description
              "Protocol name";
          }
          leaf process-name {
            type xr:Cisco-ios-xr-string;
            description
              "Process name";
          }
          uses live_ncs_OSPF-SH-REDIST;
        }
      }
      container process-areas {
        description
          "Process Area table";
        list process-area {
          description
            "Detailed information for a particular area";
          leaf area-id {
            type uint32;
            description
              "Area ID if in integer format";
          }
          leaf address {
            type inet:ipv4-address-no-zone;
            description
              "Area ID if in IP address format";
          }
          uses live_ncs_OSPF-SH-AREA;
        }
      }
      container process-summary {
        description
          "Basic OSPF summary information";
        uses live_ncs_OSPF-SH-SUMMARY;
      }
    }
  }

  grouping live_ncs_ADJACENCY-INFORMATION {
    description
      "Common node of default-vrf, vrf";
    container adjacency-information {
      description
        "Container for OSPF Interfaces";
      uses live_ncs_NEIGHBOR-TABLE;
      uses live_ncs_REQUEST-LIST-TABLE;
      uses live_ncs_RETRANSMISSION-LIST-TABLE;
      uses live_ncs_NEIGHBOR-DETAIL-TABLE;
    }
  }

  grouping live_ncs_RETRANSMISSION-LIST-TABLE {
    description
      "Common node of adjacency-information, area";
    container retransmissions {
      description
        "Retransmission list table";
      list retransmission {
        description
          "Retransmission list for a particular adjacency";
        leaf interface-name {
          type xr:Interface-name;
          description
            "Interface name";
        }
        leaf neighbor-address {
          type inet:ipv4-address-no-zone;
          description
            "Neighbor address";
        }
        uses live_ncs_OSPF-SH-RETRANS-LIST;
      }
    }
  }

  grouping live_ncs_LSA-SUMMARY-TABLE {
    description
      "Common node of database, database-area";
    container lsa-summaries {
      description
        "Link state advertisement summary table";
      list lsa-summary {
        description
          "LSA summary information";
        leaf area-id {
          type uint32;
          description
            "Area ID";
        }
        leaf ls-type {
          type Ospf-ls;
          description
            "Link state type";
        }
        leaf ls-id {
          type inet:ipv4-address-no-zone;
          description
            "Link state ID";
        }
        leaf advertising-router {
          type inet:ipv4-address-no-zone;
          description
            "Advertising Router ID";
        }
        leaf interface-name {
          type xr:Interface-name;
          description
            "Interface name";
        }
        uses live_ncs_OSPF-SH-DATABASE;
      }
    }
  }

  grouping live_ncs_ROUTE-INFORMATION {
    description
      "Common node of default-vrf, vrf";
    container route-information {
      description
        "Container for OSPF routing tables";
      container backup-routes {
        description
          "OSPF Route Table Including Backup Paths";
        list backup-route {
          description
            "OSPF route including backup paths";
          leaf prefix {
            type inet:ipv4-address-no-zone;
            description
              "Prefix";
          }
          leaf prefix-length {
            type Ospf-prefix-length;
            description
              "Prefix Length";
          }
          uses live_ncs_OSPF-SH-TOPOLOGY-BACKUP;
        }
      }
      container multicast-intact-route-table {
        description
          "OSPF Route Table including multicast-intact
           routes";
        uses live_ncs_ROUTE;
      }
      container multicast-intact-backup-routes {
        description
          "OSPF Route Table Including Multicast intact
           Backup Paths";
        list multicast-intact-backup-route {
          description
            "OSPF route including multicast backup paths";
          leaf prefix {
            type inet:ipv4-address-no-zone;
            description
              "Prefix";
          }
          leaf prefix-length {
            type Ospf-prefix-length;
            description
              "Prefix Length";
          }
          uses live_ncs_OSPF-SH-TOPOLOGY-BACKUP;
        }
      }
      container summary-information {
        description
          "OSPF route summary statistics";
        uses live_ncs_OSPF-SH-ROUTE-SUMMARY;
      }
      container connected-routes {
        description
          "OSPF Connected Route Table";
        list connected-route {
          description
            "Connected route";
          leaf prefix {
            type inet:ipv4-address-no-zone;
            description
              "Prefix";
          }
          leaf prefix-length {
            type Ospf-prefix-length;
            description
              "Prefix Length";
          }
          uses live_ncs_OSPF-SH-TOPOLOGY;
        }
      }
      container local-routes {
        description
          "OSPF Local Route Table";
        list local-route {
          description
            "Local route";
          leaf prefix {
            type inet:ipv4-address-no-zone;
            description
              "Prefix";
          }
          leaf prefix-length {
            type Ospf-prefix-length;
            description
              "Prefix Length";
          }
          uses live_ncs_OSPF-SH-TOPOLOGY;
        }
      }
      container route-areas {
        description
          "OSPF Area Route Table";
        list route-area {
          key "area-id";
          description
            "OSPF Area Route";
          container multicast-intact-backup-route-areas {
            description
              "OSPF Route Table Including Multicast Intace
               Backup Paths in an area";
            list multicast-intact-backup-route-area {
              description
                "OSPF route including Multicast intact backup
                 paths";
              leaf prefix {
                type inet:ipv4-address-no-zone;
                description
                  "Prefix";
              }
              leaf prefix-length {
                type Ospf-prefix-length;
                description
                  "Prefix Length";
              }
              uses live_ncs_OSPF-SH-TOPOLOGY-BACKUP;
            }
          }
          container connected-route-areas {
            description
              "OSPF Connected Route Table in an area";
            list connected-route-area {
              description
                "Connected route";
              leaf prefix {
                type inet:ipv4-address-no-zone;
                description
                  "Prefix";
              }
              leaf prefix-length {
                type Ospf-prefix-length;
                description
                  "Prefix Length";
              }
              uses live_ncs_OSPF-SH-TOPOLOGY;
            }
          }
          container backup-route-areas {
            description
              "OSPF Route Table Including Backup Paths in an
               area";
            list backup-route-area {
              description
                "OSPF route including backup paths";
              leaf prefix {
                type inet:ipv4-address-no-zone;
                description
                  "Prefix";
              }
              leaf prefix-length {
                type Ospf-prefix-length;
                description
                  "Prefix Length";
              }
              uses live_ncs_OSPF-SH-TOPOLOGY-BACKUP;
            }
          }
          container route-area-informations {
            description
              "OSPF Area Route Entry";
            list route-area-information {
              description
                "An OSPF route";
              leaf prefix {
                type inet:ipv4-address-no-zone;
                description
                  "Prefix";
              }
              leaf prefix-length {
                type Ospf-prefix-length;
                description
                  "Prefix Length";
              }
              uses live_ncs_OSPF-SH-TOPOLOGY;
            }
          }
          container multicast-intact-route-areas {
            description
              "OSPF Area multicast-intact included route
               entry";
            list multicast-intact-route-area {
              description
                "A Muliticast OSPF route in an area";
              leaf prefix {
                type inet:ipv4-address-no-zone;
                description
                  "Prefix";
              }
              leaf prefix-length {
                type Ospf-prefix-length;
                description
                  "Prefix Length";
              }
              uses live_ncs_OSPF-SH-TOPOLOGY;
            }
          }
          container summary-area-information {
            description
              "OSPF route summary statistics";
            uses live_ncs_OSPF-SH-ROUTE-SUMMARY;
          }
          container local-route-areas {
            description
              "OSPF Local Route Table";
            list local-route-area {
              description
                "Local route";
              leaf prefix {
                type inet:ipv4-address-no-zone;
                description
                  "Prefix";
              }
              leaf prefix-length {
                type Ospf-prefix-length;
                description
                  "Prefix Length";
              }
              uses live_ncs_OSPF-SH-TOPOLOGY;
            }
          }
          leaf area-id {
            type uint32;
            description
              "Area ID";
          }
        }
      }
      container route-table {
        description
          "OSPF Route Table";
        uses live_ncs_ROUTE;
      }
      container external-routes {
        description
          "OSPF External Route Table";
        list external-route {
          description
            "OSPF external route";
          leaf prefix {
            type inet:ipv4-address-no-zone;
            description
              "Prefix";
          }
          leaf prefix-length {
            type Ospf-prefix-length;
            description
              "Prefix Length";
          }
          uses live_ncs_OSPF-SH-ROUTE-EXT;
        }
      }
    }
  }

  grouping live_ncs_FAST-REROUTE {
    description
      "Common node of default-vrf, vrf";
    container fast-reroute {
      description
        "Container for FastReroute";
      container topologies {
        description
          "Fast-reroute topology information table";
        list topology {
          description
            "Fast-reroute topology information";
          leaf router-id {
            type inet:ipv4-address-no-zone;
            description
              "Router ID";
          }
          leaf area-id {
            type uint32;
            description
              "Area ID";
          }
          uses live_ncs_OSPF-SH-IPFRR-TOPO;
        }
      }
    }
  }

  grouping live_ncs_POLICY-MI {
    description
      "Common node of policy-ipv4-active,
       policy-ipv4-backup";
    list policy-mi {
      key "mi-id";
      description
        "Mapping Item";
      leaf mi-id {
        type xr:Cisco-ios-xr-string;
        description
          "Mapping Item ID (0, 1, 2, ...)";
      }
      uses live_ncs_SRMS-MI-T-B;
    }
  }

  grouping live_ncs_MPLS-TE {
    description
      "Common node of default-vrf, vrf";
    container mpls-te {
      description
        "Container for MPLS TE";
      container mpls-te-links {
        description
          "MPLS TE link information table";
        list mpls-te-link {
          key "area-id";
          description
            "MPLS TE link information";
          leaf area-id {
            type uint32;
            description
              "Area ID";
          }
          uses live_ncs_OSPF-SH-MPLS;
        }
      }
      container mpls-te-fragments {
        description
          "MPLS TE Fragment information table";
        list mpls-te-fragment {
          key "area-id";
          description
            "MPLS TE Fragment";
          leaf area-id {
            type uint32;
            description
              "Area ID";
          }
          uses live_ncs_OSPF-SH-MPLS;
        }
      }
    }
  }

  grouping live_ncs_FLOOD-LIST-TABLE {
    description
      "Common node of default-vrf, vrf";
    container flood-list-table {
      description
        "Flood list table";
      uses live_ncs_FLOOD-LIST;
    }
  }

  grouping live_ncs_SUMMARY-PREFIX-TABLE {
    description
      "Common node of default-vrf, vrf";
    container summary-prefixes {
      description
        "Summary prefix table";
      list summary-prefix {
        description
          "Summary prefix information";
        leaf prefix {
          type inet:ipv4-address-no-zone;
          description
            "Summary Prefix";
        }
        leaf netmask {
          type inet:ipv4-address-no-zone;
          description
            "Summary Mask";
        }
        uses live_ncs_OSPF-SH-SUMMARY-ADDRESS;
      }
    }
  }

  grouping live_ncs_NEIGHBOR-DETAIL-TABLE {
    description
      "Common node of adjacency-information, area";
    container neighbor-details {
      description
        "Neighbor detail table";
      list neighbor-detail {
        description
          "A single neighbor's detail information";
        leaf interface-name {
          type xr:Interface-name;
          description
            "Interface name";
        }
        leaf neighbor-address {
          type inet:ipv4-address-no-zone;
          description
            "Neighbor address";
        }
        uses live_ncs_OSPF-SH-NEIGHBOR-DETAIL;
      }
    }
  }

  grouping live_ncs_REQUEST-LIST-TABLE {
    description
      "Common node of adjacency-information, area";
    container requests {
      description
        "Request List table";
      list request {
        description
          "Request list for a particular adjacency";
        leaf interface-name {
          type xr:Interface-name;
          description
            "Interface";
        }
        leaf neighbor-address {
          type inet:ipv4-address-no-zone;
          description
            "Neighbor address";
        }
        uses live_ncs_OSPF-SH-REQUEST-LIST;
      }
    }
  }

  grouping live_ncs_AREA-STATISTICS {
    description
      "Common node of default-vrf, vrf, area";
    container area-statistics {
      description
        "Container for Statistics";
      uses live_ncs_INTERFACE-STATS-TABLE;
    }
  }

  grouping live_ncs_INTERFACE-TABLE {
    description
      "Common node of interface-information, area";
    container interfaces {
      description
        "OSPF Interface Table";
      list interface {
        key "interface-name";
        description
          "OSPF interface information";
        leaf interface-name {
          type xr:Interface-name;
          description
            "Interface name";
        }
        uses live_ncs_OSPF-SH-INTERFACE;
      }
    }
  }

  grouping live_ncs_INTERFACE-BRIEF-TABLE {
    description
      "Common node of interface-information, area";
    container interface-briefs {
      description
        "OSPF Interface Brief Table";
      list interface-brief {
        key "interface-name";
        description
          "OSPF interface brief information";
        leaf interface-name {
          type xr:Interface-name;
          description
            "Interface";
        }
        uses live_ncs_OSPF-SH-IF-BRIEF;
      }
    }
  }

  grouping live_ncs_DATABASE {
    description
      "Common node of default-vrf, vrf";
    container database {
      description
        "OSPF Link State Database";
      container database-areas {
        description
          "Per-Area view of Link state database";
        list database-area {
          key "area-id";
          description
            "Per-Area Link State Database data";
          leaf area-id {
            type uint32;
            description
              "Area ID";
          }
          uses live_ncs_LSA-TABLE;
          uses live_ncs_LSA-SUMMARY-TABLE;
        }
      }
      container database-summaries {
        description
          "Link State database summary table";
        list database-summary {
          key "area-id";
          description
            "Link State Database summary for a particular
             area";
          leaf area-id {
            type uint32;
            description
              "Area ID";
          }
          uses live_ncs_OSPF-SH-DB-AREA-SUM;
        }
      }
      container database-summary-as {
        description
          "Link State Database summary for the AS";
        uses live_ncs_OSPF-SH-DB-AS-SUM;
      }
      uses live_ncs_LSA-TABLE;
      uses live_ncs_LSA-SUMMARY-TABLE;
    }
  }

  grouping live_ncs_INTERFACE-INFORMATION {
    description
      "Common node of default-vrf, vrf";
    container interface-information {
      description
        "Container for OSPF Interfaces/links";
      container virtual-links {
        description
          "Virtual Link table";
        list virtual-link {
          key "virtual-link-name";
          description
            "Information for one Virtual link";
          leaf virtual-link-name {
            type xr:Cisco-ios-xr-string;
            description
              "Virtual link";
          }
          uses live_ncs_OSPF-SH-VIRTUAL-LINKS;
        }
      }
      uses live_ncs_INTERFACE-BRIEF-TABLE;
      uses live_ncs_INTERFACE-TABLE;
    }
  }

  grouping live_ncs_NEIGHBOR-TABLE {
    description
      "Common node of adjacency-information, area";
    container neighbors {
      description
        "Neighbor table";
      list neighbor {
        description
          "Neighbor information";
        leaf interface-name {
          type xr:Interface-name;
          description
            "Interface name";
        }
        leaf neighbor-address {
          type inet:ipv4-address-no-zone;
          description
            "Neighbor address";
        }
        uses live_ncs_OSPF-SH-NEIGHBOR;
      }
    }
  }

  grouping live_ncs_LSA-TABLE {
    description
      "Common node of database-area, database";
    container lsas {
      description
        "Link State Database Table";
      list lsa {
        description
          "Link State Advertisement information";
        leaf area-id {
          type uint32;
          description
            "Area ID";
        }
        leaf ls-type {
          type Ospf-ls;
          description
            "Link state type";
        }
        leaf ls-id {
          type inet:ipv4-address-no-zone;
          description
            "Link state ID";
        }
        leaf advertising-router {
          type inet:ipv4-address-no-zone;
          description
            "Advertising Router ID";
        }
        leaf interface-name {
          type xr:Interface-name;
          description
            "InterfaceName";
        }
        uses live_ncs_OSPF-SH-DATABASE-DETAIL;
      }
    }
  }

  grouping ROUTE {
    description
      "Common node of route-table,
       multicast-intact-route-table";
    list route {
      description
        "An OSPF route";
      leaf prefix {
        type inet:ipv4-address-no-zone;
        description
          "Prefix";
      }
      leaf prefix-length {
        type Ospf-prefix-length;
        description
          "Prefix Length";
      }
      uses OSPF-SH-TOPOLOGY;
    }
  }

  grouping FLOOD-LIST {
    description
      "Common node of flood-list-table,
       flood-list-area-table";
    list flood {
      key "interface-name";
      description
        "Flooding information for a specific interface";
      leaf interface-name {
        type xr:Interface-name;
        description
          "Interface name";
      }
      uses OSPF-SH-FLOOD-LIST;
    }
  }

  grouping BORDER-ROUTER-TABLE {
    description
      "Common node of default-vrf, vrf";
    container border-routers {
      description
        "Border router table";
      list border-router {
        key "border-router-id";
        description
          "Information for a particular border router";
        leaf border-router-id {
          type inet:ipv4-address-no-zone;
          description
            "Router address";
        }
        uses OSPF-SH-BORDER-ROUTER;
      }
    }
  }

  grouping SEGMENT-ROUTING {
    description
      "Common node of default-vrf, vrf";
    container segment-routing {
      description
        "Container for Segment Routing";
      container adjacency-sids {
        description
          "Container for SR Adjacency SIDs";
        list adjacency-sid {
          key "adj-sid";
          description
            "SR Adj SID Bag";
          leaf adj-sid {
            type uint32;
            description
              "Adjacency SID";
          }
          uses OSPF-SH-ADJ-SID;
        }
      }
      container sr-endpoint-policies {
        description
          "Container for SR Policies";
        list sr-endpoint-policy {
          key "endpoint-ip";
          description
            "SR Endpoint Policy Bag";
          leaf endpoint-ip {
            type inet:ip-address-no-zone;
            description
              "Endpoint IP Address";
          }
          uses OSPF-SH-SR-ENDPOINT;
        }
      }
    }
  }

  grouping AREA-TABLE {
    description
      "Common node of default-vrf, vrf";
    container areas {
      description
        "Area table";
      list area {
        key "area-id";
        description
          "Container for per area data";
        container flood-list-area-table {
          description
            "Area specific flood list table";
          uses FLOOD-LIST;
        }
        leaf area-id {
          type uint32;
          description
            "Area ID";
        }
        uses NEIGHBOR-TABLE;
        uses INTERFACE-BRIEF-TABLE;
        uses REQUEST-LIST-TABLE;
        uses RETRANSMISSION-LIST-TABLE;
        uses AREA-STATISTICS;
        uses NEIGHBOR-DETAIL-TABLE;
        uses INTERFACE-TABLE;
      }
    }
  }

  grouping INTERFACE-STATS-TABLE {
    description
      "Common node of statistics, area-statistics";
    container interface-stats-entries {
      description
        "Statistics innformation Interface table";
      list interface-stats-entry {
        key "interface-name";
        description
          "Statistics information for a specific interface";
        leaf interface-name {
          type xr:Interface-name;
          description
            "Interface name";
        }
        uses OSPF-SH-IF-STATS;
      }
    }
  }

  grouping STATISTICS {
    description
      "Common node of default-vrf, vrf";
    container statistics {
      description
        "Container for Statistics";
      container spf-stats {
        description
          "OSPF SPF statistics";
        uses OSPF-SH-STATS-SPF;
      }
      container rib-batch-stats {
        description
          "Stats concerning RIB route updates using the
           Batching API";
        uses OSPF-SH-RIB-BATCH-PRIORITY-QUEUES;
      }
      container issu-stats {
        description
          "OSPF ISSU statistics";
        uses OSPF-SH-NSR-STATS;
      }
      container rib-thread-stats {
        description
          "OSPF RIB thread statistics";
        uses OSPF-SH-STATS-WORK-QUEUES;
      }
      container nsr-pl-stats {
        description
          "OSPF NSR packet library statistics";
        uses OSPF-SH-NCD-STATS;
      }
      container nsr-stats {
        description
          "OSPF NSR thread statistics";
        uses OSPF-SH-NSR-STATS;
      }
      container frr-stats {
        description
          "OSPF fast-reroute statistics";
        uses OSPF-SH-IPFRR-STATS;
      }
      container te-stats {
        description
          "OSPF TE IO statistics";
        uses OSPF-SH-TE-STATS;
      }
      container protocol-stats {
        description
          "OSPF Protocol statistics";
        uses OSPF-SH-PROTOPKT-STATS;
      }
      container raw-io-stats {
        description
          "OSPF RAW IO statistics";
        uses OSPF-SH-RAW-STATS;
      }
      uses INTERFACE-STATS-TABLE;
    }
  }

  grouping OSPF-SUMMARY {
    description
      "Common node of default-vrf, vrf";
    container ospf-summary {
      description
        "Fast-reroute topology information";
      uses OSPF-SH-STATS-AGGT;
    }
  }

  grouping PROCESS-INFORMATION {
    description
      "Common node of default-vrf, vrf";
    container process-information {
      description
        "Container for OSPF Process information";
      container protocol-areas {
        description
          "Protocol Area table";
        list protocol-area {
          description
            "Area information";
          leaf area-id {
            type uint32;
            description
              "Area ID if in integer format";
          }
          leaf address {
            type inet:ipv4-address-no-zone;
            description
              "Area ID if in IP address format";
          }
          uses OSPF-SH-PROTO-AREA;
        }
      }
      container protocol-summary {
        description
          "Basic OSPF protocol information";
        uses OSPF-SH-PROTOCOL;
      }
      container redistributions {
        description
          "Redistribution information table";
        list redistribution {
          description
            "Redistribution information";
          leaf protocol-name {
            type xr:Cisco-ios-xr-string;
            description
              "Protocol name";
          }
          leaf process-name {
            type xr:Cisco-ios-xr-string;
            description
              "Process name";
          }
          uses OSPF-SH-REDIST;
        }
      }
      container process-areas {
        description
          "Process Area table";
        list process-area {
          description
            "Detailed information for a particular area";
          leaf area-id {
            type uint32;
            description
              "Area ID if in integer format";
          }
          leaf address {
            type inet:ipv4-address-no-zone;
            description
              "Area ID if in IP address format";
          }
          uses OSPF-SH-AREA;
        }
      }
      container process-summary {
        description
          "Basic OSPF summary information";
        uses OSPF-SH-SUMMARY;
      }
    }
  }

  grouping ADJACENCY-INFORMATION {
    description
      "Common node of default-vrf, vrf";
    container adjacency-information {
      description
        "Container for OSPF Interfaces";
      uses NEIGHBOR-TABLE;
      uses REQUEST-LIST-TABLE;
      uses RETRANSMISSION-LIST-TABLE;
      uses NEIGHBOR-DETAIL-TABLE;
    }
  }

  grouping RETRANSMISSION-LIST-TABLE {
    description
      "Common node of adjacency-information, area";
    container retransmissions {
      description
        "Retransmission list table";
      list retransmission {
        description
          "Retransmission list for a particular adjacency";
        leaf interface-name {
          type xr:Interface-name;
          description
            "Interface name";
        }
        leaf neighbor-address {
          type inet:ipv4-address-no-zone;
          description
            "Neighbor address";
        }
        uses OSPF-SH-RETRANS-LIST;
      }
    }
  }

  grouping LSA-SUMMARY-TABLE {
    description
      "Common node of database, database-area";
    container lsa-summaries {
      description
        "Link state advertisement summary table";
      list lsa-summary {
        description
          "LSA summary information";
        leaf area-id {
          type uint32;
          description
            "Area ID";
        }
        leaf ls-type {
          type Ospf-ls;
          description
            "Link state type";
        }
        leaf ls-id {
          type inet:ipv4-address-no-zone;
          description
            "Link state ID";
        }
        leaf advertising-router {
          type inet:ipv4-address-no-zone;
          description
            "Advertising Router ID";
        }
        leaf interface-name {
          type xr:Interface-name;
          description
            "Interface name";
        }
        uses OSPF-SH-DATABASE;
      }
    }
  }

  grouping ROUTE-INFORMATION {
    description
      "Common node of default-vrf, vrf";
    container route-information {
      description
        "Container for OSPF routing tables";
      container backup-routes {
        description
          "OSPF Route Table Including Backup Paths";
        list backup-route {
          description
            "OSPF route including backup paths";
          leaf prefix {
            type inet:ipv4-address-no-zone;
            description
              "Prefix";
          }
          leaf prefix-length {
            type Ospf-prefix-length;
            description
              "Prefix Length";
          }
          uses OSPF-SH-TOPOLOGY-BACKUP;
        }
      }
      container multicast-intact-route-table {
        description
          "OSPF Route Table including multicast-intact
           routes";
        uses ROUTE;
      }
      container multicast-intact-backup-routes {
        description
          "OSPF Route Table Including Multicast intact
           Backup Paths";
        list multicast-intact-backup-route {
          description
            "OSPF route including multicast backup paths";
          leaf prefix {
            type inet:ipv4-address-no-zone;
            description
              "Prefix";
          }
          leaf prefix-length {
            type Ospf-prefix-length;
            description
              "Prefix Length";
          }
          uses OSPF-SH-TOPOLOGY-BACKUP;
        }
      }
      container summary-information {
        description
          "OSPF route summary statistics";
        uses OSPF-SH-ROUTE-SUMMARY;
      }
      container connected-routes {
        description
          "OSPF Connected Route Table";
        list connected-route {
          description
            "Connected route";
          leaf prefix {
            type inet:ipv4-address-no-zone;
            description
              "Prefix";
          }
          leaf prefix-length {
            type Ospf-prefix-length;
            description
              "Prefix Length";
          }
          uses OSPF-SH-TOPOLOGY;
        }
      }
      container local-routes {
        description
          "OSPF Local Route Table";
        list local-route {
          description
            "Local route";
          leaf prefix {
            type inet:ipv4-address-no-zone;
            description
              "Prefix";
          }
          leaf prefix-length {
            type Ospf-prefix-length;
            description
              "Prefix Length";
          }
          uses OSPF-SH-TOPOLOGY;
        }
      }
      container route-areas {
        description
          "OSPF Area Route Table";
        list route-area {
          key "area-id";
          description
            "OSPF Area Route";
          container multicast-intact-backup-route-areas {
            description
              "OSPF Route Table Including Multicast Intace
               Backup Paths in an area";
            list multicast-intact-backup-route-area {
              description
                "OSPF route including Multicast intact backup
                 paths";
              leaf prefix {
                type inet:ipv4-address-no-zone;
                description
                  "Prefix";
              }
              leaf prefix-length {
                type Ospf-prefix-length;
                description
                  "Prefix Length";
              }
              uses OSPF-SH-TOPOLOGY-BACKUP;
            }
          }
          container connected-route-areas {
            description
              "OSPF Connected Route Table in an area";
            list connected-route-area {
              description
                "Connected route";
              leaf prefix {
                type inet:ipv4-address-no-zone;
                description
                  "Prefix";
              }
              leaf prefix-length {
                type Ospf-prefix-length;
                description
                  "Prefix Length";
              }
              uses OSPF-SH-TOPOLOGY;
            }
          }
          container backup-route-areas {
            description
              "OSPF Route Table Including Backup Paths in an
               area";
            list backup-route-area {
              description
                "OSPF route including backup paths";
              leaf prefix {
                type inet:ipv4-address-no-zone;
                description
                  "Prefix";
              }
              leaf prefix-length {
                type Ospf-prefix-length;
                description
                  "Prefix Length";
              }
              uses OSPF-SH-TOPOLOGY-BACKUP;
            }
          }
          container route-area-informations {
            description
              "OSPF Area Route Entry";
            list route-area-information {
              description
                "An OSPF route";
              leaf prefix {
                type inet:ipv4-address-no-zone;
                description
                  "Prefix";
              }
              leaf prefix-length {
                type Ospf-prefix-length;
                description
                  "Prefix Length";
              }
              uses OSPF-SH-TOPOLOGY;
            }
          }
          container multicast-intact-route-areas {
            description
              "OSPF Area multicast-intact included route
               entry";
            list multicast-intact-route-area {
              description
                "A Muliticast OSPF route in an area";
              leaf prefix {
                type inet:ipv4-address-no-zone;
                description
                  "Prefix";
              }
              leaf prefix-length {
                type Ospf-prefix-length;
                description
                  "Prefix Length";
              }
              uses OSPF-SH-TOPOLOGY;
            }
          }
          container summary-area-information {
            description
              "OSPF route summary statistics";
            uses OSPF-SH-ROUTE-SUMMARY;
          }
          container local-route-areas {
            description
              "OSPF Local Route Table";
            list local-route-area {
              description
                "Local route";
              leaf prefix {
                type inet:ipv4-address-no-zone;
                description
                  "Prefix";
              }
              leaf prefix-length {
                type Ospf-prefix-length;
                description
                  "Prefix Length";
              }
              uses OSPF-SH-TOPOLOGY;
            }
          }
          leaf area-id {
            type uint32;
            description
              "Area ID";
          }
        }
      }
      container route-table {
        description
          "OSPF Route Table";
        uses ROUTE;
      }
      container external-routes {
        description
          "OSPF External Route Table";
        list external-route {
          description
            "OSPF external route";
          leaf prefix {
            type inet:ipv4-address-no-zone;
            description
              "Prefix";
          }
          leaf prefix-length {
            type Ospf-prefix-length;
            description
              "Prefix Length";
          }
          uses OSPF-SH-ROUTE-EXT;
        }
      }
    }
  }

  grouping FAST-REROUTE {
    description
      "Common node of default-vrf, vrf";
    container fast-reroute {
      description
        "Container for FastReroute";
      container topologies {
        description
          "Fast-reroute topology information table";
        list topology {
          description
            "Fast-reroute topology information";
          leaf router-id {
            type inet:ipv4-address-no-zone;
            description
              "Router ID";
          }
          leaf area-id {
            type uint32;
            description
              "Area ID";
          }
          uses OSPF-SH-IPFRR-TOPO;
        }
      }
    }
  }

  grouping POLICY-MI {
    description
      "Common node of policy-ipv4-active,
       policy-ipv4-backup";
    list policy-mi {
      key "mi-id";
      description
        "Mapping Item";
      leaf mi-id {
        type xr:Cisco-ios-xr-string;
        description
          "Mapping Item ID (0, 1, 2, ...)";
      }
      uses SRMS-MI-T-B;
    }
  }

  grouping MPLS-TE {
    description
      "Common node of default-vrf, vrf";
    container mpls-te {
      description
        "Container for MPLS TE";
      container mpls-te-links {
        description
          "MPLS TE link information table";
        list mpls-te-link {
          key "area-id";
          description
            "MPLS TE link information";
          leaf area-id {
            type uint32;
            description
              "Area ID";
          }
          uses OSPF-SH-MPLS;
        }
      }
      container mpls-te-fragments {
        description
          "MPLS TE Fragment information table";
        list mpls-te-fragment {
          key "area-id";
          description
            "MPLS TE Fragment";
          leaf area-id {
            type uint32;
            description
              "Area ID";
          }
          uses OSPF-SH-MPLS;
        }
      }
    }
  }

  grouping FLOOD-LIST-TABLE {
    description
      "Common node of default-vrf, vrf";
    container flood-list-table {
      description
        "Flood list table";
      uses FLOOD-LIST;
    }
  }

  grouping SUMMARY-PREFIX-TABLE {
    description
      "Common node of default-vrf, vrf";
    container summary-prefixes {
      description
        "Summary prefix table";
      list summary-prefix {
        description
          "Summary prefix information";
        leaf prefix {
          type inet:ipv4-address-no-zone;
          description
            "Summary Prefix";
        }
        leaf netmask {
          type inet:ipv4-address-no-zone;
          description
            "Summary Mask";
        }
        uses OSPF-SH-SUMMARY-ADDRESS;
      }
    }
  }

  grouping NEIGHBOR-DETAIL-TABLE {
    description
      "Common node of adjacency-information, area";
    container neighbor-details {
      description
        "Neighbor detail table";
      list neighbor-detail {
        description
          "A single neighbor's detail information";
        leaf interface-name {
          type xr:Interface-name;
          description
            "Interface name";
        }
        leaf neighbor-address {
          type inet:ipv4-address-no-zone;
          description
            "Neighbor address";
        }
        uses OSPF-SH-NEIGHBOR-DETAIL;
      }
    }
  }

  grouping REQUEST-LIST-TABLE {
    description
      "Common node of adjacency-information, area";
    container requests {
      description
        "Request List table";
      list request {
        description
          "Request list for a particular adjacency";
        leaf interface-name {
          type xr:Interface-name;
          description
            "Interface";
        }
        leaf neighbor-address {
          type inet:ipv4-address-no-zone;
          description
            "Neighbor address";
        }
        uses OSPF-SH-REQUEST-LIST;
      }
    }
  }

  grouping AREA-STATISTICS {
    description
      "Common node of default-vrf, vrf, area";
    container area-statistics {
      description
        "Container for Statistics";
      uses INTERFACE-STATS-TABLE;
    }
  }

  grouping INTERFACE-TABLE {
    description
      "Common node of interface-information, area";
    container interfaces {
      description
        "OSPF Interface Table";
      list interface {
        key "interface-name";
        description
          "OSPF interface information";
        leaf interface-name {
          type xr:Interface-name;
          description
            "Interface name";
        }
        uses OSPF-SH-INTERFACE;
      }
    }
  }

  grouping INTERFACE-BRIEF-TABLE {
    description
      "Common node of interface-information, area";
    container interface-briefs {
      description
        "OSPF Interface Brief Table";
      list interface-brief {
        key "interface-name";
        description
          "OSPF interface brief information";
        leaf interface-name {
          type xr:Interface-name;
          description
            "Interface";
        }
        uses OSPF-SH-IF-BRIEF;
      }
    }
  }

  grouping DATABASE {
    description
      "Common node of default-vrf, vrf";
    container database {
      description
        "OSPF Link State Database";
      container database-areas {
        description
          "Per-Area view of Link state database";
        list database-area {
          key "area-id";
          description
            "Per-Area Link State Database data";
          leaf area-id {
            type uint32;
            description
              "Area ID";
          }
          uses LSA-TABLE;
          uses LSA-SUMMARY-TABLE;
        }
      }
      container database-summaries {
        description
          "Link State database summary table";
        list database-summary {
          key "area-id";
          description
            "Link State Database summary for a particular
             area";
          leaf area-id {
            type uint32;
            description
              "Area ID";
          }
          uses OSPF-SH-DB-AREA-SUM;
        }
      }
      container database-summary-as {
        description
          "Link State Database summary for the AS";
        uses OSPF-SH-DB-AS-SUM;
      }
      uses LSA-TABLE;
      uses LSA-SUMMARY-TABLE;
    }
  }

  grouping INTERFACE-INFORMATION {
    description
      "Common node of default-vrf, vrf";
    container interface-information {
      description
        "Container for OSPF Interfaces/links";
      container virtual-links {
        description
          "Virtual Link table";
        list virtual-link {
          key "virtual-link-name";
          description
            "Information for one Virtual link";
          leaf virtual-link-name {
            type xr:Cisco-ios-xr-string;
            description
              "Virtual link";
          }
          uses OSPF-SH-VIRTUAL-LINKS;
        }
      }
      uses INTERFACE-BRIEF-TABLE;
      uses INTERFACE-TABLE;
    }
  }

  grouping NEIGHBOR-TABLE {
    description
      "Common node of adjacency-information, area";
    container neighbors {
      description
        "Neighbor table";
      list neighbor {
        description
          "Neighbor information";
        leaf interface-name {
          type xr:Interface-name;
          description
            "Interface name";
        }
        leaf neighbor-address {
          type inet:ipv4-address-no-zone;
          description
            "Neighbor address";
        }
        uses OSPF-SH-NEIGHBOR;
      }
    }
  }

  grouping LSA-TABLE {
    description
      "Common node of database-area, database";
    container lsas {
      description
        "Link State Database Table";
      list lsa {
        description
          "Link State Advertisement information";
        leaf area-id {
          type uint32;
          description
            "Area ID";
        }
        leaf ls-type {
          type Ospf-ls;
          description
            "Link state type";
        }
        leaf ls-id {
          type inet:ipv4-address-no-zone;
          description
            "Link state ID";
        }
        leaf advertising-router {
          type inet:ipv4-address-no-zone;
          description
            "Advertising Router ID";
        }
        leaf interface-name {
          type xr:Interface-name;
          description
            "InterfaceName";
        }
        uses OSPF-SH-DATABASE-DETAIL;
      }
    }
  }

  augment "/ncs:devices/ncs:device/ncs:config" {
    // NCS drop config false container ospf
  }
  augment "/ncs:devices/ncs:device/ncs:live-status" {
    container ospf {
      tailf:ncs-device-type "netconf";
      tailf:display-when "not(../../ncs:module) or ../../ncs:module[ncs:name='Cisco-IOS-XR-ipv4-ospf-oper'] or (../../ncs:live-status-protocol[not(ncs:capability)]) or (../../ncs:live-status-protocol/ncs:capability/ncs:module[.='Cisco-IOS-XR-ipv4-ospf-oper'])";
      description
        "OSPF operational data";
      container processes {
        description
          "Table for each process";
        list process {
          key "process-name";
          description
            "Operational data for a particular OSPF process";
          container vrfs {
            description
              "Table for each VRF";
            list vrf {
              key "vrf-name";
              description
                "Operational data for a particular VRF
                 (instance) in the OSPF process";
              container interface-vrf-information {
                description
                  "Container for OSPF Interfaces/links under a
                   VRF";
                container sham-links {
                  description
                    "Sham Link table";
                  list sham-link {
                    key "sham-link-name";
                    description
                      "Information for one Sham link";
                    leaf sham-link-name {
                      type xr:Cisco-ios-xr-string;
                      description
                        "Sham link";
                    }
                    uses live_ncs_OSPF-SH-SHAM-LINKS;
                  }
                }
              }
              leaf vrf-name {
                type xr:Cisco-ios-xr-string;
                description
                  "VRF Name";
              }
              uses live_ncs_FLOOD-LIST-TABLE;
              uses live_ncs_SEGMENT-ROUTING;
              uses live_ncs_MPLS-TE;
              uses live_ncs_STATISTICS;
              uses live_ncs_ADJACENCY-INFORMATION;
              uses live_ncs_ROUTE-INFORMATION;
              uses live_ncs_INTERFACE-INFORMATION;
              uses live_ncs_BORDER-ROUTER-TABLE;
              uses live_ncs_PROCESS-INFORMATION;
              uses live_ncs_AREA-TABLE;
              uses live_ncs_DATABASE;
              uses live_ncs_SUMMARY-PREFIX-TABLE;
              uses live_ncs_AREA-STATISTICS;
              uses live_ncs_OSPF-SUMMARY;
              uses live_ncs_FAST-REROUTE;
            }
          }
          container srms {
            description
              "Segment Routing Mapping Server operational
               data";
            container policy {
              description
                "Policy operational data";
              container policy-ipv4 {
                description
                  "IPv4 policy operational data";
                container policy-ipv4-backup {
                  description
                    "IPv4 backup policy operational data";
                  uses live_ncs_POLICY-MI;
                }
                container policy-ipv4-active {
                  description
                    "IPv4 active policy operational data";
                  uses live_ncs_POLICY-MI;
                }
              }
            }
          }
          container default-vrf {
            description
              "Operational data for the default VRF
               (instance) in the OSPF process";
            uses live_ncs_FLOOD-LIST-TABLE;
            uses live_ncs_SEGMENT-ROUTING;
            uses live_ncs_MPLS-TE;
            uses live_ncs_STATISTICS;
            uses live_ncs_ADJACENCY-INFORMATION;
            uses live_ncs_ROUTE-INFORMATION;
            uses live_ncs_INTERFACE-INFORMATION;
            uses live_ncs_BORDER-ROUTER-TABLE;
            uses live_ncs_PROCESS-INFORMATION;
            uses live_ncs_AREA-TABLE;
            uses live_ncs_DATABASE;
            uses live_ncs_SUMMARY-PREFIX-TABLE;
            uses live_ncs_AREA-STATISTICS;
            uses live_ncs_OSPF-SUMMARY;
            uses live_ncs_FAST-REROUTE;
          }
          leaf process-name {
            type xr:Cisco-ios-xr-string;
            description
              "OSPF process";
          }
        }
      }
    }
  }
  augment "/ncs:devices/ncs:template/ncs:ned-id/ncs:config" {
    // NCS drop config false container ospf
  }
}
