submodule Cisco-IOS-XR-ipv4-ospf-oper-sub3 {
  // Generated by yanger -t ncs
  tailf:mount-id f5500-nc-1.0:f5500-nc-1.0;

  belongs-to Cisco-IOS-XR-ipv4-ospf-oper {
    prefix Cisco-IOS-XR-ipv4-ospf-oper-sub3;
  }

  import ietf-inet-types {
    prefix inet;
  }
  import ietf-yang-types {
    prefix yang;
  }
  import Cisco-IOS-XR-types {
    prefix xr;
  }
  include Cisco-IOS-XR-ipv4-ospf-oper-sub2 {
    revision-date 2018-04-18;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ipv4-ospf package operational data.

     Copyright (c) 2013-2018 by Cisco Systems, Inc.
     All rights reserved.";

  revision 2018-04-18 {
    description
      "Added keychain name to be displayed in show ospf interface bag";
  }
  revision 2017-10-26 {
    description
      "Fixed some field name and values for better interpretation";
  }
  revision 2017-09-07 {
    description
      "Fixed type translation error.";
  }
  revision 2017-05-01 {
    description
      "Fixing backward compatibility error in module.";
  }
  revision 2017-01-02 {
    description
      "IOS XR 6.2.1 revision.";
  }
  revision 2015-11-09 {
    description
      "IOS XR 6.0 revision.";
  }

  typedef Ospf-string-array {
    type string;
    description
      "Ospf string array";
  }

  grouping ncs_template_OSPF-SH-IF-STATS-ENTRY {
    description
      "OSPF interface entry for statistics";
    leaf madj-intf {
      type string;
      description
        "OSPF madj interface";
    }
    leaf area-id {
      type string;
      description
        "OSPF area id";
    }
    leaf area-id-str {
      type string;
      description
        "OSPF aread id string";
    }
    list if-stat {
      // NCS patched for predictable order
      ordered-by user;
      description
        "OSPF interface statistics";
      leaf entry {
        type string;
        description
          "OSPF interface statistics";
      }
    }
  }

  grouping ncs_template_OSPF-SH-IF-STATS {
    description
      "OSPF interface statistics";
    leaf handle {
      type string;
      description
        "interface handle type";
    }
    leaf if-name-str {
      type string;
      description
        "interface name";
    }
    list if-entry {
      // NCS patched for predictable order
      ordered-by user;
      description
        "interface entry";
      uses ncs_template_OSPF-SH-IF-STATS-ENTRY;
    }
  }

  grouping ncs_template_OSPF-SH-RAW-STATS {
    description
      "OSPF SH RAW STATS";
    leaf out-sent {
      type string;
      description
        "out sent";
    }
    leaf out-bytes-sent {
      type string;
      description
        "out bytes sent";
    }
    leaf out-no-conn-discarded {
      type string;
      description
        "out no conn discarded";
    }
    leaf out-null-src-discarded {
      type string;
      description
        "out null src discarded";
    }
    leaf out-no-pak-discarded {
      type string;
      description
        "out no pak discarded";
    }
    leaf out-ipv4-hdr-err-discarded {
      type string;
      description
        "out ipv4 hdr err discarded";
    }
    leaf out-send-pak-err-discarded {
      type string;
      description
        "out send pak err discarded";
    }
    leaf in-rcv {
      type string;
      description
        "in rcv";
    }
    leaf in-bytes-rcv {
      type string;
      description
        "in bytes rcv";
    }
    leaf in-short-msg-discarded {
      type string;
      description
        "in short msg discarded";
    }
    leaf in-no-mem-discarded {
      type string;
      description
        "in no mem discarded";
    }
    leaf in-raw-event {
      type string;
      description
        "in raw event";
    }
    leaf disconnects {
      type string;
      description
        "disconnects";
    }
    leaf in-standby-discarded {
      type string;
      description
        "in standby discarded";
    }
    leaf nsr-not-ready-discarded {
      type string;
      description
        "nsr not ready discarded";
    }
    leaf raw-connected {
      type string;
      description
        "raw connected";
    }
    leaf sl-raw-connected {
      type string;
      description
        "sl raw connected";
    }
  }

  grouping ncs_template_OSPF-SH-PROTOPKT-STATS {
    description
      "OSPF SH PROTOPKT STATS";
    leaf inputs {
      type string;
      description
        "inputs";
    }
    leaf input-hello {
      type string;
      description
        "input hello";
    }
    leaf input-dbdes {
      type string;
      description
        "input dbdes";
    }
    leaf input-dbdes-lsa {
      type string;
      description
        "input dbdes lsa";
    }
    leaf input-req {
      type string;
      description
        "input req";
    }
    leaf input-req-lsa {
      type string;
      description
        "input req lsa";
    }
    leaf input-lsupd {
      type string;
      description
        "input lsupd";
    }
    leaf input-lsupd-lsa {
      type string;
      description
        "input lsupd lsa";
    }
    leaf input-ack {
      type string;
      description
        "input ack";
    }
    leaf input-ack-lsa {
      type string;
      description
        "input ack lsa";
    }
    leaf checksumerr {
      type string;
      description
        "checksumerr";
    }
    leaf input-autherr {
      type string;
      description
        "input autherr";
    }
    leaf outputs {
      type string;
      description
        "outputs";
    }
    leaf output-hello {
      type string;
      description
        "output hello";
    }
    leaf output-dbdes {
      type string;
      description
        "output dbdes";
    }
    leaf output-dbdes-lsa {
      type string;
      description
        "output dbdes lsa";
    }
    leaf output-req {
      type string;
      description
        "output req";
    }
    leaf output-req-lsa {
      type string;
      description
        "output req lsa";
    }
    leaf output-lsupd {
      type string;
      description
        "output lsupd";
    }
    leaf output-lsupd-lsa {
      type string;
      description
        "output lsupd lsa";
    }
    leaf output-ack {
      type string;
      description
        "output ack";
    }
    leaf output-ack-lsa {
      type string;
      description
        "output ack lsa";
    }
    leaf output-autherr {
      type string;
      description
        "output autherr";
    }
    leaf h-input-dbdes {
      type string;
      description
        "h input dbdes";
    }
    leaf h-input-req {
      type string;
      description
        "h input req";
    }
    leaf h-input-lsupd {
      type string;
      description
        "h input lsupd";
    }
    leaf h-input-ack {
      type string;
      description
        "h input ack";
    }
  }

  grouping ncs_template_OSPF-SH-TE-STATS {
    description
      "OSPF SH TE STATS";
    leaf te-connected {
      type string;
      description
        "te connected";
    }
    leaf control-disconnects {
      type string;
      description
        "control disconnects";
    }
    leaf te-disconnects {
      type string;
      description
        "te disconnects";
    }
    leaf adj-gets {
      type string;
      description
        "adj gets";
    }
    leaf link-floods {
      type string;
      description
        "link floods";
    }
    leaf link-fragment-floods {
      type string;
      description
        "link fragment floods";
    }
    leaf lsp-gets {
      type string;
      description
        "lsp gets";
    }
    leaf tunnel-announces {
      type string;
      description
        "tunnel announces";
    }
    leaf total-tunnels {
      type string;
      description
        "total tunnels";
    }
    leaf control-batch-reads {
      type string;
      description
        "control batch reads";
    }
    leaf control-batch-writes {
      type string;
      description
        "control batch writes";
    }
    leaf link-batch-reads {
      type string;
      description
        "link batch reads";
    }
    leaf link-batch-writes {
      type string;
      description
        "link batch writes";
    }
    leaf adj-changes {
      type string;
      description
        "adj changes";
    }
    leaf fragment-deletes {
      type string;
      description
        "fragment deletes";
    }
    leaf fragment-announces {
      type string;
      description
        "fragment announces";
    }
    leaf data-trans-completes {
      type string;
      description
        "data trans completes";
    }
    leaf pce-listen {
      type string;
      description
        "pce listen";
    }
    leaf pce-stoplisten {
      type string;
      description
        "pce stoplisten";
    }
    leaf pce-flood {
      type string;
      description
        "pce flood";
    }
    leaf pce-get {
      type string;
      description
        "pce get";
    }
    leaf pce-br-lookup {
      type string;
      description
        "pce br lookup";
    }
    leaf pce-br-lkup-num-dests {
      type string;
      description
        "pce br lkup num dests";
    }
    leaf pce-br-resp-fails {
      type string;
      description
        "pce br resp fails";
    }
    leaf pce-node-announce-batches {
      type string;
      description
        "pce node announce batches";
    }
    leaf pce-node-delete-batches {
      type string;
      description
        "pce node delete batches";
    }
    leaf pce-num-node-announce {
      type string;
      description
        "pce num node announce";
    }
    leaf pce-num-node-delete {
      type string;
      description
        "pce num node delete";
    }
    leaf pce-node-send-fails {
      type string;
      description
        "pce node send fails";
    }
    leaf te-sr-path-reg-idt-recvd {
      type string;
      description
        "te sr path reg idt recvd";
    }
    leaf te-sr-idt-sent {
      type string;
      description
        "te sr idt sent";
    }
    leaf sr-num-area-enabled {
      type string;
      description
        "sr num area enabled";
    }
  }

  grouping ncs_template_OSPF-SH-IPFRR-STATS {
    description
      "OSPF SH IPFRR STATS";
    leaf fs-paths {
      type string;
      description
        "Number of IPFRR paths";
    }
    leaf fs-paths-eligible {
      type string;
      description
        "Number of paths enabled for protection";
    }
    leaf fs-paths-protected {
      type string;
      description
        "Number of paths protected";
    }
  }

  grouping ncs_template_NSR-PL-RECV-DROP-ARRAY {
    description
      "NSR PL RECV DROP ARRAY";
    list nsr-pl-recv-drop-array {
      // NCS patched for predictable order
      ordered-by user;
      // NCS drop max-elements statement
      description
        "nsr pl recv drop array";
      leaf entry {
        type string;
        description
          "nsr pl recv drop array";
      }
    }
  }

  grouping ncs_template_NSR-PL-SEND-DROP-ARRAY {
    description
      "NSR PL SEND DROP ARRAY";
    list nsr-pl-send-drop-array {
      // NCS patched for predictable order
      ordered-by user;
      // NCS drop max-elements statement
      description
        "nsr pl send drop array";
      leaf entry {
        type string;
        description
          "nsr pl send drop array";
      }
    }
  }

  grouping ncs_template_NSR-PL-CLIENT-STATS-TYPE {
    description
      "NSR PL stats information";
    list num-sent {
      // NCS patched for predictable order
      ordered-by user;
      // NCS drop max-elements statement
      description
        "Total sent";
      leaf entry {
        type string;
        description
          "Total sent";
      }
    }
    list num-recv {
      // NCS patched for predictable order
      ordered-by user;
      // NCS drop max-elements statement
      description
        "Total recvd";
      leaf entry {
        type string;
        description
          "Total recvd";
      }
    }
    list num-sent-drop {
      // NCS patched for predictable order
      ordered-by user;
      // NCS drop max-elements statement
      description
        "Sent Error/drops";
      uses ncs_template_NSR-PL-SEND-DROP-ARRAY;
    }
    list num-recv-drop {
      // NCS patched for predictable order
      ordered-by user;
      // NCS drop max-elements statement
      description
        "Recv Errors/drops";
      uses ncs_template_NSR-PL-RECV-DROP-ARRAY;
    }
  }

  grouping ncs_template_OSPF-SH-NCD-STATS {
    description
      "OSPF SH NCD STATS";
    list ncd-pri {
      // NCS patched for predictable order
      ordered-by user;
      // NCS drop max-elements statement
      description
        "ncd pri";
      uses ncs_template_NSR-PL-CLIENT-STATS-TYPE;
    }
  }

  grouping ncs_template_OSPF-SH-STATS-RIB-THREAD {
    description
      "OSPF SH STATS RIB THREAD";
    container rib-base-time {
      description
        "rib base time";
      uses ncs_template_BAG-TIMESPEC;
    }
    leaf wq-thread-active {
      type string;
      description
        "wq thread active";
    }
    leaf wq-dqtime {
      type string;
      description
        "wq dqtime";
    }
    leaf wqe-qtime {
      type string;
      description
        "wqe qtime";
    }
    leaf wq-len-cur {
      type string;
      description
        "wq len cur";
    }
    leaf wq-len-max {
      type string;
      description
        "wq len max";
    }
    leaf wq-total-queued {
      type string;
      description
        "wq total queued";
    }
    leaf wq-total-dequeued {
      type string;
      description
        "wq total dequeued";
    }
    leaf rib-version {
      type string;
      description
        "rib version";
    }
    leaf rib-pkts-sent {
      type string;
      description
        "rib pkts sent";
    }
    leaf rib-signals {
      type string;
      description
        "rib signals";
    }
    leaf rib-send-errs {
      type string;
      description
        "rib send errs";
    }
    leaf rib-queue-errs {
      type string;
      description
        "rib queue errs";
    }
    leaf rib-pfx-limit-errs {
      type string;
      description
        "rib pfx limit errs";
    }
    leaf rib-dequeue-errs {
      type string;
      description
        "rib dequeue errs";
    }
    leaf rib-empty-batches {
      type string;
      description
        "rib empty batches";
    }
    leaf rib-drop-before {
      type string;
      description
        "rib drop before";
    }
    leaf rib-drop-after {
      type string;
      description
        "rib drop after";
    }
    leaf rib-drop-conn {
      type string;
      description
        "rib drop conn";
    }
    leaf rib-table-not-created {
      type string;
      description
        "rib table not created";
    }
    leaf priority-level {
      type string;
      description
        "priority level";
    }
    leaf rib-base-clock {
      type string;
      description
        "rib base clock";
    }
  }

  grouping ncs_template_OSPF-SH-STATS-WORK-QUEUES {
    description
      "OSPF SH STATS WORK QUEUES";
    container internalwq {
      description
        "internalwq";
      uses ncs_template_OSPF-SH-STATS-RIB-THREAD;
    }
    list ribqueue {
      // NCS patched for predictable order
      ordered-by user;
      // NCS drop max-elements statement
      description
        "ribqueue";
      uses ncs_template_OSPF-SH-STATS-RIB-THREAD;
    }
  }

  grouping ncs_template_BAG-TIMESPEC {
    description
      "BAG TIMESPEC";
    leaf second {
      type string;
      description
        "Second";
    }
    leaf nanosecond {
      type string;
      description
        "Nanosecond";
    }
  }

  grouping ncs_template_OSPF-NSR-ERR-INFO-BAG {
    description
      "OSPF NSR ERR INFO BAG";
    container last-err-time {
      description
        "Time this error was last hit";
      uses ncs_template_BAG-TIMESPEC;
    }
    leaf err-count {
      type string;
      description
        "Count this error hit during the Nsr Revision";
    }
    leaf err-info-string {
      type string;
      description
        "Error Information";
    }
  }

  grouping ncs_template_OSPF-NSR-ERR-BLOCK-BAG {
    description
      "OSPF NSR ERR BLOCK BAG";
    leaf nsr-revisionversion {
      type string;
      description
        "Nsr Revision version";
    }
    leaf total-errors {
      type string;
      description
        "Total errors for this nsr revision version";
    }
    list nsr-error-info {
      // NCS patched for predictable order
      ordered-by user;
      description
        "List of erros";
      uses ncs_template_OSPF-NSR-ERR-INFO-BAG;
    }
  }

  grouping ncs_template_OSPF-ISSU-MILESTONE-BAG {
    description
      "OSPF ISSU MILESTONE BAG";
    leaf milestone-name {
      type string;
      description
        "Milestone Name";
    }
    leaf milestone-status {
      type string;
      description
        "Milestone Status";
    }
  }

  grouping ncs_template_OSPF-SH-NSR-STATS-PRI {
    description
      "OSPF SH NSR STATS PRI";
    leaf nsr-sched-pri {
      type string;
      description
        "nsr sched pri";
    }
    leaf nsr-sched-quant {
      type string;
      description
        "nsr sched quant";
    }
    leaf nsr-sched-remain-quant {
      type string;
      description
        "nsr sched remain quant";
    }
    leaf nsr-sched-evs-in-q {
      type string;
      description
        "nsr sched evs in q";
    }
    leaf nsr-sched-max-evs {
      type string;
      description
        "nsr sched max evs";
    }
    leaf nsr-sched-peak-q-len {
      type string;
      description
        "nsr sched peak q len";
    }
    leaf nsr-sched-evs-qd {
      type string;
      description
        "nsr sched evs qd";
    }
    leaf nsr-sched-enq-fails {
      type string;
      description
        "nsr sched enq fails";
    }
    leaf nsr-sched-evs-deqd {
      type string;
      description
        "nsr sched evs deqd";
    }
  }

  grouping ncs_template_OSPF-SH-NSR-SCHED-STATS {
    description
      "OSPF SH NSR SCHED STATS";
    leaf nsr-pulse-quant {
      type string;
      description
        "nsr pulse quant";
    }
    leaf nsr-events-in-q {
      type string;
      description
        "nsr events in q";
    }
    leaf nsr-events-tx {
      type string;
      description
        "nsr events tx";
    }
    leaf nsr-events-rx {
      type string;
      description
        "nsr events rx";
    }
    leaf nsr-bad-pulses-rx {
      type string;
      description
        "nsr bad pulses rx";
    }
    leaf nsr-good-pulses-rx {
      type string;
      description
        "nsr good pulses rx";
    }
    leaf nsr-pulses-tx {
      type string;
      description
        "nsr pulses tx";
    }
    leaf nsr-pulse-tx-fails {
      type string;
      description
        "nsr pulse tx fails";
    }
    list nsr-pri {
      // NCS patched for predictable order
      ordered-by user;
      // NCS drop max-elements statement
      description
        "nsr pri";
      uses ncs_template_OSPF-SH-NSR-STATS-PRI;
    }
  }

  grouping ncs_template_OSPF-SH-NSR-STATS {
    description
      "OSPF SH NSR STATS";
    container nsr-thd-sched {
      description
        "nsr thd sched";
      uses ncs_template_OSPF-SH-NSR-SCHED-STATS;
    }
    container nsr-rtr-thd-sched {
      description
        "nsr rtr thd sched";
      uses ncs_template_OSPF-SH-NSR-SCHED-STATS;
    }
    leaf nsr-rev {
      type string;
      description
        "nsr rev";
    }
    leaf nsr-fsm-state {
      type string;
      description
        "nsr fsm state";
    }
    leaf nsr-version {
      type string;
      description
        "nsr version";
    }
    leaf nsr-nodeid {
      type string;
      description
        "nsr nodeid";
    }
    leaf nsr-peer-version {
      type string;
      description
        "nsr peer version";
    }
    leaf nsr-peer-nodeid {
      type string;
      description
        "nsr peer nodeid";
    }
    leaf nsr-peer-ep-len {
      type string;
      description
        "nsr peer ep len";
    }
    leaf nsr-peer-ep-version {
      type string;
      description
        "nsr peer ep version";
    }
    leaf nsr-local-ep-len {
      type string;
      description
        "nsr local ep len";
    }
    leaf nsr-local-ep-version {
      type string;
      description
        "nsr local ep version";
    }
    leaf nsr-fabric-mtu {
      type string;
      description
        "nsr fabric mtu";
    }
    leaf nsr-nbr-qad-qid {
      type string;
      description
        "nsr nbr qad qid";
    }
    leaf nsr-lsa-qad-qid {
      type string;
      description
        "nsr lsa qad qid";
    }
    leaf nsr-nbr-qad-mdata-count {
      type string;
      description
        "nsr nbr qad mdata count";
    }
    leaf nsr-lsa-qad-mdata-count {
      type string;
      description
        "nsr lsa qad mdata count";
    }
    leaf nsr-nbr-init-sync-pend-count {
      type string;
      description
        "nsr nbr init sync pend count";
    }
    leaf nsr-lsa-init-sync-pend-count {
      type string;
      description
        "nsr lsa init sync pend count";
    }
    leaf nsr-nbr-seq-no {
      type string;
      description
        "nsr nbr seq no";
    }
    leaf nsr-intf-seq-no {
      type string;
      description
        "nsr intf seq no";
    }
    leaf nsr-tmr-quant {
      type string;
      description
        "nsr tmr quant";
    }
    leaf nsr-peer-ds-hdl {
      type string;
      description
        "nsr peer ds hdl";
    }
    leaf nsr-local-ds-hdl {
      type string;
      description
        "nsr local ds hdl";
    }
    leaf nsr-conn-to-active-attempts {
      type string;
      description
        "nsr conn to active attempts";
    }
    leaf nsr-conn-to-active-fails {
      type string;
      description
        "nsr conn to active fails";
    }
    leaf nsr-conn-to-active-opens {
      type string;
      description
        "nsr conn to active opens";
    }
    leaf nsr-conn-to-active-closes {
      type string;
      description
        "nsr conn to active closes";
    }
    leaf nsr-conn-to-active-errors {
      type string;
      description
        "nsr conn to active errors";
    }
    leaf nsr-peer-ep {
      type string;
      description
        "nsr peer ep";
    }
    leaf nsr-local-ep {
      type string;
      description
        "nsr local ep";
    }
    list nsr-fsm-flag {
      // NCS patched for predictable order
      ordered-by user;
      description
        "Nsr Fsm Flags information";
      leaf entry {
        type string;
        description
          "Nsr Fsm Flags information";
      }
    }
    list nsr-fsm-running-timer {
      // NCS patched for predictable order
      ordered-by user;
      description
        "Nsr Fsm Running Timers";
      leaf entry {
        type string;
        description
          "Nsr Fsm Running Timers";
      }
    }
    list nsr-issu-milestone {
      // NCS patched for predictable order
      ordered-by user;
      description
        "Nsr Issu Milestones";
      uses ncs_template_OSPF-ISSU-MILESTONE-BAG;
    }
    list nsr-err-history {
      // NCS patched for predictable order
      ordered-by user;
      description
        "Nsr Error History List";
      uses ncs_template_OSPF-NSR-ERR-BLOCK-BAG;
    }
  }

  grouping ncs_template_OSPF-SH-RIB-BATCH {
    description
      "OSPF SH RIB BATCH";
    leaf batches-sent {
      type string;
      description
        "batches sent";
    }
    leaf routes-sent {
      type string;
      description
        "routes sent";
    }
    leaf routes-pending {
      type string;
      description
        "routes pending";
    }
    leaf max-routes {
      type string;
      description
        "max routes";
    }
    leaf paths-sent {
      type string;
      description
        "paths sent";
    }
    leaf paths-pending {
      type string;
      description
        "paths pending";
    }
    leaf paths-add {
      type string;
      description
        "paths add";
    }
    leaf paths-add-errs {
      type string;
      description
        "paths add errs";
    }
    leaf paths-del {
      type string;
      description
        "paths del";
    }
    leaf paths-del-errs {
      type string;
      description
        "paths del errs";
    }
    leaf lfas-pending {
      type string;
      description
        "lfas pending";
    }
    leaf lfas-add {
      type string;
      description
        "lfas add";
    }
    leaf lfas-del {
      type string;
      description
        "lfas del";
    }
    leaf lfas-sent {
      type string;
      description
        "lfas sent";
    }
    leaf priority-level {
      type string;
      description
        "priority level";
    }
  }

  grouping ncs_template_OSPF-SH-RIB-BATCH-PRIORITY-QUEUES {
    description
      "OSPF SH RIB BATCH PRIORITY QUEUES";
    list priority-batch {
      // NCS patched for predictable order
      ordered-by user;
      // NCS drop max-elements statement
      description
        "priority batch";
      uses ncs_template_OSPF-SH-RIB-BATCH;
    }
  }

  grouping ncs_template_OSPF-EDM-AREA-SUMM {
    description
      "OSPF EDM AREA SUMM";
    leaf area-id {
      type string;
      description
        "area id";
    }
    leaf spf-count {
      type string;
      description
        "spf count";
    }
  }

  grouping ncs_template_OSPF-HEADER-INFO {
    description
      "OSPF HEADER INFO";
    leaf router-id {
      type string;
      description
        "router id";
    }
    leaf spf-count {
      type string;
      description
        "spf count";
    }
    list area-summ {
      // NCS patched for predictable order
      ordered-by user;
      description
        "area summ";
      uses ncs_template_OSPF-EDM-AREA-SUMM;
    }
  }

  grouping ncs_template_OSPF-EDM-SPF-AREA-STATS {
    description
      "OSPF EDM SPF AREA STATS";
    container spf-time {
      description
        "spf time";
      uses ncs_template_OSPF-SPF-TIME;
    }
    leaf area-id {
      type string;
      description
        "area id";
    }
    list lsa-type-cnt {
      // NCS patched for predictable order
      ordered-by user;
      // NCS drop max-elements statement
      description
        "lsa type cnt";
      leaf entry {
        type string;
        description
          "lsa type cnt";
      }
    }
  }

  grouping ncs_template_OSPF-LSA-CHANGE {
    description
      "OSPF LSA CHANGE";
    leaf area-id {
      type string;
      description
        "area id";
    }
    leaf adv-rtr {
      type string;
      description
        "adv rtr";
    }
    leaf id {
      type string;
      description
        "id";
    }
    leaf type {
      type string;
      description
        "type";
    }
    leaf flush {
      type string;
      description
        "flush";
    }
  }

  grouping ncs_template_OSPF-SPF-TIME {
    description
      "OSPF SPF TIME";
    leaf spf-dijkstra {
      type string;
      description
        "spf dijkstra";
    }
    leaf spf-intra-prefix {
      type string;
      description
        "spf intra prefix";
    }
    leaf spf-intra-prefix-del {
      type string;
      description
        "spf intra prefix del";
    }
    leaf spf-inter-prefix {
      type string;
      description
        "spf inter prefix";
    }
    leaf spf-inter-prefix-del {
      type string;
      description
        "spf inter prefix del";
    }
    leaf spf-ext-prefix {
      type string;
      description
        "spf ext prefix";
    }
    leaf spf-ext-prefix-del {
      type string;
      description
        "spf ext prefix del";
    }
  }

  grouping ncs_template_OSPF-RUNTIME-STATS {
    description
      "OSPF RUNTIME STATS";
    container gbl-spf-time {
      description
        "gbl spf time";
      uses ncs_template_OSPF-SPF-TIME;
    }
    leaf spf-start-time {
      type string;
      description
        "spf start time";
    }
    leaf lsa-change-cnt {
      type string;
      description
        "lsa change cnt";
    }
    list lsa-info {
      // NCS patched for predictable order
      ordered-by user;
      // NCS drop max-elements statement
      description
        "lsa info";
      uses ncs_template_OSPF-LSA-CHANGE;
    }
    list area-stat {
      // NCS patched for predictable order
      ordered-by user;
      description
        "area stat";
      uses ncs_template_OSPF-EDM-SPF-AREA-STATS;
    }
  }

  grouping ncs_template_OSPF-SH-STAT-PARTIAL {
    description
      "OSPF SH STAT PARTIAL";
    container sp-start-time {
      description
        "sp start time";
      uses ncs_template_OSPF-SH-TIME;
    }
    container sp-duration {
      description
        "sp duration";
      uses ncs_template_OSPF-SH-TIME;
    }
    leaf sp-adv-rtr-id {
      type string;
      description
        "sp adv rtr id";
    }
    leaf sp-dest-count {
      type string;
      description
        "sp dest count";
    }
    leaf sp-dest-addr {
      type string;
      description
        "sp dest addr";
    }
  }

  grouping ncs_template_OSPF-SH-STAT-INTRA {
    description
      "OSPF SH STAT INTRA";
    container si-start-time {
      description
        "si start time";
      uses ncs_template_OSPF-SH-TIME;
    }
    container si-duration {
      description
        "si duration";
      uses ncs_template_OSPF-SH-TIME;
    }
    leaf si-area-id-str {
      type string;
      description
        "si area id str";
    }
    leaf si-change-flags {
      type string;
      description
        "si change flags";
    }
  }

  grouping ncs_template_OSPF-SH-STATS-SPF {
    description
      "OSPF SH STATS SPF";
    container spf-header {
      description
        "spf header";
      uses ncs_template_OSPF-HEADER-INFO;
    }
    list os-runtime {
      // NCS patched for predictable order
      ordered-by user;
      description
        "os runtime";
      uses ncs_template_OSPF-SH-STAT-INTRA;
    }
    list os-sum-runtime {
      // NCS patched for predictable order
      ordered-by user;
      description
        "os sum runtime";
      uses ncs_template_OSPF-SH-STAT-PARTIAL;
    }
    list os-ex-runtime {
      // NCS patched for predictable order
      ordered-by user;
      description
        "os ex runtime";
      uses ncs_template_OSPF-SH-STAT-PARTIAL;
    }
    list runtime {
      // NCS patched for predictable order
      ordered-by user;
      description
        "runtime";
      uses ncs_template_OSPF-RUNTIME-STATS;
    }
  }

  grouping ncs_rpc_notif_OSPF-SH-IF-STATS-ENTRY {
    description
      "OSPF interface entry for statistics";
    leaf madj-intf {
      type boolean;
      description
        "OSPF madj interface";
    }
    leaf area-id {
      type uint32;
      description
        "OSPF area id";
    }
    leaf area-id-str {
      type string;
      description
        "OSPF aread id string";
    }
    list if-stat {
      description
        "OSPF interface statistics";
      leaf entry {
        type uint32;
        description
          "OSPF interface statistics";
      }
    }
  }

  grouping ncs_rpc_notif_OSPF-SH-IF-STATS {
    description
      "OSPF interface statistics";
    leaf handle {
      type xr:Interface-name;
      description
        "interface handle type";
    }
    leaf if-name-str {
      type string;
      description
        "interface name";
    }
    list if-entry {
      description
        "interface entry";
      uses ncs_rpc_notif_OSPF-SH-IF-STATS-ENTRY;
    }
  }

  grouping ncs_rpc_notif_OSPF-SH-RAW-STATS {
    description
      "OSPF SH RAW STATS";
    leaf out-sent {
      type uint32;
      description
        "out sent";
    }
    leaf out-bytes-sent {
      type uint32;
      description
        "out bytes sent";
    }
    leaf out-no-conn-discarded {
      type uint32;
      description
        "out no conn discarded";
    }
    leaf out-null-src-discarded {
      type uint32;
      description
        "out null src discarded";
    }
    leaf out-no-pak-discarded {
      type uint32;
      description
        "out no pak discarded";
    }
    leaf out-ipv4-hdr-err-discarded {
      type uint32;
      description
        "out ipv4 hdr err discarded";
    }
    leaf out-send-pak-err-discarded {
      type uint32;
      description
        "out send pak err discarded";
    }
    leaf in-rcv {
      type uint32;
      description
        "in rcv";
    }
    leaf in-bytes-rcv {
      type uint32;
      description
        "in bytes rcv";
    }
    leaf in-short-msg-discarded {
      type uint32;
      description
        "in short msg discarded";
    }
    leaf in-no-mem-discarded {
      type uint32;
      description
        "in no mem discarded";
    }
    leaf in-raw-event {
      type uint32;
      description
        "in raw event";
    }
    leaf disconnects {
      type uint32;
      description
        "disconnects";
    }
    leaf in-standby-discarded {
      type uint32;
      description
        "in standby discarded";
    }
    leaf nsr-not-ready-discarded {
      type uint32;
      description
        "nsr not ready discarded";
    }
    leaf raw-connected {
      type boolean;
      description
        "raw connected";
    }
    leaf sl-raw-connected {
      type boolean;
      description
        "sl raw connected";
    }
  }

  grouping ncs_rpc_notif_OSPF-SH-PROTOPKT-STATS {
    description
      "OSPF SH PROTOPKT STATS";
    leaf inputs {
      type uint32;
      description
        "inputs";
    }
    leaf input-hello {
      type uint32;
      description
        "input hello";
    }
    leaf input-dbdes {
      type uint32;
      description
        "input dbdes";
    }
    leaf input-dbdes-lsa {
      type uint32;
      description
        "input dbdes lsa";
    }
    leaf input-req {
      type uint32;
      description
        "input req";
    }
    leaf input-req-lsa {
      type uint32;
      description
        "input req lsa";
    }
    leaf input-lsupd {
      type uint32;
      description
        "input lsupd";
    }
    leaf input-lsupd-lsa {
      type uint32;
      description
        "input lsupd lsa";
    }
    leaf input-ack {
      type uint32;
      description
        "input ack";
    }
    leaf input-ack-lsa {
      type uint32;
      description
        "input ack lsa";
    }
    leaf checksumerr {
      type uint32;
      description
        "checksumerr";
    }
    leaf input-autherr {
      type uint32;
      description
        "input autherr";
    }
    leaf outputs {
      type uint32;
      description
        "outputs";
    }
    leaf output-hello {
      type uint32;
      description
        "output hello";
    }
    leaf output-dbdes {
      type uint32;
      description
        "output dbdes";
    }
    leaf output-dbdes-lsa {
      type uint32;
      description
        "output dbdes lsa";
    }
    leaf output-req {
      type uint32;
      description
        "output req";
    }
    leaf output-req-lsa {
      type uint32;
      description
        "output req lsa";
    }
    leaf output-lsupd {
      type uint32;
      description
        "output lsupd";
    }
    leaf output-lsupd-lsa {
      type uint32;
      description
        "output lsupd lsa";
    }
    leaf output-ack {
      type uint32;
      description
        "output ack";
    }
    leaf output-ack-lsa {
      type uint32;
      description
        "output ack lsa";
    }
    leaf output-autherr {
      type uint32;
      description
        "output autherr";
    }
    leaf h-input-dbdes {
      type uint32;
      description
        "h input dbdes";
    }
    leaf h-input-req {
      type uint32;
      description
        "h input req";
    }
    leaf h-input-lsupd {
      type uint32;
      description
        "h input lsupd";
    }
    leaf h-input-ack {
      type uint32;
      description
        "h input ack";
    }
  }

  grouping ncs_rpc_notif_OSPF-SH-TE-STATS {
    description
      "OSPF SH TE STATS";
    leaf te-connected {
      type boolean;
      description
        "te connected";
    }
    leaf control-disconnects {
      type uint32;
      description
        "control disconnects";
    }
    leaf te-disconnects {
      type uint32;
      description
        "te disconnects";
    }
    leaf adj-gets {
      type uint32;
      description
        "adj gets";
    }
    leaf link-floods {
      type uint32;
      description
        "link floods";
    }
    leaf link-fragment-floods {
      type uint32;
      description
        "link fragment floods";
    }
    leaf lsp-gets {
      type uint32;
      description
        "lsp gets";
    }
    leaf tunnel-announces {
      type uint32;
      description
        "tunnel announces";
    }
    leaf total-tunnels {
      type uint32;
      description
        "total tunnels";
    }
    leaf control-batch-reads {
      type uint32;
      description
        "control batch reads";
    }
    leaf control-batch-writes {
      type uint32;
      description
        "control batch writes";
    }
    leaf link-batch-reads {
      type uint32;
      description
        "link batch reads";
    }
    leaf link-batch-writes {
      type uint32;
      description
        "link batch writes";
    }
    leaf adj-changes {
      type uint32;
      description
        "adj changes";
    }
    leaf fragment-deletes {
      type uint32;
      description
        "fragment deletes";
    }
    leaf fragment-announces {
      type uint32;
      description
        "fragment announces";
    }
    leaf data-trans-completes {
      type uint32;
      description
        "data trans completes";
    }
    leaf pce-listen {
      type uint32;
      description
        "pce listen";
    }
    leaf pce-stoplisten {
      type uint32;
      description
        "pce stoplisten";
    }
    leaf pce-flood {
      type uint32;
      description
        "pce flood";
    }
    leaf pce-get {
      type uint32;
      description
        "pce get";
    }
    leaf pce-br-lookup {
      type uint32;
      description
        "pce br lookup";
    }
    leaf pce-br-lkup-num-dests {
      type uint32;
      description
        "pce br lkup num dests";
    }
    leaf pce-br-resp-fails {
      type uint32;
      description
        "pce br resp fails";
    }
    leaf pce-node-announce-batches {
      type uint32;
      description
        "pce node announce batches";
    }
    leaf pce-node-delete-batches {
      type uint32;
      description
        "pce node delete batches";
    }
    leaf pce-num-node-announce {
      type uint32;
      description
        "pce num node announce";
    }
    leaf pce-num-node-delete {
      type uint32;
      description
        "pce num node delete";
    }
    leaf pce-node-send-fails {
      type uint32;
      description
        "pce node send fails";
    }
    leaf te-sr-path-reg-idt-recvd {
      type boolean;
      description
        "te sr path reg idt recvd";
    }
    leaf te-sr-idt-sent {
      type boolean;
      description
        "te sr idt sent";
    }
    leaf sr-num-area-enabled {
      type uint32;
      description
        "sr num area enabled";
    }
  }

  grouping ncs_rpc_notif_OSPF-SH-IPFRR-STATS {
    description
      "OSPF SH IPFRR STATS";
    leaf fs-paths {
      type uint32;
      description
        "Number of IPFRR paths";
    }
    leaf fs-paths-eligible {
      type uint32;
      description
        "Number of paths enabled for protection";
    }
    leaf fs-paths-protected {
      type uint32;
      description
        "Number of paths protected";
    }
  }

  grouping ncs_rpc_notif_NSR-PL-RECV-DROP-ARRAY {
    description
      "NSR PL RECV DROP ARRAY";
    list nsr-pl-recv-drop-array {
      max-elements 16;
      description
        "nsr pl recv drop array";
      leaf entry {
        type uint32;
        description
          "nsr pl recv drop array";
      }
    }
  }

  grouping ncs_rpc_notif_NSR-PL-SEND-DROP-ARRAY {
    description
      "NSR PL SEND DROP ARRAY";
    list nsr-pl-send-drop-array {
      max-elements 7;
      description
        "nsr pl send drop array";
      leaf entry {
        type uint32;
        description
          "nsr pl send drop array";
      }
    }
  }

  grouping ncs_rpc_notif_NSR-PL-CLIENT-STATS-TYPE {
    description
      "NSR PL stats information";
    list num-sent {
      max-elements 5;
      description
        "Total sent";
      leaf entry {
        type uint64;
        description
          "Total sent";
      }
    }
    list num-recv {
      max-elements 6;
      description
        "Total recvd";
      leaf entry {
        type uint64;
        description
          "Total recvd";
      }
    }
    list num-sent-drop {
      max-elements 5;
      description
        "Sent Error/drops";
      uses ncs_rpc_notif_NSR-PL-SEND-DROP-ARRAY;
    }
    list num-recv-drop {
      max-elements 6;
      description
        "Recv Errors/drops";
      uses ncs_rpc_notif_NSR-PL-RECV-DROP-ARRAY;
    }
  }

  grouping ncs_rpc_notif_OSPF-SH-NCD-STATS {
    description
      "OSPF SH NCD STATS";
    list ncd-pri {
      max-elements 2;
      description
        "ncd pri";
      uses ncs_rpc_notif_NSR-PL-CLIENT-STATS-TYPE;
    }
  }

  grouping ncs_rpc_notif_OSPF-SH-STATS-RIB-THREAD {
    description
      "OSPF SH STATS RIB THREAD";
    container rib-base-time {
      description
        "rib base time";
      uses ncs_rpc_notif_BAG-TIMESPEC;
    }
    leaf wq-thread-active {
      type boolean;
      description
        "wq thread active";
    }
    leaf wq-dqtime {
      type uint64;
      description
        "wq dqtime";
    }
    leaf wqe-qtime {
      type uint64;
      description
        "wqe qtime";
    }
    leaf wq-len-cur {
      type int32;
      description
        "wq len cur";
    }
    leaf wq-len-max {
      type int32;
      description
        "wq len max";
    }
    leaf wq-total-queued {
      type uint32;
      description
        "wq total queued";
    }
    leaf wq-total-dequeued {
      type uint32;
      description
        "wq total dequeued";
    }
    leaf rib-version {
      type uint32;
      description
        "rib version";
    }
    leaf rib-pkts-sent {
      type uint32;
      description
        "rib pkts sent";
    }
    leaf rib-signals {
      type uint32;
      description
        "rib signals";
    }
    leaf rib-send-errs {
      type uint32;
      description
        "rib send errs";
    }
    leaf rib-queue-errs {
      type uint32;
      description
        "rib queue errs";
    }
    leaf rib-pfx-limit-errs {
      type uint32;
      description
        "rib pfx limit errs";
    }
    leaf rib-dequeue-errs {
      type uint32;
      description
        "rib dequeue errs";
    }
    leaf rib-empty-batches {
      type uint32;
      description
        "rib empty batches";
    }
    leaf rib-drop-before {
      type uint32;
      description
        "rib drop before";
    }
    leaf rib-drop-after {
      type uint32;
      description
        "rib drop after";
    }
    leaf rib-drop-conn {
      type uint32;
      description
        "rib drop conn";
    }
    leaf rib-table-not-created {
      type uint32;
      description
        "rib table not created";
    }
    leaf priority-level {
      type string {
        length "0..40";
      }
      description
        "priority level";
    }
    leaf rib-base-clock {
      type uint64;
      description
        "rib base clock";
    }
  }

  grouping ncs_rpc_notif_OSPF-SH-STATS-WORK-QUEUES {
    description
      "OSPF SH STATS WORK QUEUES";
    container internalwq {
      description
        "internalwq";
      uses ncs_rpc_notif_OSPF-SH-STATS-RIB-THREAD;
    }
    list ribqueue {
      max-elements 8;
      description
        "ribqueue";
      uses ncs_rpc_notif_OSPF-SH-STATS-RIB-THREAD;
    }
  }

  grouping ncs_rpc_notif_BAG-TIMESPEC {
    description
      "BAG TIMESPEC";
    leaf second {
      type uint32;
      description
        "Second";
    }
    leaf nanosecond {
      type uint32;
      description
        "Nanosecond";
    }
  }

  grouping ncs_rpc_notif_OSPF-NSR-ERR-INFO-BAG {
    description
      "OSPF NSR ERR INFO BAG";
    container last-err-time {
      description
        "Time this error was last hit";
      uses ncs_rpc_notif_BAG-TIMESPEC;
    }
    leaf err-count {
      type int32;
      description
        "Count this error hit during the Nsr Revision";
    }
    leaf err-info-string {
      type string;
      description
        "Error Information";
    }
  }

  grouping ncs_rpc_notif_OSPF-NSR-ERR-BLOCK-BAG {
    description
      "OSPF NSR ERR BLOCK BAG";
    leaf nsr-revisionversion {
      type uint32;
      description
        "Nsr Revision version";
    }
    leaf total-errors {
      type int32;
      description
        "Total errors for this nsr revision version";
    }
    list nsr-error-info {
      description
        "List of erros";
      uses ncs_rpc_notif_OSPF-NSR-ERR-INFO-BAG;
    }
  }

  grouping ncs_rpc_notif_OSPF-ISSU-MILESTONE-BAG {
    description
      "OSPF ISSU MILESTONE BAG";
    leaf milestone-name {
      type string;
      description
        "Milestone Name";
    }
    leaf milestone-status {
      type string;
      description
        "Milestone Status";
    }
  }

  grouping ncs_rpc_notif_OSPF-SH-NSR-STATS-PRI {
    description
      "OSPF SH NSR STATS PRI";
    leaf nsr-sched-pri {
      type uint32;
      description
        "nsr sched pri";
    }
    leaf nsr-sched-quant {
      type uint8;
      description
        "nsr sched quant";
    }
    leaf nsr-sched-remain-quant {
      type uint8;
      description
        "nsr sched remain quant";
    }
    leaf nsr-sched-evs-in-q {
      type uint16;
      description
        "nsr sched evs in q";
    }
    leaf nsr-sched-max-evs {
      type uint16;
      description
        "nsr sched max evs";
    }
    leaf nsr-sched-peak-q-len {
      type uint16;
      description
        "nsr sched peak q len";
    }
    leaf nsr-sched-evs-qd {
      type uint64;
      description
        "nsr sched evs qd";
    }
    leaf nsr-sched-enq-fails {
      type uint64;
      description
        "nsr sched enq fails";
    }
    leaf nsr-sched-evs-deqd {
      type uint64;
      description
        "nsr sched evs deqd";
    }
  }

  grouping ncs_rpc_notif_OSPF-SH-NSR-SCHED-STATS {
    description
      "OSPF SH NSR SCHED STATS";
    leaf nsr-pulse-quant {
      type int32;
      description
        "nsr pulse quant";
    }
    leaf nsr-events-in-q {
      type uint32;
      description
        "nsr events in q";
    }
    leaf nsr-events-tx {
      type uint64;
      description
        "nsr events tx";
    }
    leaf nsr-events-rx {
      type uint64;
      description
        "nsr events rx";
    }
    leaf nsr-bad-pulses-rx {
      type uint64;
      description
        "nsr bad pulses rx";
    }
    leaf nsr-good-pulses-rx {
      type uint64;
      description
        "nsr good pulses rx";
    }
    leaf nsr-pulses-tx {
      type uint64;
      description
        "nsr pulses tx";
    }
    leaf nsr-pulse-tx-fails {
      type uint64;
      description
        "nsr pulse tx fails";
    }
    list nsr-pri {
      max-elements 3;
      description
        "nsr pri";
      uses ncs_rpc_notif_OSPF-SH-NSR-STATS-PRI;
    }
  }

  grouping ncs_rpc_notif_OSPF-SH-NSR-STATS {
    description
      "OSPF SH NSR STATS";
    container nsr-thd-sched {
      description
        "nsr thd sched";
      uses ncs_rpc_notif_OSPF-SH-NSR-SCHED-STATS;
    }
    container nsr-rtr-thd-sched {
      description
        "nsr rtr thd sched";
      uses ncs_rpc_notif_OSPF-SH-NSR-SCHED-STATS;
    }
    leaf nsr-rev {
      type int32;
      description
        "nsr rev";
    }
    leaf nsr-fsm-state {
      type int32;
      description
        "nsr fsm state";
    }
    leaf nsr-version {
      type uint32;
      description
        "nsr version";
    }
    leaf nsr-nodeid {
      type uint32;
      description
        "nsr nodeid";
    }
    leaf nsr-peer-version {
      type uint32;
      description
        "nsr peer version";
    }
    leaf nsr-peer-nodeid {
      type uint32;
      description
        "nsr peer nodeid";
    }
    leaf nsr-peer-ep-len {
      type uint32;
      description
        "nsr peer ep len";
    }
    leaf nsr-peer-ep-version {
      type uint32;
      description
        "nsr peer ep version";
    }
    leaf nsr-local-ep-len {
      type uint32;
      description
        "nsr local ep len";
    }
    leaf nsr-local-ep-version {
      type uint32;
      description
        "nsr local ep version";
    }
    leaf nsr-fabric-mtu {
      type uint32;
      description
        "nsr fabric mtu";
    }
    leaf nsr-nbr-qad-qid {
      type uint32;
      description
        "nsr nbr qad qid";
    }
    leaf nsr-lsa-qad-qid {
      type uint32;
      description
        "nsr lsa qad qid";
    }
    leaf nsr-nbr-qad-mdata-count {
      type uint32;
      description
        "nsr nbr qad mdata count";
    }
    leaf nsr-lsa-qad-mdata-count {
      type uint32;
      description
        "nsr lsa qad mdata count";
    }
    leaf nsr-nbr-init-sync-pend-count {
      type int32;
      description
        "nsr nbr init sync pend count";
    }
    leaf nsr-lsa-init-sync-pend-count {
      type int32;
      description
        "nsr lsa init sync pend count";
    }
    leaf nsr-nbr-seq-no {
      type uint32;
      description
        "nsr nbr seq no";
    }
    leaf nsr-intf-seq-no {
      type uint32;
      description
        "nsr intf seq no";
    }
    leaf nsr-tmr-quant {
      type int32;
      description
        "nsr tmr quant";
    }
    leaf nsr-peer-ds-hdl {
      type uint64;
      description
        "nsr peer ds hdl";
    }
    leaf nsr-local-ds-hdl {
      type uint64;
      description
        "nsr local ds hdl";
    }
    leaf nsr-conn-to-active-attempts {
      type uint64;
      description
        "nsr conn to active attempts";
    }
    leaf nsr-conn-to-active-fails {
      type uint64;
      description
        "nsr conn to active fails";
    }
    leaf nsr-conn-to-active-opens {
      type uint64;
      description
        "nsr conn to active opens";
    }
    leaf nsr-conn-to-active-closes {
      type uint64;
      description
        "nsr conn to active closes";
    }
    leaf nsr-conn-to-active-errors {
      type uint64;
      description
        "nsr conn to active errors";
    }
    leaf nsr-peer-ep {
      type yang:hex-string;
      description
        "nsr peer ep";
    }
    leaf nsr-local-ep {
      type yang:hex-string;
      description
        "nsr local ep";
    }
    list nsr-fsm-flag {
      description
        "Nsr Fsm Flags information";
      leaf entry {
        type Ospf-string-array;
        description
          "Nsr Fsm Flags information";
      }
    }
    list nsr-fsm-running-timer {
      description
        "Nsr Fsm Running Timers";
      leaf entry {
        type Ospf-string-array;
        description
          "Nsr Fsm Running Timers";
      }
    }
    list nsr-issu-milestone {
      description
        "Nsr Issu Milestones";
      uses ncs_rpc_notif_OSPF-ISSU-MILESTONE-BAG;
    }
    list nsr-err-history {
      description
        "Nsr Error History List";
      uses ncs_rpc_notif_OSPF-NSR-ERR-BLOCK-BAG;
    }
  }

  grouping ncs_rpc_notif_OSPF-SH-RIB-BATCH {
    description
      "OSPF SH RIB BATCH";
    leaf batches-sent {
      type uint32;
      description
        "batches sent";
    }
    leaf routes-sent {
      type uint32;
      description
        "routes sent";
    }
    leaf routes-pending {
      type uint32;
      description
        "routes pending";
    }
    leaf max-routes {
      type uint32;
      description
        "max routes";
    }
    leaf paths-sent {
      type uint32;
      description
        "paths sent";
    }
    leaf paths-pending {
      type uint32;
      description
        "paths pending";
    }
    leaf paths-add {
      type uint32;
      description
        "paths add";
    }
    leaf paths-add-errs {
      type uint32;
      description
        "paths add errs";
    }
    leaf paths-del {
      type uint32;
      description
        "paths del";
    }
    leaf paths-del-errs {
      type uint32;
      description
        "paths del errs";
    }
    leaf lfas-pending {
      type uint32;
      description
        "lfas pending";
    }
    leaf lfas-add {
      type uint32;
      description
        "lfas add";
    }
    leaf lfas-del {
      type uint32;
      description
        "lfas del";
    }
    leaf lfas-sent {
      type uint32;
      description
        "lfas sent";
    }
    leaf priority-level {
      type string {
        length "0..40";
      }
      description
        "priority level";
    }
  }

  grouping ncs_rpc_notif_OSPF-SH-RIB-BATCH-PRIORITY-QUEUES {
    description
      "OSPF SH RIB BATCH PRIORITY QUEUES";
    list priority-batch {
      max-elements 8;
      description
        "priority batch";
      uses ncs_rpc_notif_OSPF-SH-RIB-BATCH;
    }
  }

  grouping ncs_rpc_notif_OSPF-EDM-AREA-SUMM {
    description
      "OSPF EDM AREA SUMM";
    leaf area-id {
      type uint32;
      description
        "area id";
    }
    leaf spf-count {
      type uint32;
      description
        "spf count";
    }
  }

  grouping ncs_rpc_notif_OSPF-HEADER-INFO {
    description
      "OSPF HEADER INFO";
    leaf router-id {
      type inet:ipv4-address;
      description
        "router id";
    }
    leaf spf-count {
      type uint32;
      description
        "spf count";
    }
    list area-summ {
      description
        "area summ";
      uses ncs_rpc_notif_OSPF-EDM-AREA-SUMM;
    }
  }

  grouping ncs_rpc_notif_OSPF-EDM-SPF-AREA-STATS {
    description
      "OSPF EDM SPF AREA STATS";
    container spf-time {
      description
        "spf time";
      uses ncs_rpc_notif_OSPF-SPF-TIME;
    }
    leaf area-id {
      type uint32;
      description
        "area id";
    }
    list lsa-type-cnt {
      max-elements 7;
      description
        "lsa type cnt";
      leaf entry {
        type uint32;
        description
          "lsa type cnt";
      }
    }
  }

  grouping ncs_rpc_notif_OSPF-LSA-CHANGE {
    description
      "OSPF LSA CHANGE";
    leaf area-id {
      type uint32;
      description
        "area id";
    }
    leaf adv-rtr {
      type inet:ipv4-address;
      description
        "adv rtr";
    }
    leaf id {
      type inet:ipv4-address;
      description
        "id";
    }
    leaf type {
      type uint8;
      description
        "type";
    }
    leaf flush {
      type boolean;
      description
        "flush";
    }
  }

  grouping ncs_rpc_notif_OSPF-SPF-TIME {
    description
      "OSPF SPF TIME";
    leaf spf-dijkstra {
      type uint32;
      description
        "spf dijkstra";
    }
    leaf spf-intra-prefix {
      type uint32;
      description
        "spf intra prefix";
    }
    leaf spf-intra-prefix-del {
      type uint32;
      description
        "spf intra prefix del";
    }
    leaf spf-inter-prefix {
      type uint32;
      description
        "spf inter prefix";
    }
    leaf spf-inter-prefix-del {
      type uint32;
      description
        "spf inter prefix del";
    }
    leaf spf-ext-prefix {
      type uint32;
      description
        "spf ext prefix";
    }
    leaf spf-ext-prefix-del {
      type uint32;
      description
        "spf ext prefix del";
    }
  }

  grouping ncs_rpc_notif_OSPF-RUNTIME-STATS {
    description
      "OSPF RUNTIME STATS";
    container gbl-spf-time {
      description
        "gbl spf time";
      uses ncs_rpc_notif_OSPF-SPF-TIME;
    }
    leaf spf-start-time {
      type uint32;
      description
        "spf start time";
    }
    leaf lsa-change-cnt {
      type int16;
      description
        "lsa change cnt";
    }
    list lsa-info {
      max-elements 5;
      description
        "lsa info";
      uses ncs_rpc_notif_OSPF-LSA-CHANGE;
    }
    list area-stat {
      description
        "area stat";
      uses ncs_rpc_notif_OSPF-EDM-SPF-AREA-STATS;
    }
  }

  grouping ncs_rpc_notif_OSPF-SH-STAT-PARTIAL {
    description
      "OSPF SH STAT PARTIAL";
    container sp-start-time {
      description
        "sp start time";
      uses ncs_rpc_notif_OSPF-SH-TIME;
    }
    container sp-duration {
      description
        "sp duration";
      uses ncs_rpc_notif_OSPF-SH-TIME;
    }
    leaf sp-adv-rtr-id {
      type uint32;
      description
        "sp adv rtr id";
    }
    leaf sp-dest-count {
      type uint32;
      description
        "sp dest count";
    }
    leaf sp-dest-addr {
      type uint32;
      description
        "sp dest addr";
    }
  }

  grouping ncs_rpc_notif_OSPF-SH-STAT-INTRA {
    description
      "OSPF SH STAT INTRA";
    container si-start-time {
      description
        "si start time";
      uses ncs_rpc_notif_OSPF-SH-TIME;
    }
    container si-duration {
      description
        "si duration";
      uses ncs_rpc_notif_OSPF-SH-TIME;
    }
    leaf si-area-id-str {
      type string;
      description
        "si area id str";
    }
    leaf si-change-flags {
      type uint16;
      description
        "si change flags";
    }
  }

  grouping ncs_rpc_notif_OSPF-SH-STATS-SPF {
    description
      "OSPF SH STATS SPF";
    container spf-header {
      description
        "spf header";
      uses ncs_rpc_notif_OSPF-HEADER-INFO;
    }
    list os-runtime {
      description
        "os runtime";
      uses ncs_rpc_notif_OSPF-SH-STAT-INTRA;
    }
    list os-sum-runtime {
      description
        "os sum runtime";
      uses ncs_rpc_notif_OSPF-SH-STAT-PARTIAL;
    }
    list os-ex-runtime {
      description
        "os ex runtime";
      uses ncs_rpc_notif_OSPF-SH-STAT-PARTIAL;
    }
    list runtime {
      description
        "runtime";
      uses ncs_rpc_notif_OSPF-RUNTIME-STATS;
    }
  }

  grouping live_ncs_OSPF-SH-IF-STATS-ENTRY {
    description
      "OSPF interface entry for statistics";
    leaf madj-intf {
      type boolean;
      description
        "OSPF madj interface";
    }
    leaf area-id {
      type uint32;
      description
        "OSPF area id";
    }
    leaf area-id-str {
      type string;
      description
        "OSPF aread id string";
    }
    list if-stat {
      description
        "OSPF interface statistics";
      leaf entry {
        type uint32;
        description
          "OSPF interface statistics";
      }
    }
  }

  grouping live_ncs_OSPF-SH-IF-STATS {
    description
      "OSPF interface statistics";
    leaf handle {
      type xr:Interface-name;
      description
        "interface handle type";
    }
    leaf if-name-str {
      type string;
      description
        "interface name";
    }
    list if-entry {
      description
        "interface entry";
      uses live_ncs_OSPF-SH-IF-STATS-ENTRY;
    }
  }

  grouping live_ncs_OSPF-SH-RAW-STATS {
    description
      "OSPF SH RAW STATS";
    leaf out-sent {
      type uint32;
      description
        "out sent";
    }
    leaf out-bytes-sent {
      type uint32;
      description
        "out bytes sent";
    }
    leaf out-no-conn-discarded {
      type uint32;
      description
        "out no conn discarded";
    }
    leaf out-null-src-discarded {
      type uint32;
      description
        "out null src discarded";
    }
    leaf out-no-pak-discarded {
      type uint32;
      description
        "out no pak discarded";
    }
    leaf out-ipv4-hdr-err-discarded {
      type uint32;
      description
        "out ipv4 hdr err discarded";
    }
    leaf out-send-pak-err-discarded {
      type uint32;
      description
        "out send pak err discarded";
    }
    leaf in-rcv {
      type uint32;
      description
        "in rcv";
    }
    leaf in-bytes-rcv {
      type uint32;
      description
        "in bytes rcv";
    }
    leaf in-short-msg-discarded {
      type uint32;
      description
        "in short msg discarded";
    }
    leaf in-no-mem-discarded {
      type uint32;
      description
        "in no mem discarded";
    }
    leaf in-raw-event {
      type uint32;
      description
        "in raw event";
    }
    leaf disconnects {
      type uint32;
      description
        "disconnects";
    }
    leaf in-standby-discarded {
      type uint32;
      description
        "in standby discarded";
    }
    leaf nsr-not-ready-discarded {
      type uint32;
      description
        "nsr not ready discarded";
    }
    leaf raw-connected {
      type boolean;
      description
        "raw connected";
    }
    leaf sl-raw-connected {
      type boolean;
      description
        "sl raw connected";
    }
  }

  grouping live_ncs_OSPF-SH-PROTOPKT-STATS {
    description
      "OSPF SH PROTOPKT STATS";
    leaf inputs {
      type uint32;
      description
        "inputs";
    }
    leaf input-hello {
      type uint32;
      description
        "input hello";
    }
    leaf input-dbdes {
      type uint32;
      description
        "input dbdes";
    }
    leaf input-dbdes-lsa {
      type uint32;
      description
        "input dbdes lsa";
    }
    leaf input-req {
      type uint32;
      description
        "input req";
    }
    leaf input-req-lsa {
      type uint32;
      description
        "input req lsa";
    }
    leaf input-lsupd {
      type uint32;
      description
        "input lsupd";
    }
    leaf input-lsupd-lsa {
      type uint32;
      description
        "input lsupd lsa";
    }
    leaf input-ack {
      type uint32;
      description
        "input ack";
    }
    leaf input-ack-lsa {
      type uint32;
      description
        "input ack lsa";
    }
    leaf checksumerr {
      type uint32;
      description
        "checksumerr";
    }
    leaf input-autherr {
      type uint32;
      description
        "input autherr";
    }
    leaf outputs {
      type uint32;
      description
        "outputs";
    }
    leaf output-hello {
      type uint32;
      description
        "output hello";
    }
    leaf output-dbdes {
      type uint32;
      description
        "output dbdes";
    }
    leaf output-dbdes-lsa {
      type uint32;
      description
        "output dbdes lsa";
    }
    leaf output-req {
      type uint32;
      description
        "output req";
    }
    leaf output-req-lsa {
      type uint32;
      description
        "output req lsa";
    }
    leaf output-lsupd {
      type uint32;
      description
        "output lsupd";
    }
    leaf output-lsupd-lsa {
      type uint32;
      description
        "output lsupd lsa";
    }
    leaf output-ack {
      type uint32;
      description
        "output ack";
    }
    leaf output-ack-lsa {
      type uint32;
      description
        "output ack lsa";
    }
    leaf output-autherr {
      type uint32;
      description
        "output autherr";
    }
    leaf h-input-dbdes {
      type uint32;
      description
        "h input dbdes";
    }
    leaf h-input-req {
      type uint32;
      description
        "h input req";
    }
    leaf h-input-lsupd {
      type uint32;
      description
        "h input lsupd";
    }
    leaf h-input-ack {
      type uint32;
      description
        "h input ack";
    }
  }

  grouping live_ncs_OSPF-SH-TE-STATS {
    description
      "OSPF SH TE STATS";
    leaf te-connected {
      type boolean;
      description
        "te connected";
    }
    leaf control-disconnects {
      type uint32;
      description
        "control disconnects";
    }
    leaf te-disconnects {
      type uint32;
      description
        "te disconnects";
    }
    leaf adj-gets {
      type uint32;
      description
        "adj gets";
    }
    leaf link-floods {
      type uint32;
      description
        "link floods";
    }
    leaf link-fragment-floods {
      type uint32;
      description
        "link fragment floods";
    }
    leaf lsp-gets {
      type uint32;
      description
        "lsp gets";
    }
    leaf tunnel-announces {
      type uint32;
      description
        "tunnel announces";
    }
    leaf total-tunnels {
      type uint32;
      description
        "total tunnels";
    }
    leaf control-batch-reads {
      type uint32;
      description
        "control batch reads";
    }
    leaf control-batch-writes {
      type uint32;
      description
        "control batch writes";
    }
    leaf link-batch-reads {
      type uint32;
      description
        "link batch reads";
    }
    leaf link-batch-writes {
      type uint32;
      description
        "link batch writes";
    }
    leaf adj-changes {
      type uint32;
      description
        "adj changes";
    }
    leaf fragment-deletes {
      type uint32;
      description
        "fragment deletes";
    }
    leaf fragment-announces {
      type uint32;
      description
        "fragment announces";
    }
    leaf data-trans-completes {
      type uint32;
      description
        "data trans completes";
    }
    leaf pce-listen {
      type uint32;
      description
        "pce listen";
    }
    leaf pce-stoplisten {
      type uint32;
      description
        "pce stoplisten";
    }
    leaf pce-flood {
      type uint32;
      description
        "pce flood";
    }
    leaf pce-get {
      type uint32;
      description
        "pce get";
    }
    leaf pce-br-lookup {
      type uint32;
      description
        "pce br lookup";
    }
    leaf pce-br-lkup-num-dests {
      type uint32;
      description
        "pce br lkup num dests";
    }
    leaf pce-br-resp-fails {
      type uint32;
      description
        "pce br resp fails";
    }
    leaf pce-node-announce-batches {
      type uint32;
      description
        "pce node announce batches";
    }
    leaf pce-node-delete-batches {
      type uint32;
      description
        "pce node delete batches";
    }
    leaf pce-num-node-announce {
      type uint32;
      description
        "pce num node announce";
    }
    leaf pce-num-node-delete {
      type uint32;
      description
        "pce num node delete";
    }
    leaf pce-node-send-fails {
      type uint32;
      description
        "pce node send fails";
    }
    leaf te-sr-path-reg-idt-recvd {
      type boolean;
      description
        "te sr path reg idt recvd";
    }
    leaf te-sr-idt-sent {
      type boolean;
      description
        "te sr idt sent";
    }
    leaf sr-num-area-enabled {
      type uint32;
      description
        "sr num area enabled";
    }
  }

  grouping live_ncs_OSPF-SH-IPFRR-STATS {
    description
      "OSPF SH IPFRR STATS";
    leaf fs-paths {
      type uint32;
      description
        "Number of IPFRR paths";
    }
    leaf fs-paths-eligible {
      type uint32;
      description
        "Number of paths enabled for protection";
    }
    leaf fs-paths-protected {
      type uint32;
      description
        "Number of paths protected";
    }
  }

  grouping live_ncs_NSR-PL-RECV-DROP-ARRAY {
    description
      "NSR PL RECV DROP ARRAY";
    list nsr-pl-recv-drop-array {
      // NCS drop max-elements statement
      description
        "nsr pl recv drop array";
      leaf entry {
        type uint32;
        description
          "nsr pl recv drop array";
      }
    }
  }

  grouping live_ncs_NSR-PL-SEND-DROP-ARRAY {
    description
      "NSR PL SEND DROP ARRAY";
    list nsr-pl-send-drop-array {
      // NCS drop max-elements statement
      description
        "nsr pl send drop array";
      leaf entry {
        type uint32;
        description
          "nsr pl send drop array";
      }
    }
  }

  grouping live_ncs_NSR-PL-CLIENT-STATS-TYPE {
    description
      "NSR PL stats information";
    list num-sent {
      // NCS drop max-elements statement
      description
        "Total sent";
      leaf entry {
        type uint64;
        description
          "Total sent";
      }
    }
    list num-recv {
      // NCS drop max-elements statement
      description
        "Total recvd";
      leaf entry {
        type uint64;
        description
          "Total recvd";
      }
    }
    list num-sent-drop {
      // NCS drop max-elements statement
      description
        "Sent Error/drops";
      uses live_ncs_NSR-PL-SEND-DROP-ARRAY;
    }
    list num-recv-drop {
      // NCS drop max-elements statement
      description
        "Recv Errors/drops";
      uses live_ncs_NSR-PL-RECV-DROP-ARRAY;
    }
  }

  grouping live_ncs_OSPF-SH-NCD-STATS {
    description
      "OSPF SH NCD STATS";
    list ncd-pri {
      // NCS drop max-elements statement
      description
        "ncd pri";
      uses live_ncs_NSR-PL-CLIENT-STATS-TYPE;
    }
  }

  grouping live_ncs_OSPF-SH-STATS-RIB-THREAD {
    description
      "OSPF SH STATS RIB THREAD";
    container rib-base-time {
      description
        "rib base time";
      uses live_ncs_BAG-TIMESPEC;
    }
    leaf wq-thread-active {
      type boolean;
      description
        "wq thread active";
    }
    leaf wq-dqtime {
      type uint64;
      description
        "wq dqtime";
    }
    leaf wqe-qtime {
      type uint64;
      description
        "wqe qtime";
    }
    leaf wq-len-cur {
      type int32;
      description
        "wq len cur";
    }
    leaf wq-len-max {
      type int32;
      description
        "wq len max";
    }
    leaf wq-total-queued {
      type uint32;
      description
        "wq total queued";
    }
    leaf wq-total-dequeued {
      type uint32;
      description
        "wq total dequeued";
    }
    leaf rib-version {
      type uint32;
      description
        "rib version";
    }
    leaf rib-pkts-sent {
      type uint32;
      description
        "rib pkts sent";
    }
    leaf rib-signals {
      type uint32;
      description
        "rib signals";
    }
    leaf rib-send-errs {
      type uint32;
      description
        "rib send errs";
    }
    leaf rib-queue-errs {
      type uint32;
      description
        "rib queue errs";
    }
    leaf rib-pfx-limit-errs {
      type uint32;
      description
        "rib pfx limit errs";
    }
    leaf rib-dequeue-errs {
      type uint32;
      description
        "rib dequeue errs";
    }
    leaf rib-empty-batches {
      type uint32;
      description
        "rib empty batches";
    }
    leaf rib-drop-before {
      type uint32;
      description
        "rib drop before";
    }
    leaf rib-drop-after {
      type uint32;
      description
        "rib drop after";
    }
    leaf rib-drop-conn {
      type uint32;
      description
        "rib drop conn";
    }
    leaf rib-table-not-created {
      type uint32;
      description
        "rib table not created";
    }
    leaf priority-level {
      type string {
        length "0..40";
      }
      description
        "priority level";
    }
    leaf rib-base-clock {
      type uint64;
      description
        "rib base clock";
    }
  }

  grouping live_ncs_OSPF-SH-STATS-WORK-QUEUES {
    description
      "OSPF SH STATS WORK QUEUES";
    container internalwq {
      description
        "internalwq";
      uses live_ncs_OSPF-SH-STATS-RIB-THREAD;
    }
    list ribqueue {
      // NCS drop max-elements statement
      description
        "ribqueue";
      uses live_ncs_OSPF-SH-STATS-RIB-THREAD;
    }
  }

  grouping live_ncs_BAG-TIMESPEC {
    description
      "BAG TIMESPEC";
    leaf second {
      type uint32;
      description
        "Second";
    }
    leaf nanosecond {
      type uint32;
      description
        "Nanosecond";
    }
  }

  grouping live_ncs_OSPF-NSR-ERR-INFO-BAG {
    description
      "OSPF NSR ERR INFO BAG";
    container last-err-time {
      description
        "Time this error was last hit";
      uses live_ncs_BAG-TIMESPEC;
    }
    leaf err-count {
      type int32;
      description
        "Count this error hit during the Nsr Revision";
    }
    leaf err-info-string {
      type string;
      description
        "Error Information";
    }
  }

  grouping live_ncs_OSPF-NSR-ERR-BLOCK-BAG {
    description
      "OSPF NSR ERR BLOCK BAG";
    leaf nsr-revisionversion {
      type uint32;
      description
        "Nsr Revision version";
    }
    leaf total-errors {
      type int32;
      description
        "Total errors for this nsr revision version";
    }
    list nsr-error-info {
      description
        "List of erros";
      uses live_ncs_OSPF-NSR-ERR-INFO-BAG;
    }
  }

  grouping live_ncs_OSPF-ISSU-MILESTONE-BAG {
    description
      "OSPF ISSU MILESTONE BAG";
    leaf milestone-name {
      type string;
      description
        "Milestone Name";
    }
    leaf milestone-status {
      type string;
      description
        "Milestone Status";
    }
  }

  grouping live_ncs_OSPF-SH-NSR-STATS-PRI {
    description
      "OSPF SH NSR STATS PRI";
    leaf nsr-sched-pri {
      type uint32;
      description
        "nsr sched pri";
    }
    leaf nsr-sched-quant {
      type uint8;
      description
        "nsr sched quant";
    }
    leaf nsr-sched-remain-quant {
      type uint8;
      description
        "nsr sched remain quant";
    }
    leaf nsr-sched-evs-in-q {
      type uint16;
      description
        "nsr sched evs in q";
    }
    leaf nsr-sched-max-evs {
      type uint16;
      description
        "nsr sched max evs";
    }
    leaf nsr-sched-peak-q-len {
      type uint16;
      description
        "nsr sched peak q len";
    }
    leaf nsr-sched-evs-qd {
      type uint64;
      description
        "nsr sched evs qd";
    }
    leaf nsr-sched-enq-fails {
      type uint64;
      description
        "nsr sched enq fails";
    }
    leaf nsr-sched-evs-deqd {
      type uint64;
      description
        "nsr sched evs deqd";
    }
  }

  grouping live_ncs_OSPF-SH-NSR-SCHED-STATS {
    description
      "OSPF SH NSR SCHED STATS";
    leaf nsr-pulse-quant {
      type int32;
      description
        "nsr pulse quant";
    }
    leaf nsr-events-in-q {
      type uint32;
      description
        "nsr events in q";
    }
    leaf nsr-events-tx {
      type uint64;
      description
        "nsr events tx";
    }
    leaf nsr-events-rx {
      type uint64;
      description
        "nsr events rx";
    }
    leaf nsr-bad-pulses-rx {
      type uint64;
      description
        "nsr bad pulses rx";
    }
    leaf nsr-good-pulses-rx {
      type uint64;
      description
        "nsr good pulses rx";
    }
    leaf nsr-pulses-tx {
      type uint64;
      description
        "nsr pulses tx";
    }
    leaf nsr-pulse-tx-fails {
      type uint64;
      description
        "nsr pulse tx fails";
    }
    list nsr-pri {
      // NCS drop max-elements statement
      description
        "nsr pri";
      uses live_ncs_OSPF-SH-NSR-STATS-PRI;
    }
  }

  grouping live_ncs_OSPF-SH-NSR-STATS {
    description
      "OSPF SH NSR STATS";
    container nsr-thd-sched {
      description
        "nsr thd sched";
      uses live_ncs_OSPF-SH-NSR-SCHED-STATS;
    }
    container nsr-rtr-thd-sched {
      description
        "nsr rtr thd sched";
      uses live_ncs_OSPF-SH-NSR-SCHED-STATS;
    }
    leaf nsr-rev {
      type int32;
      description
        "nsr rev";
    }
    leaf nsr-fsm-state {
      type int32;
      description
        "nsr fsm state";
    }
    leaf nsr-version {
      type uint32;
      description
        "nsr version";
    }
    leaf nsr-nodeid {
      type uint32;
      description
        "nsr nodeid";
    }
    leaf nsr-peer-version {
      type uint32;
      description
        "nsr peer version";
    }
    leaf nsr-peer-nodeid {
      type uint32;
      description
        "nsr peer nodeid";
    }
    leaf nsr-peer-ep-len {
      type uint32;
      description
        "nsr peer ep len";
    }
    leaf nsr-peer-ep-version {
      type uint32;
      description
        "nsr peer ep version";
    }
    leaf nsr-local-ep-len {
      type uint32;
      description
        "nsr local ep len";
    }
    leaf nsr-local-ep-version {
      type uint32;
      description
        "nsr local ep version";
    }
    leaf nsr-fabric-mtu {
      type uint32;
      description
        "nsr fabric mtu";
    }
    leaf nsr-nbr-qad-qid {
      type uint32;
      description
        "nsr nbr qad qid";
    }
    leaf nsr-lsa-qad-qid {
      type uint32;
      description
        "nsr lsa qad qid";
    }
    leaf nsr-nbr-qad-mdata-count {
      type uint32;
      description
        "nsr nbr qad mdata count";
    }
    leaf nsr-lsa-qad-mdata-count {
      type uint32;
      description
        "nsr lsa qad mdata count";
    }
    leaf nsr-nbr-init-sync-pend-count {
      type int32;
      description
        "nsr nbr init sync pend count";
    }
    leaf nsr-lsa-init-sync-pend-count {
      type int32;
      description
        "nsr lsa init sync pend count";
    }
    leaf nsr-nbr-seq-no {
      type uint32;
      description
        "nsr nbr seq no";
    }
    leaf nsr-intf-seq-no {
      type uint32;
      description
        "nsr intf seq no";
    }
    leaf nsr-tmr-quant {
      type int32;
      description
        "nsr tmr quant";
    }
    leaf nsr-peer-ds-hdl {
      type uint64;
      description
        "nsr peer ds hdl";
    }
    leaf nsr-local-ds-hdl {
      type uint64;
      description
        "nsr local ds hdl";
    }
    leaf nsr-conn-to-active-attempts {
      type uint64;
      description
        "nsr conn to active attempts";
    }
    leaf nsr-conn-to-active-fails {
      type uint64;
      description
        "nsr conn to active fails";
    }
    leaf nsr-conn-to-active-opens {
      type uint64;
      description
        "nsr conn to active opens";
    }
    leaf nsr-conn-to-active-closes {
      type uint64;
      description
        "nsr conn to active closes";
    }
    leaf nsr-conn-to-active-errors {
      type uint64;
      description
        "nsr conn to active errors";
    }
    leaf nsr-peer-ep {
      type yang:hex-string;
      description
        "nsr peer ep";
    }
    leaf nsr-local-ep {
      type yang:hex-string;
      description
        "nsr local ep";
    }
    list nsr-fsm-flag {
      description
        "Nsr Fsm Flags information";
      leaf entry {
        type Ospf-string-array;
        description
          "Nsr Fsm Flags information";
      }
    }
    list nsr-fsm-running-timer {
      description
        "Nsr Fsm Running Timers";
      leaf entry {
        type Ospf-string-array;
        description
          "Nsr Fsm Running Timers";
      }
    }
    list nsr-issu-milestone {
      description
        "Nsr Issu Milestones";
      uses live_ncs_OSPF-ISSU-MILESTONE-BAG;
    }
    list nsr-err-history {
      description
        "Nsr Error History List";
      uses live_ncs_OSPF-NSR-ERR-BLOCK-BAG;
    }
  }

  grouping live_ncs_OSPF-SH-RIB-BATCH {
    description
      "OSPF SH RIB BATCH";
    leaf batches-sent {
      type uint32;
      description
        "batches sent";
    }
    leaf routes-sent {
      type uint32;
      description
        "routes sent";
    }
    leaf routes-pending {
      type uint32;
      description
        "routes pending";
    }
    leaf max-routes {
      type uint32;
      description
        "max routes";
    }
    leaf paths-sent {
      type uint32;
      description
        "paths sent";
    }
    leaf paths-pending {
      type uint32;
      description
        "paths pending";
    }
    leaf paths-add {
      type uint32;
      description
        "paths add";
    }
    leaf paths-add-errs {
      type uint32;
      description
        "paths add errs";
    }
    leaf paths-del {
      type uint32;
      description
        "paths del";
    }
    leaf paths-del-errs {
      type uint32;
      description
        "paths del errs";
    }
    leaf lfas-pending {
      type uint32;
      description
        "lfas pending";
    }
    leaf lfas-add {
      type uint32;
      description
        "lfas add";
    }
    leaf lfas-del {
      type uint32;
      description
        "lfas del";
    }
    leaf lfas-sent {
      type uint32;
      description
        "lfas sent";
    }
    leaf priority-level {
      type string {
        length "0..40";
      }
      description
        "priority level";
    }
  }

  grouping live_ncs_OSPF-SH-RIB-BATCH-PRIORITY-QUEUES {
    description
      "OSPF SH RIB BATCH PRIORITY QUEUES";
    list priority-batch {
      // NCS drop max-elements statement
      description
        "priority batch";
      uses live_ncs_OSPF-SH-RIB-BATCH;
    }
  }

  grouping live_ncs_OSPF-EDM-AREA-SUMM {
    description
      "OSPF EDM AREA SUMM";
    leaf area-id {
      type uint32;
      description
        "area id";
    }
    leaf spf-count {
      type uint32;
      description
        "spf count";
    }
  }

  grouping live_ncs_OSPF-HEADER-INFO {
    description
      "OSPF HEADER INFO";
    leaf router-id {
      type inet:ipv4-address;
      description
        "router id";
    }
    leaf spf-count {
      type uint32;
      description
        "spf count";
    }
    list area-summ {
      description
        "area summ";
      uses live_ncs_OSPF-EDM-AREA-SUMM;
    }
  }

  grouping live_ncs_OSPF-EDM-SPF-AREA-STATS {
    description
      "OSPF EDM SPF AREA STATS";
    container spf-time {
      description
        "spf time";
      uses live_ncs_OSPF-SPF-TIME;
    }
    leaf area-id {
      type uint32;
      description
        "area id";
    }
    list lsa-type-cnt {
      // NCS drop max-elements statement
      description
        "lsa type cnt";
      leaf entry {
        type uint32;
        description
          "lsa type cnt";
      }
    }
  }

  grouping live_ncs_OSPF-LSA-CHANGE {
    description
      "OSPF LSA CHANGE";
    leaf area-id {
      type uint32;
      description
        "area id";
    }
    leaf adv-rtr {
      type inet:ipv4-address;
      description
        "adv rtr";
    }
    leaf id {
      type inet:ipv4-address;
      description
        "id";
    }
    leaf type {
      type uint8;
      description
        "type";
    }
    leaf flush {
      type boolean;
      description
        "flush";
    }
  }

  grouping live_ncs_OSPF-SPF-TIME {
    description
      "OSPF SPF TIME";
    leaf spf-dijkstra {
      type uint32;
      description
        "spf dijkstra";
    }
    leaf spf-intra-prefix {
      type uint32;
      description
        "spf intra prefix";
    }
    leaf spf-intra-prefix-del {
      type uint32;
      description
        "spf intra prefix del";
    }
    leaf spf-inter-prefix {
      type uint32;
      description
        "spf inter prefix";
    }
    leaf spf-inter-prefix-del {
      type uint32;
      description
        "spf inter prefix del";
    }
    leaf spf-ext-prefix {
      type uint32;
      description
        "spf ext prefix";
    }
    leaf spf-ext-prefix-del {
      type uint32;
      description
        "spf ext prefix del";
    }
  }

  grouping live_ncs_OSPF-RUNTIME-STATS {
    description
      "OSPF RUNTIME STATS";
    container gbl-spf-time {
      description
        "gbl spf time";
      uses live_ncs_OSPF-SPF-TIME;
    }
    leaf spf-start-time {
      type uint32;
      description
        "spf start time";
    }
    leaf lsa-change-cnt {
      type int16;
      description
        "lsa change cnt";
    }
    list lsa-info {
      // NCS drop max-elements statement
      description
        "lsa info";
      uses live_ncs_OSPF-LSA-CHANGE;
    }
    list area-stat {
      description
        "area stat";
      uses live_ncs_OSPF-EDM-SPF-AREA-STATS;
    }
  }

  grouping live_ncs_OSPF-SH-STAT-PARTIAL {
    description
      "OSPF SH STAT PARTIAL";
    container sp-start-time {
      description
        "sp start time";
      uses live_ncs_OSPF-SH-TIME;
    }
    container sp-duration {
      description
        "sp duration";
      uses live_ncs_OSPF-SH-TIME;
    }
    leaf sp-adv-rtr-id {
      type uint32;
      description
        "sp adv rtr id";
    }
    leaf sp-dest-count {
      type uint32;
      description
        "sp dest count";
    }
    leaf sp-dest-addr {
      type uint32;
      description
        "sp dest addr";
    }
  }

  grouping live_ncs_OSPF-SH-STAT-INTRA {
    description
      "OSPF SH STAT INTRA";
    container si-start-time {
      description
        "si start time";
      uses live_ncs_OSPF-SH-TIME;
    }
    container si-duration {
      description
        "si duration";
      uses live_ncs_OSPF-SH-TIME;
    }
    leaf si-area-id-str {
      type string;
      description
        "si area id str";
    }
    leaf si-change-flags {
      type uint16;
      description
        "si change flags";
    }
  }

  grouping live_ncs_OSPF-SH-STATS-SPF {
    description
      "OSPF SH STATS SPF";
    container spf-header {
      description
        "spf header";
      uses live_ncs_OSPF-HEADER-INFO;
    }
    list os-runtime {
      description
        "os runtime";
      uses live_ncs_OSPF-SH-STAT-INTRA;
    }
    list os-sum-runtime {
      description
        "os sum runtime";
      uses live_ncs_OSPF-SH-STAT-PARTIAL;
    }
    list os-ex-runtime {
      description
        "os ex runtime";
      uses live_ncs_OSPF-SH-STAT-PARTIAL;
    }
    list runtime {
      description
        "runtime";
      uses live_ncs_OSPF-RUNTIME-STATS;
    }
  }

  grouping OSPF-SH-IF-STATS-ENTRY {
    description
      "OSPF interface entry for statistics";
    leaf madj-intf {
      type boolean;
      description
        "OSPF madj interface";
    }
    leaf area-id {
      type uint32;
      description
        "OSPF area id";
    }
    leaf area-id-str {
      type string;
      description
        "OSPF aread id string";
    }
    list if-stat {
      description
        "OSPF interface statistics";
      leaf entry {
        type uint32;
        description
          "OSPF interface statistics";
      }
    }
  }

  grouping OSPF-SH-IF-STATS {
    description
      "OSPF interface statistics";
    leaf handle {
      type xr:Interface-name;
      description
        "interface handle type";
    }
    leaf if-name-str {
      type string;
      description
        "interface name";
    }
    list if-entry {
      description
        "interface entry";
      uses OSPF-SH-IF-STATS-ENTRY;
    }
  }

  grouping OSPF-SH-RAW-STATS {
    description
      "OSPF SH RAW STATS";
    leaf out-sent {
      type uint32;
      description
        "out sent";
    }
    leaf out-bytes-sent {
      type uint32;
      description
        "out bytes sent";
    }
    leaf out-no-conn-discarded {
      type uint32;
      description
        "out no conn discarded";
    }
    leaf out-null-src-discarded {
      type uint32;
      description
        "out null src discarded";
    }
    leaf out-no-pak-discarded {
      type uint32;
      description
        "out no pak discarded";
    }
    leaf out-ipv4-hdr-err-discarded {
      type uint32;
      description
        "out ipv4 hdr err discarded";
    }
    leaf out-send-pak-err-discarded {
      type uint32;
      description
        "out send pak err discarded";
    }
    leaf in-rcv {
      type uint32;
      description
        "in rcv";
    }
    leaf in-bytes-rcv {
      type uint32;
      description
        "in bytes rcv";
    }
    leaf in-short-msg-discarded {
      type uint32;
      description
        "in short msg discarded";
    }
    leaf in-no-mem-discarded {
      type uint32;
      description
        "in no mem discarded";
    }
    leaf in-raw-event {
      type uint32;
      description
        "in raw event";
    }
    leaf disconnects {
      type uint32;
      description
        "disconnects";
    }
    leaf in-standby-discarded {
      type uint32;
      description
        "in standby discarded";
    }
    leaf nsr-not-ready-discarded {
      type uint32;
      description
        "nsr not ready discarded";
    }
    leaf raw-connected {
      type boolean;
      description
        "raw connected";
    }
    leaf sl-raw-connected {
      type boolean;
      description
        "sl raw connected";
    }
  }

  grouping OSPF-SH-PROTOPKT-STATS {
    description
      "OSPF SH PROTOPKT STATS";
    leaf inputs {
      type uint32;
      description
        "inputs";
    }
    leaf input-hello {
      type uint32;
      description
        "input hello";
    }
    leaf input-dbdes {
      type uint32;
      description
        "input dbdes";
    }
    leaf input-dbdes-lsa {
      type uint32;
      description
        "input dbdes lsa";
    }
    leaf input-req {
      type uint32;
      description
        "input req";
    }
    leaf input-req-lsa {
      type uint32;
      description
        "input req lsa";
    }
    leaf input-lsupd {
      type uint32;
      description
        "input lsupd";
    }
    leaf input-lsupd-lsa {
      type uint32;
      description
        "input lsupd lsa";
    }
    leaf input-ack {
      type uint32;
      description
        "input ack";
    }
    leaf input-ack-lsa {
      type uint32;
      description
        "input ack lsa";
    }
    leaf checksumerr {
      type uint32;
      description
        "checksumerr";
    }
    leaf input-autherr {
      type uint32;
      description
        "input autherr";
    }
    leaf outputs {
      type uint32;
      description
        "outputs";
    }
    leaf output-hello {
      type uint32;
      description
        "output hello";
    }
    leaf output-dbdes {
      type uint32;
      description
        "output dbdes";
    }
    leaf output-dbdes-lsa {
      type uint32;
      description
        "output dbdes lsa";
    }
    leaf output-req {
      type uint32;
      description
        "output req";
    }
    leaf output-req-lsa {
      type uint32;
      description
        "output req lsa";
    }
    leaf output-lsupd {
      type uint32;
      description
        "output lsupd";
    }
    leaf output-lsupd-lsa {
      type uint32;
      description
        "output lsupd lsa";
    }
    leaf output-ack {
      type uint32;
      description
        "output ack";
    }
    leaf output-ack-lsa {
      type uint32;
      description
        "output ack lsa";
    }
    leaf output-autherr {
      type uint32;
      description
        "output autherr";
    }
    leaf h-input-dbdes {
      type uint32;
      description
        "h input dbdes";
    }
    leaf h-input-req {
      type uint32;
      description
        "h input req";
    }
    leaf h-input-lsupd {
      type uint32;
      description
        "h input lsupd";
    }
    leaf h-input-ack {
      type uint32;
      description
        "h input ack";
    }
  }

  grouping OSPF-SH-TE-STATS {
    description
      "OSPF SH TE STATS";
    leaf te-connected {
      type boolean;
      description
        "te connected";
    }
    leaf control-disconnects {
      type uint32;
      description
        "control disconnects";
    }
    leaf te-disconnects {
      type uint32;
      description
        "te disconnects";
    }
    leaf adj-gets {
      type uint32;
      description
        "adj gets";
    }
    leaf link-floods {
      type uint32;
      description
        "link floods";
    }
    leaf link-fragment-floods {
      type uint32;
      description
        "link fragment floods";
    }
    leaf lsp-gets {
      type uint32;
      description
        "lsp gets";
    }
    leaf tunnel-announces {
      type uint32;
      description
        "tunnel announces";
    }
    leaf total-tunnels {
      type uint32;
      description
        "total tunnels";
    }
    leaf control-batch-reads {
      type uint32;
      description
        "control batch reads";
    }
    leaf control-batch-writes {
      type uint32;
      description
        "control batch writes";
    }
    leaf link-batch-reads {
      type uint32;
      description
        "link batch reads";
    }
    leaf link-batch-writes {
      type uint32;
      description
        "link batch writes";
    }
    leaf adj-changes {
      type uint32;
      description
        "adj changes";
    }
    leaf fragment-deletes {
      type uint32;
      description
        "fragment deletes";
    }
    leaf fragment-announces {
      type uint32;
      description
        "fragment announces";
    }
    leaf data-trans-completes {
      type uint32;
      description
        "data trans completes";
    }
    leaf pce-listen {
      type uint32;
      description
        "pce listen";
    }
    leaf pce-stoplisten {
      type uint32;
      description
        "pce stoplisten";
    }
    leaf pce-flood {
      type uint32;
      description
        "pce flood";
    }
    leaf pce-get {
      type uint32;
      description
        "pce get";
    }
    leaf pce-br-lookup {
      type uint32;
      description
        "pce br lookup";
    }
    leaf pce-br-lkup-num-dests {
      type uint32;
      description
        "pce br lkup num dests";
    }
    leaf pce-br-resp-fails {
      type uint32;
      description
        "pce br resp fails";
    }
    leaf pce-node-announce-batches {
      type uint32;
      description
        "pce node announce batches";
    }
    leaf pce-node-delete-batches {
      type uint32;
      description
        "pce node delete batches";
    }
    leaf pce-num-node-announce {
      type uint32;
      description
        "pce num node announce";
    }
    leaf pce-num-node-delete {
      type uint32;
      description
        "pce num node delete";
    }
    leaf pce-node-send-fails {
      type uint32;
      description
        "pce node send fails";
    }
    leaf te-sr-path-reg-idt-recvd {
      type boolean;
      description
        "te sr path reg idt recvd";
    }
    leaf te-sr-idt-sent {
      type boolean;
      description
        "te sr idt sent";
    }
    leaf sr-num-area-enabled {
      type uint32;
      description
        "sr num area enabled";
    }
  }

  grouping OSPF-SH-IPFRR-STATS {
    description
      "OSPF SH IPFRR STATS";
    leaf fs-paths {
      type uint32;
      description
        "Number of IPFRR paths";
    }
    leaf fs-paths-eligible {
      type uint32;
      description
        "Number of paths enabled for protection";
    }
    leaf fs-paths-protected {
      type uint32;
      description
        "Number of paths protected";
    }
  }

  grouping NSR-PL-RECV-DROP-ARRAY {
    description
      "NSR PL RECV DROP ARRAY";
    list nsr-pl-recv-drop-array {
      max-elements 16;
      description
        "nsr pl recv drop array";
      leaf entry {
        type uint32;
        description
          "nsr pl recv drop array";
      }
    }
  }

  grouping NSR-PL-SEND-DROP-ARRAY {
    description
      "NSR PL SEND DROP ARRAY";
    list nsr-pl-send-drop-array {
      max-elements 7;
      description
        "nsr pl send drop array";
      leaf entry {
        type uint32;
        description
          "nsr pl send drop array";
      }
    }
  }

  grouping NSR-PL-CLIENT-STATS-TYPE {
    description
      "NSR PL stats information";
    list num-sent {
      max-elements 5;
      description
        "Total sent";
      leaf entry {
        type uint64;
        description
          "Total sent";
      }
    }
    list num-recv {
      max-elements 6;
      description
        "Total recvd";
      leaf entry {
        type uint64;
        description
          "Total recvd";
      }
    }
    list num-sent-drop {
      max-elements 5;
      description
        "Sent Error/drops";
      uses NSR-PL-SEND-DROP-ARRAY;
    }
    list num-recv-drop {
      max-elements 6;
      description
        "Recv Errors/drops";
      uses NSR-PL-RECV-DROP-ARRAY;
    }
  }

  grouping OSPF-SH-NCD-STATS {
    description
      "OSPF SH NCD STATS";
    list ncd-pri {
      max-elements 2;
      description
        "ncd pri";
      uses NSR-PL-CLIENT-STATS-TYPE;
    }
  }

  grouping OSPF-SH-STATS-RIB-THREAD {
    description
      "OSPF SH STATS RIB THREAD";
    container rib-base-time {
      description
        "rib base time";
      uses BAG-TIMESPEC;
    }
    leaf wq-thread-active {
      type boolean;
      description
        "wq thread active";
    }
    leaf wq-dqtime {
      type uint64;
      description
        "wq dqtime";
    }
    leaf wqe-qtime {
      type uint64;
      description
        "wqe qtime";
    }
    leaf wq-len-cur {
      type int32;
      description
        "wq len cur";
    }
    leaf wq-len-max {
      type int32;
      description
        "wq len max";
    }
    leaf wq-total-queued {
      type uint32;
      description
        "wq total queued";
    }
    leaf wq-total-dequeued {
      type uint32;
      description
        "wq total dequeued";
    }
    leaf rib-version {
      type uint32;
      description
        "rib version";
    }
    leaf rib-pkts-sent {
      type uint32;
      description
        "rib pkts sent";
    }
    leaf rib-signals {
      type uint32;
      description
        "rib signals";
    }
    leaf rib-send-errs {
      type uint32;
      description
        "rib send errs";
    }
    leaf rib-queue-errs {
      type uint32;
      description
        "rib queue errs";
    }
    leaf rib-pfx-limit-errs {
      type uint32;
      description
        "rib pfx limit errs";
    }
    leaf rib-dequeue-errs {
      type uint32;
      description
        "rib dequeue errs";
    }
    leaf rib-empty-batches {
      type uint32;
      description
        "rib empty batches";
    }
    leaf rib-drop-before {
      type uint32;
      description
        "rib drop before";
    }
    leaf rib-drop-after {
      type uint32;
      description
        "rib drop after";
    }
    leaf rib-drop-conn {
      type uint32;
      description
        "rib drop conn";
    }
    leaf rib-table-not-created {
      type uint32;
      description
        "rib table not created";
    }
    leaf priority-level {
      type string {
        length "0..40";
      }
      description
        "priority level";
    }
    leaf rib-base-clock {
      type uint64;
      description
        "rib base clock";
    }
  }

  grouping OSPF-SH-STATS-WORK-QUEUES {
    description
      "OSPF SH STATS WORK QUEUES";
    container internalwq {
      description
        "internalwq";
      uses OSPF-SH-STATS-RIB-THREAD;
    }
    list ribqueue {
      max-elements 8;
      description
        "ribqueue";
      uses OSPF-SH-STATS-RIB-THREAD;
    }
  }

  grouping BAG-TIMESPEC {
    description
      "BAG TIMESPEC";
    leaf second {
      type uint32;
      description
        "Second";
    }
    leaf nanosecond {
      type uint32;
      description
        "Nanosecond";
    }
  }

  grouping OSPF-NSR-ERR-INFO-BAG {
    description
      "OSPF NSR ERR INFO BAG";
    container last-err-time {
      description
        "Time this error was last hit";
      uses BAG-TIMESPEC;
    }
    leaf err-count {
      type int32;
      description
        "Count this error hit during the Nsr Revision";
    }
    leaf err-info-string {
      type string;
      description
        "Error Information";
    }
  }

  grouping OSPF-NSR-ERR-BLOCK-BAG {
    description
      "OSPF NSR ERR BLOCK BAG";
    leaf nsr-revisionversion {
      type uint32;
      description
        "Nsr Revision version";
    }
    leaf total-errors {
      type int32;
      description
        "Total errors for this nsr revision version";
    }
    list nsr-error-info {
      description
        "List of erros";
      uses OSPF-NSR-ERR-INFO-BAG;
    }
  }

  grouping OSPF-ISSU-MILESTONE-BAG {
    description
      "OSPF ISSU MILESTONE BAG";
    leaf milestone-name {
      type string;
      description
        "Milestone Name";
    }
    leaf milestone-status {
      type string;
      description
        "Milestone Status";
    }
  }

  grouping OSPF-SH-NSR-STATS-PRI {
    description
      "OSPF SH NSR STATS PRI";
    leaf nsr-sched-pri {
      type uint32;
      description
        "nsr sched pri";
    }
    leaf nsr-sched-quant {
      type uint8;
      description
        "nsr sched quant";
    }
    leaf nsr-sched-remain-quant {
      type uint8;
      description
        "nsr sched remain quant";
    }
    leaf nsr-sched-evs-in-q {
      type uint16;
      description
        "nsr sched evs in q";
    }
    leaf nsr-sched-max-evs {
      type uint16;
      description
        "nsr sched max evs";
    }
    leaf nsr-sched-peak-q-len {
      type uint16;
      description
        "nsr sched peak q len";
    }
    leaf nsr-sched-evs-qd {
      type uint64;
      description
        "nsr sched evs qd";
    }
    leaf nsr-sched-enq-fails {
      type uint64;
      description
        "nsr sched enq fails";
    }
    leaf nsr-sched-evs-deqd {
      type uint64;
      description
        "nsr sched evs deqd";
    }
  }

  grouping OSPF-SH-NSR-SCHED-STATS {
    description
      "OSPF SH NSR SCHED STATS";
    leaf nsr-pulse-quant {
      type int32;
      description
        "nsr pulse quant";
    }
    leaf nsr-events-in-q {
      type uint32;
      description
        "nsr events in q";
    }
    leaf nsr-events-tx {
      type uint64;
      description
        "nsr events tx";
    }
    leaf nsr-events-rx {
      type uint64;
      description
        "nsr events rx";
    }
    leaf nsr-bad-pulses-rx {
      type uint64;
      description
        "nsr bad pulses rx";
    }
    leaf nsr-good-pulses-rx {
      type uint64;
      description
        "nsr good pulses rx";
    }
    leaf nsr-pulses-tx {
      type uint64;
      description
        "nsr pulses tx";
    }
    leaf nsr-pulse-tx-fails {
      type uint64;
      description
        "nsr pulse tx fails";
    }
    list nsr-pri {
      max-elements 3;
      description
        "nsr pri";
      uses OSPF-SH-NSR-STATS-PRI;
    }
  }

  grouping OSPF-SH-NSR-STATS {
    description
      "OSPF SH NSR STATS";
    container nsr-thd-sched {
      description
        "nsr thd sched";
      uses OSPF-SH-NSR-SCHED-STATS;
    }
    container nsr-rtr-thd-sched {
      description
        "nsr rtr thd sched";
      uses OSPF-SH-NSR-SCHED-STATS;
    }
    leaf nsr-rev {
      type int32;
      description
        "nsr rev";
    }
    leaf nsr-fsm-state {
      type int32;
      description
        "nsr fsm state";
    }
    leaf nsr-version {
      type uint32;
      description
        "nsr version";
    }
    leaf nsr-nodeid {
      type uint32;
      description
        "nsr nodeid";
    }
    leaf nsr-peer-version {
      type uint32;
      description
        "nsr peer version";
    }
    leaf nsr-peer-nodeid {
      type uint32;
      description
        "nsr peer nodeid";
    }
    leaf nsr-peer-ep-len {
      type uint32;
      description
        "nsr peer ep len";
    }
    leaf nsr-peer-ep-version {
      type uint32;
      description
        "nsr peer ep version";
    }
    leaf nsr-local-ep-len {
      type uint32;
      description
        "nsr local ep len";
    }
    leaf nsr-local-ep-version {
      type uint32;
      description
        "nsr local ep version";
    }
    leaf nsr-fabric-mtu {
      type uint32;
      description
        "nsr fabric mtu";
    }
    leaf nsr-nbr-qad-qid {
      type uint32;
      description
        "nsr nbr qad qid";
    }
    leaf nsr-lsa-qad-qid {
      type uint32;
      description
        "nsr lsa qad qid";
    }
    leaf nsr-nbr-qad-mdata-count {
      type uint32;
      description
        "nsr nbr qad mdata count";
    }
    leaf nsr-lsa-qad-mdata-count {
      type uint32;
      description
        "nsr lsa qad mdata count";
    }
    leaf nsr-nbr-init-sync-pend-count {
      type int32;
      description
        "nsr nbr init sync pend count";
    }
    leaf nsr-lsa-init-sync-pend-count {
      type int32;
      description
        "nsr lsa init sync pend count";
    }
    leaf nsr-nbr-seq-no {
      type uint32;
      description
        "nsr nbr seq no";
    }
    leaf nsr-intf-seq-no {
      type uint32;
      description
        "nsr intf seq no";
    }
    leaf nsr-tmr-quant {
      type int32;
      description
        "nsr tmr quant";
    }
    leaf nsr-peer-ds-hdl {
      type uint64;
      description
        "nsr peer ds hdl";
    }
    leaf nsr-local-ds-hdl {
      type uint64;
      description
        "nsr local ds hdl";
    }
    leaf nsr-conn-to-active-attempts {
      type uint64;
      description
        "nsr conn to active attempts";
    }
    leaf nsr-conn-to-active-fails {
      type uint64;
      description
        "nsr conn to active fails";
    }
    leaf nsr-conn-to-active-opens {
      type uint64;
      description
        "nsr conn to active opens";
    }
    leaf nsr-conn-to-active-closes {
      type uint64;
      description
        "nsr conn to active closes";
    }
    leaf nsr-conn-to-active-errors {
      type uint64;
      description
        "nsr conn to active errors";
    }
    leaf nsr-peer-ep {
      type yang:hex-string;
      description
        "nsr peer ep";
    }
    leaf nsr-local-ep {
      type yang:hex-string;
      description
        "nsr local ep";
    }
    list nsr-fsm-flag {
      description
        "Nsr Fsm Flags information";
      leaf entry {
        type Ospf-string-array;
        description
          "Nsr Fsm Flags information";
      }
    }
    list nsr-fsm-running-timer {
      description
        "Nsr Fsm Running Timers";
      leaf entry {
        type Ospf-string-array;
        description
          "Nsr Fsm Running Timers";
      }
    }
    list nsr-issu-milestone {
      description
        "Nsr Issu Milestones";
      uses OSPF-ISSU-MILESTONE-BAG;
    }
    list nsr-err-history {
      description
        "Nsr Error History List";
      uses OSPF-NSR-ERR-BLOCK-BAG;
    }
  }

  grouping OSPF-SH-RIB-BATCH {
    description
      "OSPF SH RIB BATCH";
    leaf batches-sent {
      type uint32;
      description
        "batches sent";
    }
    leaf routes-sent {
      type uint32;
      description
        "routes sent";
    }
    leaf routes-pending {
      type uint32;
      description
        "routes pending";
    }
    leaf max-routes {
      type uint32;
      description
        "max routes";
    }
    leaf paths-sent {
      type uint32;
      description
        "paths sent";
    }
    leaf paths-pending {
      type uint32;
      description
        "paths pending";
    }
    leaf paths-add {
      type uint32;
      description
        "paths add";
    }
    leaf paths-add-errs {
      type uint32;
      description
        "paths add errs";
    }
    leaf paths-del {
      type uint32;
      description
        "paths del";
    }
    leaf paths-del-errs {
      type uint32;
      description
        "paths del errs";
    }
    leaf lfas-pending {
      type uint32;
      description
        "lfas pending";
    }
    leaf lfas-add {
      type uint32;
      description
        "lfas add";
    }
    leaf lfas-del {
      type uint32;
      description
        "lfas del";
    }
    leaf lfas-sent {
      type uint32;
      description
        "lfas sent";
    }
    leaf priority-level {
      type string {
        length "0..40";
      }
      description
        "priority level";
    }
  }

  grouping OSPF-SH-RIB-BATCH-PRIORITY-QUEUES {
    description
      "OSPF SH RIB BATCH PRIORITY QUEUES";
    list priority-batch {
      max-elements 8;
      description
        "priority batch";
      uses OSPF-SH-RIB-BATCH;
    }
  }

  grouping OSPF-EDM-AREA-SUMM {
    description
      "OSPF EDM AREA SUMM";
    leaf area-id {
      type uint32;
      description
        "area id";
    }
    leaf spf-count {
      type uint32;
      description
        "spf count";
    }
  }

  grouping OSPF-HEADER-INFO {
    description
      "OSPF HEADER INFO";
    leaf router-id {
      type inet:ipv4-address;
      description
        "router id";
    }
    leaf spf-count {
      type uint32;
      description
        "spf count";
    }
    list area-summ {
      description
        "area summ";
      uses OSPF-EDM-AREA-SUMM;
    }
  }

  grouping OSPF-EDM-SPF-AREA-STATS {
    description
      "OSPF EDM SPF AREA STATS";
    container spf-time {
      description
        "spf time";
      uses OSPF-SPF-TIME;
    }
    leaf area-id {
      type uint32;
      description
        "area id";
    }
    list lsa-type-cnt {
      max-elements 7;
      description
        "lsa type cnt";
      leaf entry {
        type uint32;
        description
          "lsa type cnt";
      }
    }
  }

  grouping OSPF-LSA-CHANGE {
    description
      "OSPF LSA CHANGE";
    leaf area-id {
      type uint32;
      description
        "area id";
    }
    leaf adv-rtr {
      type inet:ipv4-address;
      description
        "adv rtr";
    }
    leaf id {
      type inet:ipv4-address;
      description
        "id";
    }
    leaf type {
      type uint8;
      description
        "type";
    }
    leaf flush {
      type boolean;
      description
        "flush";
    }
  }

  grouping OSPF-SPF-TIME {
    description
      "OSPF SPF TIME";
    leaf spf-dijkstra {
      type uint32;
      description
        "spf dijkstra";
    }
    leaf spf-intra-prefix {
      type uint32;
      description
        "spf intra prefix";
    }
    leaf spf-intra-prefix-del {
      type uint32;
      description
        "spf intra prefix del";
    }
    leaf spf-inter-prefix {
      type uint32;
      description
        "spf inter prefix";
    }
    leaf spf-inter-prefix-del {
      type uint32;
      description
        "spf inter prefix del";
    }
    leaf spf-ext-prefix {
      type uint32;
      description
        "spf ext prefix";
    }
    leaf spf-ext-prefix-del {
      type uint32;
      description
        "spf ext prefix del";
    }
  }

  grouping OSPF-RUNTIME-STATS {
    description
      "OSPF RUNTIME STATS";
    container gbl-spf-time {
      description
        "gbl spf time";
      uses OSPF-SPF-TIME;
    }
    leaf spf-start-time {
      type uint32;
      description
        "spf start time";
    }
    leaf lsa-change-cnt {
      type int16;
      description
        "lsa change cnt";
    }
    list lsa-info {
      max-elements 5;
      description
        "lsa info";
      uses OSPF-LSA-CHANGE;
    }
    list area-stat {
      description
        "area stat";
      uses OSPF-EDM-SPF-AREA-STATS;
    }
  }

  grouping OSPF-SH-STAT-PARTIAL {
    description
      "OSPF SH STAT PARTIAL";
    container sp-start-time {
      description
        "sp start time";
      uses OSPF-SH-TIME;
    }
    container sp-duration {
      description
        "sp duration";
      uses OSPF-SH-TIME;
    }
    leaf sp-adv-rtr-id {
      type uint32;
      description
        "sp adv rtr id";
    }
    leaf sp-dest-count {
      type uint32;
      description
        "sp dest count";
    }
    leaf sp-dest-addr {
      type uint32;
      description
        "sp dest addr";
    }
  }

  grouping OSPF-SH-STAT-INTRA {
    description
      "OSPF SH STAT INTRA";
    container si-start-time {
      description
        "si start time";
      uses OSPF-SH-TIME;
    }
    container si-duration {
      description
        "si duration";
      uses OSPF-SH-TIME;
    }
    leaf si-area-id-str {
      type string;
      description
        "si area id str";
    }
    leaf si-change-flags {
      type uint16;
      description
        "si change flags";
    }
  }

  grouping OSPF-SH-STATS-SPF {
    description
      "OSPF SH STATS SPF";
    container spf-header {
      description
        "spf header";
      uses OSPF-HEADER-INFO;
    }
    list os-runtime {
      description
        "os runtime";
      uses OSPF-SH-STAT-INTRA;
    }
    list os-sum-runtime {
      description
        "os sum runtime";
      uses OSPF-SH-STAT-PARTIAL;
    }
    list os-ex-runtime {
      description
        "os ex runtime";
      uses OSPF-SH-STAT-PARTIAL;
    }
    list runtime {
      description
        "runtime";
      uses OSPF-RUNTIME-STATS;
    }
  }
}
