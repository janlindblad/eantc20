submodule Cisco-IOS-XR-linux-os-heap-summary-oper-sub1 {
  // Generated by yanger -t ncs
  tailf:mount-id f5500-nc-1.0:f5500-nc-1.0;

  belongs-to Cisco-IOS-XR-linux-os-heap-summary-oper {
    prefix Cisco-IOS-XR-linux-os-heap-summary-oper-sub1;
  }

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR linux-os-heap-summary package operational data.

     Copyright (c) 2013-2018 by Cisco Systems, Inc.
     All rights reserved.";

  revision 2015-11-09 {
    description
      "IOS XR 6.0 revision.";
  }

  grouping ncs_template_SHOW-MEMORY-HEAP-SUMMARY-ALL-EDM-STRING {
    description
      "SHOW MEMORY HEAP SUMMARY ALL EDM STRING";
    leaf show-output {
      type string;
      description
        "string output";
    }
  }

  grouping ncs_rpc_notif_SHOW-MEMORY-HEAP-SUMMARY-ALL-EDM-STRING {
    description
      "SHOW MEMORY HEAP SUMMARY ALL EDM STRING";
    leaf show-output {
      type string;
      description
        "string output";
    }
  }

  grouping live_ncs_SHOW-MEMORY-HEAP-SUMMARY-ALL-EDM-STRING {
    description
      "SHOW MEMORY HEAP SUMMARY ALL EDM STRING";
    leaf show-output {
      type string;
      description
        "string output";
    }
  }

  grouping SHOW-MEMORY-HEAP-SUMMARY-ALL-EDM-STRING {
    description
      "SHOW MEMORY HEAP SUMMARY ALL EDM STRING";
    leaf show-output {
      type string;
      description
        "string output";
    }
  }
}
