module Cisco-IOS-XR-linux-os-heap-summary-oper {
  // Generated by yanger -t ncs
  tailf:mount-id f5500-nc-1.0:f5500-nc-1.0;
  tailf:ncs-device-type "netconf";

  namespace "http://cisco.com/ns/yang/Cisco-IOS-XR-linux-os-heap-summary-oper";
  prefix Cisco-IOS-XR-linux-os-heap-summary-oper;

  import Cisco-IOS-XR-types {
    prefix xr;
  }
  include Cisco-IOS-XR-linux-os-heap-summary-oper-sub1 {
    revision-date 2015-11-09;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR linux-os-heap-summary package operational data.

     This module contains definitions
     for the following management objects:
       heap-summary: Heap Summary

     Copyright (c) 2013-2018 by Cisco Systems, Inc.
     All rights reserved.";

  revision 2015-11-09 {
    description
      "IOS XR 6.0 revision.";
  }

  augment "/ncs:devices/ncs:device/ncs:config" {
    // NCS drop config false container 'heap-summary'
  }
  augment "/ncs:devices/ncs:device/ncs:live-status" {
    container heap-summary {
      tailf:ncs-device-type "netconf";
      tailf:display-when "not(../../ncs:module) or ../../ncs:module[ncs:name='Cisco-IOS-XR-linux-os-heap-summary-oper'] or (../../ncs:live-status-protocol[not(ncs:capability)]) or (../../ncs:live-status-protocol/ncs:capability/ncs:module[.='Cisco-IOS-XR-linux-os-heap-summary-oper'])";
      description
        "Heap Summary";
      container location-descriptions {
        description
          "Location";
        list location-description {
          key "node";
          description
            "Location specified in location";
          leaf node {
            type xr:Node-id;
            description
              "Node location";
          }
          uses live_ncs_SHOW-MEMORY-HEAP-SUMMARY-ALL-EDM-STRING;
        }
      }
      container all {
        description
          "All locations";
        uses live_ncs_SHOW-MEMORY-HEAP-SUMMARY-ALL-EDM-STRING;
      }
    }
  }
  augment "/ncs:devices/ncs:template/ncs:ned-id/ncs:config" {
    // NCS drop config false container 'heap-summary'
  }
}
