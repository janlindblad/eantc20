module Cisco-IOS-XR-watchd-cfg {
  // Generated by yanger -t ncs
  tailf:mount-id f5500-nc-1.0:f5500-nc-1.0;
  tailf:ncs-device-type "netconf";

  namespace "http://cisco.com/ns/yang/Cisco-IOS-XR-watchd-cfg";
  prefix Cisco-IOS-XR-watchd-cfg;

  import Cisco-IOS-XR-config-mda-cfg {
    prefix node;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR watchd package configuration.

     This module contains definitions
     for the following management objects:
       watchdog: Watchdog configuration commands
       watchd: watchd

     This YANG module augments the
       Cisco-IOS-XR-config-mda-cfg
     module with configuration data.

     Copyright (c) 2013-2018 by Cisco Systems, Inc.
     All rights reserved.";

  revision 2015-11-09 {
    description
      "IOS XR 6.0 revision.";
  }
  revision 2015-10-12 {
    description
      "Descriptions updated.";
  }

  grouping ncs_template_NODE-CFG {
    description
      "active/preconfigured nodes configuration";
    container watchdog-node-threshold {
      description
        "watchdog node threshold";
      container disk-threshold {
        description
          "Disk thresholds";
        leaf minor {
          type string;
          description
            "Threshold, Range(5, 40)";
        }
        leaf severe {
          type string;
          description
            "Threshold, Range(4, minor)";
        }
        leaf critical {
          type string;
          description
            "Threshold, Range(3, severe)";
        }
      }
      container memory-threshold {
        description
          "Memory thresholds";
        leaf minor {
          type string;
          description
            "Threshold, Range(5, 40)";
        }
        leaf severe {
          type string;
          description
            "Threshold, Range(4, minor)";
        }
        leaf critical {
          type string;
          description
            "Threshold, Range(3, severe)";
        }
      }
    }
  }

  grouping ncs_rpc_notif_NODE-CFG {
    description
      "active/preconfigured nodes configuration";
    container watchdog-node-threshold {
      description
        "watchdog node threshold";
      container disk-threshold {
        description
          "Disk thresholds";
        leaf minor {
          type uint32 {
            range "5..40";
          }
          description
            "Threshold, Range(5, 40)";
        }
        leaf severe {
          type uint32 {
            range "4..40";
          }
          description
            "Threshold, Range(4, minor)";
        }
        leaf critical {
          type uint32 {
            range "3..40";
          }
          description
            "Threshold, Range(3, severe)";
        }
      }
      container memory-threshold {
        description
          "Memory thresholds";
        leaf minor {
          type uint32 {
            range "5..40";
          }
          description
            "Threshold, Range(5, 40)";
        }
        leaf severe {
          type uint32 {
            range "4..40";
          }
          description
            "Threshold, Range(4, minor)";
        }
        leaf critical {
          type uint32 {
            range "3..40";
          }
          description
            "Threshold, Range(3, severe)";
        }
      }
    }
  }

  grouping live_ncs_NODE-CFG {
    description
      "active/preconfigured nodes configuration";
    container watchdog-node-threshold {
      description
        "watchdog node threshold";
      container disk-threshold {
        description
          "Disk thresholds";
        leaf minor {
          type uint32 {
            range "5..40";
          }
          description
            "Threshold, Range(5, 40)";
        }
        leaf severe {
          type uint32 {
            range "4..40";
          }
          description
            "Threshold, Range(4, minor)";
        }
        leaf critical {
          type uint32 {
            range "3..40";
          }
          description
            "Threshold, Range(3, severe)";
        }
      }
      container memory-threshold {
        description
          "Memory thresholds";
        leaf minor {
          type uint32 {
            range "5..40";
          }
          description
            "Threshold, Range(5, 40)";
        }
        leaf severe {
          type uint32 {
            range "4..40";
          }
          description
            "Threshold, Range(4, minor)";
        }
        leaf critical {
          type uint32 {
            range "3..40";
          }
          description
            "Threshold, Range(3, severe)";
        }
      }
    }
  }

  grouping NODE-CFG {
    description
      "active/preconfigured nodes configuration";
    container watchdog-node-threshold {
      description
        "watchdog node threshold";
      container disk-threshold {
        description
          "Disk thresholds";
        leaf minor {
          type uint32 {
            range "5..40";
          }
          description
            "Threshold, Range(5, 40)";
        }
        leaf severe {
          type uint32 {
            range "4..40";
          }
          description
            "Threshold, Range(4, minor)";
        }
        leaf critical {
          type uint32 {
            range "3..40";
          }
          description
            "Threshold, Range(3, severe)";
        }
      }
      container memory-threshold {
        description
          "Memory thresholds";
        leaf minor {
          type uint32 {
            range "5..40";
          }
          description
            "Threshold, Range(5, 40)";
        }
        leaf severe {
          type uint32 {
            range "4..40";
          }
          description
            "Threshold, Range(4, minor)";
        }
        leaf critical {
          type uint32 {
            range "3..40";
          }
          description
            "Threshold, Range(3, severe)";
        }
      }
    }
  }

  augment "/ncs:devices/ncs:device/ncs:config" {
    container watchdog {
      tailf:ncs-device-type "netconf";
      tailf:display-when "not(../../ncs:module) or ../../ncs:module[ncs:name='Cisco-IOS-XR-watchd-cfg']";
      description
        "Watchdog configuration commands";
      container threshold-memory {
        description
          "Memory thresholds";
        leaf minor {
          type uint32 {
            range "5..40";
          }
          description
            "Threshold, Range (5, 40)";
        }
        leaf severe {
          type uint32 {
            range "4..40";
          }
          description
            "Threshold, Range (4, minor)";
        }
        leaf critical {
          type uint32 {
            range "3..40";
          }
          description
            "Threshold, Range (3, severe)";
        }
      }
      container disk-limit {
        description
          "Disk thresholds";
        leaf minor {
          type uint32 {
            range "5..40";
          }
          description
            "Threshold, Range (5, 40)";
        }
        leaf severe {
          type uint32 {
            range "4..40";
          }
          description
            "Threshold, Range (4, minor)";
        }
        leaf critical {
          type uint32 {
            range "3..40";
          }
          description
            "Threshold, Range (3, severe)";
        }
      }
      leaf overload-notification {
        type empty;
        description
          "Disable critical event notification";
      }
      leaf restart-deadlock-disable {
        type empty;
        description
          "Disable watchdog restart deadlock";
      }
      leaf restart-memoryhog-disable {
        type empty;
        description
          "Disable watchdog restart memory-hog";
      }
      leaf overload-throttle-timeout {
        type uint32 {
          range "5..120";
        }
        units "second";
        description
          "Watchdog overload throttle timeout configuration";
      }
    }
    container watchd {
      tailf:ncs-device-type "netconf";
      tailf:display-when "not(../../ncs:module) or ../../ncs:module[ncs:name='Cisco-IOS-XR-watchd-cfg']";
      description
        "watchd";
      leaf timeout {
        type uint32 {
          range "1..10";
        }
        units "second";
        description
          "Length of timeout in seconds";
      }
    }
  }
  augment "/ncs:devices/ncs:device/ncs:live-status" {
    container watchdog {
      tailf:ncs-device-type "netconf";
      tailf:display-when "not(../../ncs:module) or ../../ncs:module[ncs:name='Cisco-IOS-XR-watchd-cfg'] or (../../ncs:live-status-protocol[not(ncs:capability)]) or (../../ncs:live-status-protocol/ncs:capability/ncs:module[.='Cisco-IOS-XR-watchd-cfg'])";
      description
        "Watchdog configuration commands";
      container threshold-memory {
        description
          "Memory thresholds";
        leaf minor {
          type uint32 {
            range "5..40";
          }
          description
            "Threshold, Range (5, 40)";
        }
        leaf severe {
          type uint32 {
            range "4..40";
          }
          description
            "Threshold, Range (4, minor)";
        }
        leaf critical {
          type uint32 {
            range "3..40";
          }
          description
            "Threshold, Range (3, severe)";
        }
      }
      container disk-limit {
        description
          "Disk thresholds";
        leaf minor {
          type uint32 {
            range "5..40";
          }
          description
            "Threshold, Range (5, 40)";
        }
        leaf severe {
          type uint32 {
            range "4..40";
          }
          description
            "Threshold, Range (4, minor)";
        }
        leaf critical {
          type uint32 {
            range "3..40";
          }
          description
            "Threshold, Range (3, severe)";
        }
      }
      leaf overload-notification {
        type empty;
        description
          "Disable critical event notification";
      }
      leaf restart-deadlock-disable {
        type empty;
        description
          "Disable watchdog restart deadlock";
      }
      leaf restart-memoryhog-disable {
        type empty;
        description
          "Disable watchdog restart memory-hog";
      }
      leaf overload-throttle-timeout {
        type uint32 {
          range "5..120";
        }
        units "second";
        description
          "Watchdog overload throttle timeout configuration";
      }
    }
    container watchd {
      tailf:ncs-device-type "netconf";
      tailf:display-when "not(../../ncs:module) or ../../ncs:module[ncs:name='Cisco-IOS-XR-watchd-cfg'] or (../../ncs:live-status-protocol[not(ncs:capability)]) or (../../ncs:live-status-protocol/ncs:capability/ncs:module[.='Cisco-IOS-XR-watchd-cfg'])";
      description
        "watchd";
      leaf timeout {
        type uint32 {
          range "1..10";
        }
        units "second";
        description
          "Length of timeout in seconds";
      }
    }
  }
  augment "/ncs:devices/ncs:template/ncs:ned-id/ncs:config" {
    container watchdog {
      description
        "Watchdog configuration commands";
      container threshold-memory {
        description
          "Memory thresholds";
        leaf minor {
          type string;
          description
            "Threshold, Range (5, 40)";
        }
        leaf severe {
          type string;
          description
            "Threshold, Range (4, minor)";
        }
        leaf critical {
          type string;
          description
            "Threshold, Range (3, severe)";
        }
      }
      container disk-limit {
        description
          "Disk thresholds";
        leaf minor {
          type string;
          description
            "Threshold, Range (5, 40)";
        }
        leaf severe {
          type string;
          description
            "Threshold, Range (4, minor)";
        }
        leaf critical {
          type string;
          description
            "Threshold, Range (3, severe)";
        }
      }
      leaf overload-notification {
        type empty;
        description
          "Disable critical event notification";
      }
      leaf restart-deadlock-disable {
        type empty;
        description
          "Disable watchdog restart deadlock";
      }
      leaf restart-memoryhog-disable {
        type empty;
        description
          "Disable watchdog restart memory-hog";
      }
      leaf overload-throttle-timeout {
        type string;
        units "second";
        description
          "Watchdog overload throttle timeout configuration";
      }
    }
    container watchd {
      description
        "watchd";
      leaf timeout {
        type string;
        units "second";
        description
          "Length of timeout in seconds";
      }
    }
  }
  augment "/ncs:devices/ncs:template/ncs:ned-id/ncs:config/node:active-nodes/node:active-node" {
    uses ncs_template_NODE-CFG;
    description
      "This augment extends active nodes configuration";
  }
  augment "/ncs:devices/ncs:device/ncs:live-status/node:active-nodes/node:active-node" {
    uses live_ncs_NODE-CFG {
      refine watchdog-node-threshold {
        tailf:ncs-device-type "netconf";
        tailf:display-when "not(../../../../ncs:module) or ../../../../ncs:module[ncs:name='Cisco-IOS-XR-watchd-cfg'] or (../../../../ncs:live-status-protocol[not(ncs:capability)]) or (../../../../ncs:live-status-protocol/ncs:capability/ncs:module[.='Cisco-IOS-XR-watchd-cfg'])";
      }
    }
    description
      "This augment extends active nodes configuration";
  }
  augment "/ncs:devices/ncs:device/ncs:config/node:active-nodes/node:active-node" {
    uses NODE-CFG {
      refine watchdog-node-threshold {
        tailf:ncs-device-type "netconf";
        tailf:display-when "not(../../../../ncs:module) or ../../../../ncs:module[ncs:name='Cisco-IOS-XR-watchd-cfg']";
      }
    }
    description
      "This augment extends active nodes configuration";
  }
  augment "/ncs:devices/ncs:template/ncs:ned-id/ncs:config/node:preconfigured-nodes/node:preconfigured-node" {
    uses ncs_template_NODE-CFG;
    description
      "This augment extends preconfigured nodes
       configuration";
  }
  augment "/ncs:devices/ncs:device/ncs:live-status/node:preconfigured-nodes/node:preconfigured-node" {
    uses live_ncs_NODE-CFG {
      refine watchdog-node-threshold {
        tailf:ncs-device-type "netconf";
        tailf:display-when "not(../../../../ncs:module) or ../../../../ncs:module[ncs:name='Cisco-IOS-XR-watchd-cfg'] or (../../../../ncs:live-status-protocol[not(ncs:capability)]) or (../../../../ncs:live-status-protocol/ncs:capability/ncs:module[.='Cisco-IOS-XR-watchd-cfg'])";
      }
    }
    description
      "This augment extends preconfigured nodes
       configuration";
  }
  augment "/ncs:devices/ncs:device/ncs:config/node:preconfigured-nodes/node:preconfigured-node" {
    uses NODE-CFG {
      refine watchdog-node-threshold {
        tailf:ncs-device-type "netconf";
        tailf:display-when "not(../../../../ncs:module) or ../../../../ncs:module[ncs:name='Cisco-IOS-XR-watchd-cfg']";
      }
    }
    description
      "This augment extends preconfigured nodes
       configuration";
  }
}
