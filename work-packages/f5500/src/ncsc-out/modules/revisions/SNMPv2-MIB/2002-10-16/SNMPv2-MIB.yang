module SNMPv2-MIB {
  // Generated by yanger -t ncs
  tailf:mount-id f5500-nc-1.0:f5500-nc-1.0;
  tailf:ncs-device-type "netconf";

  namespace "http://tail-f.com/ns/mibs/SNMPv2-MIB/200210160000Z";
  prefix SNMPv2-MIB;
  // NCS drop tailf:id
  tailf:snmp-mib-module-name SNMPv2-MIB;

  import ietf-yang-types {
    prefix yang;
  }
  import tailf-common {
    prefix tailf;
  }
  import SNMPv2-TC {
    prefix SNMPv2_TC;
  }
  import "f5500-nc-1.0" {
    prefix "f5500-nc-1.0";
  }
  import tailf-ncs {
    prefix ncs;
  }

  revision 2002-10-16 {
    description
      "";
  }

  typedef sysORIndexType {
    type int32 {
      range "1 .. 2147483647";
    }
  }

  typedef snmpEnableAuthenTrapsType {
    type enumeration {
      enum "enabled" {
        value 1;
      }
      enum "disabled" {
        value 2;
      }
    }
  }

  typedef sysServicesType {
    type int32 {
      range "0 .. 127";
    }
  }

  typedef sysLocationType {
    type string {
      length "min .. 255";
    }
  }

  typedef sysNameType {
    type string {
      length "min .. 255";
    }
  }

  typedef sysContactType {
    type string {
      length "min .. 255";
    }
  }

  typedef sysDescrType {
    type string {
      length "min .. 255";
    }
  }

  augment "/ncs:devices/ncs:device/ncs:config" {
    container SNMPv2-MIB {
      tailf:ncs-device-type "netconf";
      tailf:display-when "not(../../ncs:module) or ../../ncs:module[ncs:name='SNMPv2-MIB']";
      container system {
        tailf:snmp-oid "1.3.6.1.2.1.1";
        // NCS drop config false leaf sysDescr
        // NCS drop config false leaf sysObjectID
        // NCS drop config false leaf sysUpTime
        leaf sysContact {
          type sysContactType;
          tailf:snmp-oid "1.3.6.1.2.1.1.4";
          default "";
        }
        leaf sysName {
          type sysNameType;
          tailf:snmp-oid "1.3.6.1.2.1.1.5";
          default "";
        }
        leaf sysLocation {
          type sysLocationType;
          tailf:snmp-oid "1.3.6.1.2.1.1.6";
          default "";
        }
        // NCS drop config false leaf sysServices
        // NCS drop config false leaf sysORLastChange
      }
      container snmp {
        tailf:snmp-oid "1.3.6.1.2.1.11";
        // NCS drop config false leaf snmpInPkts
        // NCS drop config false leaf snmpInBadVersions
        // NCS drop config false leaf snmpInBadCommunityNames
        // NCS drop config false leaf snmpInBadCommunityUses
        // NCS drop config false leaf snmpInASNParseErrs
        leaf snmpEnableAuthenTraps {
          type snmpEnableAuthenTrapsType;
          tailf:snmp-oid "1.3.6.1.2.1.11.30";
          default "disabled";
        }
        // NCS drop config false leaf snmpSilentDrops
        // NCS drop config false leaf snmpProxyDrops
      }
      container snmpSet {
        tailf:snmp-oid "1.3.6.1.6.3.1.1.6";
        // NCS drop config false leaf snmpSetSerialNo
      }
      container sysORTable {
        list sysOREntry {
          key "sysORIndex";
          tailf:sort-order snmp;
          tailf:snmp-oid "1.3.6.1.2.1.1.9";
          leaf sysORIndex {
            type sysORIndexType;
            tailf:snmp-oid "1.3.6.1.2.1.1.9.1.1";
          }
          // NCS drop config false leaf sysORID
          // NCS drop config false leaf sysORDescr
          // NCS drop config false leaf sysORUpTime
        }
      }
    }
  }
  augment "/ncs:devices/ncs:device/ncs:live-status" {
    container SNMPv2-MIB {
      tailf:ncs-device-type "netconf";
      tailf:display-when "not(../../ncs:module) or ../../ncs:module[ncs:name='SNMPv2-MIB'] or (../../ncs:live-status-protocol[not(ncs:capability)]) or (../../ncs:live-status-protocol/ncs:capability/ncs:module[.='SNMPv2-MIB'])";
      container system {
        tailf:snmp-oid "1.3.6.1.2.1.1";
        leaf sysDescr {
          type sysDescrType;
          tailf:snmp-oid "1.3.6.1.2.1.1.1";
        }
        leaf sysObjectID {
          type yang:object-identifier;
          tailf:snmp-oid "1.3.6.1.2.1.1.2";
        }
        leaf sysUpTime {
          type yang:timeticks;
          tailf:snmp-oid "1.3.6.1.2.1.1.3";
        }
        leaf sysContact {
          type sysContactType;
          tailf:snmp-oid "1.3.6.1.2.1.1.4";
          // NCS drop default statement
        }
        leaf sysName {
          type sysNameType;
          tailf:snmp-oid "1.3.6.1.2.1.1.5";
          // NCS drop default statement
        }
        leaf sysLocation {
          type sysLocationType;
          tailf:snmp-oid "1.3.6.1.2.1.1.6";
          // NCS drop default statement
        }
        leaf sysServices {
          type sysServicesType;
          tailf:snmp-oid "1.3.6.1.2.1.1.7";
        }
        leaf sysORLastChange {
          type yang:timestamp;
          tailf:snmp-oid "1.3.6.1.2.1.1.8";
        }
      }
      container snmp {
        tailf:snmp-oid "1.3.6.1.2.1.11";
        leaf snmpInPkts {
          type yang:counter32;
          tailf:snmp-oid "1.3.6.1.2.1.11.1";
        }
        leaf snmpInBadVersions {
          type yang:counter32;
          tailf:snmp-oid "1.3.6.1.2.1.11.3";
        }
        leaf snmpInBadCommunityNames {
          type yang:counter32;
          tailf:snmp-oid "1.3.6.1.2.1.11.4";
        }
        leaf snmpInBadCommunityUses {
          type yang:counter32;
          tailf:snmp-oid "1.3.6.1.2.1.11.5";
        }
        leaf snmpInASNParseErrs {
          type yang:counter32;
          tailf:snmp-oid "1.3.6.1.2.1.11.6";
        }
        leaf snmpEnableAuthenTraps {
          type snmpEnableAuthenTrapsType;
          tailf:snmp-oid "1.3.6.1.2.1.11.30";
          // NCS drop default statement
        }
        leaf snmpSilentDrops {
          type yang:counter32;
          tailf:snmp-oid "1.3.6.1.2.1.11.31";
        }
        leaf snmpProxyDrops {
          type yang:counter32;
          tailf:snmp-oid "1.3.6.1.2.1.11.32";
        }
      }
      container snmpSet {
        tailf:snmp-oid "1.3.6.1.6.3.1.1.6";
        leaf snmpSetSerialNo {
          type SNMPv2_TC:TestAndIncr;
          tailf:snmp-oid "1.3.6.1.6.3.1.1.6.1";
        }
      }
      container sysORTable {
        list sysOREntry {
          key "sysORIndex";
          tailf:sort-order snmp;
          tailf:snmp-oid "1.3.6.1.2.1.1.9";
          leaf sysORIndex {
            type sysORIndexType;
            tailf:snmp-oid "1.3.6.1.2.1.1.9.1.1";
          }
          leaf sysORID {
            type yang:object-identifier;
            tailf:snmp-oid "1.3.6.1.2.1.1.9.1.2";
          }
          leaf sysORDescr {
            type string {
              length "0 .. 255";
            }
            tailf:snmp-oid "1.3.6.1.2.1.1.9.1.3";
          }
          leaf sysORUpTime {
            type yang:timestamp;
            tailf:snmp-oid "1.3.6.1.2.1.1.9.1.4";
          }
        }
      }
    }
  }
  augment "/ncs:devices/ncs:template/ncs:ned-id/ncs:config" {
    container SNMPv2-MIB {
      container system {
        // NCS drop config false leaf sysDescr
        // NCS drop config false leaf sysObjectID
        // NCS drop config false leaf sysUpTime
        leaf sysContact {
          type string;
          // NCS drop default statement
        }
        leaf sysName {
          type string;
          // NCS drop default statement
        }
        leaf sysLocation {
          type string;
          // NCS drop default statement
        }
        // NCS drop config false leaf sysServices
        // NCS drop config false leaf sysORLastChange
      }
      container snmp {
        // NCS drop config false leaf snmpInPkts
        // NCS drop config false leaf snmpInBadVersions
        // NCS drop config false leaf snmpInBadCommunityNames
        // NCS drop config false leaf snmpInBadCommunityUses
        // NCS drop config false leaf snmpInASNParseErrs
        leaf snmpEnableAuthenTraps {
          type string;
          // NCS drop default statement
        }
        // NCS drop config false leaf snmpSilentDrops
        // NCS drop config false leaf snmpProxyDrops
      }
      container snmpSet {
        // NCS drop config false leaf snmpSetSerialNo
      }
      container sysORTable {
        list sysOREntry {
          // NCS patched for predictable order
          ordered-by user;
          key "sysORIndex";
          leaf sysORIndex {
            type string;
          }
          // NCS drop config false leaf sysORID
          // NCS drop config false leaf sysORDescr
          // NCS drop config false leaf sysORUpTime
        }
      }
    }
  }
}
