module Cisco-IOS-XR-segment-routing-ms-common-cfg {
  // Generated by yanger -t ncs
  tailf:mount-id f5500-nc-1.0:f5500-nc-1.0;
  tailf:ncs-device-type "netconf";

  namespace "http://cisco.com/ns/yang/Cisco-IOS-XR-segment-routing-ms-common-cfg";
  prefix Cisco-IOS-XR-segment-routing-ms-common-cfg;

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR segment-routing-ms-common package configuration.

     This module contains definitions
     for the following management objects:
       sr: Segment Routing

     Copyright (c) 2013-2018 by Cisco Systems, Inc.
     All rights reserved.";

  revision 2015-11-09 {
    description
      "IOS XR 6.0 revision.";
  }

  augment "/ncs:devices/ncs:device/ncs:config" {
    container sr {
      tailf:ncs-device-type "netconf";
      tailf:display-when "not(../../ncs:module) or ../../ncs:module[ncs:name='Cisco-IOS-XR-segment-routing-ms-common-cfg']";
      description
        "Segment Routing";
    }
  }
  augment "/ncs:devices/ncs:device/ncs:live-status" {
    container sr {
      tailf:ncs-device-type "netconf";
      tailf:display-when "not(../../ncs:module) or ../../ncs:module[ncs:name='Cisco-IOS-XR-segment-routing-ms-common-cfg'] or (../../ncs:live-status-protocol[not(ncs:capability)]) or (../../ncs:live-status-protocol/ncs:capability/ncs:module[.='Cisco-IOS-XR-segment-routing-ms-common-cfg'])";
      description
        "Segment Routing";
    }
  }
  augment "/ncs:devices/ncs:template/ncs:ned-id/ncs:config" {
    container sr {
      description
        "Segment Routing";
    }
  }
}
