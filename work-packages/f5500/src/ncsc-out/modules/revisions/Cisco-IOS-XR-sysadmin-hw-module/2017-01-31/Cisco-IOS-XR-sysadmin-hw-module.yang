module Cisco-IOS-XR-sysadmin-hw-module {
  // Generated by yanger -t ncs
  tailf:mount-id f5500-nc-1.0:f5500-nc-1.0;
  tailf:ncs-device-type "netconf";

  namespace "http://www.cisco.com/ns/yang/Cisco-IOS-XR-sysadmin-hw-module";
  prefix Cisco-IOS-XR-sysadmin-hw-module;

  import Cisco-IOS-XR-sysadmin-sm-hw-mod {
    prefix shelf_mgr;
  }
  import Cisco-IOS-XR-sysadmin-led-mgr-ui {
    prefix led_mgr;
  }
  import Cisco-IOS-XR-sysadmin-fpd-infra-cli-shhwfpd {
    prefix shhwfpd;
  }
  import Cisco-IOS-XR-sysadmin-obfl-conf {
    prefix obflconf;
  }
  import "f5500-nc-1.0" {
    prefix "f5500-nc-1.0";
  }
  import tailf-ncs {
    prefix ncs;
  }
  import tailf-common {
    prefix tailf;
  }

  organization
    "Cisco Systems Inc.";
  contact
    "Cisco Systems, Inc.
     Customer Service

     Postal: 170 West Tasman Drive
     San Jose, CA 95134

     Tel: +1 800 553-NETS

     E-mail: cs-yang@cisco.com";
  description
    "This module contains definitions
     for the Calvados model objects.

     This module contains a collection of YANG
     definitions for Cisco IOS-XR SysAdmin configuration.

     This module defines the top level container for
     all 'hw-module' commands for Sysadmin.

     Copyright(c) 2012-2017 by Cisco Systems, Inc.
     All rights reserved.

     Copyright (c) 2012-2018 by Cisco Systems, Inc.
     All rights reserved.";

  revision 2017-01-31 {
    description
      "Changed the namespace and module name";
  }

  augment "/ncs:devices/ncs:device/ncs:config" {
    container hw-module {
      tailf:ncs-device-type "netconf";
      tailf:display-when "not(../../ncs:module) or ../../ncs:module[ncs:name='Cisco-IOS-XR-sysadmin-hw-module']";
      container config {
        // NCS dropped explicit config true
        uses shelf_mgr:hw-module-config-group;
        uses led_mgr:hw-module-config-group;
        uses obflconf:hw-module-config-group;
      }
      // NCS drop config false container oper
      uses shhwfpd:hw-module-oper-group;
    }
  }
  augment "/ncs:devices/ncs:device/ncs:live-status" {
    container hw-module {
      tailf:ncs-device-type "netconf";
      tailf:display-when "not(../../ncs:module) or ../../ncs:module[ncs:name='Cisco-IOS-XR-sysadmin-hw-module'] or (../../ncs:live-status-protocol[not(ncs:capability)]) or (../../ncs:live-status-protocol/ncs:capability/ncs:module[.='Cisco-IOS-XR-sysadmin-hw-module'])";
      container config {
        uses shelf_mgr:live_ncs_hw-module-config-group;
        uses led_mgr:live_ncs_hw-module-config-group;
        uses obflconf:live_ncs_hw-module-config-group;
      }
      container oper {
        list location {
          key "location";
          leaf location {
            type string;
          }
          container actions {
            uses shelf_mgr:live_ncs_hw-module-action-group;
          }
          container show;
        }
      }
      uses shhwfpd:live_ncs_hw-module-oper-group;
    }
  }
  augment "/ncs:devices/ncs:template/ncs:ned-id/ncs:config" {
    container hw-module {
      container config {
        // NCS dropped explicit config true
        uses shelf_mgr:ncs_template_hw-module-config-group;
        uses led_mgr:ncs_template_hw-module-config-group;
        uses obflconf:ncs_template_hw-module-config-group;
      }
      // NCS drop config false container oper
      uses shhwfpd:ncs_template_hw-module-oper-group;
    }
  }
}
