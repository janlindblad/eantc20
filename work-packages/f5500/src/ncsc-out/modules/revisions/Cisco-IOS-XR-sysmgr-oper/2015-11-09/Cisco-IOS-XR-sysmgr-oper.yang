module Cisco-IOS-XR-sysmgr-oper {
  // Generated by yanger -t ncs
  tailf:mount-id f5500-nc-1.0:f5500-nc-1.0;
  tailf:ncs-device-type "netconf";

  namespace "http://cisco.com/ns/yang/Cisco-IOS-XR-sysmgr-oper";
  prefix Cisco-IOS-XR-sysmgr-oper;

  import Cisco-IOS-XR-types {
    prefix xr;
  }
  include Cisco-IOS-XR-sysmgr-oper-sub1 {
    revision-date 2015-11-09;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR sysmgr package operational data.

     This module contains definitions
     for the following management objects:
       system-process: Process information

     Copyright (c) 2013-2018 by Cisco Systems, Inc.
     All rights reserved.";

  revision 2015-11-09 {
    description
      "IOS XR 6.0 revision.";
  }

  grouping ncs_template_NODE {
    description
      "Common node of node-table, node-table";
    list node {
      // NCS patched for predictable order
      ordered-by user;
      key "node-name";
      description
        "Process information per node";
      container name {
        description
          "Process <WORD> information";
        container process-name-run-infos {
          description
            "Process <WORD> information";
          list process-name-run-info {
            // NCS patched for predictable order
            ordered-by user;
            key "proc-name";
            description
              "Process <WORD> run information";
            leaf proc-name {
              type string;
              description
                "Process Name";
            }
            uses ncs_template_PROC-BASIC-INFO;
          }
        }
        container process-name-infos {
          description
            "Process <WORD> information";
          list process-name-info {
            // NCS patched for predictable order
            ordered-by user;
            key "proc-name";
            description
              "Process <WORD> information";
            leaf proc-name {
              type string;
              description
                "Process Name";
            }
            uses ncs_template_PROC-BASIC-INFO;
          }
        }
        container process-name-run-details {
          description
            "Process <WORD> information";
          list process-name-run-detail {
            // NCS patched for predictable order
            ordered-by user;
            key "proc-name";
            description
              "Process <WORD> run detail information";
            leaf proc-name {
              type string;
              description
                "Process Name";
            }
            uses ncs_template_PROC-BASIC-DETAIL-INFO;
          }
        }
        container process-name-runverboses {
          description
            "Process <WORD> information";
          list process-name-runverbose {
            // NCS patched for predictable order
            ordered-by user;
            key "proc-name";
            description
              "Process <WORD> run verbose information";
            leaf proc-name {
              type string;
              description
                "Process Name";
            }
            uses ncs_template_PROC-BASIC-DETAIL-VERBOSE-INFO;
          }
        }
        container process-name-details {
          description
            "Process <WORD> information";
          list process-name-detail {
            // NCS patched for predictable order
            ordered-by user;
            key "proc-name";
            description
              "Process <WORD> detail information";
            leaf proc-name {
              type string;
              description
                "Process Name";
            }
            uses ncs_template_PROC-BASIC-DETAIL-INFO;
          }
        }
        container process-name-verboses {
          description
            "Process <WORD> information";
          list process-name-verbose {
            // NCS patched for predictable order
            ordered-by user;
            key "proc-name";
            description
              "Process <WORD> verbose information";
            leaf proc-name {
              type string;
              description
                "Process Name";
            }
            uses ncs_template_PROC-BASIC-DETAIL-VERBOSE-INFO;
          }
        }
      }
      container jids {
        description
          "Process job id information";
        list jid {
          // NCS patched for predictable order
          ordered-by user;
          key "job-id";
          description
            "Process <jid> information";
          leaf job-id {
            type string;
            description
              "Job ID";
          }
          uses ncs_template_PROC-BASIC-INFO;
        }
      }
      container dynamic {
        description
          "Process Dynamic information";
        uses ncs_template_PROCESSES-INFO;
      }
      container boot-stalled {
        description
          "Process Boot Stalled information";
        uses ncs_template_PROC-BOOT-STALLED-INFO;
      }
      container processes {
        description
          "Process all information";
        uses ncs_template_PROCESSES-INFO;
      }
      container startup {
        description
          "Process Startup information";
        uses ncs_template_PROCESSES-INFO;
      }
      container mandatory {
        description
          "Mandatory Process information";
        uses ncs_template_PROCESSES-INFO;
      }
      container abort {
        description
          "Process Abort information";
        uses ncs_template_PROC-ABORT-INFO;
      }
      container failover {
        description
          "Process Failover information";
        uses ncs_template_PROC-FAILOVER-INFO;
      }
      container boot {
        description
          "Process Boot information";
        uses ncs_template_PROC-BOOT-INFO;
      }
      container logs {
        description
          "Process Log information";
        uses ncs_template_LOG-INFO;
      }
      container searchpath {
        description
          "Process Searchpath information";
        uses ncs_template_PROC-SEARCHPATH-INFO;
      }
      leaf node-name {
        type string;
        description
          "The node name";
      }
    }
  }

  grouping ncs_rpc_notif_NODE {
    description
      "Common node of node-table, node-table";
    list node {
      key "node-name";
      description
        "Process information per node";
      container name {
        description
          "Process <WORD> information";
        container process-name-run-infos {
          description
            "Process <WORD> information";
          list process-name-run-info {
            key "proc-name";
            description
              "Process <WORD> run information";
            leaf proc-name {
              type xr:Cisco-ios-xr-string;
              description
                "Process Name";
            }
            uses ncs_rpc_notif_PROC-BASIC-INFO;
          }
        }
        container process-name-infos {
          description
            "Process <WORD> information";
          list process-name-info {
            key "proc-name";
            description
              "Process <WORD> information";
            leaf proc-name {
              type xr:Cisco-ios-xr-string;
              description
                "Process Name";
            }
            uses ncs_rpc_notif_PROC-BASIC-INFO;
          }
        }
        container process-name-run-details {
          description
            "Process <WORD> information";
          list process-name-run-detail {
            key "proc-name";
            description
              "Process <WORD> run detail information";
            leaf proc-name {
              type xr:Cisco-ios-xr-string;
              description
                "Process Name";
            }
            uses ncs_rpc_notif_PROC-BASIC-DETAIL-INFO;
          }
        }
        container process-name-runverboses {
          description
            "Process <WORD> information";
          list process-name-runverbose {
            key "proc-name";
            description
              "Process <WORD> run verbose information";
            leaf proc-name {
              type xr:Cisco-ios-xr-string;
              description
                "Process Name";
            }
            uses ncs_rpc_notif_PROC-BASIC-DETAIL-VERBOSE-INFO;
          }
        }
        container process-name-details {
          description
            "Process <WORD> information";
          list process-name-detail {
            key "proc-name";
            description
              "Process <WORD> detail information";
            leaf proc-name {
              type xr:Cisco-ios-xr-string;
              description
                "Process Name";
            }
            uses ncs_rpc_notif_PROC-BASIC-DETAIL-INFO;
          }
        }
        container process-name-verboses {
          description
            "Process <WORD> information";
          list process-name-verbose {
            key "proc-name";
            description
              "Process <WORD> verbose information";
            leaf proc-name {
              type xr:Cisco-ios-xr-string;
              description
                "Process Name";
            }
            uses ncs_rpc_notif_PROC-BASIC-DETAIL-VERBOSE-INFO;
          }
        }
      }
      container jids {
        description
          "Process job id information";
        list jid {
          key "job-id";
          description
            "Process <jid> information";
          leaf job-id {
            type uint32;
            description
              "Job ID";
          }
          uses ncs_rpc_notif_PROC-BASIC-INFO;
        }
      }
      container dynamic {
        description
          "Process Dynamic information";
        uses ncs_rpc_notif_PROCESSES-INFO;
      }
      container boot-stalled {
        description
          "Process Boot Stalled information";
        uses ncs_rpc_notif_PROC-BOOT-STALLED-INFO;
      }
      container processes {
        description
          "Process all information";
        uses ncs_rpc_notif_PROCESSES-INFO;
      }
      container startup {
        description
          "Process Startup information";
        uses ncs_rpc_notif_PROCESSES-INFO;
      }
      container mandatory {
        description
          "Mandatory Process information";
        uses ncs_rpc_notif_PROCESSES-INFO;
      }
      container abort {
        description
          "Process Abort information";
        uses ncs_rpc_notif_PROC-ABORT-INFO;
      }
      container failover {
        description
          "Process Failover information";
        uses ncs_rpc_notif_PROC-FAILOVER-INFO;
      }
      container boot {
        description
          "Process Boot information";
        uses ncs_rpc_notif_PROC-BOOT-INFO;
      }
      container logs {
        description
          "Process Log information";
        uses ncs_rpc_notif_LOG-INFO;
      }
      container searchpath {
        description
          "Process Searchpath information";
        uses ncs_rpc_notif_PROC-SEARCHPATH-INFO;
      }
      leaf node-name {
        type xr:Node-id;
        description
          "The node name";
      }
    }
  }

  grouping live_ncs_NODE {
    description
      "Common node of node-table, node-table";
    list node {
      key "node-name";
      description
        "Process information per node";
      container name {
        description
          "Process <WORD> information";
        container process-name-run-infos {
          description
            "Process <WORD> information";
          list process-name-run-info {
            key "proc-name";
            description
              "Process <WORD> run information";
            leaf proc-name {
              type xr:Cisco-ios-xr-string;
              description
                "Process Name";
            }
            uses live_ncs_PROC-BASIC-INFO;
          }
        }
        container process-name-infos {
          description
            "Process <WORD> information";
          list process-name-info {
            key "proc-name";
            description
              "Process <WORD> information";
            leaf proc-name {
              type xr:Cisco-ios-xr-string;
              description
                "Process Name";
            }
            uses live_ncs_PROC-BASIC-INFO;
          }
        }
        container process-name-run-details {
          description
            "Process <WORD> information";
          list process-name-run-detail {
            key "proc-name";
            description
              "Process <WORD> run detail information";
            leaf proc-name {
              type xr:Cisco-ios-xr-string;
              description
                "Process Name";
            }
            uses live_ncs_PROC-BASIC-DETAIL-INFO;
          }
        }
        container process-name-runverboses {
          description
            "Process <WORD> information";
          list process-name-runverbose {
            key "proc-name";
            description
              "Process <WORD> run verbose information";
            leaf proc-name {
              type xr:Cisco-ios-xr-string;
              description
                "Process Name";
            }
            uses live_ncs_PROC-BASIC-DETAIL-VERBOSE-INFO;
          }
        }
        container process-name-details {
          description
            "Process <WORD> information";
          list process-name-detail {
            key "proc-name";
            description
              "Process <WORD> detail information";
            leaf proc-name {
              type xr:Cisco-ios-xr-string;
              description
                "Process Name";
            }
            uses live_ncs_PROC-BASIC-DETAIL-INFO;
          }
        }
        container process-name-verboses {
          description
            "Process <WORD> information";
          list process-name-verbose {
            key "proc-name";
            description
              "Process <WORD> verbose information";
            leaf proc-name {
              type xr:Cisco-ios-xr-string;
              description
                "Process Name";
            }
            uses live_ncs_PROC-BASIC-DETAIL-VERBOSE-INFO;
          }
        }
      }
      container jids {
        description
          "Process job id information";
        list jid {
          key "job-id";
          description
            "Process <jid> information";
          leaf job-id {
            type uint32;
            description
              "Job ID";
          }
          uses live_ncs_PROC-BASIC-INFO;
        }
      }
      container dynamic {
        description
          "Process Dynamic information";
        uses live_ncs_PROCESSES-INFO;
      }
      container boot-stalled {
        description
          "Process Boot Stalled information";
        uses live_ncs_PROC-BOOT-STALLED-INFO;
      }
      container processes {
        description
          "Process all information";
        uses live_ncs_PROCESSES-INFO;
      }
      container startup {
        description
          "Process Startup information";
        uses live_ncs_PROCESSES-INFO;
      }
      container mandatory {
        description
          "Mandatory Process information";
        uses live_ncs_PROCESSES-INFO;
      }
      container abort {
        description
          "Process Abort information";
        uses live_ncs_PROC-ABORT-INFO;
      }
      container failover {
        description
          "Process Failover information";
        uses live_ncs_PROC-FAILOVER-INFO;
      }
      container boot {
        description
          "Process Boot information";
        uses live_ncs_PROC-BOOT-INFO;
      }
      container logs {
        description
          "Process Log information";
        uses live_ncs_LOG-INFO;
      }
      container searchpath {
        description
          "Process Searchpath information";
        uses live_ncs_PROC-SEARCHPATH-INFO;
      }
      leaf node-name {
        type xr:Node-id;
        description
          "The node name";
      }
    }
  }

  grouping NODE {
    description
      "Common node of node-table, node-table";
    list node {
      key "node-name";
      description
        "Process information per node";
      container name {
        description
          "Process <WORD> information";
        container process-name-run-infos {
          description
            "Process <WORD> information";
          list process-name-run-info {
            key "proc-name";
            description
              "Process <WORD> run information";
            leaf proc-name {
              type xr:Cisco-ios-xr-string;
              description
                "Process Name";
            }
            uses PROC-BASIC-INFO;
          }
        }
        container process-name-infos {
          description
            "Process <WORD> information";
          list process-name-info {
            key "proc-name";
            description
              "Process <WORD> information";
            leaf proc-name {
              type xr:Cisco-ios-xr-string;
              description
                "Process Name";
            }
            uses PROC-BASIC-INFO;
          }
        }
        container process-name-run-details {
          description
            "Process <WORD> information";
          list process-name-run-detail {
            key "proc-name";
            description
              "Process <WORD> run detail information";
            leaf proc-name {
              type xr:Cisco-ios-xr-string;
              description
                "Process Name";
            }
            uses PROC-BASIC-DETAIL-INFO;
          }
        }
        container process-name-runverboses {
          description
            "Process <WORD> information";
          list process-name-runverbose {
            key "proc-name";
            description
              "Process <WORD> run verbose information";
            leaf proc-name {
              type xr:Cisco-ios-xr-string;
              description
                "Process Name";
            }
            uses PROC-BASIC-DETAIL-VERBOSE-INFO;
          }
        }
        container process-name-details {
          description
            "Process <WORD> information";
          list process-name-detail {
            key "proc-name";
            description
              "Process <WORD> detail information";
            leaf proc-name {
              type xr:Cisco-ios-xr-string;
              description
                "Process Name";
            }
            uses PROC-BASIC-DETAIL-INFO;
          }
        }
        container process-name-verboses {
          description
            "Process <WORD> information";
          list process-name-verbose {
            key "proc-name";
            description
              "Process <WORD> verbose information";
            leaf proc-name {
              type xr:Cisco-ios-xr-string;
              description
                "Process Name";
            }
            uses PROC-BASIC-DETAIL-VERBOSE-INFO;
          }
        }
      }
      container jids {
        description
          "Process job id information";
        list jid {
          key "job-id";
          description
            "Process <jid> information";
          leaf job-id {
            type uint32;
            description
              "Job ID";
          }
          uses PROC-BASIC-INFO;
        }
      }
      container dynamic {
        description
          "Process Dynamic information";
        uses PROCESSES-INFO;
      }
      container boot-stalled {
        description
          "Process Boot Stalled information";
        uses PROC-BOOT-STALLED-INFO;
      }
      container processes {
        description
          "Process all information";
        uses PROCESSES-INFO;
      }
      container startup {
        description
          "Process Startup information";
        uses PROCESSES-INFO;
      }
      container mandatory {
        description
          "Mandatory Process information";
        uses PROCESSES-INFO;
      }
      container abort {
        description
          "Process Abort information";
        uses PROC-ABORT-INFO;
      }
      container failover {
        description
          "Process Failover information";
        uses PROC-FAILOVER-INFO;
      }
      container boot {
        description
          "Process Boot information";
        uses PROC-BOOT-INFO;
      }
      container logs {
        description
          "Process Log information";
        uses LOG-INFO;
      }
      container searchpath {
        description
          "Process Searchpath information";
        uses PROC-SEARCHPATH-INFO;
      }
      leaf node-name {
        type xr:Node-id;
        description
          "The node name";
      }
    }
  }

  augment "/ncs:devices/ncs:device/ncs:config" {
    // NCS drop config false container 'system-process'
  }
  augment "/ncs:devices/ncs:device/ncs:live-status" {
    container system-process {
      tailf:ncs-device-type "netconf";
      tailf:display-when "not(../../ncs:module) or ../../ncs:module[ncs:name='Cisco-IOS-XR-sysmgr-oper'] or (../../ncs:live-status-protocol[not(ncs:capability)]) or (../../ncs:live-status-protocol/ncs:capability/ncs:module[.='Cisco-IOS-XR-sysmgr-oper'])";
      description
        "Process information";
      container node-table {
        description
          "List of nodes";
        uses live_ncs_NODE;
      }
    }
  }
  augment "/ncs:devices/ncs:template/ncs:ned-id/ncs:config" {
    // NCS drop config false container 'system-process'
  }
}
