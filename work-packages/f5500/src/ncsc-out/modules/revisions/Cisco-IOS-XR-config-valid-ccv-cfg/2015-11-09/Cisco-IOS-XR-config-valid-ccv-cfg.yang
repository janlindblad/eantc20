module Cisco-IOS-XR-config-valid-ccv-cfg {
  // Generated by yanger -t ncs
  tailf:mount-id f5500-nc-1.0:f5500-nc-1.0;
  tailf:ncs-device-type "netconf";

  namespace "http://cisco.com/ns/yang/Cisco-IOS-XR-config-valid-ccv-cfg";
  prefix Cisco-IOS-XR-config-valid-ccv-cfg;

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR config-valid-ccv package configuration.

     This module contains definitions
     for the following management objects:
       configurationvalidation: Configuration for the Configuration
         Validation feature

     Copyright (c) 2013-2018 by Cisco Systems, Inc.
     All rights reserved.";

  revision 2015-11-09 {
    description
      "IOS XR 6.0 revision.";
  }

  typedef Failure {
    type enumeration {
      enum "unsupported" {
        value 0;
        description
          "Unsupported failure type";
      }
    }
    description
      "Failure";
  }

  typedef Failure-action {
    type enumeration {
      enum "report" {
        value 1;
        description
          "Report this failure type";
      }
    }
    description
      "Failure action";
  }

  augment "/ncs:devices/ncs:device/ncs:config" {
    container configurationvalidation {
      tailf:ncs-device-type "netconf";
      tailf:display-when "not(../../ncs:module) or ../../ncs:module[ncs:name='Cisco-IOS-XR-config-valid-ccv-cfg']";
      description
        "Configuration for the Configuration Validation
         feature";
      container failure-type-actions {
        description
          "Table for failure type actions";
        list failure-type-action {
          key "failure";
          description
            "Failure type action configuration";
          leaf action {
            type Failure-action;
            description
              "Action configuration for this failure type";
          }
          leaf failure {
            type Failure;
            description
              "Failure type";
          }
        }
      }
      leaf enable {
        type empty;
        description
          "Enable configuration validation";
      }
    }
  }
  augment "/ncs:devices/ncs:device/ncs:live-status" {
    container configurationvalidation {
      tailf:ncs-device-type "netconf";
      tailf:display-when "not(../../ncs:module) or ../../ncs:module[ncs:name='Cisco-IOS-XR-config-valid-ccv-cfg'] or (../../ncs:live-status-protocol[not(ncs:capability)]) or (../../ncs:live-status-protocol/ncs:capability/ncs:module[.='Cisco-IOS-XR-config-valid-ccv-cfg'])";
      description
        "Configuration for the Configuration Validation
         feature";
      container failure-type-actions {
        description
          "Table for failure type actions";
        list failure-type-action {
          key "failure";
          description
            "Failure type action configuration";
          leaf action {
            type Failure-action;
            description
              "Action configuration for this failure type";
          }
          leaf failure {
            type Failure;
            description
              "Failure type";
          }
        }
      }
      leaf enable {
        type empty;
        description
          "Enable configuration validation";
      }
    }
  }
  augment "/ncs:devices/ncs:template/ncs:ned-id/ncs:config" {
    container configurationvalidation {
      description
        "Configuration for the Configuration Validation
         feature";
      container failure-type-actions {
        description
          "Table for failure type actions";
        list failure-type-action {
          // NCS patched for predictable order
          ordered-by user;
          key "failure";
          description
            "Failure type action configuration";
          leaf action {
            type string;
            description
              "Action configuration for this failure type";
          }
          leaf failure {
            type string;
            description
              "Failure type";
          }
        }
      }
      leaf enable {
        type empty;
        description
          "Enable configuration validation";
      }
    }
  }
}
