module Cisco-IOS-XR-config-cfgmgr-cfg {
  // Generated by yanger -t ncs
  tailf:mount-id f5500-nc-1.0:f5500-nc-1.0;
  tailf:ncs-device-type "netconf";

  namespace "http://cisco.com/ns/yang/Cisco-IOS-XR-config-cfgmgr-cfg";
  prefix Cisco-IOS-XR-config-cfgmgr-cfg;

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR config-cfgmgr package configuration.

     This module contains definitions
     for the following management objects:
       cfgmgr: Cfgmgr configuration

     Copyright (c) 2013-2018 by Cisco Systems, Inc.
     All rights reserved.";

  revision 2015-11-09 {
    description
      "IOS XR 6.0 revision.";
  }

  augment "/ncs:devices/ncs:device/ncs:config" {
    container cfgmgr {
      tailf:ncs-device-type "netconf";
      tailf:display-when "not(../../ncs:module) or ../../ncs:module[ncs:name='Cisco-IOS-XR-config-cfgmgr-cfg']";
      description
        "Cfgmgr configuration";
      leaf mode-exclusive {
        type boolean;
        default "true";
        description
          "Enabled or Disabled";
      }
    }
  }
  augment "/ncs:devices/ncs:device/ncs:live-status" {
    container cfgmgr {
      tailf:ncs-device-type "netconf";
      tailf:display-when "not(../../ncs:module) or ../../ncs:module[ncs:name='Cisco-IOS-XR-config-cfgmgr-cfg'] or (../../ncs:live-status-protocol[not(ncs:capability)]) or (../../ncs:live-status-protocol/ncs:capability/ncs:module[.='Cisco-IOS-XR-config-cfgmgr-cfg'])";
      description
        "Cfgmgr configuration";
      leaf mode-exclusive {
        type boolean;
        // NCS drop default statement
        description
          "Enabled or Disabled";
      }
    }
  }
  augment "/ncs:devices/ncs:template/ncs:ned-id/ncs:config" {
    container cfgmgr {
      description
        "Cfgmgr configuration";
      leaf mode-exclusive {
        type string;
        // NCS drop default statement
        description
          "Enabled or Disabled";
      }
    }
  }
}
