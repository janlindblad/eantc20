module Cisco-IOS-XR-infra-xtc-agent-oper {
  // Generated by yanger -t ncs
  tailf:mount-id f5500-nc-1.0:f5500-nc-1.0;
  tailf:ncs-device-type "netconf";

  namespace "http://cisco.com/ns/yang/Cisco-IOS-XR-infra-xtc-agent-oper";
  prefix Cisco-IOS-XR-infra-xtc-agent-oper;

  import ietf-inet-types {
    prefix inet;
  }
  import Cisco-IOS-XR-types {
    prefix xr;
  }
  include Cisco-IOS-XR-infra-xtc-agent-oper-sub2 {
    revision-date 2018-11-28;
  }
  include Cisco-IOS-XR-infra-xtc-agent-oper-sub1 {
    revision-date 2018-11-28;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR infra-xtc-agent package operational data.

     This module contains definitions
     for the following management objects:
       pcc: Path-computation client in XTC
       xtc: xtc

     Copyright (c) 2013-2018 by Cisco Systems, Inc.
     All rights reserved.";

  revision 2018-11-28 {
    description
      "Various modifications to policy-related models for better compatibility with the IETF policy draft.";
  }
  revision 2017-09-11 {
    description
      "Initial version";
  }
  revision 2015-11-09 {
    description
      "IOS XR 6.0 revision.";
  }

  typedef Xtc-address-family {
    type enumeration {
      enum "ipv4" {
        value 1;
        description
          "IPv4 address family";
      }
      enum "ipv6" {
        value 2;
        description
          "IPv6 address family";
      }
    }
    description
      "Xtc address family";
  }

  typedef Xtcigp-protocol {
    type enumeration {
      enum "unknown" {
        value 0;
        description
          "Unknown protocol";
      }
      enum "isis" {
        value 1;
        description
          "ISIS protocol";
      }
      enum "ospf" {
        value 2;
        description
          "OSPF protocol";
      }
      enum "bgp" {
        value 4;
        description
          "BGP protocol";
      }
      enum "te" {
        value 8;
        description
          "TE protocol";
      }
    }
    description
      "Xtcigp protocol";
  }

  augment "/ncs:devices/ncs:device/ncs:config" {
    // NCS drop config false container pcc
    // NCS drop config false container xtc
  }
  augment "/ncs:devices/ncs:device/ncs:live-status" {
    container pcc {
      tailf:ncs-device-type "netconf";
      tailf:display-when "not(../../ncs:module) or ../../ncs:module[ncs:name='Cisco-IOS-XR-infra-xtc-agent-oper'] or (../../ncs:live-status-protocol[not(ncs:capability)]) or (../../ncs:live-status-protocol/ncs:capability/ncs:module[.='Cisco-IOS-XR-infra-xtc-agent-oper'])";
      description
        "Path-computation client in XTC";
      container plsps {
        description
          "PCC PLSP database in XTC";
        list plsp {
          key "plsp-id";
          description
            "PCC PLSP information";
          leaf plsp-id {
            type uint32;
            description
              "PLSP ID";
          }
          uses live_ncs_PCEP-PLSP-BAG;
        }
      }
      container peers {
        description
          "PCC peer database in XTC";
        list peer {
          key "peer-addr";
          description
            "PCC peer information";
          leaf peer-addr {
            type inet:ip-address-no-zone;
            description
              "Peer Address";
          }
          uses live_ncs_PCEP-CONN-BAG;
        }
      }
    }
    container xtc {
      tailf:ncs-device-type "netconf";
      tailf:display-when "not(../../ncs:module) or ../../ncs:module[ncs:name='Cisco-IOS-XR-infra-xtc-agent-oper'] or (../../ncs:live-status-protocol[not(ncs:capability)]) or (../../ncs:live-status-protocol/ncs:capability/ncs:module[.='Cisco-IOS-XR-infra-xtc-agent-oper'])";
      description
        "xtc";
      container policies {
        description
          "Policy database in XTC Agent";
        list policy {
          key "id";
          description
            "Policy information";
          leaf id {
            type uint32;
            description
              "Policy ID";
          }
          uses live_ncs_XTC-POLICY-BAG;
        }
      }
      container policy-forwardings {
        description
          "Forwarding information for policies";
        list policy-forwarding {
          key "name";
          description
            "Forwarding information for the policy";
          leaf name {
            type xr:Cisco-ios-xr-string;
            description
              "Policy Name";
          }
          uses live_ncs_XTC-FWDING-POLICY-BAG;
        }
      }
      container policy-summary {
        description
          "Summary of all policies";
        uses live_ncs_XTC-POLICY-SUMMARY-BAG;
      }
      container on-demand-colors {
        description
          "On-Demand Color database in XTC Agent";
        list on-demand-color {
          key "color";
          description
            "On Demand Color information";
          leaf color {
            type uint32;
            description
              "Color";
          }
          uses live_ncs_XTC-ON-DEMAND-COLOR-BAG;
        }
      }
      container controller {
        description
          "Controller information";
        container policy-requests {
          description
            "Table containing policy requests";
          list policy-request {
            key "source-address end-point-type end-point-address color route-distinguisher";
            description
              "Policy request information";
            leaf source-address {
              type inet:ip-address-no-zone;
              description
                "Source Address";
            }
            leaf end-point-type {
              type Xtc-address-family;
              description
                "Endpoint Address Type";
            }
            leaf end-point-address {
              type inet:ip-address-no-zone;
              description
                "Endpoint Address";
            }
            leaf color {
              type uint32 {
                range "1..4294967295";
              }
              description
                "Color";
            }
            leaf route-distinguisher {
              type uint32 {
                range "0..4294967295";
              }
              description
                "Route Distinguisher";
            }
            uses live_ncs_XTC-CONTROLLER-POLICY-REQ-BAG;
          }
        }
      }
      container topology-nodes {
        description
          "Node database in XTC Agent";
        list topology-node {
          key "node-identifier";
          description
            "Node information";
          leaf node-identifier {
            type uint32;
            description
              "Node Identifier";
          }
          uses live_ncs_XTC-TOPO-NODE-BAG;
        }
      }
      container topology-summaries {
        description
          "Node summary table";
        list topology-summary {
          description
            "Node summary database";
          leaf af {
            type Xtc-address-family;
            description
              "Only show data related to the specified
               address family";
          }
          leaf protocol {
            type Xtcigp-protocol;
            description
              "Match nodes from the specified IGP protocol";
          }
          uses live_ncs_XTC-TOPO-SUMMARY-BAG;
        }
      }
      container prefix-infos {
        description
          "Prefixes database in XTC Agent";
        list prefix-info {
          key "node-identifier";
          description
            "Prefix information";
          leaf node-identifier {
            type uint32;
            description
              "Node ID";
          }
          uses live_ncs_XTC-PFX-BAG;
        }
      }
    }
  }
  augment "/ncs:devices/ncs:template/ncs:ned-id/ncs:config" {
    // NCS drop config false container pcc
    // NCS drop config false container xtc
  }
}
