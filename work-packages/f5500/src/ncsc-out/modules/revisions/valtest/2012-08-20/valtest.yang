module valtest {
  // Generated by yanger -t ncs
  tailf:mount-id f5500-nc-1.0:f5500-nc-1.0;
  tailf:ncs-device-type "netconf";

  namespace "http://www.cisco.com/panini/calvados/valtest";
  prefix valtest;

  import "f5500-nc-1.0" {
    prefix "f5500-nc-1.0";
  }
  import tailf-ncs {
    prefix ncs;
  }
  import tailf-common {
    prefix tailf;
  }

  organization
    "Cisco Systems Inc.";
  contact
    "conger@cisco.com";
  description
    "This module contains definitions
     for the Calvados model objects.

     This module holds a sample validation.

     Copyright (c) 2012-2018 by Cisco Systems, Inc.
     All rights reserved.";

  revision 2012-08-20 {
    description
      "Initial revision";
  }

  augment "/ncs:devices/ncs:device/ncs:config" {
    container config {
      tailf:ncs-device-type "netconf";
      tailf:display-when "not(../../ncs:module) or ../../ncs:module[ncs:name='valtest']";
      // NCS dropped explicit config true
      container valtest {
        leaf a_number {
          type int64;
          default "42";
        }
        leaf b_number {
          type int64;
          default "7";
        }
      }
    }
  }
  augment "/ncs:devices/ncs:device/ncs:live-status" {
    container config {
      tailf:ncs-device-type "netconf";
      tailf:display-when "not(../../ncs:module) or ../../ncs:module[ncs:name='valtest'] or (../../ncs:live-status-protocol[not(ncs:capability)]) or (../../ncs:live-status-protocol/ncs:capability/ncs:module[.='valtest'])";
      container valtest {
        leaf a_number {
          type int64;
          // NCS drop default statement
        }
        leaf b_number {
          type int64;
          // NCS drop default statement
        }
      }
    }
  }
  augment "/ncs:devices/ncs:template/ncs:ned-id/ncs:config" {
    container config {
      // NCS dropped explicit config true
      container valtest {
        leaf a_number {
          type string;
          // NCS drop default statement
        }
        leaf b_number {
          type string;
          // NCS drop default statement
        }
      }
    }
  }
}
