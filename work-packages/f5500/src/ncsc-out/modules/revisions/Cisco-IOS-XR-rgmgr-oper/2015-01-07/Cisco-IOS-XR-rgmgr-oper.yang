module Cisco-IOS-XR-rgmgr-oper {
  // Generated by yanger -t ncs
  tailf:mount-id f5500-nc-1.0:f5500-nc-1.0;
  tailf:ncs-device-type "netconf";

  namespace "http://cisco.com/ns/yang/Cisco-IOS-XR-rgmgr-oper";
  prefix Cisco-IOS-XR-rgmgr-oper;

  import Cisco-IOS-XR-types {
    prefix xr;
  }
  include Cisco-IOS-XR-rgmgr-oper-sub1 {
    revision-date 2015-01-07;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR rgmgr package operational data.

     This module contains definitions
     for the following management objects:
       redundancy-group-manager: Redundancy group manager operational
         data

     Copyright (c) 2013-2018 by Cisco Systems, Inc.
     All rights reserved.";

  revision 2015-01-07 {
    description
      "IOS XR 5.3.1 revision.";
  }

  augment "/ncs:devices/ncs:device/ncs:config" {
    // NCS drop config false container 'redundancy-group-manager'
  }
  augment "/ncs:devices/ncs:device/ncs:live-status" {
    container redundancy-group-manager {
      tailf:ncs-device-type "netconf";
      tailf:display-when "not(../../ncs:module) or ../../ncs:module[ncs:name='Cisco-IOS-XR-rgmgr-oper'] or (../../ncs:live-status-protocol[not(ncs:capability)]) or (../../ncs:live-status-protocol/ncs:capability/ncs:module[.='Cisco-IOS-XR-rgmgr-oper'])";
      description
        "Redundancy group manager operational data";
      container controllers {
        description
          "Redundancy group manager data";
        list controller {
          key "controller-name";
          description
            "Display redundancy group by controller name";
          leaf controller-name {
            type xr:Interface-name;
            description
              "Controller name";
          }
          uses live_ncs_RGMGR-RED-GRP;
        }
      }
    }
  }
  augment "/ncs:devices/ncs:template/ncs:ned-id/ncs:config" {
    // NCS drop config false container 'redundancy-group-manager'
  }
}
