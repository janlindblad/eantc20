module Cisco-IOS-XR-sysadmin-show-inv {
  // Generated by yanger -t ncs
  tailf:mount-id f5500-nc-1.0:f5500-nc-1.0;
  tailf:ncs-device-type "netconf";

  namespace "http://www.cisco.com/ns/yang/Cisco-IOS-XR-sysadmin-show-inv";
  prefix Cisco-IOS-XR-sysadmin-show-inv;

  import "f5500-nc-1.0" {
    prefix "f5500-nc-1.0";
  }
  import tailf-ncs {
    prefix ncs;
  }
  import tailf-common {
    prefix tailf;
  }

  organization
    "Cisco Systems Inc.";
  contact
    "Cisco Systems, Inc.
     Customer Service

     Postal: 170 West Tasman Drive
     San Jose, CA 95134

     Tel: +1 800 553-NETS

     E-mail: cs-yang@cisco.com";
  description
    "This module contains definitions
     for the Calvados model objects.

     This module contains a collection of YANG
     definitions for Cisco IOS-XR SysAdmin configuration.

     Calvados Inventory Service maintain entity database

     Copyright(c) 2011-2017 by Cisco Systems, Inc.
     All rights reserved.

     Copyright (c) 2012-2018 by Cisco Systems, Inc.
     All rights reserved.";

  revision 2017-04-12 {
    description
      "Changed the namespace and module name";
  }

  grouping ncs_template_target_str {
    leaf name {
      type string;
      description
        "Name of the entity";
    }
    leaf Description {
      type string;
      description
        "Description of the entity";
    }
    leaf PID {
      type string;
      description
        "Product ID of the entity";
    }
    leaf VID {
      type string;
      description
        "Version ID of the entity";
    }
    leaf SN {
      type string;
      description
        "Serial Numbe of the entity";
    }
    leaf loc {
      type string;
      description
        "Node id of the entity";
    }
    leaf index {
      type string;
      description
        "Index for the entity";
    }
  }

  grouping ncs_template_inv-loc {
    list location {
      // NCS patched for predictable order
      ordered-by user;
      key "loc";
      uses ncs_template_target_str;
    }
  }

  grouping ncs_template_inv-all {
    list all {
      // NCS patched for predictable order
      ordered-by user;
      key "index";
      uses ncs_template_target_str;
    }
  }

  grouping ncs_template_inv-chassis {
    list chassis {
      // NCS patched for predictable order
      ordered-by user;
      key "index";
      uses ncs_template_target_str;
    }
  }

  grouping ncs_template_inv-power {
    list power {
      // NCS patched for predictable order
      ordered-by user;
      key "index";
      uses ncs_template_target_str;
    }
  }

  grouping ncs_template_inv-fan {
    list fan {
      // NCS patched for predictable order
      ordered-by user;
      key "index";
      uses ncs_template_target_str;
    }
  }

  grouping ncs_template_inv-raw {
    list raw {
      // NCS patched for predictable order
      ordered-by user;
      key "index";
      uses ncs_template_target_str;
    }
  }

  grouping ncs_rpc_notif_target_str {
    leaf name {
      type string;
      description
        "Name of the entity";
    }
    leaf Description {
      type string;
      description
        "Description of the entity";
    }
    leaf PID {
      type string;
      description
        "Product ID of the entity";
    }
    leaf VID {
      type string;
      description
        "Version ID of the entity";
    }
    leaf SN {
      type string;
      description
        "Serial Numbe of the entity";
    }
    leaf loc {
      type string;
      description
        "Node id of the entity";
    }
    leaf index {
      type uint32;
      description
        "Index for the entity";
    }
  }

  grouping ncs_rpc_notif_inv-loc {
    list location {
      key "loc";
      uses ncs_rpc_notif_target_str;
    }
  }

  grouping ncs_rpc_notif_inv-all {
    list all {
      key "index";
      uses ncs_rpc_notif_target_str;
    }
  }

  grouping ncs_rpc_notif_inv-chassis {
    list chassis {
      key "index";
      uses ncs_rpc_notif_target_str;
    }
  }

  grouping ncs_rpc_notif_inv-power {
    list power {
      key "index";
      uses ncs_rpc_notif_target_str;
    }
  }

  grouping ncs_rpc_notif_inv-fan {
    list fan {
      key "index";
      uses ncs_rpc_notif_target_str;
    }
  }

  grouping ncs_rpc_notif_inv-raw {
    list raw {
      key "index";
      uses ncs_rpc_notif_target_str;
    }
  }

  grouping live_ncs_target_str {
    leaf name {
      type string;
      description
        "Name of the entity";
    }
    leaf Description {
      type string;
      description
        "Description of the entity";
    }
    leaf PID {
      type string;
      description
        "Product ID of the entity";
    }
    leaf VID {
      type string;
      description
        "Version ID of the entity";
    }
    leaf SN {
      type string;
      description
        "Serial Numbe of the entity";
    }
    leaf loc {
      type string;
      description
        "Node id of the entity";
    }
    leaf index {
      type uint32;
      description
        "Index for the entity";
    }
  }

  grouping live_ncs_inv-loc {
    list location {
      key "loc";
      uses live_ncs_target_str;
    }
  }

  grouping live_ncs_inv-all {
    list all {
      key "index";
      uses live_ncs_target_str;
    }
  }

  grouping live_ncs_inv-chassis {
    list chassis {
      key "index";
      uses live_ncs_target_str;
    }
  }

  grouping live_ncs_inv-power {
    list power {
      key "index";
      uses live_ncs_target_str;
    }
  }

  grouping live_ncs_inv-fan {
    list fan {
      key "index";
      uses live_ncs_target_str;
    }
  }

  grouping live_ncs_inv-raw {
    list raw {
      key "index";
      uses live_ncs_target_str;
    }
  }

  grouping target_str {
    leaf name {
      type string;
      description
        "Name of the entity";
    }
    leaf Description {
      type string;
      description
        "Description of the entity";
    }
    leaf PID {
      type string;
      description
        "Product ID of the entity";
    }
    leaf VID {
      type string;
      description
        "Version ID of the entity";
    }
    leaf SN {
      type string;
      description
        "Serial Numbe of the entity";
    }
    leaf loc {
      type string;
      description
        "Node id of the entity";
    }
    leaf index {
      type uint32;
      description
        "Index for the entity";
    }
  }

  grouping inv-loc {
    list location {
      key "loc";
      uses target_str;
    }
  }

  grouping inv-all {
    list all {
      key "index";
      uses target_str;
    }
  }

  grouping inv-chassis {
    list chassis {
      key "index";
      uses target_str;
    }
  }

  grouping inv-power {
    list power {
      key "index";
      uses target_str;
    }
  }

  grouping inv-fan {
    list fan {
      key "index";
      uses target_str;
    }
  }

  grouping inv-raw {
    list raw {
      key "index";
      uses target_str;
    }
  }

  augment "/ncs:devices/ncs:device/ncs:config" {
    // NCS drop config false container inventory
  }
  augment "/ncs:devices/ncs:device/ncs:live-status" {
    container inventory {
      tailf:ncs-device-type "netconf";
      tailf:display-when "not(../../ncs:module) or ../../ncs:module[ncs:name='Cisco-IOS-XR-sysadmin-show-inv'] or (../../ncs:live-status-protocol[not(ncs:capability)]) or (../../ncs:live-status-protocol/ncs:capability/ncs:module[.='Cisco-IOS-XR-sysadmin-show-inv'])";
      description
        "show inventory";
      uses live_ncs_inv-loc;
      uses live_ncs_inv-all;
      uses live_ncs_inv-chassis;
      uses live_ncs_inv-power;
      uses live_ncs_inv-fan;
      uses live_ncs_inv-raw;
    }
  }
  augment "/ncs:devices/ncs:template/ncs:ned-id/ncs:config" {
    // NCS drop config false container inventory
  }
}
