module Cisco-IOS-XR-sysadmin-nto-misc-set-hostname {
  // Generated by yanger -t ncs
  tailf:mount-id f5500-nc-1.0:f5500-nc-1.0;
  tailf:ncs-device-type "netconf";

  namespace "http://www.cisco.com/ns/yang/Cisco-IOS-XR-sysadmin-nto-misc-set-hostname";
  prefix Cisco-IOS-XR-sysadmin-nto-misc-set-hostname;

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains definitions
     for the Calvados model objects.

     This module contains a collection of YANG definitions
     for Cisco IOS-XR syadmin hostname configuration and cli.

     This module contains definitions
     for the following management objects:
     hostname cli and configuration data

     Copyright (c) 2017 by Cisco Systems, Inc.
     All rights reserved.

     Copyright (c) 2012-2018 by Cisco Systems, Inc.
     All rights reserved.";

  revision 2017-04-12 {
    description
      "Initial version.";
  }

  augment "/ncs:devices/ncs:device/ncs:config" {
    container hostname {
      tailf:ncs-device-type "netconf";
      tailf:display-when "not(../../ncs:module) or ../../ncs:module[ncs:name='Cisco-IOS-XR-sysadmin-nto-misc-set-hostname']";
      description
        "Set system`s network name";
      leaf name {
        type string {
          length "1..255";
          pattern '[a-zA-Z0-9_.{}+-]+';
        }
      }
    }
  }
  augment "/ncs:devices/ncs:device/ncs:live-status" {
    container hostname {
      tailf:ncs-device-type "netconf";
      tailf:display-when "not(../../ncs:module) or ../../ncs:module[ncs:name='Cisco-IOS-XR-sysadmin-nto-misc-set-hostname'] or (../../ncs:live-status-protocol[not(ncs:capability)]) or (../../ncs:live-status-protocol/ncs:capability/ncs:module[.='Cisco-IOS-XR-sysadmin-nto-misc-set-hostname'])";
      description
        "Set system`s network name";
      leaf name {
        type string {
          length "1..255";
          pattern '[a-zA-Z0-9_.{}+-]+';
        }
      }
    }
  }
  augment "/ncs:devices/ncs:template/ncs:ned-id/ncs:config" {
    container hostname {
      description
        "Set system`s network name";
      leaf name {
        type string;
      }
    }
  }
}
