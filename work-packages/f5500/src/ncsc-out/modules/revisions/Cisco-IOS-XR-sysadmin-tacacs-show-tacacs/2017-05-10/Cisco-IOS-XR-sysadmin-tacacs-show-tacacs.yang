module Cisco-IOS-XR-sysadmin-tacacs-show-tacacs {
  // Generated by yanger -t ncs
  tailf:mount-id f5500-nc-1.0:f5500-nc-1.0;
  tailf:ncs-device-type "netconf";

  namespace "http://www.cisco.com/ns/yang/Cisco-IOS-XR-sysadmin-tacacs-show-tacacs";
  prefix Cisco-IOS-XR-sysadmin-tacacs-show-tacacs;

  import tailf-common {
    prefix tailf;
  }
  import ietf-inet-types {
    prefix inet;
  }
  import Cisco-IOS-XR-sysadmin-tacacs-tacacs-server {
    prefix tacacs-server;
  }
  import "f5500-nc-1.0" {
    prefix "f5500-nc-1.0";
  }
  import tailf-ncs {
    prefix ncs;
  }

  organization
    "Cisco Systems Inc.";
  contact
    "aaa-ng-tacacs-dev@cisco.com";
  description
    "This module contains definitions
     for the Calvados model objects.

     This module defines yang model
     for displaying tacacs+ server host info

     Copyright (c) 2012-2018 by Cisco Systems, Inc.
     All rights reserved.";

  revision 2017-05-10 {
    description
      "Namespace changed from show_tacacs to Cisco-IOS-XR-sysadmin-tacacs-show-tacacs";
  }

  typedef passwdStr {
    type tailf:md5-digest-string;
  }

  augment "/ncs:devices/ncs:template/ncs:ned-id/ncs:config/tacacs-server:tacacs-server" {
    // NCS drop config false container requests
  }
  augment "/ncs:devices/ncs:device/ncs:live-status/tacacs-server:tacacs-server" {
    container requests {
      tailf:ncs-device-type "netconf";
      tailf:display-when "not(../../../ncs:module) or ../../../ncs:module[ncs:name='Cisco-IOS-XR-sysadmin-tacacs-show-tacacs'] or (../../../ncs:live-status-protocol[not(ncs:capability)]) or (../../../ncs:live-status-protocol/ncs:capability/ncs:module[.='Cisco-IOS-XR-sysadmin-tacacs-show-tacacs'])";
      list ipv4 {
        key "addr port";
        leaf addr {
          description
            "Server IPv4 address";
          type inet:ip-address;
        }
        leaf port {
          description
            "Server Port";
          type inet:port-number;
        }
        leaf opens {
          description
            "Socket open count";
          type uint32;
        }
        leaf closes {
          description
            "Socket close count";
          type uint32;
        }
        leaf aborts {
          description
            "Socket abort count";
          type uint32;
        }
        leaf errors {
          description
            "Socket error count";
          type uint32;
        }
        leaf packets_in {
          description
            "Packets received count";
          type uint32;
        }
        leaf packets_out {
          description
            "Packets transmitted count";
          type uint32;
        }
      }
    }
  }
  augment "/ncs:devices/ncs:device/ncs:config/tacacs-server:tacacs-server" {
    // NCS drop config false container requests
  }
}
