submodule Cisco-IOS-XR-tty-server-oper-sub5 {
  // Generated by yanger -t ncs
  tailf:mount-id f5500-nc-1.0:f5500-nc-1.0;

  belongs-to Cisco-IOS-XR-tty-server-oper {
    prefix Cisco-IOS-XR-tty-server-oper-sub5;
  }

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR tty-server package operational data.

     Copyright (c) 2013-2018 by Cisco Systems, Inc.
     All rights reserved.";

  revision 2017-09-07 {
    description
      "Fixed type translation error.";
  }
  revision 2015-07-30 {
    description
      "Descriptions updated.";
  }
  revision 2015-01-07 {
    description
      "IOS XR 5.3.1 revision.";
  }

  grouping ncs_template_TTY-RS232-STATS {
    description
      "RS232 TTY statistics";
    leaf data-bits {
      type string;
      units "bit";
      description
        "Number of databits";
    }
    leaf exec-disabled {
      type string;
      description
        "Exec disabled on TTY";
    }
    leaf hardware-flow-control-status {
      type string;
      description
        "Hardware flow control status";
    }
    leaf parity-status {
      type string;
      description
        "Parity status";
    }
    leaf baud-rate {
      type string;
      units "bit/s";
      description
        "Inbound/Outbound baud rate in bps";
    }
    leaf stop-bits {
      type string;
      units "bit";
      description
        "Number of stopbits";
    }
    leaf overrun-error-count {
      type string;
      description
        "Overrun error count";
    }
    leaf framing-error-count {
      type string;
      description
        "Framing error count";
    }
    leaf parity-error-count {
      type string;
      description
        "Parity error count";
    }
  }

  grouping ncs_rpc_notif_TTY-RS232-STATS {
    description
      "RS232 TTY statistics";
    leaf data-bits {
      type uint32;
      units "bit";
      description
        "Number of databits";
    }
    leaf exec-disabled {
      type boolean;
      description
        "Exec disabled on TTY";
    }
    leaf hardware-flow-control-status {
      type uint32;
      description
        "Hardware flow control status";
    }
    leaf parity-status {
      type uint32;
      description
        "Parity status";
    }
    leaf baud-rate {
      type uint32;
      units "bit/s";
      description
        "Inbound/Outbound baud rate in bps";
    }
    leaf stop-bits {
      type uint32;
      units "bit";
      description
        "Number of stopbits";
    }
    leaf overrun-error-count {
      type uint32;
      description
        "Overrun error count";
    }
    leaf framing-error-count {
      type uint32;
      description
        "Framing error count";
    }
    leaf parity-error-count {
      type uint32;
      description
        "Parity error count";
    }
  }

  grouping live_ncs_TTY-RS232-STATS {
    description
      "RS232 TTY statistics";
    leaf data-bits {
      type uint32;
      units "bit";
      description
        "Number of databits";
    }
    leaf exec-disabled {
      type boolean;
      description
        "Exec disabled on TTY";
    }
    leaf hardware-flow-control-status {
      type uint32;
      description
        "Hardware flow control status";
    }
    leaf parity-status {
      type uint32;
      description
        "Parity status";
    }
    leaf baud-rate {
      type uint32;
      units "bit/s";
      description
        "Inbound/Outbound baud rate in bps";
    }
    leaf stop-bits {
      type uint32;
      units "bit";
      description
        "Number of stopbits";
    }
    leaf overrun-error-count {
      type uint32;
      description
        "Overrun error count";
    }
    leaf framing-error-count {
      type uint32;
      description
        "Framing error count";
    }
    leaf parity-error-count {
      type uint32;
      description
        "Parity error count";
    }
  }

  grouping TTY-RS232-STATS {
    description
      "RS232 TTY statistics";
    leaf data-bits {
      type uint32;
      units "bit";
      description
        "Number of databits";
    }
    leaf exec-disabled {
      type boolean;
      description
        "Exec disabled on TTY";
    }
    leaf hardware-flow-control-status {
      type uint32;
      description
        "Hardware flow control status";
    }
    leaf parity-status {
      type uint32;
      description
        "Parity status";
    }
    leaf baud-rate {
      type uint32;
      units "bit/s";
      description
        "Inbound/Outbound baud rate in bps";
    }
    leaf stop-bits {
      type uint32;
      units "bit";
      description
        "Number of stopbits";
    }
    leaf overrun-error-count {
      type uint32;
      description
        "Overrun error count";
    }
    leaf framing-error-count {
      type uint32;
      description
        "Framing error count";
    }
    leaf parity-error-count {
      type uint32;
      description
        "Parity error count";
    }
  }
}
