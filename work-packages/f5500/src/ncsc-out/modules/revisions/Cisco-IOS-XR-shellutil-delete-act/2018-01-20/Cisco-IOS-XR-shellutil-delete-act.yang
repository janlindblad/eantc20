module Cisco-IOS-XR-shellutil-delete-act {
  // Generated by yanger -t ncs
  tailf:mount-id f5500-nc-1.0:f5500-nc-1.0;
  tailf:ncs-device-type "netconf";

  namespace "http://cisco.com/ns/yang/Cisco-IOS-XR-shellutil-delete-act";
  prefix Cisco-IOS-XR-shellutil-delete-act;

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2016, 2018 by Cisco Systems, Inc.
     All rights reserved.";

  revision 2018-01-20 {
    description
      "IOS XR 7.0.1 revision.";
  }

  augment "/ncs:devices/ncs:device/ncs:rpc" {
    container rpc-delete {
      tailf:ncs-device-type "netconf";
      tailf:display-when "not(../../ncs:module) or ../../ncs:module[ncs:name='Cisco-IOS-XR-shellutil-delete-act']";
      tailf:action delete {
        tailf:actionpoint ncsproxy {
          tailf:internal;
        }
        input {
          leaf name {
            type string;
            description
              "file name";
            mandatory true;
          }
          leaf location {
            type string;
            description
              "location";
          }
          leaf recurse {
            type boolean;
            description
              "Files in dir";
          }
        }
        output {
          leaf response {
            type string;
            description
              "Status of delete operation";
          }
        }
      }
    }
  }
  augment "/ncs:devices/ncs:device-group/ncs:ned-id/ncs:rpc" {
    container rpc-delete {
      tailf:ncs-device-type "netconf";
      tailf:display-when "/ncs:devices/ncs:device[ncs:name=current()/../../../ncs:member]/ncs:module[ncs:name='Cisco-IOS-XR-shellutil-delete-act']";
      tailf:action delete {
        tailf:actionpoint ncsproxy {
          tailf:internal;
        }
        input {
          leaf name {
            type string;
            description
              "file name";
            mandatory true;
          }
          leaf location {
            type string;
            description
              "location";
          }
          leaf recurse {
            type boolean;
            description
              "Files in dir";
          }
        }
        output {
          container "device" {
            leaf "name" {
              type string;
            }
            leaf "info" {
              type string;
            }
            container "result" {
              leaf response {
                type string;
                description
                  "Status of delete operation";
              }
            }
          }
        }
      }
    }
  }
}
