module Cisco-IOS-XR-sysadmin-fabric-mgr-fgid {
  // Generated by yanger -t ncs
  tailf:mount-id f5500-nc-1.0:f5500-nc-1.0;
  tailf:ncs-device-type "netconf";

  namespace "http://www.cisco.com/ns/yang/Cisco-IOS-XR-sysadmin-fabric-mgr-fgid";
  prefix Cisco-IOS-XR-sysadmin-fabric-mgr-fgid;

  import Cisco-IOS-XR-sysadmin-fabric-types {
    prefix fabric-types;
  }
  import Cisco-IOS-XR-sysadmin-show-trace {
    prefix show-trace;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains definitions
     for the Calvados model objects.

     Copyright (c) 2012-2018 by Cisco Systems, Inc.
     All rights reserved.";

  revision 2018-04-09 {
    description
      "Required changes for ConfD 6.4.5";
  }

  grouping ncs_template_fgid_conf_resource {
    container fgid {
      container resource {
        container sdr {
          container allocation {
            leaf percent {
              type string;
            }
          }
        }
      }
    }
  }

  grouping ncs_template_fgid_information_show {
    list id {
      // NCS patched for predictable order
      ordered-by user;
      key "fgid_id";
      leaf fgid_id {
        type string;
      }
      list hex_bitmaps {
        // NCS patched for predictable order
        ordered-by user;
        key "rack_number";
        leaf rack_number {
          type string;
        }
        leaf bitmap {
          type string;
        }
      }
      list binary_bitmaps {
        // NCS patched for predictable order
        ordered-by user;
        key "rack_number";
        leaf rack_number {
          type string;
        }
        leaf bitmap {
          type string;
        }
      }
      leaf total_asso_fabricq_ids {
        type string;
      }
      list asso_fabricq_ids {
        // NCS patched for predictable order
        ordered-by user;
        key "fabricq_id";
        leaf fabricq_id {
          type string;
        }
      }
      leaf asso_client_info {
        type string;
      }
      list drivers {
        // NCS patched for predictable order
        ordered-by user;
        key "rack_number";
        leaf rack_number {
          type string;
        }
        list clients {
          // NCS patched for predictable order
          ordered-by user;
          key "client_idx";
          leaf client_idx {
            type string;
          }
          leaf show_asic_0 {
            type string;
            // NCS drop default statement
          }
          leaf asic_0_bitmap {
            type string;
          }
          leaf show_asic_1 {
            type string;
            // NCS drop default statement
          }
          leaf asic_1_bitmap {
            type string;
          }
          leaf show_asic_2 {
            type string;
            // NCS drop default statement
          }
          leaf asic_2_bitmap {
            type string;
          }
          leaf show_asic_3 {
            type string;
            // NCS drop default statement
          }
          leaf asic_3_bitmap {
            type string;
          }
          leaf show_asic_4 {
            type string;
            // NCS drop default statement
          }
          leaf asic_4_bitmap {
            type string;
          }
          leaf show_asic_5 {
            type string;
            // NCS drop default statement
          }
          leaf asic_5_bitmap {
            type string;
          }
          leaf show_asic_6 {
            type string;
            // NCS drop default statement
          }
          leaf asic_6_bitmap {
            type string;
          }
          leaf show_asic_7 {
            type string;
            // NCS drop default statement
          }
          leaf asic_7_bitmap {
            type string;
          }
          leaf show_asic_8 {
            type string;
            // NCS drop default statement
          }
          leaf asic_8_bitmap {
            type string;
          }
          leaf show_asic_9 {
            type string;
            // NCS drop default statement
          }
          leaf asic_9_bitmap {
            type string;
          }
          leaf show_asic_10 {
            type string;
            // NCS drop default statement
          }
          leaf asic_10_bitmap {
            type string;
          }
          leaf show_asic_11 {
            type string;
            // NCS drop default statement
          }
          leaf asic_11_bitmap {
            type string;
          }
          leaf show_asic_12 {
            type string;
            // NCS drop default statement
          }
          leaf asic_12_bitmap {
            type string;
          }
          leaf show_asic_13 {
            type string;
            // NCS drop default statement
          }
          leaf asic_13_bitmap {
            type string;
          }
          leaf show_asic_14 {
            type string;
            // NCS drop default statement
          }
          leaf asic_14_bitmap {
            type string;
          }
          leaf show_asic_15 {
            type string;
            // NCS drop default statement
          }
          leaf asic_15_bitmap {
            type string;
          }
          leaf show_asic_16 {
            type string;
            // NCS drop default statement
          }
          leaf asic_16_bitmap {
            type string;
          }
          leaf show_asic_17 {
            type string;
            // NCS drop default statement
          }
          leaf asic_17_bitmap {
            type string;
          }
          leaf show_asic_18 {
            type string;
            // NCS drop default statement
          }
          leaf asic_18_bitmap {
            type string;
          }
          leaf show_asic_19 {
            type string;
            // NCS drop default statement
          }
          leaf asic_19_bitmap {
            type string;
          }
          leaf show_asic_20 {
            type string;
            // NCS drop default statement
          }
          leaf asic_20_bitmap {
            type string;
          }
          leaf show_asic_21 {
            type string;
            // NCS drop default statement
          }
          leaf asic_21_bitmap {
            type string;
          }
          leaf show_asic_22 {
            type string;
            // NCS drop default statement
          }
          leaf asic_22_bitmap {
            type string;
          }
          leaf show_asic_23 {
            type string;
            // NCS drop default statement
          }
          leaf asic_23_bitmap {
            type string;
          }
          leaf show_asic_24 {
            type string;
            // NCS drop default statement
          }
          leaf asic_24_bitmap {
            type string;
          }
          leaf show_asic_25 {
            type string;
            // NCS drop default statement
          }
          leaf asic_25_bitmap {
            type string;
          }
          leaf show_asic_26 {
            type string;
            // NCS drop default statement
          }
          leaf asic_26_bitmap {
            type string;
          }
          leaf show_asic_27 {
            type string;
            // NCS drop default statement
          }
          leaf asic_27_bitmap {
            type string;
          }
          leaf show_asic_28 {
            type string;
            // NCS drop default statement
          }
          leaf asic_28_bitmap {
            type string;
          }
          leaf show_asic_29 {
            type string;
            // NCS drop default statement
          }
          leaf asic_29_bitmap {
            type string;
          }
          leaf show_asic_30 {
            type string;
            // NCS drop default statement
          }
          leaf asic_30_bitmap {
            type string;
          }
          leaf show_asic_31 {
            type string;
            // NCS drop default statement
          }
          leaf asic_31_bitmap {
            type string;
          }
          leaf show_asic_32 {
            type string;
            // NCS drop default statement
          }
          leaf asic_32_bitmap {
            type string;
          }
          leaf show_asic_33 {
            type string;
            // NCS drop default statement
          }
          leaf asic_33_bitmap {
            type string;
          }
          leaf show_asic_34 {
            type string;
            // NCS drop default statement
          }
          leaf asic_34_bitmap {
            type string;
          }
          leaf show_asic_35 {
            type string;
            // NCS drop default statement
          }
          leaf asic_35_bitmap {
            type string;
          }
        }
      }
    }
  }

  grouping ncs_template_fgid_resource_show {
    list sdr {
      // NCS patched for predictable order
      ordered-by user;
      key "sdr_name";
      leaf sdr_name {
        type string;
      }
      leaf description {
        type string;
        // NCS drop default statement
      }
      list application {
        // NCS patched for predictable order
        ordered-by user;
        key "app_name";
        leaf app_name {
          type string;
        }
        leaf description {
          type string;
          // NCS drop default statement
        }
        list ids_range {
          // NCS patched for predictable order
          ordered-by user;
          key "id elements";
          leaf id {
            type string;
          }
          leaf elements {
            type string;
          }
          list fgid_ids {
            // NCS patched for predictable order
            ordered-by user;
            key "fgid_id line_idx";
            leaf fgid_id {
              type string;
            }
            leaf line_idx {
              type string;
            }
            leaf sdr_name_h {
              type string;
            }
            leaf app_name_h {
              type string;
            }
          }
        }
      }
    }
  }

  grouping ncs_template_fgid_trace {
    container fgid_mgr {
      uses show-trace:ncs_template_traceable;
    }
  }

  grouping ncs_template_fgid_statistics_app_show {
    list application {
      // NCS patched for predictable order
      ordered-by user;
      key "app_name";
      leaf app_name {
        type string;
      }
      leaf description {
        type string;
        // NCS drop default statement
      }
      leaf app_id {
        type string;
      }
      leaf pool_id {
        type string;
      }
      leaf inuse_fgids {
        type string;
      }
      leaf hwm_fgids {
        type string;
      }
    }
  }

  grouping ncs_template_fgid_statistics_pool_show {
    list pool_list {
      // NCS patched for predictable order
      ordered-by user;
      key "pool_id";
      leaf pool_id {
        type string;
      }
      leaf pool_name {
        type string;
      }
      leaf pool_type {
        type string;
      }
      leaf start_fgid {
        type string;
      }
      leaf total_fgids {
        type string;
      }
      leaf current_fgids {
        type string;
      }
      leaf hwm_fgids {
        type string;
      }
    }
  }

  grouping ncs_template_fgid_statistics_sdr_show {
    list sdr_list {
      // NCS patched for predictable order
      ordered-by user;
      key "sdr_name";
      leaf sdr_name {
        type string;
      }
      leaf description {
        type string;
        // NCS drop default statement
      }
      leaf sdr_total_fgids {
        type string;
      }
      leaf sdr_inuse_fgids {
        type string;
      }
      leaf sdr_hwm_fgids {
        type string;
      }
      uses ncs_template_fgid_statistics_app_show;
    }
  }

  grouping ncs_template_fgid_statistics_system_show {
    list stats_list {
      // NCS patched for predictable order
      ordered-by user;
      key "system_stats";
      leaf system_stats {
        type string;
      }
      leaf system_total_fgids {
        type string;
      }
      leaf system_inuse_fgids {
        type string;
      }
      leaf system_hwm_fgids {
        type string;
      }
    }
  }

  grouping ncs_template_fgid_statistics_show {
    uses ncs_template_fgid_statistics_system_show;
    uses ncs_template_fgid_statistics_sdr_show;
    uses ncs_template_fgid_statistics_pool_show;
  }

  grouping ncs_template_fgid_program_error_show {
    list program_error {
      // NCS patched for predictable order
      ordered-by user;
      key "start end";
      leaf start {
        type string;
      }
      leaf end {
        type string;
      }
      list rack {
        // NCS patched for predictable order
        ordered-by user;
        key "rack_id";
        leaf rack_id {
          type string;
        }
        leaf rack_id_str {
          type string;
        }
        leaf fgids_in_error {
          type string;
        }
        leaf found_fgids_in_error {
          type string;
        }
        leaf total_error_fgids {
          type string;
        }
        leaf incorrect_fgids_range {
          type string;
        }
        leaf cmd_not_supported {
          type string;
        }
      }
    }
  }

  grouping ncs_template_fgid {
    container fgid {
      description
        "FGID management information";
      container information {
        uses ncs_template_fgid_information_show;
      }
      container resource {
        uses ncs_template_fgid_resource_show;
      }
      container statistics {
        container all {
          uses ncs_template_fgid_statistics_show;
        }
        container sdr {
          uses ncs_template_fgid_statistics_sdr_show;
        }
        container pool {
          uses ncs_template_fgid_statistics_pool_show;
        }
        container system {
          uses ncs_template_fgid_statistics_system_show;
        }
      }
      uses ncs_template_fgid_trace;
      uses ncs_template_fgid_program_error_show;
    }
  }

  grouping ncs_rpc_notif_fgid_conf_resource {
    container fgid {
      container resource {
        container sdr {
          container allocation {
            leaf percent {
              type int32 {
                range "20..50";
              }
            }
          }
        }
      }
    }
  }

  grouping ncs_rpc_notif_fgid_information_show {
    list id {
      key "fgid_id";
      leaf fgid_id {
        type fabric-types:fabric_fgid_id_type;
      }
      list hex_bitmaps {
        key "rack_number";
        leaf rack_number {
          type int32;
        }
        leaf bitmap {
          type string;
        }
      }
      list binary_bitmaps {
        key "rack_number";
        leaf rack_number {
          type int32;
        }
        leaf bitmap {
          type string;
        }
      }
      leaf total_asso_fabricq_ids {
        type int32;
      }
      list asso_fabricq_ids {
        key "fabricq_id";
        leaf fabricq_id {
          type string;
        }
      }
      leaf asso_client_info {
        type string;
      }
      list drivers {
        key "rack_number";
        leaf rack_number {
          type int32;
        }
        list clients {
          key "client_idx";
          leaf client_idx {
            type int32;
          }
          leaf show_asic_0 {
            type boolean;
            default "false";
          }
          leaf asic_0_bitmap {
            type string;
          }
          leaf show_asic_1 {
            type boolean;
            default "false";
          }
          leaf asic_1_bitmap {
            type string;
          }
          leaf show_asic_2 {
            type boolean;
            default "false";
          }
          leaf asic_2_bitmap {
            type string;
          }
          leaf show_asic_3 {
            type boolean;
            default "false";
          }
          leaf asic_3_bitmap {
            type string;
          }
          leaf show_asic_4 {
            type boolean;
            default "false";
          }
          leaf asic_4_bitmap {
            type string;
          }
          leaf show_asic_5 {
            type boolean;
            default "false";
          }
          leaf asic_5_bitmap {
            type string;
          }
          leaf show_asic_6 {
            type boolean;
            default "false";
          }
          leaf asic_6_bitmap {
            type string;
          }
          leaf show_asic_7 {
            type boolean;
            default "false";
          }
          leaf asic_7_bitmap {
            type string;
          }
          leaf show_asic_8 {
            type boolean;
            default "false";
          }
          leaf asic_8_bitmap {
            type string;
          }
          leaf show_asic_9 {
            type boolean;
            default "false";
          }
          leaf asic_9_bitmap {
            type string;
          }
          leaf show_asic_10 {
            type boolean;
            default "false";
          }
          leaf asic_10_bitmap {
            type string;
          }
          leaf show_asic_11 {
            type boolean;
            default "false";
          }
          leaf asic_11_bitmap {
            type string;
          }
          leaf show_asic_12 {
            type boolean;
            default "false";
          }
          leaf asic_12_bitmap {
            type string;
          }
          leaf show_asic_13 {
            type boolean;
            default "false";
          }
          leaf asic_13_bitmap {
            type string;
          }
          leaf show_asic_14 {
            type boolean;
            default "false";
          }
          leaf asic_14_bitmap {
            type string;
          }
          leaf show_asic_15 {
            type boolean;
            default "false";
          }
          leaf asic_15_bitmap {
            type string;
          }
          leaf show_asic_16 {
            type boolean;
            default "false";
          }
          leaf asic_16_bitmap {
            type string;
          }
          leaf show_asic_17 {
            type boolean;
            default "false";
          }
          leaf asic_17_bitmap {
            type string;
          }
          leaf show_asic_18 {
            type boolean;
            default "false";
          }
          leaf asic_18_bitmap {
            type string;
          }
          leaf show_asic_19 {
            type boolean;
            default "false";
          }
          leaf asic_19_bitmap {
            type string;
          }
          leaf show_asic_20 {
            type boolean;
            default "false";
          }
          leaf asic_20_bitmap {
            type string;
          }
          leaf show_asic_21 {
            type boolean;
            default "false";
          }
          leaf asic_21_bitmap {
            type string;
          }
          leaf show_asic_22 {
            type boolean;
            default "false";
          }
          leaf asic_22_bitmap {
            type string;
          }
          leaf show_asic_23 {
            type boolean;
            default "false";
          }
          leaf asic_23_bitmap {
            type string;
          }
          leaf show_asic_24 {
            type boolean;
            default "false";
          }
          leaf asic_24_bitmap {
            type string;
          }
          leaf show_asic_25 {
            type boolean;
            default "false";
          }
          leaf asic_25_bitmap {
            type string;
          }
          leaf show_asic_26 {
            type boolean;
            default "false";
          }
          leaf asic_26_bitmap {
            type string;
          }
          leaf show_asic_27 {
            type boolean;
            default "false";
          }
          leaf asic_27_bitmap {
            type string;
          }
          leaf show_asic_28 {
            type boolean;
            default "false";
          }
          leaf asic_28_bitmap {
            type string;
          }
          leaf show_asic_29 {
            type boolean;
            default "false";
          }
          leaf asic_29_bitmap {
            type string;
          }
          leaf show_asic_30 {
            type boolean;
            default "false";
          }
          leaf asic_30_bitmap {
            type string;
          }
          leaf show_asic_31 {
            type boolean;
            default "false";
          }
          leaf asic_31_bitmap {
            type string;
          }
          leaf show_asic_32 {
            type boolean;
            default "false";
          }
          leaf asic_32_bitmap {
            type string;
          }
          leaf show_asic_33 {
            type boolean;
            default "false";
          }
          leaf asic_33_bitmap {
            type string;
          }
          leaf show_asic_34 {
            type boolean;
            default "false";
          }
          leaf asic_34_bitmap {
            type string;
          }
          leaf show_asic_35 {
            type boolean;
            default "false";
          }
          leaf asic_35_bitmap {
            type string;
          }
        }
      }
    }
  }

  grouping ncs_rpc_notif_fgid_resource_show {
    list sdr {
      key "sdr_name";
      leaf sdr_name {
        type string;
      }
      leaf description {
        type string;
        default "Secure Domain Router name.";
      }
      list application {
        key "app_name";
        leaf app_name {
          type string;
        }
        leaf description {
          type string;
          default "application.";
        }
        list ids_range {
          key "id elements";
          leaf id {
            type fabric-types:fabric_fgid_id_type;
          }
          leaf elements {
            type fabric-types:fabric_fgid_elements_type;
          }
          list fgid_ids {
            key "fgid_id line_idx";
            leaf fgid_id {
              type string;
            }
            leaf line_idx {
              type int32;
            }
            leaf sdr_name_h {
              type string;
            }
            leaf app_name_h {
              type string;
            }
          }
        }
      }
    }
  }

  grouping ncs_rpc_notif_fgid_trace {
    container fgid_mgr {
      uses show-trace:ncs_rpc_notif_traceable;
    }
  }

  grouping ncs_rpc_notif_fgid_statistics_app_show {
    list application {
      key "app_name";
      leaf app_name {
        type string;
      }
      leaf description {
        type string;
        default "application.";
      }
      leaf app_id {
        type uint32;
      }
      leaf pool_id {
        type uint32;
      }
      leaf inuse_fgids {
        type uint32;
      }
      leaf hwm_fgids {
        type uint32;
      }
    }
  }

  grouping ncs_rpc_notif_fgid_statistics_pool_show {
    list pool_list {
      key "pool_id";
      leaf pool_id {
        type uint32;
      }
      leaf pool_name {
        type string;
      }
      leaf pool_type {
        type string;
      }
      leaf start_fgid {
        type string;
      }
      leaf total_fgids {
        type uint32;
      }
      leaf current_fgids {
        type uint32;
      }
      leaf hwm_fgids {
        type uint32;
      }
    }
  }

  grouping ncs_rpc_notif_fgid_statistics_sdr_show {
    list sdr_list {
      key "sdr_name";
      leaf sdr_name {
        type string;
      }
      leaf description {
        type string;
        default "Secure Domain Router name.";
      }
      leaf sdr_total_fgids {
        type uint32;
      }
      leaf sdr_inuse_fgids {
        type uint32;
      }
      leaf sdr_hwm_fgids {
        type uint32;
      }
      uses ncs_rpc_notif_fgid_statistics_app_show;
    }
  }

  grouping ncs_rpc_notif_fgid_statistics_system_show {
    list stats_list {
      key "system_stats";
      leaf system_stats {
        type int32;
      }
      leaf system_total_fgids {
        type uint32;
      }
      leaf system_inuse_fgids {
        type uint32;
      }
      leaf system_hwm_fgids {
        type uint32;
      }
    }
  }

  grouping ncs_rpc_notif_fgid_statistics_show {
    uses ncs_rpc_notif_fgid_statistics_system_show;
    uses ncs_rpc_notif_fgid_statistics_sdr_show;
    uses ncs_rpc_notif_fgid_statistics_pool_show;
  }

  grouping ncs_rpc_notif_fgid_program_error_show {
    list program_error {
      key "start end";
      leaf start {
        type fabric-types:fabric_fgid_start_id_type;
      }
      leaf end {
        type fabric-types:fabric_fgid_end_id_type;
      }
      list rack {
        key "rack_id";
        leaf rack_id {
          type int32;
        }
        leaf rack_id_str {
          type string;
        }
        leaf fgids_in_error {
          type string;
        }
        leaf found_fgids_in_error {
          type boolean;
        }
        leaf total_error_fgids {
          type int32;
        }
        leaf incorrect_fgids_range {
          type boolean;
        }
        leaf cmd_not_supported {
          type boolean;
        }
      }
    }
  }

  grouping ncs_rpc_notif_fgid {
    container fgid {
      description
        "FGID management information";
      container information {
        uses ncs_rpc_notif_fgid_information_show;
      }
      container resource {
        uses ncs_rpc_notif_fgid_resource_show;
      }
      container statistics {
        container all {
          uses ncs_rpc_notif_fgid_statistics_show;
        }
        container sdr {
          uses ncs_rpc_notif_fgid_statistics_sdr_show;
        }
        container pool {
          uses ncs_rpc_notif_fgid_statistics_pool_show;
        }
        container system {
          uses ncs_rpc_notif_fgid_statistics_system_show;
        }
      }
      uses ncs_rpc_notif_fgid_trace;
      uses ncs_rpc_notif_fgid_program_error_show;
    }
  }

  grouping live_ncs_fgid_conf_resource {
    container fgid {
      container resource {
        container sdr {
          container allocation {
            leaf percent {
              type int32 {
                range "20..50";
              }
            }
          }
        }
      }
    }
  }

  grouping live_ncs_fgid_information_show {
    list id {
      key "fgid_id";
      leaf fgid_id {
        type fabric-types:fabric_fgid_id_type;
      }
      list hex_bitmaps {
        key "rack_number";
        leaf rack_number {
          type int32;
        }
        leaf bitmap {
          type string;
        }
      }
      list binary_bitmaps {
        key "rack_number";
        leaf rack_number {
          type int32;
        }
        leaf bitmap {
          type string;
        }
      }
      leaf total_asso_fabricq_ids {
        type int32;
      }
      list asso_fabricq_ids {
        key "fabricq_id";
        leaf fabricq_id {
          type string;
        }
      }
      leaf asso_client_info {
        type string;
      }
      list drivers {
        key "rack_number";
        leaf rack_number {
          type int32;
        }
        list clients {
          key "client_idx";
          leaf client_idx {
            type int32;
          }
          leaf show_asic_0 {
            type boolean;
            // NCS drop default statement
          }
          leaf asic_0_bitmap {
            type string;
          }
          leaf show_asic_1 {
            type boolean;
            // NCS drop default statement
          }
          leaf asic_1_bitmap {
            type string;
          }
          leaf show_asic_2 {
            type boolean;
            // NCS drop default statement
          }
          leaf asic_2_bitmap {
            type string;
          }
          leaf show_asic_3 {
            type boolean;
            // NCS drop default statement
          }
          leaf asic_3_bitmap {
            type string;
          }
          leaf show_asic_4 {
            type boolean;
            // NCS drop default statement
          }
          leaf asic_4_bitmap {
            type string;
          }
          leaf show_asic_5 {
            type boolean;
            // NCS drop default statement
          }
          leaf asic_5_bitmap {
            type string;
          }
          leaf show_asic_6 {
            type boolean;
            // NCS drop default statement
          }
          leaf asic_6_bitmap {
            type string;
          }
          leaf show_asic_7 {
            type boolean;
            // NCS drop default statement
          }
          leaf asic_7_bitmap {
            type string;
          }
          leaf show_asic_8 {
            type boolean;
            // NCS drop default statement
          }
          leaf asic_8_bitmap {
            type string;
          }
          leaf show_asic_9 {
            type boolean;
            // NCS drop default statement
          }
          leaf asic_9_bitmap {
            type string;
          }
          leaf show_asic_10 {
            type boolean;
            // NCS drop default statement
          }
          leaf asic_10_bitmap {
            type string;
          }
          leaf show_asic_11 {
            type boolean;
            // NCS drop default statement
          }
          leaf asic_11_bitmap {
            type string;
          }
          leaf show_asic_12 {
            type boolean;
            // NCS drop default statement
          }
          leaf asic_12_bitmap {
            type string;
          }
          leaf show_asic_13 {
            type boolean;
            // NCS drop default statement
          }
          leaf asic_13_bitmap {
            type string;
          }
          leaf show_asic_14 {
            type boolean;
            // NCS drop default statement
          }
          leaf asic_14_bitmap {
            type string;
          }
          leaf show_asic_15 {
            type boolean;
            // NCS drop default statement
          }
          leaf asic_15_bitmap {
            type string;
          }
          leaf show_asic_16 {
            type boolean;
            // NCS drop default statement
          }
          leaf asic_16_bitmap {
            type string;
          }
          leaf show_asic_17 {
            type boolean;
            // NCS drop default statement
          }
          leaf asic_17_bitmap {
            type string;
          }
          leaf show_asic_18 {
            type boolean;
            // NCS drop default statement
          }
          leaf asic_18_bitmap {
            type string;
          }
          leaf show_asic_19 {
            type boolean;
            // NCS drop default statement
          }
          leaf asic_19_bitmap {
            type string;
          }
          leaf show_asic_20 {
            type boolean;
            // NCS drop default statement
          }
          leaf asic_20_bitmap {
            type string;
          }
          leaf show_asic_21 {
            type boolean;
            // NCS drop default statement
          }
          leaf asic_21_bitmap {
            type string;
          }
          leaf show_asic_22 {
            type boolean;
            // NCS drop default statement
          }
          leaf asic_22_bitmap {
            type string;
          }
          leaf show_asic_23 {
            type boolean;
            // NCS drop default statement
          }
          leaf asic_23_bitmap {
            type string;
          }
          leaf show_asic_24 {
            type boolean;
            // NCS drop default statement
          }
          leaf asic_24_bitmap {
            type string;
          }
          leaf show_asic_25 {
            type boolean;
            // NCS drop default statement
          }
          leaf asic_25_bitmap {
            type string;
          }
          leaf show_asic_26 {
            type boolean;
            // NCS drop default statement
          }
          leaf asic_26_bitmap {
            type string;
          }
          leaf show_asic_27 {
            type boolean;
            // NCS drop default statement
          }
          leaf asic_27_bitmap {
            type string;
          }
          leaf show_asic_28 {
            type boolean;
            // NCS drop default statement
          }
          leaf asic_28_bitmap {
            type string;
          }
          leaf show_asic_29 {
            type boolean;
            // NCS drop default statement
          }
          leaf asic_29_bitmap {
            type string;
          }
          leaf show_asic_30 {
            type boolean;
            // NCS drop default statement
          }
          leaf asic_30_bitmap {
            type string;
          }
          leaf show_asic_31 {
            type boolean;
            // NCS drop default statement
          }
          leaf asic_31_bitmap {
            type string;
          }
          leaf show_asic_32 {
            type boolean;
            // NCS drop default statement
          }
          leaf asic_32_bitmap {
            type string;
          }
          leaf show_asic_33 {
            type boolean;
            // NCS drop default statement
          }
          leaf asic_33_bitmap {
            type string;
          }
          leaf show_asic_34 {
            type boolean;
            // NCS drop default statement
          }
          leaf asic_34_bitmap {
            type string;
          }
          leaf show_asic_35 {
            type boolean;
            // NCS drop default statement
          }
          leaf asic_35_bitmap {
            type string;
          }
        }
      }
    }
  }

  grouping live_ncs_fgid_resource_show {
    list sdr {
      key "sdr_name";
      leaf sdr_name {
        type string;
      }
      leaf description {
        type string;
        // NCS drop default statement
      }
      list application {
        key "app_name";
        leaf app_name {
          type string;
        }
        leaf description {
          type string;
          // NCS drop default statement
        }
        list ids_range {
          key "id elements";
          leaf id {
            type fabric-types:fabric_fgid_id_type;
          }
          leaf elements {
            type fabric-types:fabric_fgid_elements_type;
          }
          list fgid_ids {
            key "fgid_id line_idx";
            leaf fgid_id {
              type string;
            }
            leaf line_idx {
              type int32;
            }
            leaf sdr_name_h {
              type string;
            }
            leaf app_name_h {
              type string;
            }
          }
        }
      }
    }
  }

  grouping live_ncs_fgid_trace {
    container fgid_mgr {
      uses show-trace:live_ncs_traceable;
    }
  }

  grouping live_ncs_fgid_statistics_app_show {
    list application {
      key "app_name";
      leaf app_name {
        type string;
      }
      leaf description {
        type string;
        // NCS drop default statement
      }
      leaf app_id {
        type uint32;
      }
      leaf pool_id {
        type uint32;
      }
      leaf inuse_fgids {
        type uint32;
      }
      leaf hwm_fgids {
        type uint32;
      }
    }
  }

  grouping live_ncs_fgid_statistics_pool_show {
    list pool_list {
      key "pool_id";
      leaf pool_id {
        type uint32;
      }
      leaf pool_name {
        type string;
      }
      leaf pool_type {
        type string;
      }
      leaf start_fgid {
        type string;
      }
      leaf total_fgids {
        type uint32;
      }
      leaf current_fgids {
        type uint32;
      }
      leaf hwm_fgids {
        type uint32;
      }
    }
  }

  grouping live_ncs_fgid_statistics_sdr_show {
    list sdr_list {
      key "sdr_name";
      leaf sdr_name {
        type string;
      }
      leaf description {
        type string;
        // NCS drop default statement
      }
      leaf sdr_total_fgids {
        type uint32;
      }
      leaf sdr_inuse_fgids {
        type uint32;
      }
      leaf sdr_hwm_fgids {
        type uint32;
      }
      uses live_ncs_fgid_statistics_app_show;
    }
  }

  grouping live_ncs_fgid_statistics_system_show {
    list stats_list {
      key "system_stats";
      leaf system_stats {
        type int32;
      }
      leaf system_total_fgids {
        type uint32;
      }
      leaf system_inuse_fgids {
        type uint32;
      }
      leaf system_hwm_fgids {
        type uint32;
      }
    }
  }

  grouping live_ncs_fgid_statistics_show {
    uses live_ncs_fgid_statistics_system_show;
    uses live_ncs_fgid_statistics_sdr_show;
    uses live_ncs_fgid_statistics_pool_show;
  }

  grouping live_ncs_fgid_program_error_show {
    list program_error {
      key "start end";
      leaf start {
        type fabric-types:fabric_fgid_start_id_type;
      }
      leaf end {
        type fabric-types:fabric_fgid_end_id_type;
      }
      list rack {
        key "rack_id";
        leaf rack_id {
          type int32;
        }
        leaf rack_id_str {
          type string;
        }
        leaf fgids_in_error {
          type string;
        }
        leaf found_fgids_in_error {
          type boolean;
        }
        leaf total_error_fgids {
          type int32;
        }
        leaf incorrect_fgids_range {
          type boolean;
        }
        leaf cmd_not_supported {
          type boolean;
        }
      }
    }
  }

  grouping live_ncs_fgid {
    container fgid {
      description
        "FGID management information";
      container information {
        uses live_ncs_fgid_information_show;
      }
      container resource {
        uses live_ncs_fgid_resource_show;
      }
      container statistics {
        container all {
          uses live_ncs_fgid_statistics_show;
        }
        container sdr {
          uses live_ncs_fgid_statistics_sdr_show;
        }
        container pool {
          uses live_ncs_fgid_statistics_pool_show;
        }
        container system {
          uses live_ncs_fgid_statistics_system_show;
        }
      }
      uses live_ncs_fgid_trace;
      uses live_ncs_fgid_program_error_show;
    }
  }

  grouping fgid_conf_resource {
    container fgid {
      container resource {
        container sdr {
          container allocation {
            leaf percent {
              type int32 {
                range "20..50";
              }
            }
          }
        }
      }
    }
  }

  grouping fgid_information_show {
    list id {
      key "fgid_id";
      leaf fgid_id {
        type fabric-types:fabric_fgid_id_type;
      }
      list hex_bitmaps {
        key "rack_number";
        leaf rack_number {
          type int32;
        }
        leaf bitmap {
          type string;
        }
      }
      list binary_bitmaps {
        key "rack_number";
        leaf rack_number {
          type int32;
        }
        leaf bitmap {
          type string;
        }
      }
      leaf total_asso_fabricq_ids {
        type int32;
      }
      list asso_fabricq_ids {
        key "fabricq_id";
        leaf fabricq_id {
          type string;
        }
      }
      leaf asso_client_info {
        type string;
      }
      list drivers {
        key "rack_number";
        leaf rack_number {
          type int32;
        }
        list clients {
          key "client_idx";
          leaf client_idx {
            type int32;
          }
          leaf show_asic_0 {
            type boolean;
            default "false";
          }
          leaf asic_0_bitmap {
            type string;
          }
          leaf show_asic_1 {
            type boolean;
            default "false";
          }
          leaf asic_1_bitmap {
            type string;
          }
          leaf show_asic_2 {
            type boolean;
            default "false";
          }
          leaf asic_2_bitmap {
            type string;
          }
          leaf show_asic_3 {
            type boolean;
            default "false";
          }
          leaf asic_3_bitmap {
            type string;
          }
          leaf show_asic_4 {
            type boolean;
            default "false";
          }
          leaf asic_4_bitmap {
            type string;
          }
          leaf show_asic_5 {
            type boolean;
            default "false";
          }
          leaf asic_5_bitmap {
            type string;
          }
          leaf show_asic_6 {
            type boolean;
            default "false";
          }
          leaf asic_6_bitmap {
            type string;
          }
          leaf show_asic_7 {
            type boolean;
            default "false";
          }
          leaf asic_7_bitmap {
            type string;
          }
          leaf show_asic_8 {
            type boolean;
            default "false";
          }
          leaf asic_8_bitmap {
            type string;
          }
          leaf show_asic_9 {
            type boolean;
            default "false";
          }
          leaf asic_9_bitmap {
            type string;
          }
          leaf show_asic_10 {
            type boolean;
            default "false";
          }
          leaf asic_10_bitmap {
            type string;
          }
          leaf show_asic_11 {
            type boolean;
            default "false";
          }
          leaf asic_11_bitmap {
            type string;
          }
          leaf show_asic_12 {
            type boolean;
            default "false";
          }
          leaf asic_12_bitmap {
            type string;
          }
          leaf show_asic_13 {
            type boolean;
            default "false";
          }
          leaf asic_13_bitmap {
            type string;
          }
          leaf show_asic_14 {
            type boolean;
            default "false";
          }
          leaf asic_14_bitmap {
            type string;
          }
          leaf show_asic_15 {
            type boolean;
            default "false";
          }
          leaf asic_15_bitmap {
            type string;
          }
          leaf show_asic_16 {
            type boolean;
            default "false";
          }
          leaf asic_16_bitmap {
            type string;
          }
          leaf show_asic_17 {
            type boolean;
            default "false";
          }
          leaf asic_17_bitmap {
            type string;
          }
          leaf show_asic_18 {
            type boolean;
            default "false";
          }
          leaf asic_18_bitmap {
            type string;
          }
          leaf show_asic_19 {
            type boolean;
            default "false";
          }
          leaf asic_19_bitmap {
            type string;
          }
          leaf show_asic_20 {
            type boolean;
            default "false";
          }
          leaf asic_20_bitmap {
            type string;
          }
          leaf show_asic_21 {
            type boolean;
            default "false";
          }
          leaf asic_21_bitmap {
            type string;
          }
          leaf show_asic_22 {
            type boolean;
            default "false";
          }
          leaf asic_22_bitmap {
            type string;
          }
          leaf show_asic_23 {
            type boolean;
            default "false";
          }
          leaf asic_23_bitmap {
            type string;
          }
          leaf show_asic_24 {
            type boolean;
            default "false";
          }
          leaf asic_24_bitmap {
            type string;
          }
          leaf show_asic_25 {
            type boolean;
            default "false";
          }
          leaf asic_25_bitmap {
            type string;
          }
          leaf show_asic_26 {
            type boolean;
            default "false";
          }
          leaf asic_26_bitmap {
            type string;
          }
          leaf show_asic_27 {
            type boolean;
            default "false";
          }
          leaf asic_27_bitmap {
            type string;
          }
          leaf show_asic_28 {
            type boolean;
            default "false";
          }
          leaf asic_28_bitmap {
            type string;
          }
          leaf show_asic_29 {
            type boolean;
            default "false";
          }
          leaf asic_29_bitmap {
            type string;
          }
          leaf show_asic_30 {
            type boolean;
            default "false";
          }
          leaf asic_30_bitmap {
            type string;
          }
          leaf show_asic_31 {
            type boolean;
            default "false";
          }
          leaf asic_31_bitmap {
            type string;
          }
          leaf show_asic_32 {
            type boolean;
            default "false";
          }
          leaf asic_32_bitmap {
            type string;
          }
          leaf show_asic_33 {
            type boolean;
            default "false";
          }
          leaf asic_33_bitmap {
            type string;
          }
          leaf show_asic_34 {
            type boolean;
            default "false";
          }
          leaf asic_34_bitmap {
            type string;
          }
          leaf show_asic_35 {
            type boolean;
            default "false";
          }
          leaf asic_35_bitmap {
            type string;
          }
        }
      }
    }
  }

  grouping fgid_resource_show {
    list sdr {
      key "sdr_name";
      leaf sdr_name {
        type string;
      }
      leaf description {
        type string;
        default "Secure Domain Router name.";
      }
      list application {
        key "app_name";
        leaf app_name {
          type string;
        }
        leaf description {
          type string;
          default "application.";
        }
        list ids_range {
          key "id elements";
          leaf id {
            type fabric-types:fabric_fgid_id_type;
          }
          leaf elements {
            type fabric-types:fabric_fgid_elements_type;
          }
          list fgid_ids {
            key "fgid_id line_idx";
            leaf fgid_id {
              type string;
            }
            leaf line_idx {
              type int32;
            }
            leaf sdr_name_h {
              type string;
            }
            leaf app_name_h {
              type string;
            }
          }
        }
      }
    }
  }

  grouping fgid_trace {
    container fgid_mgr {
      uses show-trace:traceable;
    }
  }

  grouping fgid_statistics_app_show {
    list application {
      key "app_name";
      leaf app_name {
        type string;
      }
      leaf description {
        type string;
        default "application.";
      }
      leaf app_id {
        type uint32;
      }
      leaf pool_id {
        type uint32;
      }
      leaf inuse_fgids {
        type uint32;
      }
      leaf hwm_fgids {
        type uint32;
      }
    }
  }

  grouping fgid_statistics_pool_show {
    list pool_list {
      key "pool_id";
      leaf pool_id {
        type uint32;
      }
      leaf pool_name {
        type string;
      }
      leaf pool_type {
        type string;
      }
      leaf start_fgid {
        type string;
      }
      leaf total_fgids {
        type uint32;
      }
      leaf current_fgids {
        type uint32;
      }
      leaf hwm_fgids {
        type uint32;
      }
    }
  }

  grouping fgid_statistics_sdr_show {
    list sdr_list {
      key "sdr_name";
      leaf sdr_name {
        type string;
      }
      leaf description {
        type string;
        default "Secure Domain Router name.";
      }
      leaf sdr_total_fgids {
        type uint32;
      }
      leaf sdr_inuse_fgids {
        type uint32;
      }
      leaf sdr_hwm_fgids {
        type uint32;
      }
      uses fgid_statistics_app_show;
    }
  }

  grouping fgid_statistics_system_show {
    list stats_list {
      key "system_stats";
      leaf system_stats {
        type int32;
      }
      leaf system_total_fgids {
        type uint32;
      }
      leaf system_inuse_fgids {
        type uint32;
      }
      leaf system_hwm_fgids {
        type uint32;
      }
    }
  }

  grouping fgid_statistics_show {
    uses fgid_statistics_system_show;
    uses fgid_statistics_sdr_show;
    uses fgid_statistics_pool_show;
  }

  grouping fgid_program_error_show {
    list program_error {
      key "start end";
      leaf start {
        type fabric-types:fabric_fgid_start_id_type;
      }
      leaf end {
        type fabric-types:fabric_fgid_end_id_type;
      }
      list rack {
        key "rack_id";
        leaf rack_id {
          type int32;
        }
        leaf rack_id_str {
          type string;
        }
        leaf fgids_in_error {
          type string;
        }
        leaf found_fgids_in_error {
          type boolean;
        }
        leaf total_error_fgids {
          type int32;
        }
        leaf incorrect_fgids_range {
          type boolean;
        }
        leaf cmd_not_supported {
          type boolean;
        }
      }
    }
  }

  grouping fgid {
    container fgid {
      description
        "FGID management information";
      container information {
        uses fgid_information_show;
      }
      container resource {
        uses fgid_resource_show;
      }
      container statistics {
        container all {
          uses fgid_statistics_show;
        }
        container sdr {
          uses fgid_statistics_sdr_show;
        }
        container pool {
          uses fgid_statistics_pool_show;
        }
        container system {
          uses fgid_statistics_system_show;
        }
      }
      uses fgid_trace;
      uses fgid_program_error_show;
    }
  }
}
