module Cisco-IOS-XR-call-home-cfg {
  // Generated by yanger -t ncs
  tailf:mount-id f5500-nc-1.0:f5500-nc-1.0;
  tailf:ncs-device-type "netconf";

  namespace "http://cisco.com/ns/yang/Cisco-IOS-XR-call-home-cfg";
  prefix Cisco-IOS-XR-call-home-cfg;

  import Cisco-IOS-XR-types {
    prefix xr;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR call-home package configuration.

     This module contains definitions
     for the following management objects:
       call-home: Set CallHome parameters

     Copyright (c) 2013-2018 by Cisco Systems, Inc.
     All rights reserved.";

  revision 2018-07-24 {
    description
      "Add resolution for YANG enter-tuple issue.";
  }
  revision 2018-06-21 {
    description
      "Remove container smart-licensing.";
  }
  revision 2017-03-13 {
    description
      "Initial version.";
  }
  revision 2015-11-09 {
    description
      "IOS XR 6.0 revision.";
  }

  typedef Data-privacy-level {
    type enumeration {
      enum "normal" {
        value 0;
        description
          "Normal";
      }
      enum "high" {
        value 1;
        description
          "High";
      }
      enum "host-name" {
        value 2;
        description
          "HostName";
      }
    }
    description
      "Data privacy level";
  }

  typedef Call-home-trans-method {
    type enumeration {
      enum "email" {
        value 1;
        description
          "To add email address to lthis profile";
      }
      enum "http" {
        value 2;
        description
          "To add destination address(1-200) characters";
      }
    }
    description
      "Call home trans method";
  }

  typedef Snapshot-interval {
    type enumeration {
      enum "daily" {
        value 0;
        description
          "Daily call-home message";
      }
      enum "weekly" {
        value 1;
        description
          "Weekly call-home message";
      }
      enum "monthly" {
        value 2;
        description
          "Monthly call-home message";
      }
    }
    description
      "Snapshot interval";
  }

  typedef Call-home-event-severity {
    type enumeration {
      enum "debugging" {
        value 0;
        description
          "Debugging event";
      }
      enum "normal" {
        value 1;
        description
          "Normal event";
      }
      enum "notification" {
        value 2;
        description
          "Notification event";
      }
      enum "warning" {
        value 3;
        description
          "Warning event";
      }
      enum "minor" {
        value 4;
        description
          "Minor event";
      }
      enum "major" {
        value 5;
        description
          "Major event";
      }
      enum "critical" {
        value 6;
        description
          "Critical event";
      }
      enum "fatal" {
        value 7;
        description
          "Fatal event";
      }
      enum "disaster" {
        value 8;
        description
          "Disaster event";
      }
      enum "catastrophic" {
        value 9;
        description
          "Catastrophic event";
      }
    }
    description
      "Call home event severity";
  }

  typedef Call-home-day-of-week {
    type enumeration {
      enum "sunday" {
        value 0;
        description
          "Sunday";
      }
      enum "monday" {
        value 1;
        description
          "Monday";
      }
      enum "tuesday" {
        value 2;
        description
          "Tuesday";
      }
      enum "wednesday" {
        value 3;
        description
          "Wednesday";
      }
      enum "thursday" {
        value 4;
        description
          "Thursday";
      }
      enum "friday" {
        value 5;
        description
          "Friday";
      }
      enum "saturday" {
        value 6;
        description
          "Saturday";
      }
    }
    description
      "Call home day of week";
  }

  typedef Call-home-mail-send-interval {
    type enumeration {
      enum "daily" {
        value 0;
        description
          "Daily call-home message";
      }
      enum "weekly" {
        value 1;
        description
          "Weekly call-home message";
      }
      enum "monthly" {
        value 2;
        description
          "Monthly call-home message";
      }
    }
    description
      "Call home mail send interval";
  }

  augment "/ncs:devices/ncs:device/ncs:config" {
    container call-home {
      tailf:ncs-device-type "netconf";
      tailf:display-when "not(../../ncs:module) or ../../ncs:module[ncs:name='Cisco-IOS-XR-call-home-cfg']";
      description
        "Set CallHome parameters";
      container mail-servers {
        description
          "List of call-home mail_server";
        list mail-server {
          key "mail-serv-address";
          description
            "Email server";
          leaf priority {
            type uint32 {
              range "1..100";
            }
            description
              "Mail server with lower # will be used first";
          }
          leaf mail-serv-address {
            type string;
            description
              "Email server";
          }
        }
      }
      container syslog-throttling {
        description
          "Enable or disable call-home syslog message
           throttling";
        leaf active {
          type boolean;
          description
            "Active syslog throttling";
        }
      }
      container http-proxy {
        description
          "http proxy server address and port";
        leaf server-address {
          type string;
          description
            "http proxy server address";
        }
        leaf port {
          type xr:Cisco-ios-xr-port-number;
          description
            "http proxy server's port";
        }
      }
      container profiles {
        description
          "List of profiles";
        list profile {
          key "profile-name";
          description
            "A specific profile";
          container report-type {
            description
              "Choose what data to report";
            container reporting-callhome-data {
              description
                "Report smart call-home data";
              leaf enable {
                type boolean;
                description
                  "Enable report smart call-home data";
              }
            }
            container reporting-licensing-data {
              description
                "Report smart licensing data";
              leaf enable {
                type boolean;
                description
                  "Enable report smart licensing data";
              }
            }
          }
          container methods {
            description
              "Transport method (http or email)";
            list method {
              key "method";
              description
                "Transport method";
              leaf enable {
                type boolean;
                description
                  "Enable this transport method";
              }
              leaf method {
                type Call-home-trans-method;
                description
                  "Transport Method";
              }
            }
          }
          container addresses {
            description
              "List of destination address";
            list address {
              key "method destination-addr";
              description
                "A specific address";
              leaf enable {
                type boolean;
                description
                  "Set the address";
              }
              leaf method {
                type Call-home-trans-method;
                description
                  "Transpotation Method";
              }
              leaf destination-addr {
                type string {
                  length "1..200";
                }
                description
                  "Destination address (1-200) characters";
              }
            }
          }
          container subscribe-alert-group {
            description
              "Subscribe to alert-group";
            container environment {
              description
                "environmental info";
              leaf severity {
                type Call-home-event-severity;
                description
                  "Severity";
              }
            }
            container configuration {
              description
                "configuration info";
              container periodic {
                description
                  "Periodic call-home message";
                leaf interval {
                  type Call-home-mail-send-interval;
                  description
                    "none";
                }
                leaf day {
                  type uint32 {
                    range "0..31";
                  }
                  description
                    "Day";
                }
                leaf weekday {
                  type Call-home-day-of-week;
                  description
                    "Day of week";
                }
                leaf hour {
                  type uint32 {
                    range "0..23";
                  }
                  description
                    "Hour";
                }
                leaf minute {
                  type uint32 {
                    range "0..59";
                  }
                  description
                    "Minute";
                }
              }
              leaf subscribe {
                type empty;
                description
                  "Subscribe the alert-group";
              }
            }
            container snapshot {
              description
                "snapshot info";
              container periodic {
                description
                  "Periodic call-home message";
                leaf interval {
                  type Snapshot-interval;
                  description
                    "none";
                }
                leaf day {
                  type uint32 {
                    range "0..31";
                  }
                  description
                    "Day of month";
                }
                leaf weekday {
                  type Call-home-day-of-week;
                  description
                    "Day of week";
                }
                leaf hour {
                  type uint32 {
                    range "0..23";
                  }
                  description
                    "Hour";
                }
                leaf minute {
                  type uint32 {
                    range "0..59";
                  }
                  description
                    "Minute";
                }
              }
            }
            container inventory {
              description
                "inventory info";
              container periodic {
                description
                  "Periodic call-home message";
                leaf interval {
                  type Call-home-mail-send-interval;
                  description
                    "none";
                }
                leaf day {
                  type uint32 {
                    range "0..31";
                  }
                  description
                    "Day of month";
                }
                leaf weekday {
                  type Call-home-day-of-week;
                  description
                    "Day of week";
                }
                leaf hour {
                  type uint32 {
                    range "0..23";
                  }
                  description
                    "Hour";
                }
                leaf minute {
                  type uint32 {
                    range "0..59";
                  }
                  description
                    "Minute";
                }
              }
              leaf subscribe {
                type empty;
                description
                  "Subscribe the alert-group";
              }
            }
            container crash {
              description
                "Crash info";
              leaf subscribe {
                type empty;
                description
                  "Subscribe crash group";
              }
            }
            container syslogs {
              description
                "syslog info";
              list syslog {
                key "syslog-pattern";
                description
                  "Syslog message pattern to be matched";
                leaf severity {
                  type Call-home-event-severity;
                  description
                    "Severity";
                }
                leaf syslog-pattern {
                  type string {
                    length "1..80";
                  }
                  description
                    "Syslog message pattern to be matched";
                }
              }
            }
          }
          leaf message-format {
            type string;
            description
              "none";
          }
          leaf anonymous {
            type boolean;
            description
              "Enable call-home anonymous reporting only";
          }
          leaf message-size-limit {
            type uint32 {
              range "50..3145728";
            }
            description
              "To specify message size limit for this profile";
          }
          leaf active {
            type empty;
            description
              "Activate the current profile";
          }
          leaf profile-name {
            type xr:Cisco-ios-xr-string;
            description
              "Profile name";
          }
        }
      }
      container alert-groups {
        description
          "List of alert-group";
        list alert-group {
          key "alert-group-name";
          description
            "A specific alert-group";
          leaf enable {
            type boolean;
            description
              "Enable the alert-group";
          }
          leaf disable {
            type boolean;
            description
              "Disable the alert-group";
          }
          leaf alert-group-name {
            type xr:Cisco-ios-xr-string;
            description
              "none";
          }
        }
      }
      container data-privacies {
        description
          "Set call-home data-privacy";
        list data-privacy {
          key "host-name";
          description
            "level hostname";
          leaf level {
            type Data-privacy-level;
            description
              "Set call-home data-privacy level";
          }
          leaf host-name {
            type string;
            description
              "Data privacy type (hostname or level)";
          }
        }
      }
      container alert-group-config {
        description
          "alert-group config";
        container snapshot-commands {
          description
            "snapshot for adding CLI command";
          list snapshot-command {
            key "command";
            description
              "A specific CLI cmd for snapshot";
            leaf active {
              type empty;
              description
                "enable snapshot cmd";
            }
            leaf command {
              type string {
                length "1..127";
              }
              description
                "new added command";
            }
          }
        }
      }
      container authorization {
        description
          "Config aaa authorization, default username is
           callhome";
        leaf username {
          type xr:Cisco-ios-xr-string {
            length "1..64";
          }
          description
            "Username for authorization. default is callhome";
        }
        leaf active {
          type empty;
          description
            "Enable call-home aaa-authorization";
        }
      }
      leaf customer-id {
        type string {
          length "1..64";
        }
        description
          "Customer identification for Cisco Smart Call
           Home";
      }
      leaf phone-number {
        type string {
          length "1..17";
        }
        description
          "Phone number of the contact person.";
      }
      leaf contact-smart-licensing {
        type boolean;
        description
          "System Contact is Smart Licensing";
      }
      leaf contact-email-address {
        type string {
          length "1..194";
        }
        description
          "Contact person's email address";
      }
      leaf rate-limit {
        type uint32 {
          range "1..5";
        }
        description
          "Call-home event trigger rate-limit threshold per
           minute.";
      }
      leaf site-id {
        type string {
          length "1..200";
        }
        description
          "Site identification for Cisco Smart Call Home";
      }
      leaf vrf {
        type xr:Cisco-ios-xr-string {
          length "1..32";
        }
        description
          "Vrf routing/forwarding instance name";
      }
      leaf street-address {
        type string {
          length "1..200";
        }
        description
          "Street address, city, state, and zip code.";
      }
      leaf source-interface {
        type xr:Interface-name;
        description
          "Source interface name to send call-home messages";
      }
      leaf contract-id {
        type string {
          length "1..64";
        }
        description
          "Contract identification for Cisco Smart Call
           Home";
      }
      leaf reply-to {
        type string;
        description
          "Call home msg's reply-to email address";
      }
      leaf from {
        type string;
        description
          "Call home msg's from email address";
      }
      leaf active {
        type empty;
        description
          "Enable call-home service";
      }
    }
  }
  augment "/ncs:devices/ncs:device/ncs:live-status" {
    container call-home {
      tailf:ncs-device-type "netconf";
      tailf:display-when "not(../../ncs:module) or ../../ncs:module[ncs:name='Cisco-IOS-XR-call-home-cfg'] or (../../ncs:live-status-protocol[not(ncs:capability)]) or (../../ncs:live-status-protocol/ncs:capability/ncs:module[.='Cisco-IOS-XR-call-home-cfg'])";
      description
        "Set CallHome parameters";
      container mail-servers {
        description
          "List of call-home mail_server";
        list mail-server {
          key "mail-serv-address";
          description
            "Email server";
          leaf priority {
            type uint32 {
              range "1..100";
            }
            description
              "Mail server with lower # will be used first";
          }
          leaf mail-serv-address {
            type string;
            description
              "Email server";
          }
        }
      }
      container syslog-throttling {
        description
          "Enable or disable call-home syslog message
           throttling";
        leaf active {
          type boolean;
          description
            "Active syslog throttling";
        }
      }
      container http-proxy {
        description
          "http proxy server address and port";
        leaf server-address {
          type string;
          description
            "http proxy server address";
        }
        leaf port {
          type xr:Cisco-ios-xr-port-number;
          description
            "http proxy server's port";
        }
      }
      container profiles {
        description
          "List of profiles";
        list profile {
          key "profile-name";
          description
            "A specific profile";
          container report-type {
            description
              "Choose what data to report";
            container reporting-callhome-data {
              description
                "Report smart call-home data";
              leaf enable {
                type boolean;
                description
                  "Enable report smart call-home data";
              }
            }
            container reporting-licensing-data {
              description
                "Report smart licensing data";
              leaf enable {
                type boolean;
                description
                  "Enable report smart licensing data";
              }
            }
          }
          container methods {
            description
              "Transport method (http or email)";
            list method {
              key "method";
              description
                "Transport method";
              leaf enable {
                type boolean;
                description
                  "Enable this transport method";
              }
              leaf method {
                type Call-home-trans-method;
                description
                  "Transport Method";
              }
            }
          }
          container addresses {
            description
              "List of destination address";
            list address {
              key "method destination-addr";
              description
                "A specific address";
              leaf enable {
                type boolean;
                description
                  "Set the address";
              }
              leaf method {
                type Call-home-trans-method;
                description
                  "Transpotation Method";
              }
              leaf destination-addr {
                type string {
                  length "1..200";
                }
                description
                  "Destination address (1-200) characters";
              }
            }
          }
          container subscribe-alert-group {
            description
              "Subscribe to alert-group";
            container environment {
              description
                "environmental info";
              leaf severity {
                type Call-home-event-severity;
                description
                  "Severity";
              }
            }
            container configuration {
              description
                "configuration info";
              container periodic {
                description
                  "Periodic call-home message";
                leaf interval {
                  type Call-home-mail-send-interval;
                  description
                    "none";
                }
                leaf day {
                  type uint32 {
                    range "0..31";
                  }
                  description
                    "Day";
                }
                leaf weekday {
                  type Call-home-day-of-week;
                  description
                    "Day of week";
                }
                leaf hour {
                  type uint32 {
                    range "0..23";
                  }
                  description
                    "Hour";
                }
                leaf minute {
                  type uint32 {
                    range "0..59";
                  }
                  description
                    "Minute";
                }
              }
              leaf subscribe {
                type empty;
                description
                  "Subscribe the alert-group";
              }
            }
            container snapshot {
              description
                "snapshot info";
              container periodic {
                description
                  "Periodic call-home message";
                leaf interval {
                  type Snapshot-interval;
                  description
                    "none";
                }
                leaf day {
                  type uint32 {
                    range "0..31";
                  }
                  description
                    "Day of month";
                }
                leaf weekday {
                  type Call-home-day-of-week;
                  description
                    "Day of week";
                }
                leaf hour {
                  type uint32 {
                    range "0..23";
                  }
                  description
                    "Hour";
                }
                leaf minute {
                  type uint32 {
                    range "0..59";
                  }
                  description
                    "Minute";
                }
              }
            }
            container inventory {
              description
                "inventory info";
              container periodic {
                description
                  "Periodic call-home message";
                leaf interval {
                  type Call-home-mail-send-interval;
                  description
                    "none";
                }
                leaf day {
                  type uint32 {
                    range "0..31";
                  }
                  description
                    "Day of month";
                }
                leaf weekday {
                  type Call-home-day-of-week;
                  description
                    "Day of week";
                }
                leaf hour {
                  type uint32 {
                    range "0..23";
                  }
                  description
                    "Hour";
                }
                leaf minute {
                  type uint32 {
                    range "0..59";
                  }
                  description
                    "Minute";
                }
              }
              leaf subscribe {
                type empty;
                description
                  "Subscribe the alert-group";
              }
            }
            container crash {
              description
                "Crash info";
              leaf subscribe {
                type empty;
                description
                  "Subscribe crash group";
              }
            }
            container syslogs {
              description
                "syslog info";
              list syslog {
                key "syslog-pattern";
                description
                  "Syslog message pattern to be matched";
                leaf severity {
                  type Call-home-event-severity;
                  description
                    "Severity";
                }
                leaf syslog-pattern {
                  type string {
                    length "1..80";
                  }
                  description
                    "Syslog message pattern to be matched";
                }
              }
            }
          }
          leaf message-format {
            type string;
            description
              "none";
          }
          leaf anonymous {
            type boolean;
            description
              "Enable call-home anonymous reporting only";
          }
          leaf message-size-limit {
            type uint32 {
              range "50..3145728";
            }
            description
              "To specify message size limit for this profile";
          }
          leaf active {
            type empty;
            description
              "Activate the current profile";
          }
          leaf profile-name {
            type xr:Cisco-ios-xr-string;
            description
              "Profile name";
          }
        }
      }
      container alert-groups {
        description
          "List of alert-group";
        list alert-group {
          key "alert-group-name";
          description
            "A specific alert-group";
          leaf enable {
            type boolean;
            description
              "Enable the alert-group";
          }
          leaf disable {
            type boolean;
            description
              "Disable the alert-group";
          }
          leaf alert-group-name {
            type xr:Cisco-ios-xr-string;
            description
              "none";
          }
        }
      }
      container data-privacies {
        description
          "Set call-home data-privacy";
        list data-privacy {
          key "host-name";
          description
            "level hostname";
          leaf level {
            type Data-privacy-level;
            description
              "Set call-home data-privacy level";
          }
          leaf host-name {
            type string;
            description
              "Data privacy type (hostname or level)";
          }
        }
      }
      container alert-group-config {
        description
          "alert-group config";
        container snapshot-commands {
          description
            "snapshot for adding CLI command";
          list snapshot-command {
            key "command";
            description
              "A specific CLI cmd for snapshot";
            leaf active {
              type empty;
              description
                "enable snapshot cmd";
            }
            leaf command {
              type string {
                length "1..127";
              }
              description
                "new added command";
            }
          }
        }
      }
      container authorization {
        description
          "Config aaa authorization, default username is
           callhome";
        leaf username {
          type xr:Cisco-ios-xr-string {
            length "1..64";
          }
          description
            "Username for authorization. default is callhome";
        }
        leaf active {
          type empty;
          description
            "Enable call-home aaa-authorization";
        }
      }
      leaf customer-id {
        type string {
          length "1..64";
        }
        description
          "Customer identification for Cisco Smart Call
           Home";
      }
      leaf phone-number {
        type string {
          length "1..17";
        }
        description
          "Phone number of the contact person.";
      }
      leaf contact-smart-licensing {
        type boolean;
        description
          "System Contact is Smart Licensing";
      }
      leaf contact-email-address {
        type string {
          length "1..194";
        }
        description
          "Contact person's email address";
      }
      leaf rate-limit {
        type uint32 {
          range "1..5";
        }
        description
          "Call-home event trigger rate-limit threshold per
           minute.";
      }
      leaf site-id {
        type string {
          length "1..200";
        }
        description
          "Site identification for Cisco Smart Call Home";
      }
      leaf vrf {
        type xr:Cisco-ios-xr-string {
          length "1..32";
        }
        description
          "Vrf routing/forwarding instance name";
      }
      leaf street-address {
        type string {
          length "1..200";
        }
        description
          "Street address, city, state, and zip code.";
      }
      leaf source-interface {
        type xr:Interface-name;
        description
          "Source interface name to send call-home messages";
      }
      leaf contract-id {
        type string {
          length "1..64";
        }
        description
          "Contract identification for Cisco Smart Call
           Home";
      }
      leaf reply-to {
        type string;
        description
          "Call home msg's reply-to email address";
      }
      leaf from {
        type string;
        description
          "Call home msg's from email address";
      }
      leaf active {
        type empty;
        description
          "Enable call-home service";
      }
    }
  }
  augment "/ncs:devices/ncs:template/ncs:ned-id/ncs:config" {
    container call-home {
      description
        "Set CallHome parameters";
      container mail-servers {
        description
          "List of call-home mail_server";
        list mail-server {
          // NCS patched for predictable order
          ordered-by user;
          key "mail-serv-address";
          description
            "Email server";
          leaf priority {
            type string;
            description
              "Mail server with lower # will be used first";
          }
          leaf mail-serv-address {
            type string;
            description
              "Email server";
          }
        }
      }
      container syslog-throttling {
        description
          "Enable or disable call-home syslog message
           throttling";
        leaf active {
          type string;
          description
            "Active syslog throttling";
        }
      }
      container http-proxy {
        description
          "http proxy server address and port";
        leaf server-address {
          type string;
          description
            "http proxy server address";
        }
        leaf port {
          type string;
          description
            "http proxy server's port";
        }
      }
      container profiles {
        description
          "List of profiles";
        list profile {
          // NCS patched for predictable order
          ordered-by user;
          key "profile-name";
          description
            "A specific profile";
          container report-type {
            description
              "Choose what data to report";
            container reporting-callhome-data {
              description
                "Report smart call-home data";
              leaf enable {
                type string;
                description
                  "Enable report smart call-home data";
              }
            }
            container reporting-licensing-data {
              description
                "Report smart licensing data";
              leaf enable {
                type string;
                description
                  "Enable report smart licensing data";
              }
            }
          }
          container methods {
            description
              "Transport method (http or email)";
            list method {
              // NCS patched for predictable order
              ordered-by user;
              key "method";
              description
                "Transport method";
              leaf enable {
                type string;
                description
                  "Enable this transport method";
              }
              leaf method {
                type string;
                description
                  "Transport Method";
              }
            }
          }
          container addresses {
            description
              "List of destination address";
            list address {
              // NCS patched for predictable order
              ordered-by user;
              key "method destination-addr";
              description
                "A specific address";
              leaf enable {
                type string;
                description
                  "Set the address";
              }
              leaf method {
                type string;
                description
                  "Transpotation Method";
              }
              leaf destination-addr {
                type string;
                description
                  "Destination address (1-200) characters";
              }
            }
          }
          container subscribe-alert-group {
            description
              "Subscribe to alert-group";
            container environment {
              description
                "environmental info";
              leaf severity {
                type string;
                description
                  "Severity";
              }
            }
            container configuration {
              description
                "configuration info";
              container periodic {
                description
                  "Periodic call-home message";
                leaf interval {
                  type string;
                  description
                    "none";
                }
                leaf day {
                  type string;
                  description
                    "Day";
                }
                leaf weekday {
                  type string;
                  description
                    "Day of week";
                }
                leaf hour {
                  type string;
                  description
                    "Hour";
                }
                leaf minute {
                  type string;
                  description
                    "Minute";
                }
              }
              leaf subscribe {
                type empty;
                description
                  "Subscribe the alert-group";
              }
            }
            container snapshot {
              description
                "snapshot info";
              container periodic {
                description
                  "Periodic call-home message";
                leaf interval {
                  type string;
                  description
                    "none";
                }
                leaf day {
                  type string;
                  description
                    "Day of month";
                }
                leaf weekday {
                  type string;
                  description
                    "Day of week";
                }
                leaf hour {
                  type string;
                  description
                    "Hour";
                }
                leaf minute {
                  type string;
                  description
                    "Minute";
                }
              }
            }
            container inventory {
              description
                "inventory info";
              container periodic {
                description
                  "Periodic call-home message";
                leaf interval {
                  type string;
                  description
                    "none";
                }
                leaf day {
                  type string;
                  description
                    "Day of month";
                }
                leaf weekday {
                  type string;
                  description
                    "Day of week";
                }
                leaf hour {
                  type string;
                  description
                    "Hour";
                }
                leaf minute {
                  type string;
                  description
                    "Minute";
                }
              }
              leaf subscribe {
                type empty;
                description
                  "Subscribe the alert-group";
              }
            }
            container crash {
              description
                "Crash info";
              leaf subscribe {
                type empty;
                description
                  "Subscribe crash group";
              }
            }
            container syslogs {
              description
                "syslog info";
              list syslog {
                // NCS patched for predictable order
                ordered-by user;
                key "syslog-pattern";
                description
                  "Syslog message pattern to be matched";
                leaf severity {
                  type string;
                  description
                    "Severity";
                }
                leaf syslog-pattern {
                  type string;
                  description
                    "Syslog message pattern to be matched";
                }
              }
            }
          }
          leaf message-format {
            type string;
            description
              "none";
          }
          leaf anonymous {
            type string;
            description
              "Enable call-home anonymous reporting only";
          }
          leaf message-size-limit {
            type string;
            description
              "To specify message size limit for this profile";
          }
          leaf active {
            type empty;
            description
              "Activate the current profile";
          }
          leaf profile-name {
            type string;
            description
              "Profile name";
          }
        }
      }
      container alert-groups {
        description
          "List of alert-group";
        list alert-group {
          // NCS patched for predictable order
          ordered-by user;
          key "alert-group-name";
          description
            "A specific alert-group";
          leaf enable {
            type string;
            description
              "Enable the alert-group";
          }
          leaf disable {
            type string;
            description
              "Disable the alert-group";
          }
          leaf alert-group-name {
            type string;
            description
              "none";
          }
        }
      }
      container data-privacies {
        description
          "Set call-home data-privacy";
        list data-privacy {
          // NCS patched for predictable order
          ordered-by user;
          key "host-name";
          description
            "level hostname";
          leaf level {
            type string;
            description
              "Set call-home data-privacy level";
          }
          leaf host-name {
            type string;
            description
              "Data privacy type (hostname or level)";
          }
        }
      }
      container alert-group-config {
        description
          "alert-group config";
        container snapshot-commands {
          description
            "snapshot for adding CLI command";
          list snapshot-command {
            // NCS patched for predictable order
            ordered-by user;
            key "command";
            description
              "A specific CLI cmd for snapshot";
            leaf active {
              type empty;
              description
                "enable snapshot cmd";
            }
            leaf command {
              type string;
              description
                "new added command";
            }
          }
        }
      }
      container authorization {
        description
          "Config aaa authorization, default username is
           callhome";
        leaf username {
          type string;
          description
            "Username for authorization. default is callhome";
        }
        leaf active {
          type empty;
          description
            "Enable call-home aaa-authorization";
        }
      }
      leaf customer-id {
        type string;
        description
          "Customer identification for Cisco Smart Call
           Home";
      }
      leaf phone-number {
        type string;
        description
          "Phone number of the contact person.";
      }
      leaf contact-smart-licensing {
        type string;
        description
          "System Contact is Smart Licensing";
      }
      leaf contact-email-address {
        type string;
        description
          "Contact person's email address";
      }
      leaf rate-limit {
        type string;
        description
          "Call-home event trigger rate-limit threshold per
           minute.";
      }
      leaf site-id {
        type string;
        description
          "Site identification for Cisco Smart Call Home";
      }
      leaf vrf {
        type string;
        description
          "Vrf routing/forwarding instance name";
      }
      leaf street-address {
        type string;
        description
          "Street address, city, state, and zip code.";
      }
      leaf source-interface {
        type string;
        description
          "Source interface name to send call-home messages";
      }
      leaf contract-id {
        type string;
        description
          "Contract identification for Cisco Smart Call
           Home";
      }
      leaf reply-to {
        type string;
        description
          "Call home msg's reply-to email address";
      }
      leaf from {
        type string;
        description
          "Call home msg's from email address";
      }
      leaf active {
        type empty;
        description
          "Enable call-home service";
      }
    }
  }
}
