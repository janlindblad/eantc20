module Cisco-IOS-XR-infra-infra-cfg {
  // Generated by yanger -t ncs
  tailf:mount-id f5500-nc-1.0:f5500-nc-1.0;
  tailf:ncs-device-type "netconf";

  namespace "http://cisco.com/ns/yang/Cisco-IOS-XR-infra-infra-cfg";
  prefix Cisco-IOS-XR-infra-infra-cfg;

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR infra-infra package configuration.

     This module contains definitions
     for the following management objects:
       banners: Schema for Banner configuration commands

     Copyright (c) 2013-2018 by Cisco Systems, Inc.
     All rights reserved.";

  revision 2016-06-16 {
    description
      "Initial Rev 1";
  }
  revision 2015-01-07 {
    description
      "IOS XR 5.3.1 revision.";
  }

  typedef Banner {
    type enumeration {
      enum "exec" {
        value 0;
        description
          "Set EXEC process creation banner";
      }
      enum "incoming" {
        value 1;
        description
          "Set incoming terminal line banner";
      }
      enum "motd" {
        value 2;
        description
          "Set Message of the Day banner";
      }
      enum "login" {
        value 3;
        description
          "Set login banner";
      }
      enum "slip-ppp" {
        value 4;
        description
          "Set Message for SLIP/PPP";
      }
      enum "prompt-timeout" {
        value 5;
        description
          "Set Message for login authentication timeout";
      }
    }
    description
      "Banner";
  }

  augment "/ncs:devices/ncs:device/ncs:config" {
    container banners {
      tailf:ncs-device-type "netconf";
      tailf:display-when "not(../../ncs:module) or ../../ncs:module[ncs:name='Cisco-IOS-XR-infra-infra-cfg']";
      description
        "Schema for Banner configuration commands";
      list banner {
        key "banner-name";
        description
          "Select a Banner Type";
        leaf banner-name {
          type Banner;
          description
            "Banner Type";
        }
        leaf banner-text {
          type string;
          mandatory true;
          description
            "Banner text message";
        }
      }
    }
  }
  augment "/ncs:devices/ncs:device/ncs:live-status" {
    container banners {
      tailf:ncs-device-type "netconf";
      tailf:display-when "not(../../ncs:module) or ../../ncs:module[ncs:name='Cisco-IOS-XR-infra-infra-cfg'] or (../../ncs:live-status-protocol[not(ncs:capability)]) or (../../ncs:live-status-protocol/ncs:capability/ncs:module[.='Cisco-IOS-XR-infra-infra-cfg'])";
      description
        "Schema for Banner configuration commands";
      list banner {
        key "banner-name";
        description
          "Select a Banner Type";
        leaf banner-name {
          type Banner;
          description
            "Banner Type";
        }
        leaf banner-text {
          type string;
          // NCS drop mandatory statement
          description
            "Banner text message";
        }
      }
    }
  }
  augment "/ncs:devices/ncs:template/ncs:ned-id/ncs:config" {
    container banners {
      description
        "Schema for Banner configuration commands";
      list banner {
        // NCS patched for predictable order
        ordered-by user;
        key "banner-name";
        description
          "Select a Banner Type";
        leaf banner-name {
          type string;
          description
            "Banner Type";
        }
        leaf banner-text {
          type string;
          // NCS drop mandatory statement
          description
            "Banner text message";
        }
      }
    }
  }
}
