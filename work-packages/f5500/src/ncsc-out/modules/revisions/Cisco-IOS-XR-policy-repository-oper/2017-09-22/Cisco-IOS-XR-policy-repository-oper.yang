module Cisco-IOS-XR-policy-repository-oper {
  // Generated by yanger -t ncs
  tailf:mount-id f5500-nc-1.0:f5500-nc-1.0;
  tailf:ncs-device-type "netconf";

  namespace "http://cisco.com/ns/yang/Cisco-IOS-XR-policy-repository-oper";
  prefix Cisco-IOS-XR-policy-repository-oper;

  import Cisco-IOS-XR-types {
    prefix xr;
  }
  include Cisco-IOS-XR-policy-repository-oper-sub1 {
    revision-date 2017-09-22;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR policy-repository package operational data.

     This module contains definitions
     for the following management objects:
       routing-policy: Routing policy operational data
       routing-policy-shadow: routing policy shadow

     Copyright (c) 2013-2018 by Cisco Systems, Inc.
     All rights reserved.";

  revision 2017-09-22 {
    description
      "Introduced shadow process container.";
  }
  revision 2017-05-01 {
    description
      "Fixing backward compatibility error in module.";
  }
  revision 2015-11-09 {
    description
      "IOS XR 6.0 revision.";
  }

  grouping ncs_template_UNUSED {
    description
      "Common node of policies, as-path, community,
       large-community, extended-community-cost, rd,
       extended-community-rt, extended-community-soo,
       extended-community-opaque,
       extended-community-seg-nh,
       extended-community-bandwidth, prefix, esi, etag,
       mac, tag, ospf-area";
    container unused {
      description
        "All objects of a given type that are not
         referenced at all";
      uses ncs_template_RPL-OBJECTS-INFO;
    }
  }

  grouping ncs_template_SET-TABLE {
    description
      "Common node of as-path, community,
       large-community, extended-community-cost, rd,
       extended-community-rt, extended-community-soo,
       extended-community-opaque,
       extended-community-seg-nh,
       extended-community-bandwidth, prefix, esi, etag,
       mac, tag, ospf-area";
    container sets {
      description
        "Information about individual sets";
      list set {
        // NCS patched for predictable order
        ordered-by user;
        key "set-name";
        description
          "Information about an individual set";
        leaf set-name {
          type string;
          description
            "Set name";
        }
        uses ncs_template_USED-BY;
        uses ncs_template_ATTACHED;
      }
    }
  }

  grouping ncs_template_SETS {
    description
      "Common node of routing-policy,
       routing-policy-shadow";
    container sets {
      description
        "Information about configured sets";
      container etag {
        description
          "Information about Etag sets";
        uses ncs_template_SET-TABLE;
        uses ncs_template_UNUSED;
        uses ncs_template_INACTIVE;
        uses ncs_template_ACTIVE;
      }
      container ospf-area {
        description
          "Information about OSPF Area sets";
        uses ncs_template_SET-TABLE;
        uses ncs_template_UNUSED;
        uses ncs_template_INACTIVE;
        uses ncs_template_ACTIVE;
      }
      container extended-community-opaque {
        description
          "Information about Extended Community Opaque
           sets";
        uses ncs_template_SET-TABLE;
        uses ncs_template_UNUSED;
        uses ncs_template_INACTIVE;
        uses ncs_template_ACTIVE;
      }
      container extended-community-seg-nh {
        description
          "Information about Extended Community SegNH sets";
        uses ncs_template_SET-TABLE;
        uses ncs_template_UNUSED;
        uses ncs_template_INACTIVE;
        uses ncs_template_ACTIVE;
      }
      container extended-community-soo {
        description
          "Information about Extended Community SOO sets";
        uses ncs_template_SET-TABLE;
        uses ncs_template_UNUSED;
        uses ncs_template_INACTIVE;
        uses ncs_template_ACTIVE;
      }
      container tag {
        description
          "Information about Tag sets";
        uses ncs_template_SET-TABLE;
        uses ncs_template_UNUSED;
        uses ncs_template_INACTIVE;
        uses ncs_template_ACTIVE;
      }
      container prefix {
        description
          "Information about AS Path sets";
        uses ncs_template_SET-TABLE;
        uses ncs_template_UNUSED;
        uses ncs_template_INACTIVE;
        uses ncs_template_ACTIVE;
      }
      container community {
        description
          "Information about Community sets";
        uses ncs_template_SET-TABLE;
        uses ncs_template_UNUSED;
        uses ncs_template_INACTIVE;
        uses ncs_template_ACTIVE;
      }
      container as-path {
        description
          "Information about AS Path sets";
        uses ncs_template_SET-TABLE;
        uses ncs_template_UNUSED;
        uses ncs_template_INACTIVE;
        uses ncs_template_ACTIVE;
      }
      container large-community {
        description
          "Information about Large Community sets";
        uses ncs_template_SET-TABLE;
        uses ncs_template_UNUSED;
        uses ncs_template_INACTIVE;
        uses ncs_template_ACTIVE;
      }
      container esi {
        description
          "Information about Esi sets";
        uses ncs_template_SET-TABLE;
        uses ncs_template_UNUSED;
        uses ncs_template_INACTIVE;
        uses ncs_template_ACTIVE;
      }
      container extended-community-bandwidth {
        description
          "Information about Extended Community Bandwidth
           sets";
        uses ncs_template_SET-TABLE;
        uses ncs_template_UNUSED;
        uses ncs_template_INACTIVE;
      }
      container extended-community-rt {
        description
          "Information about Extended Community RT sets";
        uses ncs_template_SET-TABLE;
        uses ncs_template_UNUSED;
        uses ncs_template_INACTIVE;
        uses ncs_template_ACTIVE;
      }
      container rd {
        description
          "Information about RD sets";
        uses ncs_template_SET-TABLE;
        uses ncs_template_UNUSED;
        uses ncs_template_INACTIVE;
        uses ncs_template_ACTIVE;
      }
      container mac {
        description
          "Information about Mac sets";
        uses ncs_template_SET-TABLE;
        uses ncs_template_UNUSED;
        uses ncs_template_INACTIVE;
        uses ncs_template_ACTIVE;
      }
      container extended-community-cost {
        description
          "Information about Extended Community Cost sets";
        uses ncs_template_SET-TABLE;
        uses ncs_template_UNUSED;
        uses ncs_template_INACTIVE;
        uses ncs_template_ACTIVE;
      }
    }
  }

  grouping ncs_template_LIMITS {
    description
      "Common node of routing-policy,
       routing-policy-shadow";
    container limits {
      description
        "Information about configured limits and the
         current values";
      uses ncs_template_RPL-MAX-LIMITS-INFO;
    }
  }

  grouping ncs_template_INACTIVE {
    description
      "Common node of policies, as-path, community,
       large-community, extended-community-cost, rd,
       extended-community-rt, extended-community-soo,
       extended-community-opaque,
       extended-community-seg-nh,
       extended-community-bandwidth, prefix, esi, etag,
       mac, tag, ospf-area";
    container inactive {
      description
        "All objects of a given type that are not
         attached to a protocol";
      uses ncs_template_RPL-OBJECTS-INFO;
    }
  }

  grouping ncs_template_POLICIES {
    description
      "Common node of routing-policy,
       routing-policy-shadow";
    container policies {
      description
        "Information about configured route policies";
      container route-policies {
        description
          "Information about individual policies";
        list route-policy {
          // NCS patched for predictable order
          ordered-by user;
          key "route-policy-name";
          description
            "Information about an individual policy";
          container policy-uses {
            description
              "Information about which policies and sets
               this policy uses";
            container directly-used-policies {
              description
                "Policies that this policy uses directly";
              uses ncs_template_RPL-OBJECTS-INFO;
            }
            container all-used-sets {
              description
                "Sets used by this policy, or by policies
                 that it uses";
              uses ncs_template_RPL-SETS-INFO;
            }
            container directly-used-sets {
              description
                "Sets that this policy uses directly";
              uses ncs_template_RPL-SETS-INFO;
            }
            container all-used-policies {
              description
                "Policies used by this policy, or by policies
                 that it uses";
              uses ncs_template_RPL-OBJECTS-INFO;
            }
          }
          leaf route-policy-name {
            type string;
            description
              "Route policy name";
          }
          uses ncs_template_USED-BY;
          uses ncs_template_ATTACHED;
        }
      }
      uses ncs_template_UNUSED;
      uses ncs_template_INACTIVE;
      uses ncs_template_ACTIVE;
    }
  }

  grouping ncs_template_USED-BY {
    description
      "Common node of route-policy, set";
    container used-by {
      description
        "Policies that use this object, directly or
         indirectly";
      uses ncs_template_RPL-REFERENCES-INFO;
    }
  }

  grouping ncs_template_ACTIVE {
    description
      "Common node of policies, as-path, community,
       large-community, extended-community-cost, rd,
       extended-community-rt, extended-community-soo,
       extended-community-opaque,
       extended-community-seg-nh, prefix, esi, etag, mac
       , tag, ospf-area";
    container active {
      description
        "All objects of a given type that are attached to
         a protocol";
      uses ncs_template_RPL-OBJECTS-INFO;
    }
  }

  grouping ncs_template_ATTACHED {
    description
      "Common node of route-policy, set";
    container attached {
      description
        "Information about where this policy or set is
         attached";
      uses ncs_template_RPL-ATTACHMENT-INFO;
    }
  }

  grouping ncs_rpc_notif_UNUSED {
    description
      "Common node of policies, as-path, community,
       large-community, extended-community-cost, rd,
       extended-community-rt, extended-community-soo,
       extended-community-opaque,
       extended-community-seg-nh,
       extended-community-bandwidth, prefix, esi, etag,
       mac, tag, ospf-area";
    container unused {
      description
        "All objects of a given type that are not
         referenced at all";
      uses ncs_rpc_notif_RPL-OBJECTS-INFO;
    }
  }

  grouping ncs_rpc_notif_SET-TABLE {
    description
      "Common node of as-path, community,
       large-community, extended-community-cost, rd,
       extended-community-rt, extended-community-soo,
       extended-community-opaque,
       extended-community-seg-nh,
       extended-community-bandwidth, prefix, esi, etag,
       mac, tag, ospf-area";
    container sets {
      description
        "Information about individual sets";
      list set {
        key "set-name";
        description
          "Information about an individual set";
        leaf set-name {
          type xr:Cisco-ios-xr-string;
          description
            "Set name";
        }
        uses ncs_rpc_notif_USED-BY;
        uses ncs_rpc_notif_ATTACHED;
      }
    }
  }

  grouping ncs_rpc_notif_SETS {
    description
      "Common node of routing-policy,
       routing-policy-shadow";
    container sets {
      description
        "Information about configured sets";
      container etag {
        description
          "Information about Etag sets";
        uses ncs_rpc_notif_SET-TABLE;
        uses ncs_rpc_notif_UNUSED;
        uses ncs_rpc_notif_INACTIVE;
        uses ncs_rpc_notif_ACTIVE;
      }
      container ospf-area {
        description
          "Information about OSPF Area sets";
        uses ncs_rpc_notif_SET-TABLE;
        uses ncs_rpc_notif_UNUSED;
        uses ncs_rpc_notif_INACTIVE;
        uses ncs_rpc_notif_ACTIVE;
      }
      container extended-community-opaque {
        description
          "Information about Extended Community Opaque
           sets";
        uses ncs_rpc_notif_SET-TABLE;
        uses ncs_rpc_notif_UNUSED;
        uses ncs_rpc_notif_INACTIVE;
        uses ncs_rpc_notif_ACTIVE;
      }
      container extended-community-seg-nh {
        description
          "Information about Extended Community SegNH sets";
        uses ncs_rpc_notif_SET-TABLE;
        uses ncs_rpc_notif_UNUSED;
        uses ncs_rpc_notif_INACTIVE;
        uses ncs_rpc_notif_ACTIVE;
      }
      container extended-community-soo {
        description
          "Information about Extended Community SOO sets";
        uses ncs_rpc_notif_SET-TABLE;
        uses ncs_rpc_notif_UNUSED;
        uses ncs_rpc_notif_INACTIVE;
        uses ncs_rpc_notif_ACTIVE;
      }
      container tag {
        description
          "Information about Tag sets";
        uses ncs_rpc_notif_SET-TABLE;
        uses ncs_rpc_notif_UNUSED;
        uses ncs_rpc_notif_INACTIVE;
        uses ncs_rpc_notif_ACTIVE;
      }
      container prefix {
        description
          "Information about AS Path sets";
        uses ncs_rpc_notif_SET-TABLE;
        uses ncs_rpc_notif_UNUSED;
        uses ncs_rpc_notif_INACTIVE;
        uses ncs_rpc_notif_ACTIVE;
      }
      container community {
        description
          "Information about Community sets";
        uses ncs_rpc_notif_SET-TABLE;
        uses ncs_rpc_notif_UNUSED;
        uses ncs_rpc_notif_INACTIVE;
        uses ncs_rpc_notif_ACTIVE;
      }
      container as-path {
        description
          "Information about AS Path sets";
        uses ncs_rpc_notif_SET-TABLE;
        uses ncs_rpc_notif_UNUSED;
        uses ncs_rpc_notif_INACTIVE;
        uses ncs_rpc_notif_ACTIVE;
      }
      container large-community {
        description
          "Information about Large Community sets";
        uses ncs_rpc_notif_SET-TABLE;
        uses ncs_rpc_notif_UNUSED;
        uses ncs_rpc_notif_INACTIVE;
        uses ncs_rpc_notif_ACTIVE;
      }
      container esi {
        description
          "Information about Esi sets";
        uses ncs_rpc_notif_SET-TABLE;
        uses ncs_rpc_notif_UNUSED;
        uses ncs_rpc_notif_INACTIVE;
        uses ncs_rpc_notif_ACTIVE;
      }
      container extended-community-bandwidth {
        description
          "Information about Extended Community Bandwidth
           sets";
        uses ncs_rpc_notif_SET-TABLE;
        uses ncs_rpc_notif_UNUSED;
        uses ncs_rpc_notif_INACTIVE;
      }
      container extended-community-rt {
        description
          "Information about Extended Community RT sets";
        uses ncs_rpc_notif_SET-TABLE;
        uses ncs_rpc_notif_UNUSED;
        uses ncs_rpc_notif_INACTIVE;
        uses ncs_rpc_notif_ACTIVE;
      }
      container rd {
        description
          "Information about RD sets";
        uses ncs_rpc_notif_SET-TABLE;
        uses ncs_rpc_notif_UNUSED;
        uses ncs_rpc_notif_INACTIVE;
        uses ncs_rpc_notif_ACTIVE;
      }
      container mac {
        description
          "Information about Mac sets";
        uses ncs_rpc_notif_SET-TABLE;
        uses ncs_rpc_notif_UNUSED;
        uses ncs_rpc_notif_INACTIVE;
        uses ncs_rpc_notif_ACTIVE;
      }
      container extended-community-cost {
        description
          "Information about Extended Community Cost sets";
        uses ncs_rpc_notif_SET-TABLE;
        uses ncs_rpc_notif_UNUSED;
        uses ncs_rpc_notif_INACTIVE;
        uses ncs_rpc_notif_ACTIVE;
      }
    }
  }

  grouping ncs_rpc_notif_LIMITS {
    description
      "Common node of routing-policy,
       routing-policy-shadow";
    container limits {
      description
        "Information about configured limits and the
         current values";
      uses ncs_rpc_notif_RPL-MAX-LIMITS-INFO;
    }
  }

  grouping ncs_rpc_notif_INACTIVE {
    description
      "Common node of policies, as-path, community,
       large-community, extended-community-cost, rd,
       extended-community-rt, extended-community-soo,
       extended-community-opaque,
       extended-community-seg-nh,
       extended-community-bandwidth, prefix, esi, etag,
       mac, tag, ospf-area";
    container inactive {
      description
        "All objects of a given type that are not
         attached to a protocol";
      uses ncs_rpc_notif_RPL-OBJECTS-INFO;
    }
  }

  grouping ncs_rpc_notif_POLICIES {
    description
      "Common node of routing-policy,
       routing-policy-shadow";
    container policies {
      description
        "Information about configured route policies";
      container route-policies {
        description
          "Information about individual policies";
        list route-policy {
          key "route-policy-name";
          description
            "Information about an individual policy";
          container policy-uses {
            description
              "Information about which policies and sets
               this policy uses";
            container directly-used-policies {
              description
                "Policies that this policy uses directly";
              uses ncs_rpc_notif_RPL-OBJECTS-INFO;
            }
            container all-used-sets {
              description
                "Sets used by this policy, or by policies
                 that it uses";
              uses ncs_rpc_notif_RPL-SETS-INFO;
            }
            container directly-used-sets {
              description
                "Sets that this policy uses directly";
              uses ncs_rpc_notif_RPL-SETS-INFO;
            }
            container all-used-policies {
              description
                "Policies used by this policy, or by policies
                 that it uses";
              uses ncs_rpc_notif_RPL-OBJECTS-INFO;
            }
          }
          leaf route-policy-name {
            type xr:Cisco-ios-xr-string;
            description
              "Route policy name";
          }
          uses ncs_rpc_notif_USED-BY;
          uses ncs_rpc_notif_ATTACHED;
        }
      }
      uses ncs_rpc_notif_UNUSED;
      uses ncs_rpc_notif_INACTIVE;
      uses ncs_rpc_notif_ACTIVE;
    }
  }

  grouping ncs_rpc_notif_USED-BY {
    description
      "Common node of route-policy, set";
    container used-by {
      description
        "Policies that use this object, directly or
         indirectly";
      uses ncs_rpc_notif_RPL-REFERENCES-INFO;
    }
  }

  grouping ncs_rpc_notif_ACTIVE {
    description
      "Common node of policies, as-path, community,
       large-community, extended-community-cost, rd,
       extended-community-rt, extended-community-soo,
       extended-community-opaque,
       extended-community-seg-nh, prefix, esi, etag, mac
       , tag, ospf-area";
    container active {
      description
        "All objects of a given type that are attached to
         a protocol";
      uses ncs_rpc_notif_RPL-OBJECTS-INFO;
    }
  }

  grouping ncs_rpc_notif_ATTACHED {
    description
      "Common node of route-policy, set";
    container attached {
      description
        "Information about where this policy or set is
         attached";
      uses ncs_rpc_notif_RPL-ATTACHMENT-INFO;
    }
  }

  grouping live_ncs_UNUSED {
    description
      "Common node of policies, as-path, community,
       large-community, extended-community-cost, rd,
       extended-community-rt, extended-community-soo,
       extended-community-opaque,
       extended-community-seg-nh,
       extended-community-bandwidth, prefix, esi, etag,
       mac, tag, ospf-area";
    container unused {
      description
        "All objects of a given type that are not
         referenced at all";
      uses live_ncs_RPL-OBJECTS-INFO;
    }
  }

  grouping live_ncs_SET-TABLE {
    description
      "Common node of as-path, community,
       large-community, extended-community-cost, rd,
       extended-community-rt, extended-community-soo,
       extended-community-opaque,
       extended-community-seg-nh,
       extended-community-bandwidth, prefix, esi, etag,
       mac, tag, ospf-area";
    container sets {
      description
        "Information about individual sets";
      list set {
        key "set-name";
        description
          "Information about an individual set";
        leaf set-name {
          type xr:Cisco-ios-xr-string;
          description
            "Set name";
        }
        uses live_ncs_USED-BY;
        uses live_ncs_ATTACHED;
      }
    }
  }

  grouping live_ncs_SETS {
    description
      "Common node of routing-policy,
       routing-policy-shadow";
    container sets {
      description
        "Information about configured sets";
      container etag {
        description
          "Information about Etag sets";
        uses live_ncs_SET-TABLE;
        uses live_ncs_UNUSED;
        uses live_ncs_INACTIVE;
        uses live_ncs_ACTIVE;
      }
      container ospf-area {
        description
          "Information about OSPF Area sets";
        uses live_ncs_SET-TABLE;
        uses live_ncs_UNUSED;
        uses live_ncs_INACTIVE;
        uses live_ncs_ACTIVE;
      }
      container extended-community-opaque {
        description
          "Information about Extended Community Opaque
           sets";
        uses live_ncs_SET-TABLE;
        uses live_ncs_UNUSED;
        uses live_ncs_INACTIVE;
        uses live_ncs_ACTIVE;
      }
      container extended-community-seg-nh {
        description
          "Information about Extended Community SegNH sets";
        uses live_ncs_SET-TABLE;
        uses live_ncs_UNUSED;
        uses live_ncs_INACTIVE;
        uses live_ncs_ACTIVE;
      }
      container extended-community-soo {
        description
          "Information about Extended Community SOO sets";
        uses live_ncs_SET-TABLE;
        uses live_ncs_UNUSED;
        uses live_ncs_INACTIVE;
        uses live_ncs_ACTIVE;
      }
      container tag {
        description
          "Information about Tag sets";
        uses live_ncs_SET-TABLE;
        uses live_ncs_UNUSED;
        uses live_ncs_INACTIVE;
        uses live_ncs_ACTIVE;
      }
      container prefix {
        description
          "Information about AS Path sets";
        uses live_ncs_SET-TABLE;
        uses live_ncs_UNUSED;
        uses live_ncs_INACTIVE;
        uses live_ncs_ACTIVE;
      }
      container community {
        description
          "Information about Community sets";
        uses live_ncs_SET-TABLE;
        uses live_ncs_UNUSED;
        uses live_ncs_INACTIVE;
        uses live_ncs_ACTIVE;
      }
      container as-path {
        description
          "Information about AS Path sets";
        uses live_ncs_SET-TABLE;
        uses live_ncs_UNUSED;
        uses live_ncs_INACTIVE;
        uses live_ncs_ACTIVE;
      }
      container large-community {
        description
          "Information about Large Community sets";
        uses live_ncs_SET-TABLE;
        uses live_ncs_UNUSED;
        uses live_ncs_INACTIVE;
        uses live_ncs_ACTIVE;
      }
      container esi {
        description
          "Information about Esi sets";
        uses live_ncs_SET-TABLE;
        uses live_ncs_UNUSED;
        uses live_ncs_INACTIVE;
        uses live_ncs_ACTIVE;
      }
      container extended-community-bandwidth {
        description
          "Information about Extended Community Bandwidth
           sets";
        uses live_ncs_SET-TABLE;
        uses live_ncs_UNUSED;
        uses live_ncs_INACTIVE;
      }
      container extended-community-rt {
        description
          "Information about Extended Community RT sets";
        uses live_ncs_SET-TABLE;
        uses live_ncs_UNUSED;
        uses live_ncs_INACTIVE;
        uses live_ncs_ACTIVE;
      }
      container rd {
        description
          "Information about RD sets";
        uses live_ncs_SET-TABLE;
        uses live_ncs_UNUSED;
        uses live_ncs_INACTIVE;
        uses live_ncs_ACTIVE;
      }
      container mac {
        description
          "Information about Mac sets";
        uses live_ncs_SET-TABLE;
        uses live_ncs_UNUSED;
        uses live_ncs_INACTIVE;
        uses live_ncs_ACTIVE;
      }
      container extended-community-cost {
        description
          "Information about Extended Community Cost sets";
        uses live_ncs_SET-TABLE;
        uses live_ncs_UNUSED;
        uses live_ncs_INACTIVE;
        uses live_ncs_ACTIVE;
      }
    }
  }

  grouping live_ncs_LIMITS {
    description
      "Common node of routing-policy,
       routing-policy-shadow";
    container limits {
      description
        "Information about configured limits and the
         current values";
      uses live_ncs_RPL-MAX-LIMITS-INFO;
    }
  }

  grouping live_ncs_INACTIVE {
    description
      "Common node of policies, as-path, community,
       large-community, extended-community-cost, rd,
       extended-community-rt, extended-community-soo,
       extended-community-opaque,
       extended-community-seg-nh,
       extended-community-bandwidth, prefix, esi, etag,
       mac, tag, ospf-area";
    container inactive {
      description
        "All objects of a given type that are not
         attached to a protocol";
      uses live_ncs_RPL-OBJECTS-INFO;
    }
  }

  grouping live_ncs_POLICIES {
    description
      "Common node of routing-policy,
       routing-policy-shadow";
    container policies {
      description
        "Information about configured route policies";
      container route-policies {
        description
          "Information about individual policies";
        list route-policy {
          key "route-policy-name";
          description
            "Information about an individual policy";
          container policy-uses {
            description
              "Information about which policies and sets
               this policy uses";
            container directly-used-policies {
              description
                "Policies that this policy uses directly";
              uses live_ncs_RPL-OBJECTS-INFO;
            }
            container all-used-sets {
              description
                "Sets used by this policy, or by policies
                 that it uses";
              uses live_ncs_RPL-SETS-INFO;
            }
            container directly-used-sets {
              description
                "Sets that this policy uses directly";
              uses live_ncs_RPL-SETS-INFO;
            }
            container all-used-policies {
              description
                "Policies used by this policy, or by policies
                 that it uses";
              uses live_ncs_RPL-OBJECTS-INFO;
            }
          }
          leaf route-policy-name {
            type xr:Cisco-ios-xr-string;
            description
              "Route policy name";
          }
          uses live_ncs_USED-BY;
          uses live_ncs_ATTACHED;
        }
      }
      uses live_ncs_UNUSED;
      uses live_ncs_INACTIVE;
      uses live_ncs_ACTIVE;
    }
  }

  grouping live_ncs_USED-BY {
    description
      "Common node of route-policy, set";
    container used-by {
      description
        "Policies that use this object, directly or
         indirectly";
      uses live_ncs_RPL-REFERENCES-INFO;
    }
  }

  grouping live_ncs_ACTIVE {
    description
      "Common node of policies, as-path, community,
       large-community, extended-community-cost, rd,
       extended-community-rt, extended-community-soo,
       extended-community-opaque,
       extended-community-seg-nh, prefix, esi, etag, mac
       , tag, ospf-area";
    container active {
      description
        "All objects of a given type that are attached to
         a protocol";
      uses live_ncs_RPL-OBJECTS-INFO;
    }
  }

  grouping live_ncs_ATTACHED {
    description
      "Common node of route-policy, set";
    container attached {
      description
        "Information about where this policy or set is
         attached";
      uses live_ncs_RPL-ATTACHMENT-INFO;
    }
  }

  grouping UNUSED {
    description
      "Common node of policies, as-path, community,
       large-community, extended-community-cost, rd,
       extended-community-rt, extended-community-soo,
       extended-community-opaque,
       extended-community-seg-nh,
       extended-community-bandwidth, prefix, esi, etag,
       mac, tag, ospf-area";
    container unused {
      description
        "All objects of a given type that are not
         referenced at all";
      uses RPL-OBJECTS-INFO;
    }
  }

  grouping SET-TABLE {
    description
      "Common node of as-path, community,
       large-community, extended-community-cost, rd,
       extended-community-rt, extended-community-soo,
       extended-community-opaque,
       extended-community-seg-nh,
       extended-community-bandwidth, prefix, esi, etag,
       mac, tag, ospf-area";
    container sets {
      description
        "Information about individual sets";
      list set {
        key "set-name";
        description
          "Information about an individual set";
        leaf set-name {
          type xr:Cisco-ios-xr-string;
          description
            "Set name";
        }
        uses USED-BY;
        uses ATTACHED;
      }
    }
  }

  grouping SETS {
    description
      "Common node of routing-policy,
       routing-policy-shadow";
    container sets {
      description
        "Information about configured sets";
      container etag {
        description
          "Information about Etag sets";
        uses SET-TABLE;
        uses UNUSED;
        uses INACTIVE;
        uses ACTIVE;
      }
      container ospf-area {
        description
          "Information about OSPF Area sets";
        uses SET-TABLE;
        uses UNUSED;
        uses INACTIVE;
        uses ACTIVE;
      }
      container extended-community-opaque {
        description
          "Information about Extended Community Opaque
           sets";
        uses SET-TABLE;
        uses UNUSED;
        uses INACTIVE;
        uses ACTIVE;
      }
      container extended-community-seg-nh {
        description
          "Information about Extended Community SegNH sets";
        uses SET-TABLE;
        uses UNUSED;
        uses INACTIVE;
        uses ACTIVE;
      }
      container extended-community-soo {
        description
          "Information about Extended Community SOO sets";
        uses SET-TABLE;
        uses UNUSED;
        uses INACTIVE;
        uses ACTIVE;
      }
      container tag {
        description
          "Information about Tag sets";
        uses SET-TABLE;
        uses UNUSED;
        uses INACTIVE;
        uses ACTIVE;
      }
      container prefix {
        description
          "Information about AS Path sets";
        uses SET-TABLE;
        uses UNUSED;
        uses INACTIVE;
        uses ACTIVE;
      }
      container community {
        description
          "Information about Community sets";
        uses SET-TABLE;
        uses UNUSED;
        uses INACTIVE;
        uses ACTIVE;
      }
      container as-path {
        description
          "Information about AS Path sets";
        uses SET-TABLE;
        uses UNUSED;
        uses INACTIVE;
        uses ACTIVE;
      }
      container large-community {
        description
          "Information about Large Community sets";
        uses SET-TABLE;
        uses UNUSED;
        uses INACTIVE;
        uses ACTIVE;
      }
      container esi {
        description
          "Information about Esi sets";
        uses SET-TABLE;
        uses UNUSED;
        uses INACTIVE;
        uses ACTIVE;
      }
      container extended-community-bandwidth {
        description
          "Information about Extended Community Bandwidth
           sets";
        uses SET-TABLE;
        uses UNUSED;
        uses INACTIVE;
      }
      container extended-community-rt {
        description
          "Information about Extended Community RT sets";
        uses SET-TABLE;
        uses UNUSED;
        uses INACTIVE;
        uses ACTIVE;
      }
      container rd {
        description
          "Information about RD sets";
        uses SET-TABLE;
        uses UNUSED;
        uses INACTIVE;
        uses ACTIVE;
      }
      container mac {
        description
          "Information about Mac sets";
        uses SET-TABLE;
        uses UNUSED;
        uses INACTIVE;
        uses ACTIVE;
      }
      container extended-community-cost {
        description
          "Information about Extended Community Cost sets";
        uses SET-TABLE;
        uses UNUSED;
        uses INACTIVE;
        uses ACTIVE;
      }
    }
  }

  grouping LIMITS {
    description
      "Common node of routing-policy,
       routing-policy-shadow";
    container limits {
      description
        "Information about configured limits and the
         current values";
      uses RPL-MAX-LIMITS-INFO;
    }
  }

  grouping INACTIVE {
    description
      "Common node of policies, as-path, community,
       large-community, extended-community-cost, rd,
       extended-community-rt, extended-community-soo,
       extended-community-opaque,
       extended-community-seg-nh,
       extended-community-bandwidth, prefix, esi, etag,
       mac, tag, ospf-area";
    container inactive {
      description
        "All objects of a given type that are not
         attached to a protocol";
      uses RPL-OBJECTS-INFO;
    }
  }

  grouping POLICIES {
    description
      "Common node of routing-policy,
       routing-policy-shadow";
    container policies {
      description
        "Information about configured route policies";
      container route-policies {
        description
          "Information about individual policies";
        list route-policy {
          key "route-policy-name";
          description
            "Information about an individual policy";
          container policy-uses {
            description
              "Information about which policies and sets
               this policy uses";
            container directly-used-policies {
              description
                "Policies that this policy uses directly";
              uses RPL-OBJECTS-INFO;
            }
            container all-used-sets {
              description
                "Sets used by this policy, or by policies
                 that it uses";
              uses RPL-SETS-INFO;
            }
            container directly-used-sets {
              description
                "Sets that this policy uses directly";
              uses RPL-SETS-INFO;
            }
            container all-used-policies {
              description
                "Policies used by this policy, or by policies
                 that it uses";
              uses RPL-OBJECTS-INFO;
            }
          }
          leaf route-policy-name {
            type xr:Cisco-ios-xr-string;
            description
              "Route policy name";
          }
          uses USED-BY;
          uses ATTACHED;
        }
      }
      uses UNUSED;
      uses INACTIVE;
      uses ACTIVE;
    }
  }

  grouping USED-BY {
    description
      "Common node of route-policy, set";
    container used-by {
      description
        "Policies that use this object, directly or
         indirectly";
      uses RPL-REFERENCES-INFO;
    }
  }

  grouping ACTIVE {
    description
      "Common node of policies, as-path, community,
       large-community, extended-community-cost, rd,
       extended-community-rt, extended-community-soo,
       extended-community-opaque,
       extended-community-seg-nh, prefix, esi, etag, mac
       , tag, ospf-area";
    container active {
      description
        "All objects of a given type that are attached to
         a protocol";
      uses RPL-OBJECTS-INFO;
    }
  }

  grouping ATTACHED {
    description
      "Common node of route-policy, set";
    container attached {
      description
        "Information about where this policy or set is
         attached";
      uses RPL-ATTACHMENT-INFO;
    }
  }

  augment "/ncs:devices/ncs:device/ncs:config" {
    // NCS drop config false container 'routing-policy'
    // NCS drop config false container 'routing-policy-shadow'
  }
  augment "/ncs:devices/ncs:device/ncs:live-status" {
    container routing-policy {
      tailf:ncs-device-type "netconf";
      tailf:display-when "not(../../ncs:module) or ../../ncs:module[ncs:name='Cisco-IOS-XR-policy-repository-oper'] or (../../ncs:live-status-protocol[not(ncs:capability)]) or (../../ncs:live-status-protocol/ncs:capability/ncs:module[.='Cisco-IOS-XR-policy-repository-oper'])";
      description
        "Routing policy operational data";
      uses live_ncs_LIMITS;
      uses live_ncs_POLICIES;
      uses live_ncs_SETS;
    }
    container routing-policy-shadow {
      tailf:ncs-device-type "netconf";
      tailf:display-when "not(../../ncs:module) or ../../ncs:module[ncs:name='Cisco-IOS-XR-policy-repository-oper'] or (../../ncs:live-status-protocol[not(ncs:capability)]) or (../../ncs:live-status-protocol/ncs:capability/ncs:module[.='Cisco-IOS-XR-policy-repository-oper'])";
      description
        "routing policy shadow";
      uses live_ncs_LIMITS;
      uses live_ncs_POLICIES;
      uses live_ncs_SETS;
    }
  }
  augment "/ncs:devices/ncs:template/ncs:ned-id/ncs:config" {
    // NCS drop config false container 'routing-policy'
    // NCS drop config false container 'routing-policy-shadow'
  }
}
