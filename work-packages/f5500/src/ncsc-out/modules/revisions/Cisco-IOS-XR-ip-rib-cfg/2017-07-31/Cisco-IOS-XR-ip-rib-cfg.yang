module Cisco-IOS-XR-ip-rib-cfg {
  // Generated by yanger -t ncs
  tailf:mount-id f5500-nc-1.0:f5500-nc-1.0;
  tailf:ncs-device-type "netconf";

  namespace "http://cisco.com/ns/yang/Cisco-IOS-XR-ip-rib-cfg";
  prefix Cisco-IOS-XR-ip-rib-cfg;

  import Cisco-IOS-XR-infra-rsi-cfg {
    prefix a1;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ip-rib package configuration.

     This module contains definitions
     for the following management objects:
       rib: RIB configuration.

     This YANG module augments the
       Cisco-IOS-XR-infra-rsi-cfg
     module with configuration data.

     Copyright (c) 2013-2018 by Cisco Systems, Inc.
     All rights reserved.";

  revision 2017-07-31 {
    description
      "Fixed missing augmentation from multiple MDA parent.";
  }
  revision 2015-11-09 {
    description
      "IOS XR 6.0 revision.";
  }

  grouping ncs_template_NEXT-HOP-DAMPENING-DISABLE {
    description
      "Common node of ipv4, ipv6";
    leaf next-hop-dampening-disable {
      type empty;
      description
        "Disable next-hop dampening";
    }
  }

  grouping ncs_template_REDISTRIBUTION-HISTORY {
    description
      "Common node of ipv4, ipv6";
    container redistribution-history {
      description
        "Redistribution history related configs";
      container keep {
        description
          "Retain redistribution history after disconnect.";
        leaf bcdl {
          type empty;
          description
            "Enable retain BCDL history";
        }
      }
      leaf bcdl-client {
        type string;
        description
          "Maximum BCDL redistribution history size.";
      }
      leaf protocol-client {
        type string;
        description
          "Maximum protocol redistribution history size.";
      }
    }
  }

  grouping ncs_rpc_notif_NEXT-HOP-DAMPENING-DISABLE {
    description
      "Common node of ipv4, ipv6";
    leaf next-hop-dampening-disable {
      type empty;
      description
        "Disable next-hop dampening";
    }
  }

  grouping ncs_rpc_notif_REDISTRIBUTION-HISTORY {
    description
      "Common node of ipv4, ipv6";
    container redistribution-history {
      description
        "Redistribution history related configs";
      container keep {
        description
          "Retain redistribution history after disconnect.";
        leaf bcdl {
          type empty;
          description
            "Enable retain BCDL history";
        }
      }
      leaf bcdl-client {
        type uint32 {
          range "10..2000000";
        }
        description
          "Maximum BCDL redistribution history size.";
      }
      leaf protocol-client {
        type uint32 {
          range "10..250000";
        }
        description
          "Maximum protocol redistribution history size.";
      }
    }
  }

  grouping live_ncs_NEXT-HOP-DAMPENING-DISABLE {
    description
      "Common node of ipv4, ipv6";
    leaf next-hop-dampening-disable {
      type empty;
      description
        "Disable next-hop dampening";
    }
  }

  grouping live_ncs_REDISTRIBUTION-HISTORY {
    description
      "Common node of ipv4, ipv6";
    container redistribution-history {
      description
        "Redistribution history related configs";
      container keep {
        description
          "Retain redistribution history after disconnect.";
        leaf bcdl {
          type empty;
          description
            "Enable retain BCDL history";
        }
      }
      leaf bcdl-client {
        type uint32 {
          range "10..2000000";
        }
        description
          "Maximum BCDL redistribution history size.";
      }
      leaf protocol-client {
        type uint32 {
          range "10..250000";
        }
        description
          "Maximum protocol redistribution history size.";
      }
    }
  }

  grouping NEXT-HOP-DAMPENING-DISABLE {
    description
      "Common node of ipv4, ipv6";
    leaf next-hop-dampening-disable {
      type empty;
      description
        "Disable next-hop dampening";
    }
  }

  grouping REDISTRIBUTION-HISTORY {
    description
      "Common node of ipv4, ipv6";
    container redistribution-history {
      description
        "Redistribution history related configs";
      container keep {
        description
          "Retain redistribution history after disconnect.";
        leaf bcdl {
          type empty;
          description
            "Enable retain BCDL history";
        }
      }
      leaf bcdl-client {
        type uint32 {
          range "10..2000000";
        }
        description
          "Maximum BCDL redistribution history size.";
      }
      leaf protocol-client {
        type uint32 {
          range "10..250000";
        }
        description
          "Maximum protocol redistribution history size.";
      }
    }
  }

  augment "/ncs:devices/ncs:device/ncs:config" {
    container rib {
      tailf:ncs-device-type "netconf";
      tailf:display-when "not(../../ncs:module) or ../../ncs:module[ncs:name='Cisco-IOS-XR-ip-rib-cfg']";
      description
        "RIB configuration.";
      container af {
        description
          "RIB address family configuration";
        container ipv4 {
          description
            "IPv4 configuration";
          uses NEXT-HOP-DAMPENING-DISABLE;
          uses REDISTRIBUTION-HISTORY;
        }
        container ipv6 {
          description
            "IPv6 configuration";
          uses NEXT-HOP-DAMPENING-DISABLE;
          uses REDISTRIBUTION-HISTORY;
        }
      }
      leaf max-recursion-depth {
        type uint32 {
          range "5..16";
        }
        description
          "Set maximum depth for route recursion check";
      }
    }
  }
  augment "/ncs:devices/ncs:device/ncs:live-status" {
    container rib {
      tailf:ncs-device-type "netconf";
      tailf:display-when "not(../../ncs:module) or ../../ncs:module[ncs:name='Cisco-IOS-XR-ip-rib-cfg'] or (../../ncs:live-status-protocol[not(ncs:capability)]) or (../../ncs:live-status-protocol/ncs:capability/ncs:module[.='Cisco-IOS-XR-ip-rib-cfg'])";
      description
        "RIB configuration.";
      container af {
        description
          "RIB address family configuration";
        container ipv4 {
          description
            "IPv4 configuration";
          uses live_ncs_NEXT-HOP-DAMPENING-DISABLE;
          uses live_ncs_REDISTRIBUTION-HISTORY;
        }
        container ipv6 {
          description
            "IPv6 configuration";
          uses live_ncs_NEXT-HOP-DAMPENING-DISABLE;
          uses live_ncs_REDISTRIBUTION-HISTORY;
        }
      }
      leaf max-recursion-depth {
        type uint32 {
          range "5..16";
        }
        description
          "Set maximum depth for route recursion check";
      }
    }
  }
  augment "/ncs:devices/ncs:template/ncs:ned-id/ncs:config" {
    container rib {
      description
        "RIB configuration.";
      container af {
        description
          "RIB address family configuration";
        container ipv4 {
          description
            "IPv4 configuration";
          uses ncs_template_NEXT-HOP-DAMPENING-DISABLE;
          uses ncs_template_REDISTRIBUTION-HISTORY;
        }
        container ipv6 {
          description
            "IPv6 configuration";
          uses ncs_template_NEXT-HOP-DAMPENING-DISABLE;
          uses ncs_template_REDISTRIBUTION-HISTORY;
        }
      }
      leaf max-recursion-depth {
        type string;
        description
          "Set maximum depth for route recursion check";
      }
    }
  }
  augment "/ncs:devices/ncs:template/ncs:ned-id/ncs:config/a1:vrfs/a1:vrf/a1:afs/a1:af" {
    container maximum-prefix {
      presence "Indicates a maximum-prefix node is configured.";
      description
        "Set maximum prefix limits";
      leaf prefix-limit {
        type string;
        // NCS drop mandatory statement
        description
          "Set table's maximum prefix limit";
      }
      leaf mid-threshold {
        type string;
        description
          "Mid-threshold (% of maximum)";
      }
    }
    description
      "This augment extends the configuration data of
       'Cisco-IOS-XR-infra-rsi-cfg'";
  }
  augment "/ncs:devices/ncs:device/ncs:live-status/a1:vrfs/a1:vrf/a1:afs/a1:af" {
    container maximum-prefix {
      tailf:ncs-device-type "netconf";
      tailf:display-when "not(../../../../../../ncs:module) or ../../../../../../ncs:module[ncs:name='Cisco-IOS-XR-ip-rib-cfg'] or (../../../../../../ncs:live-status-protocol[not(ncs:capability)]) or (../../../../../../ncs:live-status-protocol/ncs:capability/ncs:module[.='Cisco-IOS-XR-ip-rib-cfg'])";
      presence "Indicates a maximum-prefix node is configured.";
      description
        "Set maximum prefix limits";
      leaf prefix-limit {
        type uint32 {
          range "32..10000000";
        }
        // NCS drop mandatory statement
        description
          "Set table's maximum prefix limit";
      }
      leaf mid-threshold {
        type uint32 {
          range "1..100";
        }
        description
          "Mid-threshold (% of maximum)";
      }
    }
    description
      "This augment extends the configuration data of
       'Cisco-IOS-XR-infra-rsi-cfg'";
  }
  augment "/ncs:devices/ncs:device/ncs:config/a1:vrfs/a1:vrf/a1:afs/a1:af" {
    container maximum-prefix {
      tailf:ncs-device-type "netconf";
      tailf:display-when "not(../../../../../../ncs:module) or ../../../../../../ncs:module[ncs:name='Cisco-IOS-XR-ip-rib-cfg']";
      presence "Indicates a maximum-prefix node is configured.";
      description
        "Set maximum prefix limits";
      leaf prefix-limit {
        type uint32 {
          range "32..10000000";
        }
        mandatory true;
        description
          "Set table's maximum prefix limit";
      }
      leaf mid-threshold {
        type uint32 {
          range "1..100";
        }
        description
          "Mid-threshold (% of maximum)";
      }
    }
    description
      "This augment extends the configuration data of
       'Cisco-IOS-XR-infra-rsi-cfg'";
  }
  augment "/ncs:devices/ncs:template/ncs:ned-id/ncs:config/a1:global-af/a1:afs/a1:af" {
    container maximum-prefix {
      presence "Indicates a maximum-prefix node is configured.";
      description
        "Set maximum prefix limits";
      leaf prefix-limit {
        type string;
        // NCS drop mandatory statement
        description
          "Set table's maximum prefix limit";
      }
      leaf mid-threshold {
        type string;
        description
          "Mid-threshold (% of maximum)";
      }
    }
    description
      "This augment extends the configuration data of
       'Cisco-IOS-XR-infra-rsi-cfg'";
  }
  augment "/ncs:devices/ncs:device/ncs:live-status/a1:global-af/a1:afs/a1:af" {
    container maximum-prefix {
      tailf:ncs-device-type "netconf";
      tailf:display-when "not(../../../../../ncs:module) or ../../../../../ncs:module[ncs:name='Cisco-IOS-XR-ip-rib-cfg'] or (../../../../../ncs:live-status-protocol[not(ncs:capability)]) or (../../../../../ncs:live-status-protocol/ncs:capability/ncs:module[.='Cisco-IOS-XR-ip-rib-cfg'])";
      presence "Indicates a maximum-prefix node is configured.";
      description
        "Set maximum prefix limits";
      leaf prefix-limit {
        type uint32 {
          range "32..10000000";
        }
        // NCS drop mandatory statement
        description
          "Set table's maximum prefix limit";
      }
      leaf mid-threshold {
        type uint32 {
          range "1..100";
        }
        description
          "Mid-threshold (% of maximum)";
      }
    }
    description
      "This augment extends the configuration data of
       'Cisco-IOS-XR-infra-rsi-cfg'";
  }
  augment "/ncs:devices/ncs:device/ncs:config/a1:global-af/a1:afs/a1:af" {
    container maximum-prefix {
      tailf:ncs-device-type "netconf";
      tailf:display-when "not(../../../../../ncs:module) or ../../../../../ncs:module[ncs:name='Cisco-IOS-XR-ip-rib-cfg']";
      presence "Indicates a maximum-prefix node is configured.";
      description
        "Set maximum prefix limits";
      leaf prefix-limit {
        type uint32 {
          range "32..10000000";
        }
        mandatory true;
        description
          "Set table's maximum prefix limit";
      }
      leaf mid-threshold {
        type uint32 {
          range "1..100";
        }
        description
          "Mid-threshold (% of maximum)";
      }
    }
    description
      "This augment extends the configuration data of
       'Cisco-IOS-XR-infra-rsi-cfg'";
  }
}
