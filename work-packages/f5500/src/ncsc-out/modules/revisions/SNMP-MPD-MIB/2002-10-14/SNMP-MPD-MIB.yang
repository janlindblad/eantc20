module SNMP-MPD-MIB {
  // Generated by yanger -t ncs
  tailf:mount-id f5500-nc-1.0:f5500-nc-1.0;
  tailf:ncs-device-type "netconf";

  namespace "http://tail-f.com/ns/mibs/SNMP-MPD-MIB/200210140000Z";
  prefix SNMP-MPD-MIB;
  // NCS drop tailf:id
  tailf:snmp-mib-module-name SNMP-MPD-MIB;

  import ietf-yang-types {
    prefix yang;
  }
  import tailf-common {
    prefix tailf;
  }
  import "f5500-nc-1.0" {
    prefix "f5500-nc-1.0";
  }
  import tailf-ncs {
    prefix ncs;
  }

  revision 2002-10-14 {
    description
      "";
  }

  augment "/ncs:devices/ncs:device/ncs:config" {
    // NCS drop config false container 'SNMP-MPD-MIB'
  }
  augment "/ncs:devices/ncs:device/ncs:live-status" {
    container SNMP-MPD-MIB {
      tailf:ncs-device-type "netconf";
      tailf:display-when "not(../../ncs:module) or ../../ncs:module[ncs:name='SNMP-MPD-MIB'] or (../../ncs:live-status-protocol[not(ncs:capability)]) or (../../ncs:live-status-protocol/ncs:capability/ncs:module[.='SNMP-MPD-MIB'])";
      container snmpMPDStats {
        tailf:snmp-oid "1.3.6.1.6.3.11.2.1";
        leaf snmpUnknownSecurityModels {
          type yang:counter32;
          tailf:snmp-oid "1.3.6.1.6.3.11.2.1.1";
        }
        leaf snmpInvalidMsgs {
          type yang:counter32;
          tailf:snmp-oid "1.3.6.1.6.3.11.2.1.2";
        }
        leaf snmpUnknownPDUHandlers {
          type yang:counter32;
          tailf:snmp-oid "1.3.6.1.6.3.11.2.1.3";
        }
      }
    }
  }
  augment "/ncs:devices/ncs:template/ncs:ned-id/ncs:config" {
    // NCS drop config false container 'SNMP-MPD-MIB'
  }
}
