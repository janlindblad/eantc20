module Cisco-IOS-XR-drivers-media-eth-act {
  // Generated by yanger -t ncs
  tailf:mount-id f5500-nc-1.0:f5500-nc-1.0;
  tailf:ncs-device-type "netconf";

  namespace "http://cisco.com/ns/yang/Cisco-IOS-XR-drivers-media-eth-act";
  prefix Cisco-IOS-XR-drivers-media-eth-act;

  import Cisco-IOS-XR-types {
    prefix csc;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2018 by Cisco Systems, Inc.
     All rights reserved.";

  revision 2018-02-12 {
    description
      "IOS XR 6.5.1 revision.";
  }

  augment "/ncs:devices/ncs:device/ncs:rpc" {
    container rpc-clear-controller-counters {
      tailf:ncs-device-type "netconf";
      tailf:display-when "not(../../ncs:module) or ../../ncs:module[ncs:name='Cisco-IOS-XR-drivers-media-eth-act']";
      tailf:action clear-controller-counters {
        tailf:actionpoint ncsproxy {
          tailf:internal;
        }
        csc:xr-task "interface";
        csc:cli-command "clear controller <controller-name> stats";
        description
          "Clear Ethernet MAC ASIC statistics.";
        input {
          leaf controller-name {
            mandatory true;
            type csc:Interface-name;
            description
              "Controller name";
          }
        }
      }
    }
  }
  augment "/ncs:devices/ncs:device-group/ncs:ned-id/ncs:rpc" {
    container rpc-clear-controller-counters {
      tailf:ncs-device-type "netconf";
      tailf:display-when "/ncs:devices/ncs:device[ncs:name=current()/../../../ncs:member]/ncs:module[ncs:name='Cisco-IOS-XR-drivers-media-eth-act']";
      tailf:action clear-controller-counters {
        tailf:actionpoint ncsproxy {
          tailf:internal;
        }
        csc:xr-task "interface";
        csc:cli-command "clear controller <controller-name> stats";
        description
          "Clear Ethernet MAC ASIC statistics.";
        input {
          leaf controller-name {
            mandatory true;
            type csc:Interface-name;
            description
              "Controller name";
          }
        }
      }
    }
  }
}
