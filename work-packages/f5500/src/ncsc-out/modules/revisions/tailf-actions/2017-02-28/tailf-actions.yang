module tailf-actions {
  // Generated by yanger -t ncs
  tailf:mount-id f5500-nc-1.0:f5500-nc-1.0;
  tailf:ncs-device-type "netconf";

  namespace "http://tail-f.com/ns/netconf/actions/1.0";
  prefix act;

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains YANG definitions
     for Cisco IOS-XR and Tail-F action support.

     Copyright (c) 2017 by Cisco Systems, Inc.
     All rights reserved.";

  revision 2017-02-28 {
    description
      "Descriptions Initial support for Tail-F actions.
       IOS XR 6.3.1 revision.";
  }

  augment "/ncs:devices/ncs:device/ncs:rpc" {
    container rpc-action {
      tailf:ncs-device-type "netconf";
      tailf:display-when "not(../../ncs:module) or ../../ncs:module[ncs:name='tailf-actions']";
      tailf:action action {
        tailf:actionpoint ncsproxy {
          tailf:internal;
        }
        description
          "Support Tail-F actions rpc format.";
        reference "RFC 6241, Section 7.1";
        input {
          anyxml data {
            description
              "Data section of the YANG action hierarchy.";
          }
        }
        output {
          anyxml data {
            description
              "Data and messages returned by the Tail-F ConfD agent.";
          }
        }
      }
    }
  }
  augment "/ncs:devices/ncs:device-group/ncs:ned-id/ncs:rpc" {
    container rpc-action {
      tailf:ncs-device-type "netconf";
      tailf:display-when "/ncs:devices/ncs:device[ncs:name=current()/../../../ncs:member]/ncs:module[ncs:name='tailf-actions']";
      tailf:action action {
        tailf:actionpoint ncsproxy {
          tailf:internal;
        }
        description
          "Support Tail-F actions rpc format.";
        reference "RFC 6241, Section 7.1";
        input {
          anyxml data {
            description
              "Data section of the YANG action hierarchy.";
          }
        }
        output {
          container "device" {
            leaf "name" {
              type string;
            }
            leaf "info" {
              type string;
            }
            container "result" {
              anyxml data {
                description
                  "Data and messages returned by the Tail-F ConfD agent.";
              }
            }
          }
        }
      }
    }
  }
}
