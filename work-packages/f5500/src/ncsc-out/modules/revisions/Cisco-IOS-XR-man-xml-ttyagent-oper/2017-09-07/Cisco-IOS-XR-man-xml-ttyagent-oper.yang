module Cisco-IOS-XR-man-xml-ttyagent-oper {
  // Generated by yanger -t ncs
  tailf:mount-id f5500-nc-1.0:f5500-nc-1.0;
  tailf:ncs-device-type "netconf";

  namespace "http://cisco.com/ns/yang/Cisco-IOS-XR-man-xml-ttyagent-oper";
  prefix Cisco-IOS-XR-man-xml-ttyagent-oper;

  include Cisco-IOS-XR-man-xml-ttyagent-oper-sub1 {
    revision-date 2017-09-07;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR man-xml-ttyagent package operational data.

     This module contains definitions
     for the following management objects:
       netconf: NETCONF operational information
       xr-xml: xr xml

     Copyright (c) 2013-2018 by Cisco Systems, Inc.
     All rights reserved.";

  revision 2017-09-07 {
    description
      "Fixed type translation error.";
  }
  revision 2015-07-30 {
    description
      "Descriptions updated.";
  }
  revision 2015-01-07 {
    description
      "IOS XR 5.3.1 revision.";
  }

  grouping ncs_template_SESSION-TABLE {
    description
      "Common node of default, tty, ssl";
    container sessions {
      description
        "sessions information";
      list session {
        // NCS patched for predictable order
        ordered-by user;
        key "session-id";
        description
          "xml sessions information";
        leaf session-id {
          type string;
          description
            "Session Id";
        }
        uses ncs_template_XR-XML-SESSION-INFO;
      }
    }
  }

  grouping ncs_rpc_notif_SESSION-TABLE {
    description
      "Common node of default, tty, ssl";
    container sessions {
      description
        "sessions information";
      list session {
        key "session-id";
        description
          "xml sessions information";
        leaf session-id {
          type uint32;
          description
            "Session Id";
        }
        uses ncs_rpc_notif_XR-XML-SESSION-INFO;
      }
    }
  }

  grouping live_ncs_SESSION-TABLE {
    description
      "Common node of default, tty, ssl";
    container sessions {
      description
        "sessions information";
      list session {
        key "session-id";
        description
          "xml sessions information";
        leaf session-id {
          type uint32;
          description
            "Session Id";
        }
        uses live_ncs_XR-XML-SESSION-INFO;
      }
    }
  }

  grouping SESSION-TABLE {
    description
      "Common node of default, tty, ssl";
    container sessions {
      description
        "sessions information";
      list session {
        key "session-id";
        description
          "xml sessions information";
        leaf session-id {
          type uint32;
          description
            "Session Id";
        }
        uses XR-XML-SESSION-INFO;
      }
    }
  }

  augment "/ncs:devices/ncs:device/ncs:config" {
    // NCS drop config false container netconf
    // NCS drop config false container 'xr-xml'
  }
  augment "/ncs:devices/ncs:device/ncs:live-status" {
    container netconf {
      tailf:ncs-device-type "netconf";
      tailf:display-when "not(../../ncs:module) or ../../ncs:module[ncs:name='Cisco-IOS-XR-man-xml-ttyagent-oper'] or (../../ncs:live-status-protocol[not(ncs:capability)]) or (../../ncs:live-status-protocol/ncs:capability/ncs:module[.='Cisco-IOS-XR-man-xml-ttyagent-oper'])";
      description
        "NETCONF operational information";
      container agent {
        description
          "NETCONF agent operational information";
        container tty {
          description
            "NETCONF agent over TTY";
          container sessions {
            description
              "Session information";
            list session {
              key "session-id";
              description
                "Session information";
              leaf session-id {
                type uint32;
                description
                  "Session ID";
              }
              uses live_ncs_XR-XML-SESSION-INFO;
            }
          }
        }
      }
    }
    container xr-xml {
      tailf:ncs-device-type "netconf";
      tailf:display-when "not(../../ncs:module) or ../../ncs:module[ncs:name='Cisco-IOS-XR-man-xml-ttyagent-oper'] or (../../ncs:live-status-protocol[not(ncs:capability)]) or (../../ncs:live-status-protocol/ncs:capability/ncs:module[.='Cisco-IOS-XR-man-xml-ttyagent-oper'])";
      description
        "xr xml";
      container agent {
        description
          "XML agents";
        container tty {
          description
            "TTY sessions information";
          uses live_ncs_SESSION-TABLE;
        }
        container default {
          description
            "Default sessions information";
          uses live_ncs_SESSION-TABLE;
        }
        container ssl {
          description
            "SSL sessions information";
          uses live_ncs_SESSION-TABLE;
        }
      }
    }
  }
  augment "/ncs:devices/ncs:template/ncs:ned-id/ncs:config" {
    // NCS drop config false container netconf
    // NCS drop config false container 'xr-xml'
  }
}
