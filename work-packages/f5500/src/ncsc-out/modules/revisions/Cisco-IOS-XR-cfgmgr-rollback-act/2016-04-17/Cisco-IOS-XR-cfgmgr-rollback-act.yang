module Cisco-IOS-XR-cfgmgr-rollback-act {
  // Generated by yanger -t ncs
  tailf:mount-id f5500-nc-1.0:f5500-nc-1.0;
  tailf:ncs-device-type "netconf";

  namespace "http://cisco.com/ns/yang/Cisco-IOS-XR-cfgmgr-rollback-act";
  prefix Cisco-IOS-XR-cfgmgr-rollback-act;

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2016 by Cisco Systems, Inc.
     All rights reserved.";

  revision 2016-04-17 {
    description
      "IOS XR 6.1.1 revision.";
  }

  grouping ncs_template_ROLLBACK-ATTRIBUTES {
    leaf force {
      // NCS drop when statement
      description
        "Override commit blocks";
      type string;
      // NCS drop default statement
    }
    leaf best-effort {
      // NCS drop when statement
      description
        "Rollback via best-effort operation";
      type string;
      // NCS drop default statement
    }
    leaf label {
      description
        "Assign a label to this rollback";
      type string;
    }
    leaf comment {
      description
        "Assign a comment to this rollback";
      type string;
    }
  }

  grouping ncs_rpc_notif_ROLLBACK-ATTRIBUTES {
    leaf force {
      when "../best-effort = 'false'" {
        tailf:xpath-root 3;
        description
          "Only when best-effort is false.";
      }
      description
        "Override commit blocks";
      type boolean;
      default "false";
    }
    leaf best-effort {
      when "../force = 'false'" {
        tailf:xpath-root 3;
        description
          "Only when force is false.";
      }
      description
        "Rollback via best-effort operation";
      type boolean;
      default "false";
    }
    leaf label {
      description
        "Assign a label to this rollback";
      type string;
    }
    leaf comment {
      description
        "Assign a comment to this rollback";
      type string;
    }
  }

  grouping live_ncs_ROLLBACK-ATTRIBUTES {
    leaf force {
      // NCS drop when statement
      description
        "Override commit blocks";
      type boolean;
      // NCS drop default statement
    }
    leaf best-effort {
      // NCS drop when statement
      description
        "Rollback via best-effort operation";
      type boolean;
      // NCS drop default statement
    }
    leaf label {
      description
        "Assign a label to this rollback";
      type string;
    }
    leaf comment {
      description
        "Assign a comment to this rollback";
      type string;
    }
  }

  grouping ROLLBACK-ATTRIBUTES {
    leaf force {
      when "../best-effort = 'false'" {
        tailf:xpath-root 3;
        description
          "Only when best-effort is false.";
      }
      description
        "Override commit blocks";
      type boolean;
      default "false";
    }
    leaf best-effort {
      when "../force = 'false'" {
        tailf:xpath-root 3;
        description
          "Only when force is false.";
      }
      description
        "Rollback via best-effort operation";
      type boolean;
      default "false";
    }
    leaf label {
      description
        "Assign a label to this rollback";
      type string;
    }
    leaf comment {
      description
        "Assign a comment to this rollback";
      type string;
    }
  }

  augment "/ncs:devices/ncs:device/ncs:rpc" {
    container rpc-roll-back-configuration {
      tailf:ncs-device-type "netconf";
      tailf:display-when "not(../../ncs:module) or ../../ncs:module[ncs:name='Cisco-IOS-XR-cfgmgr-rollback-act']";
      tailf:action roll-back-configuration {
        tailf:actionpoint ncsproxy {
          tailf:internal;
        }
        description
          "Rollback a specific commit";
        input {
          leaf commit-id {
            description
              "Commit ID";
            type string;
            mandatory true;
          }
          uses ncs_rpc_notif_ROLLBACK-ATTRIBUTES;
        }
      }
    }
  }
  augment "/ncs:devices/ncs:device-group/ncs:ned-id/ncs:rpc" {
    container rpc-roll-back-configuration {
      tailf:ncs-device-type "netconf";
      tailf:display-when "/ncs:devices/ncs:device[ncs:name=current()/../../../ncs:member]/ncs:module[ncs:name='Cisco-IOS-XR-cfgmgr-rollback-act']";
      tailf:action roll-back-configuration {
        tailf:actionpoint ncsproxy {
          tailf:internal;
        }
        description
          "Rollback a specific commit";
        input {
          leaf commit-id {
            description
              "Commit ID";
            type string;
            mandatory true;
          }
          uses ncs_rpc_notif_ROLLBACK-ATTRIBUTES;
        }
      }
    }
  }
  augment "/ncs:devices/ncs:device/ncs:rpc" {
    container rpc-roll-back-configuration-to-exclude {
      tailf:ncs-device-type "netconf";
      tailf:display-when "not(../../ncs:module) or ../../ncs:module[ncs:name='Cisco-IOS-XR-cfgmgr-rollback-act']";
      tailf:action roll-back-configuration-to-exclude {
        tailf:actionpoint ncsproxy {
          tailf:internal;
        }
        description
          "Rollback up to (and excluding) a specific commit";
        input {
          leaf commit-id {
            description
              "Commit ID";
            type string;
            mandatory true;
          }
          uses ncs_rpc_notif_ROLLBACK-ATTRIBUTES;
        }
      }
    }
  }
  augment "/ncs:devices/ncs:device-group/ncs:ned-id/ncs:rpc" {
    container rpc-roll-back-configuration-to-exclude {
      tailf:ncs-device-type "netconf";
      tailf:display-when "/ncs:devices/ncs:device[ncs:name=current()/../../../ncs:member]/ncs:module[ncs:name='Cisco-IOS-XR-cfgmgr-rollback-act']";
      tailf:action roll-back-configuration-to-exclude {
        tailf:actionpoint ncsproxy {
          tailf:internal;
        }
        description
          "Rollback up to (and excluding) a specific commit";
        input {
          leaf commit-id {
            description
              "Commit ID";
            type string;
            mandatory true;
          }
          uses ncs_rpc_notif_ROLLBACK-ATTRIBUTES;
        }
      }
    }
  }
  augment "/ncs:devices/ncs:device/ncs:rpc" {
    container rpc-roll-back-configuration-to {
      tailf:ncs-device-type "netconf";
      tailf:display-when "not(../../ncs:module) or ../../ncs:module[ncs:name='Cisco-IOS-XR-cfgmgr-rollback-act']";
      tailf:action roll-back-configuration-to {
        tailf:actionpoint ncsproxy {
          tailf:internal;
        }
        description
          "Rollback up to (and including) a specific commit";
        input {
          leaf commit-id {
            description
              "Commit ID";
            type string;
            mandatory true;
          }
          uses ncs_rpc_notif_ROLLBACK-ATTRIBUTES;
        }
      }
    }
  }
  augment "/ncs:devices/ncs:device-group/ncs:ned-id/ncs:rpc" {
    container rpc-roll-back-configuration-to {
      tailf:ncs-device-type "netconf";
      tailf:display-when "/ncs:devices/ncs:device[ncs:name=current()/../../../ncs:member]/ncs:module[ncs:name='Cisco-IOS-XR-cfgmgr-rollback-act']";
      tailf:action roll-back-configuration-to {
        tailf:actionpoint ncsproxy {
          tailf:internal;
        }
        description
          "Rollback up to (and including) a specific commit";
        input {
          leaf commit-id {
            description
              "Commit ID";
            type string;
            mandatory true;
          }
          uses ncs_rpc_notif_ROLLBACK-ATTRIBUTES;
        }
      }
    }
  }
  augment "/ncs:devices/ncs:device/ncs:rpc" {
    container rpc-roll-back-configuration-last {
      tailf:ncs-device-type "netconf";
      tailf:display-when "not(../../ncs:module) or ../../ncs:module[ncs:name='Cisco-IOS-XR-cfgmgr-rollback-act']";
      tailf:action roll-back-configuration-last {
        tailf:actionpoint ncsproxy {
          tailf:internal;
        }
        description
          "Rollback last <n> commits made";
        input {
          leaf count {
            description
              "Number of commits to rollback";
            type int32 {
              range "1..100";
            }
            mandatory true;
          }
          uses ncs_rpc_notif_ROLLBACK-ATTRIBUTES;
        }
      }
    }
  }
  augment "/ncs:devices/ncs:device-group/ncs:ned-id/ncs:rpc" {
    container rpc-roll-back-configuration-last {
      tailf:ncs-device-type "netconf";
      tailf:display-when "/ncs:devices/ncs:device[ncs:name=current()/../../../ncs:member]/ncs:module[ncs:name='Cisco-IOS-XR-cfgmgr-rollback-act']";
      tailf:action roll-back-configuration-last {
        tailf:actionpoint ncsproxy {
          tailf:internal;
        }
        description
          "Rollback last <n> commits made";
        input {
          leaf count {
            description
              "Number of commits to rollback";
            type int32 {
              range "1..100";
            }
            mandatory true;
          }
          uses ncs_rpc_notif_ROLLBACK-ATTRIBUTES;
        }
      }
    }
  }
}
