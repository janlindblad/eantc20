module Cisco-IOS-XR-sysadmin-ds {
  // Generated by yanger -t ncs
  tailf:mount-id f5500-nc-1.0:f5500-nc-1.0;
  tailf:ncs-device-type "netconf";

  namespace "http://www.cisco.com/ns/yang/Cisco-IOS-XR-sysadmin-ds";
  prefix Cisco-IOS-XR-sysadmin-ds;

  import ietf-inet-types {
    prefix inet;
  }
  import Cisco-IOS-XR-sysadmin-show-trace {
    prefix show_trace;
  }
  import "f5500-nc-1.0" {
    prefix "f5500-nc-1.0";
  }
  import tailf-ncs {
    prefix ncs;
  }
  import tailf-common {
    prefix tailf;
  }

  organization
    "Cisco Systems Inc.";
  contact
    "Cisco Systems, Inc.
     Customer Service

     Postal: 170 West Tasman Drive
     San Jose, CA 95134

     Tel: +1 800 553-NETS

     E-mail: cs-yang@cisco.com";
  description
    "This module contains definitions
     for the Calvados model objects.

     This module contains a collection of YANG
     definitions for Cisco IOS-XR SysAdmin configuration.

     The Directory Services (DS).

     Copyright(c) 2010-2017 by Cisco Systems, Inc.
     All rights reserved.

     Copyright (c) 2012-2018 by Cisco Systems, Inc.
     All rights reserved.";

  revision 2018-05-21 {
    description
      "Added string description for some show options";
  }

  typedef process-issu-role {
    type enumeration {
      enum "Primary" {
        value 1;
      }
      enum "Secondary" {
        value 2;
      }
      enum "Tertiary" {
        value 3;
      }
      enum "Unknown" {
        value 254;
      }
    }
  }

  typedef process-role {
    type enumeration {
      enum "NoRole";
      enum "Active";
      enum "Standby";
      enum "None";
      enum "Unknown" {
        value 254;
      }
    }
  }

  typedef service-scope {
    type enumeration {
      enum "None";
      enum "Rack";
      enum "System";
      enum "Node";
    }
  }

  grouping ncs_template_servicesGroup {
    list services {
      // NCS patched for predictable order
      ordered-by user;
      key "name";
      leaf name {
        type string;
        description
          "Name of the service";
      }
      list endpoint {
        // NCS patched for predictable order
        ordered-by user;
        description
          "endpoint info for a service in DS";
        leaf scope {
          type string;
        }
        leaf ip {
          type string;
        }
        leaf port {
          type string;
        }
        leaf role {
          type string;
        }
        leaf issu_role {
          type string;
        }
        leaf node {
          type string;
          description
            "Ethernet address of the node hosting the endpoint";
        }
      }
      list registrations {
        // NCS patched for predictable order
        ordered-by user;
        description
          "clients registered for a service in DS";
        leaf client {
          type string;
        }
        leaf pid {
          type string;
        }
      }
    }
  }

  grouping ncs_rpc_notif_servicesGroup {
    list services {
      key "name";
      leaf name {
        type string;
        description
          "Name of the service";
      }
      list endpoint {
        description
          "endpoint info for a service in DS";
        leaf scope {
          type service-scope;
        }
        leaf ip {
          type inet:ipv4-address;
        }
        leaf port {
          type inet:port-number;
        }
        leaf role {
          type process-role;
        }
        leaf issu_role {
          type process-issu-role;
        }
        leaf node {
          type string;
          description
            "Ethernet address of the node hosting the endpoint";
        }
      }
      list registrations {
        description
          "clients registered for a service in DS";
        leaf client {
          type string;
        }
        leaf pid {
          type uint32;
        }
      }
    }
  }

  grouping live_ncs_servicesGroup {
    list services {
      key "name";
      leaf name {
        type string;
        description
          "Name of the service";
      }
      list endpoint {
        description
          "endpoint info for a service in DS";
        leaf scope {
          type service-scope;
        }
        leaf ip {
          type inet:ipv4-address;
        }
        leaf port {
          type inet:port-number;
        }
        leaf role {
          type process-role;
        }
        leaf issu_role {
          type process-issu-role;
        }
        leaf node {
          type string;
          description
            "Ethernet address of the node hosting the endpoint";
        }
      }
      list registrations {
        description
          "clients registered for a service in DS";
        leaf client {
          type string;
        }
        leaf pid {
          type uint32;
        }
      }
    }
  }

  grouping servicesGroup {
    list services {
      key "name";
      leaf name {
        type string;
        description
          "Name of the service";
      }
      list endpoint {
        description
          "endpoint info for a service in DS";
        leaf scope {
          type service-scope;
        }
        leaf ip {
          type inet:ipv4-address;
        }
        leaf port {
          type inet:port-number;
        }
        leaf role {
          type process-role;
        }
        leaf issu_role {
          type process-issu-role;
        }
        leaf node {
          type string;
          description
            "Ethernet address of the node hosting the endpoint";
        }
      }
      list registrations {
        description
          "clients registered for a service in DS";
        leaf client {
          type string;
        }
        leaf pid {
          type uint32;
        }
      }
    }
  }

  augment "/ncs:devices/ncs:device/ncs:config" {
    // NCS drop config false container services
    // NCS drop config false container 'services-stats'
  }
  augment "/ncs:devices/ncs:device/ncs:live-status" {
    container services {
      tailf:ncs-device-type "netconf";
      tailf:display-when "not(../../ncs:module) or ../../ncs:module[ncs:name='Cisco-IOS-XR-sysadmin-ds'] or (../../ncs:live-status-protocol[not(ncs:capability)]) or (../../ncs:live-status-protocol/ncs:capability/ncs:module[.='Cisco-IOS-XR-sysadmin-ds'])";
      description
        "Directory Services Entries";
      list all-locations {
        key "location";
        leaf location {
          type string;
          description
            "Node Location";
        }
        uses live_ncs_servicesGroup;
      }
    }
    container services-stats {
      tailf:ncs-device-type "netconf";
      tailf:display-when "not(../../ncs:module) or ../../ncs:module[ncs:name='Cisco-IOS-XR-sysadmin-ds'] or (../../ncs:live-status-protocol[not(ncs:capability)]) or (../../ncs:live-status-protocol/ncs:capability/ncs:module[.='Cisco-IOS-XR-sysadmin-ds'])";
      description
        "Directory Services Stats";
      container ds {
        uses show_trace:live_ncs_traceable;
      }
      list all-locations {
        key "location";
        leaf location {
          type string;
        }
        list stats {
          key "name";
          leaf name {
            type string;
            description
              "Name of the service";
          }
          leaf published {
            type uint32;
            description
              "number of endpoints published for this service";
          }
          leaf deleted {
            type uint32;
            description
              "number of endpoints deleted for this service";
          }
          leaf modified {
            type uint32;
            description
              "number of endpoints modified for this service";
          }
          leaf registered {
            type uint32;
            description
              "number of clients registered for this service";
          }
          leaf unregistered {
            type uint32;
            description
              "number of clients un-registered for this service";
          }
          leaf notifications {
            type uint32;
            description
              "number of clients notified for this service";
          }
          leaf remote_sent {
            type uint32;
            description
              "number of remote service updates sent to remote nodes";
          }
          leaf remote_recv {
            type uint32;
            description
              "number of remote service received from remote nodes";
          }
        }
      }
    }
  }
  augment "/ncs:devices/ncs:template/ncs:ned-id/ncs:config" {
    // NCS drop config false container services
    // NCS drop config false container 'services-stats'
  }
}
