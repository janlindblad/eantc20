module Cisco-IOS-XR-fretta-bcm-dpa-drop-stats-oper {
  // Generated by yanger -t ncs
  tailf:mount-id f5500-nc-1.0:f5500-nc-1.0;
  tailf:ncs-device-type "netconf";

  namespace "http://cisco.com/ns/yang/Cisco-IOS-XR-fretta-bcm-dpa-drop-stats-oper";
  prefix Cisco-IOS-XR-fretta-bcm-dpa-drop-stats-oper;

  import Cisco-IOS-XR-types {
    prefix xr;
  }
  include Cisco-IOS-XR-fretta-bcm-dpa-drop-stats-oper-sub1 {
    revision-date 2015-11-09;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR fretta-bcm-dpa-drop-stats package operational data.

     This module contains definitions
     for the following management objects:
       drop: Drop stats data

     Copyright (c) 2013-2018 by Cisco Systems, Inc.
     All rights reserved.";

  revision 2015-11-09 {
    description
      "IOS XR 6.0 revision.";
  }

  augment "/ncs:devices/ncs:device/ncs:config" {
    // NCS drop config false container drop
  }
  augment "/ncs:devices/ncs:device/ncs:live-status" {
    container drop {
      tailf:ncs-device-type "netconf";
      tailf:display-when "not(../../ncs:module) or ../../ncs:module[ncs:name='Cisco-IOS-XR-fretta-bcm-dpa-drop-stats-oper'] or (../../ncs:live-status-protocol[not(ncs:capability)]) or (../../ncs:live-status-protocol/ncs:capability/ncs:module[.='Cisco-IOS-XR-fretta-bcm-dpa-drop-stats-oper'])";
      description
        "Drop stats data";
      container nodes {
        description
          "Drop data per node";
        list node {
          key "node-name";
          description
            "Drop stats data for a particular node";
          container npu-number-for-drop-stats {
            description
              "NPU drop stats";
            list npu-number-for-drop-stat {
              key "npu-id";
              description
                "All drop stats for a particular NPU";
              leaf npu-id {
                type uint32;
                description
                  "NPU number";
              }
              list drop-specific-stats-data {
                key "drop-data";
                description
                  "Second argument to the module";
                leaf drop-data {
                  type uint32;
                  description
                    "Drop ID";
                }
                uses live_ncs_DROP-STATS;
              }
            }
          }
          leaf node-name {
            type xr:Node-id;
            description
              "Node ID";
          }
        }
      }
    }
  }
  augment "/ncs:devices/ncs:template/ncs:ned-id/ncs:config" {
    // NCS drop config false container drop
  }
}
