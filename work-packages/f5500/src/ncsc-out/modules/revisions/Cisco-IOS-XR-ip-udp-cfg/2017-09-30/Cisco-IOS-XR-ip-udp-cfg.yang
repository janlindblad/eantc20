module Cisco-IOS-XR-ip-udp-cfg {
  // Generated by yanger -t ncs
  tailf:mount-id f5500-nc-1.0:f5500-nc-1.0;
  tailf:ncs-device-type "netconf";

  namespace "http://cisco.com/ns/yang/Cisco-IOS-XR-ip-udp-cfg";
  prefix Cisco-IOS-XR-ip-udp-cfg;

  import Cisco-IOS-XR-types {
    prefix xr;
  }
  import Cisco-IOS-XR-ip-tcp-cfg {
    prefix a1;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR ip-udp package configuration.

     This module contains definitions
     for the following management objects:
       ip-udp: Global IP UDP configuration

     This YANG module augments the
       Cisco-IOS-XR-ip-tcp-cfg
     module with configuration data.

     Copyright (c) 2013-2018 by Cisco Systems, Inc.
     All rights reserved.";

  revision 2017-09-30 {
    description
      "Ensure propagation of MDA mandatory state to YANG model.";
  }
  revision 2017-07-31 {
    description
      "Fixed missing augmentation from multiple MDA parent.";
  }
  revision 2017-05-01 {
    description
      "Fixing backward compatibility error in module.";
  }
  revision 2016-02-26 {
    description
      "Descriptions updated.";
  }
  revision 2015-11-09 {
    description
      "IOS XR 6.0 revision.";
  }

  augment "/ncs:devices/ncs:device/ncs:config" {
    container ip-udp {
      tailf:ncs-device-type "netconf";
      tailf:display-when "not(../../ncs:module) or ../../ncs:module[ncs:name='Cisco-IOS-XR-ip-udp-cfg']";
      description
        "Global IP UDP configuration";
      container num-thread {
        presence "Indicates a num-thread node is configured.";
        description
          "UDP InQueue and OutQueue threads";
        leaf udp-in-q-threads {
          type uint32 {
            range "1..16";
          }
          mandatory true;
          description
            "InQ Threads";
        }
        leaf udp-out-q-threads {
          type uint32 {
            range "1..16";
          }
          mandatory true;
          description
            "OutQ Threads";
        }
      }
      container directory {
        presence "Indicates a directory node is configured.";
        description
          "UDP directory details";
        leaf directoryname {
          type string;
          mandatory true;
          description
            "Directory name";
        }
        leaf max-udp-debug-files {
          type uint32 {
            range "1..5000";
          }
          default "256";
          description
            "Set number of Debug files";
        }
        leaf max-file-size-files {
          type uint32 {
            range "1024..4294967295";
          }
          units "byte";
          description
            "Set size of debug files in bytes";
        }
      }
      leaf receive-q {
        type uint32 {
          range "40..800";
        }
        description
          "UDP receive Queue Size";
      }
    }
  }
  augment "/ncs:devices/ncs:device/ncs:live-status" {
    container ip-udp {
      tailf:ncs-device-type "netconf";
      tailf:display-when "not(../../ncs:module) or ../../ncs:module[ncs:name='Cisco-IOS-XR-ip-udp-cfg'] or (../../ncs:live-status-protocol[not(ncs:capability)]) or (../../ncs:live-status-protocol/ncs:capability/ncs:module[.='Cisco-IOS-XR-ip-udp-cfg'])";
      description
        "Global IP UDP configuration";
      container num-thread {
        presence "Indicates a num-thread node is configured.";
        description
          "UDP InQueue and OutQueue threads";
        leaf udp-in-q-threads {
          type uint32 {
            range "1..16";
          }
          // NCS drop mandatory statement
          description
            "InQ Threads";
        }
        leaf udp-out-q-threads {
          type uint32 {
            range "1..16";
          }
          // NCS drop mandatory statement
          description
            "OutQ Threads";
        }
      }
      container directory {
        presence "Indicates a directory node is configured.";
        description
          "UDP directory details";
        leaf directoryname {
          type string;
          // NCS drop mandatory statement
          description
            "Directory name";
        }
        leaf max-udp-debug-files {
          type uint32 {
            range "1..5000";
          }
          // NCS drop default statement
          description
            "Set number of Debug files";
        }
        leaf max-file-size-files {
          type uint32 {
            range "1024..4294967295";
          }
          units "byte";
          description
            "Set size of debug files in bytes";
        }
      }
      leaf receive-q {
        type uint32 {
          range "40..800";
        }
        description
          "UDP receive Queue Size";
      }
    }
  }
  augment "/ncs:devices/ncs:template/ncs:ned-id/ncs:config" {
    container ip-udp {
      description
        "Global IP UDP configuration";
      container num-thread {
        presence "Indicates a num-thread node is configured.";
        description
          "UDP InQueue and OutQueue threads";
        leaf udp-in-q-threads {
          type string;
          // NCS drop mandatory statement
          description
            "InQ Threads";
        }
        leaf udp-out-q-threads {
          type string;
          // NCS drop mandatory statement
          description
            "OutQ Threads";
        }
      }
      container directory {
        presence "Indicates a directory node is configured.";
        description
          "UDP directory details";
        leaf directoryname {
          type string;
          // NCS drop mandatory statement
          description
            "Directory name";
        }
        leaf max-udp-debug-files {
          type string;
          // NCS drop default statement
          description
            "Set number of Debug files";
        }
        leaf max-file-size-files {
          type string;
          units "byte";
          description
            "Set size of debug files in bytes";
        }
      }
      leaf receive-q {
        type string;
        description
          "UDP receive Queue Size";
      }
    }
  }
  augment "/ncs:devices/ncs:template/ncs:ned-id/ncs:config/a1:ip" {
    container forward-protocol {
      description
        "Controls forwarding of physical and directed IP
         broadcasts";
      container udp {
        description
          "Packets to a specific UDP port";
        container ports {
          description
            "Port configuration";
          list port {
            // NCS patched for predictable order
            ordered-by user;
            key "port-id";
            description
              "Well-known ports are enabled by default and
               non well-known ports are disabled by default.
               It is not allowed to configure the default.";
            leaf port-id {
              type string;
              description
                "Port number";
            }
            leaf enable {
              type string;
              // NCS drop mandatory statement
              description
                "Specify 'false' to disable well-known ports
                 Domain (53), TFTP (69), NameServer (42),
                 TACACS (49), NetBiosNameService (137), or
                 NetBiosDatagramService (138).  Specify
                 'true' to enable non well-known ports.";
            }
          }
        }
        leaf disable {
          type empty;
          description
            "Disable IP Forward Protocol UDP";
        }
      }
    }
    description
      "This augment extends the configuration data of
       'Cisco-IOS-XR-ip-tcp-cfg'";
  }
  augment "/ncs:devices/ncs:device/ncs:live-status/a1:ip" {
    container forward-protocol {
      tailf:ncs-device-type "netconf";
      tailf:display-when "not(../../../ncs:module) or ../../../ncs:module[ncs:name='Cisco-IOS-XR-ip-udp-cfg'] or (../../../ncs:live-status-protocol[not(ncs:capability)]) or (../../../ncs:live-status-protocol/ncs:capability/ncs:module[.='Cisco-IOS-XR-ip-udp-cfg'])";
      description
        "Controls forwarding of physical and directed IP
         broadcasts";
      container udp {
        description
          "Packets to a specific UDP port";
        container ports {
          description
            "Port configuration";
          list port {
            key "port-id";
            description
              "Well-known ports are enabled by default and
               non well-known ports are disabled by default.
               It is not allowed to configure the default.";
            leaf port-id {
              type xr:Cisco-ios-xr-port-number;
              description
                "Port number";
            }
            leaf enable {
              type boolean;
              // NCS drop mandatory statement
              description
                "Specify 'false' to disable well-known ports
                 Domain (53), TFTP (69), NameServer (42),
                 TACACS (49), NetBiosNameService (137), or
                 NetBiosDatagramService (138).  Specify
                 'true' to enable non well-known ports.";
            }
          }
        }
        leaf disable {
          type empty;
          description
            "Disable IP Forward Protocol UDP";
        }
      }
    }
    description
      "This augment extends the configuration data of
       'Cisco-IOS-XR-ip-tcp-cfg'";
  }
  augment "/ncs:devices/ncs:device/ncs:config/a1:ip" {
    container forward-protocol {
      tailf:ncs-device-type "netconf";
      tailf:display-when "not(../../../ncs:module) or ../../../ncs:module[ncs:name='Cisco-IOS-XR-ip-udp-cfg']";
      description
        "Controls forwarding of physical and directed IP
         broadcasts";
      container udp {
        description
          "Packets to a specific UDP port";
        container ports {
          description
            "Port configuration";
          list port {
            key "port-id";
            description
              "Well-known ports are enabled by default and
               non well-known ports are disabled by default.
               It is not allowed to configure the default.";
            leaf port-id {
              type xr:Cisco-ios-xr-port-number;
              description
                "Port number";
            }
            leaf enable {
              type boolean;
              mandatory true;
              description
                "Specify 'false' to disable well-known ports
                 Domain (53), TFTP (69), NameServer (42),
                 TACACS (49), NetBiosNameService (137), or
                 NetBiosDatagramService (138).  Specify
                 'true' to enable non well-known ports.";
            }
          }
        }
        leaf disable {
          type empty;
          description
            "Disable IP Forward Protocol UDP";
        }
      }
    }
    description
      "This augment extends the configuration data of
       'Cisco-IOS-XR-ip-tcp-cfg'";
  }
  augment "/ncs:devices/ncs:template/ncs:ned-id/ncs:config/a1:ip/a1:cinetd/a1:services/a1:ipv4/a1:small-servers" {
    container udp-small-servers {
      presence "Indicates a udp-small-servers node is configured.";
      description
        "UDP small servers configuration";
      leaf access-control-list-name {
        type string;
        description
          "Specify the access list";
      }
      leaf small-server {
        type string;
        // NCS drop mandatory statement
        description
          "Set number of allowable small servers, specify
           0 for no-limit";
      }
    }
    description
      "This augment extends the configuration data of
       'Cisco-IOS-XR-ip-tcp-cfg'";
  }
  augment "/ncs:devices/ncs:device/ncs:live-status/a1:ip/a1:cinetd/a1:services/a1:ipv4/a1:small-servers" {
    container udp-small-servers {
      tailf:ncs-device-type "netconf";
      tailf:display-when "not(../../../../../../../ncs:module) or ../../../../../../../ncs:module[ncs:name='Cisco-IOS-XR-ip-udp-cfg'] or (../../../../../../../ncs:live-status-protocol[not(ncs:capability)]) or (../../../../../../../ncs:live-status-protocol/ncs:capability/ncs:module[.='Cisco-IOS-XR-ip-udp-cfg'])";
      presence "Indicates a udp-small-servers node is configured.";
      description
        "UDP small servers configuration";
      leaf access-control-list-name {
        type string;
        description
          "Specify the access list";
      }
      leaf small-server {
        type union {
          type enumeration {
            enum "no-limit" {
              value 0;
              description
                "Unlimited Servers";
            }
          }
          type uint32 {
            range "0..2147483647";
          }
        }
        // NCS drop mandatory statement
        description
          "Set number of allowable small servers, specify
           0 for no-limit";
      }
    }
    description
      "This augment extends the configuration data of
       'Cisco-IOS-XR-ip-tcp-cfg'";
  }
  augment "/ncs:devices/ncs:device/ncs:config/a1:ip/a1:cinetd/a1:services/a1:ipv4/a1:small-servers" {
    container udp-small-servers {
      tailf:ncs-device-type "netconf";
      tailf:display-when "not(../../../../../../../ncs:module) or ../../../../../../../ncs:module[ncs:name='Cisco-IOS-XR-ip-udp-cfg']";
      presence "Indicates a udp-small-servers node is configured.";
      description
        "UDP small servers configuration";
      leaf access-control-list-name {
        type string;
        description
          "Specify the access list";
      }
      leaf small-server {
        type union {
          type enumeration {
            enum "no-limit" {
              value 0;
              description
                "Unlimited Servers";
            }
          }
          type uint32 {
            range "0..2147483647";
          }
        }
        mandatory true;
        description
          "Set number of allowable small servers, specify
           0 for no-limit";
      }
    }
    description
      "This augment extends the configuration data of
       'Cisco-IOS-XR-ip-tcp-cfg'";
  }
  augment "/ncs:devices/ncs:template/ncs:ned-id/ncs:config/a1:ip/a1:cinetd/a1:services/a1:ipv6/a1:small-servers" {
    container udp-small-servers {
      presence "Indicates a udp-small-servers node is configured.";
      description
        "UDP small servers configuration";
      leaf access-control-list-name {
        type string;
        description
          "Specify the access list";
      }
      leaf small-server {
        type string;
        // NCS drop mandatory statement
        description
          "Set number of allowable small servers, specify
           0 for no-limit";
      }
    }
    description
      "This augment extends the configuration data of
       'Cisco-IOS-XR-ip-tcp-cfg'";
  }
  augment "/ncs:devices/ncs:device/ncs:live-status/a1:ip/a1:cinetd/a1:services/a1:ipv6/a1:small-servers" {
    container udp-small-servers {
      tailf:ncs-device-type "netconf";
      tailf:display-when "not(../../../../../../../ncs:module) or ../../../../../../../ncs:module[ncs:name='Cisco-IOS-XR-ip-udp-cfg'] or (../../../../../../../ncs:live-status-protocol[not(ncs:capability)]) or (../../../../../../../ncs:live-status-protocol/ncs:capability/ncs:module[.='Cisco-IOS-XR-ip-udp-cfg'])";
      presence "Indicates a udp-small-servers node is configured.";
      description
        "UDP small servers configuration";
      leaf access-control-list-name {
        type string;
        description
          "Specify the access list";
      }
      leaf small-server {
        type union {
          type enumeration {
            enum "no-limit" {
              value 0;
              description
                "Unlimited Servers";
            }
          }
          type uint32 {
            range "0..2147483647";
          }
        }
        // NCS drop mandatory statement
        description
          "Set number of allowable small servers, specify
           0 for no-limit";
      }
    }
    description
      "This augment extends the configuration data of
       'Cisco-IOS-XR-ip-tcp-cfg'";
  }
  augment "/ncs:devices/ncs:device/ncs:config/a1:ip/a1:cinetd/a1:services/a1:ipv6/a1:small-servers" {
    container udp-small-servers {
      tailf:ncs-device-type "netconf";
      tailf:display-when "not(../../../../../../../ncs:module) or ../../../../../../../ncs:module[ncs:name='Cisco-IOS-XR-ip-udp-cfg']";
      presence "Indicates a udp-small-servers node is configured.";
      description
        "UDP small servers configuration";
      leaf access-control-list-name {
        type string;
        description
          "Specify the access list";
      }
      leaf small-server {
        type union {
          type enumeration {
            enum "no-limit" {
              value 0;
              description
                "Unlimited Servers";
            }
          }
          type uint32 {
            range "0..2147483647";
          }
        }
        mandatory true;
        description
          "Set number of allowable small servers, specify
           0 for no-limit";
      }
    }
    description
      "This augment extends the configuration data of
       'Cisco-IOS-XR-ip-tcp-cfg'";
  }
}
