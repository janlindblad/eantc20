module Cisco-IOS-XR-mpls-te-cfg {
  // Generated by yanger -t ncs
  tailf:mount-id f5500-nc-1.0:f5500-nc-1.0;
  tailf:ncs-device-type "netconf";

  namespace "http://cisco.com/ns/yang/Cisco-IOS-XR-mpls-te-cfg";
  prefix Cisco-IOS-XR-mpls-te-cfg;

  import ietf-inet-types {
    prefix inet;
  }
  import Cisco-IOS-XR-types {
    prefix xr;
  }
  import Cisco-IOS-XR-ifmgr-cfg {
    prefix a1;
  }
  import Cisco-IOS-XR-snmp-agent-cfg {
    prefix a2;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR mpls-te package configuration.

     This module contains definitions
     for the following management objects:
       mpls-te: The root of MPLS TE configuration

     This YANG module augments the
       Cisco-IOS-XR-ifmgr-cfg,
       Cisco-IOS-XR-snmp-agent-cfg
     modules with configuration data.

     Copyright (c) 2013-2018 by Cisco Systems, Inc.
     All rights reserved.";

  revision 2017-09-07 {
    description
      "Fixed type translation error.";
  }
  revision 2017-05-01 {
    description
      "Fixing backward compatibility error in module.";
  }
  revision 2015-11-09 {
    description
      "IOS XR 6.0 revision.";
  }

  typedef Mpls-te-bandwidth-limit {
    type enumeration {
      enum "unlimited" {
        value 64;
        description
          "Unlimited";
      }
      enum "limited" {
        value 128;
        description
          "Limited";
      }
    }
    description
      "Mpls te bandwidth limit";
  }

  typedef Mpls-te-path-option-protection {
    type enumeration {
      enum "active" {
        value 0;
        description
          "Active path";
      }
      enum "protecting" {
        value 1;
        description
          "Protecting Path";
      }
    }
    description
      "Mpls te path option protection";
  }

  typedef Mpls-te-backup-bandwidth-class {
    type enumeration {
      enum "class0" {
        value 0;
        description
          "Class 0";
      }
      enum "class1" {
        value 1;
        description
          "Class 1";
      }
      enum "any-class" {
        value 9;
        description
          "Any Class";
      }
    }
    description
      "Mpls te backup bandwidth class";
  }

  typedef Mpls-te-switching-encode {
    type enumeration {
      enum "none" {
        value 0;
        description
          "None";
      }
      enum "packet" {
        value 1;
        description
          "Packet";
      }
      enum "ethernet" {
        value 2;
        description
          "Ethernet";
      }
      enum "sondet-sdh" {
        value 5;
        description
          "SONET SDH";
      }
    }
    description
      "Mpls te switching encode";
  }

  typedef Mpls-te-backup-bandwidth-pool {
    type enumeration {
      enum "any-pool" {
        value 1;
        description
          "Any Pool";
      }
      enum "global-pool" {
        value 2;
        description
          "Global Pool";
      }
      enum "sub-pool" {
        value 4;
        description
          "Sub Pool";
      }
    }
    description
      "Mpls te backup bandwidth pool";
  }

  typedef Binding-segment-id {
    type enumeration {
      enum "any-label" {
        value 1;
        description
          "AnyLabel";
      }
      enum "specified-label" {
        value 2;
        description
          "SpecifiedLabel";
      }
    }
    description
      "Binding segment id";
  }

  typedef Mpls-tebfd-session {
    type enumeration {
      enum "regular-bfd" {
        value 1;
        description
          "Regular BFD";
      }
      enum "sbfd" {
        value 2;
        description
          "Seamless BFD";
      }
      enum "redundant-sbfd" {
        value 3;
        description
          "Redundant SBFD";
      }
    }
    description
      "Mpls tebfd session";
  }

  typedef Mpls-te-igp-protocol {
    type enumeration {
      enum "none" {
        value 0;
        description
          "Not set";
      }
      enum "isis" {
        value 1;
        description
          "IS IS";
      }
      enum "ospf" {
        value 2;
        description
          "OSPF";
      }
    }
    description
      "Mpls te igp protocol";
  }

  typedef Mpls-te-switching-index {
    type union {
      type enumeration {
        enum "link" {
          value 255;
          description
            "Link";
        }
      }
      type uint32 {
        range "1..255";
      }
    }
    description
      "Mpls te switching index";
  }

  typedef Path-invalidation-action {
    type enumeration {
      enum "tear" {
        value 1;
        description
          "Tear";
      }
      enum "drop" {
        value 2;
        description
          "Drop";
      }
    }
    description
      "Path invalidation action";
  }

  typedef Mesh-group-id {
    type uint32 {
      range "0..4294967295";
    }
    description
      "Mesh group id";
  }

  typedef Mpls-te-policy-class-range {
    type uint32 {
      range "1..8";
    }
    description
      "Mpls te policy class range";
  }

  typedef Mpls-te-sig-name-option {
    type enumeration {
      enum "none" {
        value 0;
        description
          "None";
      }
      enum "address" {
        value 1;
        description
          "Address";
      }
      enum "name" {
        value 2;
        description
          "Name";
      }
    }
    description
      "Mpls te sig name option";
  }

  typedef Mpls-te-switching-encoding {
    type enumeration {
      enum "packet" {
        value 1;
        description
          "Packet";
      }
      enum "ethernet" {
        value 2;
        description
          "Ethernet";
      }
      enum "sondet-sdh" {
        value 5;
        description
          "SONET SDH";
      }
    }
    description
      "Mpls te switching encoding";
  }

  typedef Gmplstti-mode {
    type enumeration {
      enum "sm" {
        value 1;
        description
          "Section Monitoring";
      }
      enum "pm" {
        value 2;
        description
          "Path Monitoring";
      }
      enum "tcm" {
        value 3;
        description
          "Tandem Connection";
      }
    }
    description
      "Gmplstti mode";
  }

  typedef Mpls-te-path-selection-segment-routing-adjacency-protection {
    type enumeration {
      enum "not-set" {
        value 0;
        description
          "Any segment can be used in a path.";
      }
      enum "adj-unprotected" {
        value 1;
        description
          "Only unprotected adjacency segments can be used
           in a path.";
      }
      enum "adj-protected" {
        value 2;
        description
          "Only protected adjacency segments can be used
           in a path.";
      }
    }
    description
      "Mpls te path selection segment routing adjacency
       protection";
  }

  typedef Mpls-te-otn-aps-restoration-style {
    type enumeration {
      enum "keep-failed-lsp" {
        value 1;
        description
          "Keep Failed Lsp";
      }
      enum "delete-failed-lsp" {
        value 2;
        description
          "Delete Failed Lsp";
      }
    }
    description
      "Mpls te otn aps restoration style";
  }

  typedef Ietf-mode {
    type enumeration {
      enum "standard" {
        value 3;
        description
          "IETF Standard";
      }
    }
    description
      "Ietf mode";
  }

  typedef Mpls-lcac-flooding-threshold-percent-range {
    type uint32 {
      range "0..100";
    }
    description
      "Mpls lcac flooding threshold percent range";
  }

  typedef Mpls-te-path-diversity-conformance {
    type enumeration {
      enum "strict" {
        value 0;
        description
          "Strict";
      }
      enum "best-effort" {
        value 1;
        description
          "Best effort";
      }
    }
    description
      "Mpls te path diversity conformance";
  }

  typedef Attribute-set-affinity-name-length {
    type xr:Cisco-ios-xr-string {
      length "1..64";
    }
    description
      "Attribute set affinity name length";
  }

  typedef Mpls-te-path-selection-invalidation-timer-expire {
    type enumeration {
      enum "tunnel-action-tear" {
        value 1;
        description
          "Tear down tunnel.";
      }
      enum "tunnel-action-drop" {
        value 2;
        description
          "Drop tunnel traffic.";
      }
    }
    description
      "Mpls te path selection invalidation timer expire";
  }

  typedef Mpls-te-bandwidth-dste {
    type enumeration {
      enum "standard-dste" {
        value 0;
        description
          "IETF-Standard DSTE";
      }
      enum "pre-standard-dste" {
        value 1;
        description
          "Pre-Standard DSTE";
      }
    }
    description
      "Mpls te bandwidth dste";
  }

  typedef Otn-signaled-bandwidth {
    type enumeration {
      enum "odu1" {
        value 1;
        description
          "Signalled BW for ODU1";
      }
      enum "odu2" {
        value 2;
        description
          "Signalled BW for ODU2";
      }
      enum "odu3" {
        value 3;
        description
          "Signalled BW for ODU3";
      }
      enum "odu4" {
        value 4;
        description
          "Signalled BW for ODU4";
      }
      enum "odu0" {
        value 10;
        description
          "Signalled BW for ODU0";
      }
      enum "odu2e" {
        value 11;
        description
          "Signalled BW for ODU2e";
      }
      enum "od-uflex-cbr" {
        value 20;
        description
          "Signalled BW for ODUflex CBR";
      }
      enum "od-uflex-gfp-resize" {
        value 21;
        description
          "Signalled BW for ODUflex GFP Resizable";
      }
      enum "od-uflex-gfp-not-resize" {
        value 22;
        description
          "Signalled BW for ODUflex GFP not Resizable";
      }
      enum "odu1e" {
        value 23;
        description
          "Signalled BW for ODU1e";
      }
      enum "odu1f" {
        value 24;
        description
          "Signalled BW for ODU1f";
      }
      enum "odu2f" {
        value 25;
        description
          "Signalled BW for ODU2f";
      }
      enum "odu3e1" {
        value 26;
        description
          "Signalled BW for ODU3e1";
      }
      enum "odu3e2" {
        value 27;
        description
          "Signalled BW for ODU3e2";
      }
    }
    description
      "Otn signaled bandwidth";
  }

  typedef Mpls-te-tunnel-id {
    type enumeration {
      enum "auto" {
        value 0;
        description
          "Auto";
      }
      enum "explicit" {
        value 1;
        description
          "Explicit";
      }
    }
    description
      "Mpls te tunnel id";
  }

  typedef Otn-protection-switch-lockout {
    type enumeration {
      enum "none" {
        value 0;
        description
          "No Lockout";
      }
      enum "working" {
        value 1;
        description
          "Lockout Working";
      }
    }
    description
      "Otn protection switch lockout";
  }

  typedef Mpls-lcac-flooding-igp {
    type enumeration {
      enum "ospf" {
        value 0;
        description
          "OSPF";
      }
    }
    description
      "Mpls lcac flooding igp";
  }

  typedef Mpls-te-path-option {
    type enumeration {
      enum "not-set" {
        value 0;
        description
          "Not Set";
      }
      enum "dynamic" {
        value 1;
        description
          "Dynamic";
      }
      enum "explicit-name" {
        value 3;
        description
          "Explicit, identified by name";
      }
      enum "explicit-number" {
        value 4;
        description
          "Explicit, identified by number";
      }
      enum "no-ero" {
        value 5;
        description
          "No ERO";
      }
      enum "sr" {
        value 6;
        description
          "Deprecated";
      }
    }
    description
      "Mpls te path option";
  }

  typedef Mpls-te-path-selection-metric {
    type enumeration {
      enum "igp" {
        value 1;
        description
          "IGP Metric";
      }
      enum "te" {
        value 2;
        description
          "TE Metric";
      }
      enum "delay" {
        value 4;
        description
          "DELAY Metric";
      }
    }
    description
      "Mpls te path selection metric";
  }

  typedef Bfd-reverse-path {
    type enumeration {
      enum "bfd-reverse-path-binding-label" {
        value 1;
        description
          "BindingLabel";
      }
    }
    description
      "Bfd reverse path";
  }

  typedef Mpls-te-otn-snc-mode {
    type enumeration {
      enum "snc-n" {
        value 1;
        description
          "SNC N";
      }
      enum "snc-i" {
        value 2;
        description
          "SNC I";
      }
      enum "snc-s" {
        value 3;
        description
          "SNC S";
      }
    }
    description
      "Mpls te otn snc mode";
  }

  typedef Otn-payload {
    type enumeration {
      enum "unknown" {
        value 0;
        description
          "Payload unknown";
      }
      enum "bmp" {
        value 50;
        description
          "Bmp Payload";
      }
      enum "gfp-f" {
        value 54;
        description
          "Gfp_F Payload";
      }
      enum "gmp" {
        value 55;
        description
          "GMP Payload";
      }
      enum "gfp-f-ext" {
        value 70;
        description
          "Gfp_F_EXT Payload";
      }
    }
    description
      "Otn payload";
  }

  typedef Bandwidth-constraint {
    type enumeration {
      enum "bandwidth-constraint-maximum-allocation-model" {
        value 1;
        description
          "Maximum Allocation Bandwidth Constaints Model";
      }
    }
    description
      "Bandwidth constraint";
  }

  typedef Mpls-te-autoroute-metric {
    type enumeration {
      enum "relative" {
        value 1;
        description
          "Relative";
      }
      enum "absolute" {
        value 2;
        description
          "Absolute";
      }
      enum "constant" {
        value 3;
        description
          "Constant";
      }
    }
    description
      "Mpls te autoroute metric";
  }

  typedef Mpls-lcac-bandwidth-hold-timer-range {
    type uint32 {
      range "1..300";
    }
    description
      "Mpls lcac bandwidth hold timer range";
  }

  typedef Link-next-hop {
    type enumeration {
      enum "none" {
        value 1;
        description
          "No next hop";
      }
      enum "ipv4-address" {
        value 2;
        description
          "IPv4 next-hop address";
      }
    }
    description
      "Link next hop";
  }

  typedef Mpls-te-log-frr-protection {
    type enumeration {
      enum "frr-active-primary" {
        value 1;
        description
          "Track only FRR active on primary LSP";
      }
      enum "backup" {
        value 256;
        description
          "backup tunnel";
      }
      enum "frr-ready-primary" {
        value 512;
        description
          "Track only FRR ready on primary LSP";
      }
      enum "primary" {
        value 513;
        description
          "primary LSP";
      }
      enum "all" {
        value 769;
        description
          "all";
      }
    }
    description
      "Mpls te log frr protection";
  }

  typedef Mpls-te-bfd-session-down-action {
    type enumeration {
      enum "re-setup" {
        value 1;
        description
          "Tear down and resetup";
      }
    }
    description
      "Mpls te bfd session down action";
  }

  typedef Mpls-te-config-tunnel {
    type enumeration {
      enum "p2p" {
        value 0;
        description
          "P2P";
      }
      enum "p2mp" {
        value 1;
        description
          "P2MP";
      }
    }
    description
      "Mpls te config tunnel";
  }

  typedef Mpls-te-otn-aps-protection-mode {
    type enumeration {
      enum "revertive" {
        value 1;
        description
          "Revertive";
      }
      enum "non-revertive" {
        value 2;
        description
          "Non Revertive";
      }
    }
    description
      "Mpls te otn aps protection mode";
  }

  typedef Mpls-te-switching-cap {
    type enumeration {
      enum "psc1" {
        value 1;
        description
          "PSC1";
      }
      enum "lsc" {
        value 150;
        description
          "LSC";
      }
      enum "fsc" {
        value 200;
        description
          "FSC";
      }
    }
    description
      "Mpls te switching cap";
  }

  typedef Otn-static-uni {
    type enumeration {
      enum "unknown" {
        value 0;
        description
          "Uni-Type None";
      }
      enum "xc" {
        value 1;
        description
          "Uni-Type XC";
      }
      enum "termination" {
        value 2;
        description
          "Uni-Type Termination";
      }
    }
    description
      "Otn static uni";
  }

  typedef Mpls-te-tunnel-affinity {
    type enumeration {
      enum "include" {
        value 1;
        description
          "Include Affinity";
      }
      enum "include-strict" {
        value 2;
        description
          "Strictly Include Affinity";
      }
      enum "exclude" {
        value 3;
        description
          "Exclude Affinity";
      }
      enum "exclude-all" {
        value 4;
        description
          "Exclude All Affinities";
      }
      enum "ignore" {
        value 5;
        description
          "Ignore Affinity";
      }
    }
    description
      "Mpls te tunnel affinity";
  }

  typedef Otn-destination {
    type enumeration {
      enum "number-ed" {
        value 0;
        description
          "Destination numbered";
      }
      enum "un-number-ed" {
        value 1;
        description
          "Destination unnumbered";
      }
    }
    description
      "Otn destination";
  }

  typedef Mpls-te-path-option-xro {
    type empty;
    description
      "Defined as attribute-set";
  }

  typedef Mpls-te-signaled-label {
    type enumeration {
      enum "not-set" {
        value 0;
        description
          "Not Set";
      }
      enum "dwdm" {
        value 1;
        description
          "DWDM Label (RFC 6205), 50GHz channel spacing";
      }
    }
    description
      "Mpls te signaled label";
  }

  typedef Mpls-te-path-computation-method {
    type enumeration {
      enum "not-set" {
        value 0;
        description
          "NotSet";
      }
      enum "dynamic" {
        value 1;
        description
          "Dynamic";
      }
      enum "pce" {
        value 2;
        description
          "PCE";
      }
      enum "explicit" {
        value 3;
        description
          "Explicit";
      }
    }
    description
      "Mpls te path computation method";
  }

  typedef Mpls-te-path-option-property {
    type enumeration {
      enum "none" {
        value 0;
        description
          "No property";
      }
      enum "lockdown" {
        value 1;
        description
          "Path is not a candidate for reoptimization";
      }
      enum "verbatim" {
        value 4;
        description
          "Explicit path does not require topology
           database";
      }
      enum "pce" {
        value 8;
        description
          "Dynamic path found by PCE server";
      }
      enum "segment-routing" {
        value 16;
        description
          "Segment Routing path";
      }
      enum "sticky" {
        value 32;
        description
          "Force tunnel to remain on same path";
      }
    }
    description
      "Mpls te path option property";
  }

  typedef Ospf-area-mode {
    type enumeration {
      enum "ospf-int" {
        value 0;
        description
          "OSPF area in integer format";
      }
      enum "ospfip-addr" {
        value 1;
        description
          "OSPF area in IP address format";
      }
    }
    description
      "Ospf area mode";
  }

  typedef Mpls-te-otn-aps-protection {
    type enumeration {
      enum "1plus1-unidir-no-aps" {
        value 4;
        description
          "1PLUS1 UNIDIR NO APS";
      }
      enum "1plus1-unidir-aps" {
        value 8;
        description
          "1PLUS1 UNIDIR APS";
      }
      enum "1plus1-bdir-aps" {
        value 16;
        description
          "1PLUS1 BIDIR APS";
      }
    }
    description
      "Mpls te otn aps protection";
  }

  typedef Attribute-set-name-length {
    type string {
      length "1..64";
    }
    description
      "Attribute set name length";
  }

  typedef Mpls-te-path-selection-tiebreaker {
    type enumeration {
      enum "min-fill" {
        value 1;
        description
          "Prefer the path with the least-utilized links";
      }
      enum "max-fill" {
        value 2;
        description
          "Prefer the path with the most-utilized links";
      }
      enum "random" {
        value 3;
        description
          "Prefer a path with links utilized randomly";
      }
    }
    description
      "Mpls te path selection tiebreaker";
  }

  typedef Sr-prepend {
    type enumeration {
      enum "none-type" {
        value 0;
        description
          "NoneType";
      }
      enum "next-label" {
        value 1;
        description
          "Next Label";
      }
      enum "bgp-n-hop" {
        value 2;
        description
          "BGP NHOP";
      }
    }
    description
      "Sr prepend";
  }

  typedef Otn-signaled-bandwidth-flex-framing {
    type enumeration {
      enum "cbr" {
        value 20;
        description
          "CBR";
      }
      enum "framed-gfp-fixed" {
        value 21;
        description
          "GFP fixed framing type";
      }
      enum "framed-gfp-resize" {
        value 22;
        description
          "GFP resizeable framing type";
      }
    }
    description
      "Otn signaled bandwidth flex framing";
  }

  typedef Mpls-percent-range {
    type uint32 {
      range "0..100";
    }
    description
      "Mpls percent range";
  }

  typedef Route-priority-role {
    type enumeration {
      enum "route-priority-role-head-back-up" {
        value 0;
        description
          "TE Route Priority Role Head Backup";
      }
      enum "route-priority-role-head-primary" {
        value 1;
        description
          "TE Route Priority Role Head Primary";
      }
      enum "route-priority-role-middle" {
        value 2;
        description
          "TE Route Priority Role Middle";
      }
    }
    description
      "Route priority role";
  }

  typedef Destination-list-name-length {
    type string {
      length "1..32";
    }
    description
      "Destination list name length";
  }

  typedef Mpls-te-affinity-value {
    type enumeration {
      enum "hex-value" {
        value 1;
        description
          "Affinity value in Hex number";
      }
      enum "bit-position" {
        value 2;
        description
          "Affinity value by Bit-Position";
      }
    }
    description
      "Mpls te affinity value";
  }

  typedef Mpls-tesrlg-exclude {
    type enumeration {
      enum "mandatory" {
        value 1;
        description
          "SRLG Mandatory Exclude";
      }
      enum "preferred" {
        value 2;
        description
          "SRLG Preferred Exclude";
      }
      enum "weighted" {
        value 3;
        description
          "SRLG Weighted Exclude";
      }
    }
    description
      "Mpls tesrlg exclude";
  }

  grouping ncs_template_OOR-ACCEPT-REOPT-LSP {
    description
      "Common node of oor-green-state, oor-yellow-state,
       oor-red-state";
    leaf oor-accept-reopt-lsp {
      type empty;
      description
        "Allow the setup of reoptimized LSPs over the
         link in this OOR State";
    }
  }

  grouping ncs_template_PCALC-FAILURE-MESSAGE {
    description
      "Common node of logging, auto-mesh-logging";
    leaf pcalc-failure-message {
      type empty;
      description
        "Enable logging for path-calculation failures";
    }
  }

  grouping ncs_template_POLICY-CLASSES {
    description
      "Common node of tunnel-te-attributes,
       auto-mesh-attribute, auto-backup-attribute";
    container policy-classes {
      description
        "Policy classes for PBTS";
      leaf-list policy-class {
        // NCS patched for predictable order
        ordered-by user;
        type string;
        // NCS drop max-elements statement
        description
          "Array of Policy class";
      }
    }
  }

  grouping ncs_template_UNPROTECTED-TRANSIT-LSP-THRESHOLD {
    description
      "Common node of lsp-oor-yellow-state,
       lsp-oor-red-state";
    leaf unprotected-transit-lsp-threshold {
      type string;
      description
        "Threshold for unprotected transit LSPs";
    }
  }

  grouping ncs_template_AFFINITY-MASK {
    description
      "Common node of tunnel-te-attributes,
       tunnel-attributes, auto-mesh-attribute,
       auto-backup-attribute, path-option-attribute,
       p2mpte-attribute, p2p-te-attribute";
    container affinity-mask {
      presence "Indicates a affinity-mask node is configured.";
      description
        "Set the affinity flags and mask";
      leaf affinity {
        type string;
        // NCS drop mandatory statement
        description
          "Affinity flags";
      }
      leaf mask {
        type string;
        // NCS drop mandatory statement
        description
          "Affinity mask";
      }
    }
  }

  grouping ncs_template_BANDWIDTH-CHANGE-MESSAGE {
    description
      "Common node of logging, auto-backup-logging,
       auto-mesh-logging";
    leaf bandwidth-change-message {
      type empty;
      description
        "Log tunnel messages for bandwidth change";
    }
  }

  grouping ncs_template_REOPTIMIZE-ATTEMPTS-MESSAGE {
    description
      "Common node of logging, auto-backup-logging,
       auto-mesh-logging";
    leaf reoptimize-attempts-message {
      type empty;
      description
        "Log tunnel reoptimization attempts messages";
    }
  }

  grouping ncs_template_OOR-AVAILABLE-BANDWIDTH-PERCENTAGE {
    description
      "Common node of oor-green-state, oor-yellow-state,
       oor-red-state";
    leaf oor-available-bandwidth-percentage {
      type string;
      units "percentage";
      // NCS drop default statement
      description
        "Flood a specific percentage of the available
         bandwidth";
    }
  }

  grouping ncs_template_TIMERS {
    description
      "Common node of backup, mesh";
    container timers {
      description
        "Configure auto-tunnel backup timers value";
      container removal {
        description
          "Configure auto-tunnel backup removal timers
           value";
        leaf unused {
          type string;
          units "minute";
          // NCS drop default statement
          description
            "Auto-tunnel backup unused timeout in minutes
             (0=never timeout)";
        }
      }
    }
  }

  grouping ncs_template_TUNNEL-PATH-SELECTION {
    description
      "Common node of tunnel-te-attributes,
       tunnel-attributes";
    container tunnel-path-selection {
      description
        "Configure path selection properties";
      leaf tiebreaker {
        type string;
        description
          "CSPF tiebreaker to use in path calculation";
      }
      leaf path-selection-hop-limit {
        type string;
        description
          "Path selection hop limit configuration for this
           specific tunnel";
      }
      uses ncs_template_PATH-SELECTION-DELAY-LIMIT;
      uses ncs_template_INVALIDATION;
      uses ncs_template_PATH-SELECTION-COST-LIMIT;
    }
  }

  grouping ncs_template_INVALIDATION {
    description
      "Common node of tunnel-te-attributes,
       tunnel-attributesCommon node of
       tunnel-path-selection,
       att-path-option-path-selection";
    container invalidation {
      presence "enable invalidation";
      description
        "Deprecated";
      leaf path-invalidation-timeout {
        type string;
        description
          "Path Invalidation Timeout";
      }
      leaf path-invalidation-action {
        type string;
        description
          "Path Invalidation Action";
      }
    }
  }

  grouping ncs_template_PRECEDENCE {
    description
      "Common node of peer, pce-attributes";
    leaf precedence {
      type string;
      description
        "Precedence order";
    }
  }

  grouping ncs_template_SOFT-PREEMPTION {
    description
      "Common node of tunnel-attributes,
       tunnel-te-attributes, auto-mesh-attribute";
    leaf soft-preemption {
      type empty;
      description
        "Enable the soft-preemption feature on the tunnel";
    }
  }

  grouping ncs_template_PATH-SELECTION-COST-LIMIT {
    description
      "Common node of tunnel-path-selection,
       att-path-option-path-selection";
    leaf path-selection-cost-limit {
      type string;
      description
        "Path selection cost limit configuration for this
         specific tunnel";
    }
  }

  grouping ncs_template_AUTO-BANDWIDTH {
    description
      "Common node of tunnel-attributes,
       tunnel-te-attributes";
    container auto-bandwidth {
      description
        "Tunnel Interface Auto-bandwidth configuration
         data";
      container underflow {
        presence "Indicates a underflow node is configured.";
        description
          "Configuring the tunnel underflow detection";
        leaf underflow-threshold-percent {
          type string;
          units "percentage";
          // NCS drop mandatory statement
          description
            "Bandwidth change percent to trigger an
             underflow";
        }
        leaf underflow-threshold-value {
          type string;
          units "kbit/s";
          // NCS drop mandatory statement
          description
            "Bandwidth change value to trigger an underflow
             (kbps)";
        }
        leaf underflow-threshold-limit {
          type string;
          // NCS drop mandatory statement
          description
            "Number of consecutive collections exceeding
             threshold";
        }
      }
      container overflow {
        presence "Indicates a overflow node is configured.";
        description
          "Configuring the tunnel overflow detection";
        leaf overflow-threshold-percent {
          type string;
          units "percentage";
          // NCS drop mandatory statement
          description
            "Bandwidth change percent to trigger an
             overflow";
        }
        leaf overflow-threshold-value {
          type string;
          units "kbit/s";
          // NCS drop mandatory statement
          description
            "Bandwidth change value to trigger an overflow
             (kbps)";
        }
        leaf overflow-threshold-limit {
          type string;
          // NCS drop mandatory statement
          description
            "Number of consecutive collections exceeding
             threshold";
        }
      }
      container bandwidth-limits {
        presence "Indicates a bandwidth-limits node is configured.";
        description
          "Set min/max bandwidth auto-bw can apply on a
           tunnel";
        leaf bandwidth-min-limit {
          type string;
          // NCS drop mandatory statement
          description
            "Set minimum bandwidth auto-bw can apply on a
             tunnel";
        }
        leaf bandwidth-max-limit {
          type string;
          // NCS drop mandatory statement
          description
            "Set maximum bandwidth auto-bw can apply on a
             tunnel";
        }
      }
      container adjustment-threshold {
        presence "Indicates a adjustment-threshold node is configured.";
        description
          "Set the bandwidth change threshold to trigger
           adjustment";
        leaf adjustment-threshold-percent {
          type string;
          units "percentage";
          // NCS drop mandatory statement
          description
            "Bandwidth change percent to trigger adjustment";
        }
        leaf adjustment-threshold-value {
          type string;
          units "kbit/s";
          // NCS drop mandatory statement
          description
            "Bandwidth change value to trigger adjustment
             (kbps)";
        }
      }
      container auto-capacity {
        description
          "Tunnel auto-capacity configuration data";
        leaf nominal-bandwidth {
          type string;
          units "kbit/s";
          description
            "Bandwidth value used to compute the desired
             number of tunnels for auto-capacity";
        }
        leaf enable {
          type string;
          description
            "Enable auto-capacityThe object must be set
             before any other auto capacity configuration
             is supplied for the tunnel,and must be the
             last auto-capacity configuration object to be
             removed.";
        }
        leaf clones-minimum {
          type string;
          // NCS drop default statement
          description
            "Lower limit on the number of clones can be
             created for the tunnel";
        }
        leaf split-bandwidth {
          type string;
          units "kbit/s";
          description
            "Upper bandwidth limit that causes the tunnel
             to be split";
        }
        leaf merge-bandwidth {
          type string;
          units "kbit/s";
          description
            "Lower bandwidth limit that causes the tunnel
             to be merged";
        }
        leaf clones-maximum {
          type string;
          // NCS drop default statement
          description
            "Upper limit on the number of clones can be
             created for the tunnel";
        }
      }
      leaf underflow-enable {
        type string;
        description
          "Enable auto bandwidth underflow detection";
      }
      leaf resignal-last-bandwidth-time-out {
        type string;
        units "second";
        description
          "Set the tunnel auto-bw resignal last bandwidth
           time-out in seconds";
      }
      leaf enabled {
        type string;
        description
          "This object is only valid for tunnel interfaces
           and it controls whether that interface has
           auto-bw enabled on it or not.The object must be
           set before any other auto-bw configuration is
           supplied for the interface, and must be the
           last auto-bw configuration object to be removed
           .";
      }
      leaf application-frequency {
        type string;
        units "minute";
        description
          "Set the tunnel auto-bw application frequency in
           minutes";
      }
      leaf overflow-enable {
        type string;
        description
          "Enable auto bandwidth overflow detection";
      }
      uses ncs_template_COLLECTION-ONLY;
    }
  }

  grouping ncs_template_RECORD-ROUTE {
    description
      "Common node of tunnel-attributes,
       tunnel-te-attributes, auto-mesh-attribute,
       auto-backup-attribute, gmpls-unitunnel-head,
       p2mpte-attribute, tunnel-head";
    leaf record-route {
      type empty;
      description
        "Record the route used by the tunnel";
    }
  }

  grouping ncs_template_OOR-ACCEPT-LSP-MIN-BANDWIDTH {
    description
      "Common node of oor-green-state, oor-yellow-state,
       oor-red-state";
    leaf oor-accept-lsp-min-bandwidth {
      type string;
      units "kbit/s";
      // NCS drop default statement
      description
        "Only accept LSPs with at least the specified
         bandwidth (in kbps).";
    }
  }

  grouping ncs_template_LOGGING {
    description
      "Common node of tunnel-te-attributes,
       tunnel-attributes, p2p-te-attribute";
    container logging {
      description
        "Log tunnel LSP messages";
      leaf lsp-switch-over-change-message {
        type empty;
        description
          "Log tunnel messages for bandwidth change";
      }
      leaf all {
        type empty;
        description
          "Log all events for a tunnel";
      }
      leaf record-route-messsage {
        type empty;
        description
          "Log tunnel record-route messages";
      }
      leaf bfd-state-message {
        type empty;
        description
          "Enable BFD session state change alarm";
      }
      uses ncs_template_BANDWIDTH-CHANGE-MESSAGE;
      uses ncs_template_REOPTIMIZE-ATTEMPTS-MESSAGE;
      uses ncs_template_REROUTE-MESSSAGE;
      uses ncs_template_STATE-MESSAGE;
      uses ncs_template_INSUFFICIENT-BW-MESSAGE;
      uses ncs_template_REOPTIMIZED-MESSAGE;
      uses ncs_template_PCALC-FAILURE-MESSAGE;
    }
  }

  grouping ncs_template_MPLS-MTE-TUNNEL-CFG-LOGGING {
    description
      "Common node of tunnel-te-attributes,
       tunnel-attributes, p2p-te-attributeCommon node of
       mte-tunnel-attributes, p2mpte-attribute";
    container logging {
      description
        "Log tunnel LSP messages";
      leaf insufficient-bw-message {
        type empty;
        description
          "Log tunnel messages for insufficient bandwidth";
      }
      leaf reoptimized-message {
        type empty;
        description
          "Log tunnel reoptimized messages";
      }
      leaf bandwidth-change-message {
        type empty;
        description
          "Log tunnel bandwidth change messages";
      }
      leaf all {
        type empty;
        description
          "Log all events for a tunnel";
      }
      leaf pcalc-failure-message {
        type empty;
        description
          "Enable logging for path-calculation failures";
      }
      leaf state-message {
        type empty;
        description
          "Log tunnel state messages";
      }
      leaf reoptimize-attempts-message {
        type empty;
        description
          "Log tunnel reoptimization attempts messages";
      }
      leaf sub-lsp-state-message {
        type empty;
        description
          "Log all tunnel sub-LSP state messages";
      }
      leaf reroute-messsage {
        type empty;
        description
          "Log tunnel rereoute messages";
      }
    }
  }

  grouping ncs_template_COLLECTION-ONLY {
    description
      "Common node of auto-bandwidth,
       auto-mesh-attribute";
    leaf collection-only {
      type empty;
      description
        "Enable bandwidth collection only, no auto-bw
         adjustment";
    }
  }

  grouping ncs_template_PCE {
    description
      "Common node of path-option-attribute,
       p2p-te-attribute";
    container pce {
      description
        "Configure pce properties";
      container bidirectional {
        presence "Indicates a bidirectional node is configured.";
        description
          "Bidirectional parameters";
        leaf bd-source-address {
          type string;
          // NCS drop mandatory statement
          description
            "Bidirectional Source IP Address";
        }
        leaf bd-group-id {
          type string;
          // NCS drop mandatory statement
          description
            "Bidirectional Group ID";
        }
      }
      container disjoint-path {
        presence "Indicates a disjoint-path node is configured.";
        description
          "Disjoint path parameters";
        leaf dp-source-address {
          type string;
          // NCS drop mandatory statement
          description
            "Disjoint Path Source IP Address";
        }
        leaf dp-type {
          type string;
          // NCS drop mandatory statement
          description
            "Disjoint Path Type";
        }
        leaf dp-group-id {
          type string;
          // NCS drop mandatory statement
          description
            "Disjoint Path Group ID";
        }
      }
      leaf enable {
        type empty;
        description
          "Always set to true";
      }
    }
  }

  grouping ncs_template_DESTINATION {
    description
      "Common node of tunnel-te-attributes,
       tunnel-attributes";
    leaf destination {
      type string;
      description
        "Set the destination of the tunnel";
    }
  }

  grouping ncs_template_STATE-MESSAGE {
    description
      "Common node of logging, logging,
       auto-backup-logging, auto-mesh-logging";
    leaf state-message {
      type empty;
      description
        "Log tunnel state messages";
    }
  }

  grouping ncs_template_LOAD-SHARE {
    description
      "Common node of tunnel-attributes,
       tunnel-te-attributes, auto-mesh-attribute";
    leaf load-share {
      type string;
      description
        "Tunnel loadsharing metric";
    }
  }

  grouping ncs_template_PATH-SELECTION {
    description
      "Common node of auto-mesh-attribute, xro-attribute
       , auto-backup-attribute, p2mpte-attribute,
       otn-pp-attribute";
    container path-selection {
      description
        "Configure path selection properties";
      leaf enable {
        type empty;
        description
          "Enable path selection";
      }
    }
  }

  grouping ncs_template_SIGNALLED-NAME {
    description
      "Common node of tunnel-te-attributes,
       gmpls-unitunnel-head, tunnel-head";
    leaf signalled-name {
      type string;
      description
        "The name of the tunnel to be included in
         signalling messages";
    }
  }

  grouping ncs_template_REOPTIMIZED-MESSAGE {
    description
      "Common node of logging, auto-backup-logging,
       auto-mesh-logging";
    leaf reoptimized-message {
      type empty;
      description
        "Log tunnel reoptimized messages";
    }
  }

  grouping ncs_template_NEW-STYLE-AFFINITY-TABLE {
    description
      "Common node of logging, auto-backup-logging,
       auto-mesh-loggingCommon node of tunnel-attributes
       , tunnel-te-attributes, path-option-attribute,
       auto-backup-attribute, auto-mesh-attribute,
       p2mpte-attribute, p2p-te-attribute";
    container new-style-affinity-affinity-types {
      description
        "Tunnel new style affinity attributes table";
      list new-style-affinity-affinity-type {
        // NCS patched for predictable order
        ordered-by user;
        key "affinity-type";
        description
          "Tunnel new style affinity attribute";
        leaf affinity-type {
          type string;
          description
            "The type of the affinity entry";
        }
      }
      list new-style-affinity-affinity-type-affinity1 {
        // NCS patched for predictable order
        ordered-by user;
        key "affinity-type affinity1";
        description
          "Tunnel new style affinity attribute";
        leaf affinity-type {
          type string;
          description
            "The type of the affinity entry";
        }
        leaf affinity1 {
          type string;
          description
            "The name of the first affinity";
        }
      }
      list new-style-affinity-affinity-type-affinity1-affinity2 {
        // NCS patched for predictable order
        ordered-by user;
        key "affinity-type affinity1 affinity2";
        description
          "Tunnel new style affinity attribute";
        leaf affinity-type {
          type string;
          description
            "The type of the affinity entry";
        }
        leaf affinity1 {
          type string;
          description
            "The name of the first affinity";
        }
        leaf affinity2 {
          type string;
          description
            "The name of the second affinity";
        }
      }
      list new-style-affinity-affinity-type-affinity1-affinity2-affinity3 {
        // NCS patched for predictable order
        ordered-by user;
        key "affinity-type affinity1 affinity2 affinity3";
        description
          "Tunnel new style affinity attribute";
        leaf affinity-type {
          type string;
          description
            "The type of the affinity entry";
        }
        leaf affinity1 {
          type string;
          description
            "The name of the first affinity";
        }
        leaf affinity2 {
          type string;
          description
            "The name of the second affinity";
        }
        leaf affinity3 {
          type string;
          description
            "The name of the third affinity";
        }
      }
      list new-style-affinity-affinity-type-affinity1-affinity2-affinity3-affinity4 {
        // NCS patched for predictable order
        ordered-by user;
        key "affinity-type affinity1 affinity2 affinity3 affinity4";
        description
          "Tunnel new style affinity attribute";
        leaf affinity-type {
          type string;
          description
            "The type of the affinity entry";
        }
        leaf affinity1 {
          type string;
          description
            "The name of the first affinity";
        }
        leaf affinity2 {
          type string;
          description
            "The name of the second affinity";
        }
        leaf affinity3 {
          type string;
          description
            "The name of the third affinity";
        }
        leaf affinity4 {
          type string;
          description
            "The name of the fourth affinity";
        }
      }
      list new-style-affinity-affinity-type-affinity1-affinity2-affinity3-affinity4-affinity5 {
        // NCS patched for predictable order
        ordered-by user;
        key "affinity-type affinity1 affinity2 affinity3 affinity4 affinity5";
        description
          "Tunnel new style affinity attribute";
        leaf affinity-type {
          type string;
          description
            "The type of the affinity entry";
        }
        leaf affinity1 {
          type string;
          description
            "The name of the first affinity";
        }
        leaf affinity2 {
          type string;
          description
            "The name of the second affinity";
        }
        leaf affinity3 {
          type string;
          description
            "The name of the third affinity";
        }
        leaf affinity4 {
          type string;
          description
            "The name of the fourth affinity";
        }
        leaf affinity5 {
          type string;
          description
            "The name of the fifth affinity";
        }
      }
      list new-style-affinity-affinity-type-affinity1-affinity2-affinity3-affinity4-affinity5-affinity6 {
        // NCS patched for predictable order
        ordered-by user;
        key "affinity-type affinity1 affinity2 affinity3 affinity4 affinity5 affinity6";
        description
          "Tunnel new style affinity attribute";
        leaf affinity-type {
          type string;
          description
            "The type of the affinity entry";
        }
        leaf affinity1 {
          type string;
          description
            "The name of the first affinity";
        }
        leaf affinity2 {
          type string;
          description
            "The name of the second affinity";
        }
        leaf affinity3 {
          type string;
          description
            "The name of the third affinity";
        }
        leaf affinity4 {
          type string;
          description
            "The name of the fourth affinity";
        }
        leaf affinity5 {
          type string;
          description
            "The name of the fifth affinity";
        }
        leaf affinity6 {
          type string;
          description
            "The name of the sixth affinity";
        }
      }
      list new-style-affinity-affinity-type-affinity1-affinity2-affinity3-affinity4-affinity5-affinity6-affinity7 {
        // NCS patched for predictable order
        ordered-by user;
        key "affinity-type affinity1 affinity2 affinity3 affinity4 affinity5 affinity6 affinity7";
        description
          "Tunnel new style affinity attribute";
        leaf affinity-type {
          type string;
          description
            "The type of the affinity entry";
        }
        leaf affinity1 {
          type string;
          description
            "The name of the first affinity";
        }
        leaf affinity2 {
          type string;
          description
            "The name of the second affinity";
        }
        leaf affinity3 {
          type string;
          description
            "The name of the third affinity";
        }
        leaf affinity4 {
          type string;
          description
            "The name of the fourth affinity";
        }
        leaf affinity5 {
          type string;
          description
            "The name of the fifth affinity";
        }
        leaf affinity6 {
          type string;
          description
            "The name of the sixth affinity";
        }
        leaf affinity7 {
          type string;
          description
            "The name of the seventh affinity";
        }
      }
      list new-style-affinity-affinity-type-affinity1-affinity2-affinity3-affinity4-affinity5-affinity6-affinity7-affinity8 {
        // NCS patched for predictable order
        ordered-by user;
        key "affinity-type affinity1 affinity2 affinity3 affinity4 affinity5 affinity6 affinity7 affinity8";
        description
          "Tunnel new style affinity attribute";
        leaf affinity-type {
          type string;
          description
            "The type of the affinity entry";
        }
        leaf affinity1 {
          type string;
          description
            "The name of the first affinity";
        }
        leaf affinity2 {
          type string;
          description
            "The name of the second affinity";
        }
        leaf affinity3 {
          type string;
          description
            "The name of the third affinity";
        }
        leaf affinity4 {
          type string;
          description
            "The name of the fourth affinity";
        }
        leaf affinity5 {
          type string;
          description
            "The name of the fifth affinity";
        }
        leaf affinity6 {
          type string;
          description
            "The name of the sixth affinity";
        }
        leaf affinity7 {
          type string;
          description
            "The name of the seventh affinity";
        }
        leaf affinity8 {
          type string;
          description
            "The name of the eighth affinity";
        }
      }
      list new-style-affinity-affinity-type-affinity1-affinity2-affinity3-affinity4-affinity5-affinity6-affinity7-affinity8-affinity9 {
        // NCS patched for predictable order
        ordered-by user;
        key "affinity-type affinity1 affinity2 affinity3 affinity4 affinity5 affinity6 affinity7 affinity8 affinity9";
        description
          "Tunnel new style affinity attribute";
        leaf affinity-type {
          type string;
          description
            "The type of the affinity entry";
        }
        leaf affinity1 {
          type string;
          description
            "The name of the first affinity";
        }
        leaf affinity2 {
          type string;
          description
            "The name of the second affinity";
        }
        leaf affinity3 {
          type string;
          description
            "The name of the third affinity";
        }
        leaf affinity4 {
          type string;
          description
            "The name of the fourth affinity";
        }
        leaf affinity5 {
          type string;
          description
            "The name of the fifth affinity";
        }
        leaf affinity6 {
          type string;
          description
            "The name of the sixth affinity";
        }
        leaf affinity7 {
          type string;
          description
            "The name of the seventh affinity";
        }
        leaf affinity8 {
          type string;
          description
            "The name of the eighth affinity";
        }
        leaf affinity9 {
          type string;
          description
            "The name of the nineth affinity";
        }
      }
      list new-style-affinity-affinity-type-affinity1-affinity2-affinity3-affinity4-affinity5-affinity6-affinity7-affinity8-affinity9-affinity10 {
        // NCS patched for predictable order
        ordered-by user;
        key "affinity-type affinity1 affinity2 affinity3 affinity4 affinity5 affinity6 affinity7 affinity8 affinity9 affinity10";
        description
          "Tunnel new style affinity attribute";
        leaf affinity-type {
          type string;
          description
            "The type of the affinity entry";
        }
        leaf affinity1 {
          type string;
          description
            "The name of the first affinity";
        }
        leaf affinity2 {
          type string;
          description
            "The name of the second affinity";
        }
        leaf affinity3 {
          type string;
          description
            "The name of the third affinity";
        }
        leaf affinity4 {
          type string;
          description
            "The name of the fourth affinity";
        }
        leaf affinity5 {
          type string;
          description
            "The name of the fifth affinity";
        }
        leaf affinity6 {
          type string;
          description
            "The name of the sixth affinity";
        }
        leaf affinity7 {
          type string;
          description
            "The name of the seventh affinity";
        }
        leaf affinity8 {
          type string;
          description
            "The name of the eighth affinity";
        }
        leaf affinity9 {
          type string;
          description
            "The name of the nineth affinity";
        }
        leaf affinity10 {
          type string;
          description
            "The name of the tenth affinity";
        }
      }
    }
  }

  grouping ncs_template_FAST-REROUTE {
    description
      "Common node of tunnel-attributes,
       tunnel-te-attributes, auto-mesh-attribute,
       p2mpte-attribute";
    container fast-reroute {
      presence "Indicates a fast-reroute node is configured.";
      description
        "Specify MPLS tunnel can be fast-rerouted";
      leaf bandwidth-protection {
        type string;
        // NCS drop mandatory statement
        description
          "Bandwidth Protection";
      }
      leaf node-protection {
        type string;
        // NCS drop mandatory statement
        description
          "Node Protection";
      }
    }
  }

  grouping ncs_template_TUNNEL-RANGE {
    description
      "Common node of backup, mesh, p2mp-auto-tunnel,
       p2p-auto-tunnel, pcc";
    container tunnel-range {
      presence "Indicates a tunnel-range node is configured.";
      description
        "Configure tunnel ID range for auto-tunnel
         features";
      leaf min-tunnel-id {
        type string;
        // NCS drop mandatory statement
        description
          "Minimum tunnel ID for auto-tunnels";
      }
      leaf max-tunnel-id {
        type string;
        // NCS drop mandatory statement
        description
          "Maximum tunnel ID for auto-tunnels";
      }
    }
  }

  grouping ncs_template_ENABLE {
    description
      "Common node of path-selection,
       att-path-option-path-selection";
    leaf enable {
      type empty;
      description
        "Enter path selection configuration";
    }
  }

  grouping ncs_template_AUTOROUTE {
    description
      "Common node of tunnel-attributes,
       tunnel-te-attributes";
    container autoroute {
      description
        "Parameters for IGP routing over tunnel";
      container autoroute-announce {
        description
          "Announce tunnel to IGP";
        container exclude-traffic {
          description
            "Exclude traffic on autorouted tunnel";
          leaf segment-routing {
            type empty;
            description
              "Exclude tunnel in IGP for SR prefixes";
          }
        }
        container metric {
          description
            "Specify MPLS tunnel metric";
          leaf metric-type {
            type string;
            description
              "Autoroute tunnel metric type";
          }
          leaf absolute-metric {
            // NCS drop when statement
            type string;
            description
              "The absolute metric value";
          }
          leaf relative-metric {
            // NCS drop when statement
            type string;
            description
              "The value of the adjustment";
          }
          leaf constant-metric {
            // NCS drop when statement
            type string;
            description
              "The constant metric value";
          }
        }
        leaf enable {
          type empty;
          description
            "Enable autoroute announce";
        }
        leaf include-ipv6 {
          type empty;
          description
            "Specify that the tunnel should be an IPv6
             autoroute announce also";
        }
      }
      container destinations {
        description
          "Tunnel Autoroute Destination(s)";
        list destination {
          // NCS patched for predictable order
          ordered-by user;
          key "destination-address";
          description
            "Destination address to add in RIB";
          leaf destination-address {
            type string;
            description
              "IP address of destination";
          }
        }
      }
    }
  }

  grouping ncs_template_OOR-NODE-PROTECTION-DISABLE {
    description
      "Common node of oor-green-state, oor-yellow-state,
       oor-red-state";
    leaf oor-node-protection-disable {
      type empty;
      description
        "Disable FRR node-protection when the link is in
         this OOR State";
    }
  }

  grouping ncs_template_REROUTE-MESSSAGE {
    description
      "Common node of logging, auto-mesh-logging";
    leaf reroute-messsage {
      type empty;
      description
        "Log tunnel rereoute messages";
    }
  }

  grouping ncs_template_CACHE-TIMER {
    description
      "Common node of mpls-te-mib, mpls-frr-mib,
       mpls-p2mp-mib, mpls-te-ext-mib,
       mpls-te-ext-std-mib";
    leaf cache-timer {
      type string;
      units "second";
      // NCS drop default statement
      description
        "Configure the cache time for the mib.";
    }
  }

  grouping ncs_template_PATH-SELECTION-METRIC {
    description
      "Common node of tunnel-attributes,
       tunnel-te-attributes";
    leaf path-selection-metric {
      type string;
      description
        "Path selection metric to use in path calculation";
    }
  }

  grouping ncs_template_PASSWORD {
    description
      "Common node of peer, pce-attributes";
    leaf password {
      type string;
      description
        "MD5 password";
    }
  }

  grouping ncs_template_BANDWIDTH {
    description
      "Common node of tunnel-attributes,
       tunnel-te-attributes, auto-mesh-attribute,
       path-option-attribute, p2mpte-attribute";
    container bandwidth {
      presence "Indicates a bandwidth node is configured.";
      description
        "Tunnel bandwidth requirement";
      leaf dste-type {
        type string;
        // NCS drop mandatory statement
        description
          "DSTE-standard flag";
      }
      leaf class-or-pool-type {
        type string;
        // NCS drop mandatory statement
        description
          "Class type for the bandwidth allocation";
      }
      leaf bandwidth {
        type string;
        units "kbit/s";
        // NCS drop mandatory statement
        description
          "The value of the bandwidth reserved by this
           tunnel in kbps";
      }
    }
  }

  grouping ncs_template_INTERFACE-BANDWIDTH {
    description
      "Common node of auto-mesh-attribute,
       p2mpte-attribute";
    leaf interface-bandwidth {
      type string;
      units "kbit/s";
      description
        "The bandwidth of the interface in kbps";
    }
  }

  grouping ncs_template_FORWARD-CLASS {
    description
      "Common node of tunnel-attributes,
       tunnel-te-attributes, auto-mesh-attribute";
    leaf forward-class {
      type string;
      description
        "Forward class value";
    }
  }

  grouping ncs_template_INSUFFICIENT-BW-MESSAGE {
    description
      "Common node of logging, auto-mesh-logging";
    leaf insufficient-bw-message {
      type empty;
      description
        "Log tunnel messages for insufficient bandwidth";
    }
  }

  grouping ncs_template_PATH-SELECTION-DELAY-LIMIT {
    description
      "Common node of tunnel-path-selection,
       att-path-option-path-selection";
    leaf path-selection-delay-limit {
      type string;
      description
        "Path selection delay limit (usec) configuration
         for this specific tunnel";
    }
  }

  grouping ncs_template_OOR-METRIC-TE-PENALTY {
    description
      "Common node of oor-green-state, oor-yellow-state,
       oor-red-state";
    leaf oor-metric-te-penalty {
      type string;
      // NCS drop default statement
      description
        "Penalty applied to the TE metric of a link in
         OOR state";
    }
  }

  grouping ncs_template_KEYCHAIN {
    description
      "Common node of peer, pce-attributes";
    leaf keychain {
      type string;
      description
        "Keychain based authentication";
    }
  }

  grouping ncs_template_FORWARDING-ADJACENCY {
    description
      "Common node of tunnel-attributes,
       tunnel-te-attributes";
    container forwarding-adjacency {
      description
        "Forwarding adjacency announcement to IGP";
      leaf enable {
        type empty;
        description
          "Enable forwarding adjacency";
      }
      leaf include-ipv6 {
        type empty;
        description
          "Specify that the tunnel should be an IPv6
           forwarding adjacency also";
      }
      leaf hold-time {
        type string;
        description
          "Specify the holdtime for the tunnel as
           forwarding adjacency";
      }
    }
  }

  grouping ncs_template_ALL-TRANSIT-LSP-THRESHOLD {
    description
      "Common node of lsp-oor-yellow-state,
       lsp-oor-red-state";
    leaf all-transit-lsp-threshold {
      type string;
      description
        "Threshold for all transit LSPs";
    }
  }

  grouping ncs_template_PRIORITY {
    description
      "Common node of tunnel-te-attributes,
       tunnel-attributes, auto-mesh-attribute,
       gmpls-unitunnel-head, auto-backup-attribute,
       p2mpte-attribute";
    container priority {
      presence "Indicates a priority node is configured.";
      description
        "Tunnel Setup and Hold Priorities";
      leaf setup-priority {
        type string;
        // NCS drop mandatory statement
        description
          "Setup Priority";
      }
      leaf hold-priority {
        type string;
        // NCS drop mandatory statement
        description
          "Hold Priority";
      }
    }
  }

  grouping ncs_rpc_notif_OOR-ACCEPT-REOPT-LSP {
    description
      "Common node of oor-green-state, oor-yellow-state,
       oor-red-state";
    leaf oor-accept-reopt-lsp {
      type empty;
      description
        "Allow the setup of reoptimized LSPs over the
         link in this OOR State";
    }
  }

  grouping ncs_rpc_notif_PCALC-FAILURE-MESSAGE {
    description
      "Common node of logging, auto-mesh-logging";
    leaf pcalc-failure-message {
      type empty;
      description
        "Enable logging for path-calculation failures";
    }
  }

  grouping ncs_rpc_notif_POLICY-CLASSES {
    description
      "Common node of tunnel-te-attributes,
       auto-mesh-attribute, auto-backup-attribute";
    container policy-classes {
      description
        "Policy classes for PBTS";
      leaf-list policy-class {
        type Mpls-te-policy-class-range;
        max-elements 7;
        description
          "Array of Policy class";
      }
    }
  }

  grouping ncs_rpc_notif_UNPROTECTED-TRANSIT-LSP-THRESHOLD {
    description
      "Common node of lsp-oor-yellow-state,
       lsp-oor-red-state";
    leaf unprotected-transit-lsp-threshold {
      type uint32;
      description
        "Threshold for unprotected transit LSPs";
    }
  }

  grouping ncs_rpc_notif_AFFINITY-MASK {
    description
      "Common node of tunnel-te-attributes,
       tunnel-attributes, auto-mesh-attribute,
       auto-backup-attribute, path-option-attribute,
       p2mpte-attribute, p2p-te-attribute";
    container affinity-mask {
      presence "Indicates a affinity-mask node is configured.";
      description
        "Set the affinity flags and mask";
      leaf affinity {
        type xr:Hex-integer;
        mandatory true;
        description
          "Affinity flags";
      }
      leaf mask {
        type xr:Hex-integer;
        mandatory true;
        description
          "Affinity mask";
      }
    }
  }

  grouping ncs_rpc_notif_BANDWIDTH-CHANGE-MESSAGE {
    description
      "Common node of logging, auto-backup-logging,
       auto-mesh-logging";
    leaf bandwidth-change-message {
      type empty;
      description
        "Log tunnel messages for bandwidth change";
    }
  }

  grouping ncs_rpc_notif_REOPTIMIZE-ATTEMPTS-MESSAGE {
    description
      "Common node of logging, auto-backup-logging,
       auto-mesh-logging";
    leaf reoptimize-attempts-message {
      type empty;
      description
        "Log tunnel reoptimization attempts messages";
    }
  }

  grouping ncs_rpc_notif_OOR-AVAILABLE-BANDWIDTH-PERCENTAGE {
    description
      "Common node of oor-green-state, oor-yellow-state,
       oor-red-state";
    leaf oor-available-bandwidth-percentage {
      type uint32 {
        range "0..100";
      }
      units "percentage";
      default "100";
      description
        "Flood a specific percentage of the available
         bandwidth";
    }
  }

  grouping ncs_rpc_notif_TIMERS {
    description
      "Common node of backup, mesh";
    container timers {
      description
        "Configure auto-tunnel backup timers value";
      container removal {
        description
          "Configure auto-tunnel backup removal timers
           value";
        leaf unused {
          type uint32 {
            range "0..10080";
          }
          units "minute";
          default "3600";
          description
            "Auto-tunnel backup unused timeout in minutes
             (0=never timeout)";
        }
      }
    }
  }

  grouping ncs_rpc_notif_TUNNEL-PATH-SELECTION {
    description
      "Common node of tunnel-te-attributes,
       tunnel-attributes";
    container tunnel-path-selection {
      description
        "Configure path selection properties";
      leaf tiebreaker {
        type Mpls-te-path-selection-tiebreaker;
        description
          "CSPF tiebreaker to use in path calculation";
      }
      leaf path-selection-hop-limit {
        type uint32 {
          range "1..255";
        }
        description
          "Path selection hop limit configuration for this
           specific tunnel";
      }
      uses ncs_rpc_notif_PATH-SELECTION-DELAY-LIMIT;
      uses ncs_rpc_notif_INVALIDATION;
      uses ncs_rpc_notif_PATH-SELECTION-COST-LIMIT;
    }
  }

  grouping ncs_rpc_notif_INVALIDATION {
    description
      "Common node of tunnel-te-attributes,
       tunnel-attributesCommon node of
       tunnel-path-selection,
       att-path-option-path-selection";
    container invalidation {
      presence "enable invalidation";
      description
        "Deprecated";
      leaf path-invalidation-timeout {
        type uint32 {
          range "0..60000";
        }
        description
          "Path Invalidation Timeout";
      }
      leaf path-invalidation-action {
        type Path-invalidation-action;
        description
          "Path Invalidation Action";
      }
    }
  }

  grouping ncs_rpc_notif_PRECEDENCE {
    description
      "Common node of peer, pce-attributes";
    leaf precedence {
      type uint32 {
        range "0..255";
      }
      description
        "Precedence order";
    }
  }

  grouping ncs_rpc_notif_SOFT-PREEMPTION {
    description
      "Common node of tunnel-attributes,
       tunnel-te-attributes, auto-mesh-attribute";
    leaf soft-preemption {
      type empty;
      description
        "Enable the soft-preemption feature on the tunnel";
    }
  }

  grouping ncs_rpc_notif_PATH-SELECTION-COST-LIMIT {
    description
      "Common node of tunnel-path-selection,
       att-path-option-path-selection";
    leaf path-selection-cost-limit {
      type uint32 {
        range "1..4294967295";
      }
      description
        "Path selection cost limit configuration for this
         specific tunnel";
    }
  }

  grouping ncs_rpc_notif_AUTO-BANDWIDTH {
    description
      "Common node of tunnel-attributes,
       tunnel-te-attributes";
    container auto-bandwidth {
      description
        "Tunnel Interface Auto-bandwidth configuration
         data";
      container underflow {
        presence "Indicates a underflow node is configured.";
        description
          "Configuring the tunnel underflow detection";
        leaf underflow-threshold-percent {
          type uint32 {
            range "1..100";
          }
          units "percentage";
          mandatory true;
          description
            "Bandwidth change percent to trigger an
             underflow";
        }
        leaf underflow-threshold-value {
          type uint32 {
            range "10..4294967295";
          }
          units "kbit/s";
          mandatory true;
          description
            "Bandwidth change value to trigger an underflow
             (kbps)";
        }
        leaf underflow-threshold-limit {
          type uint32 {
            range "1..10";
          }
          mandatory true;
          description
            "Number of consecutive collections exceeding
             threshold";
        }
      }
      container overflow {
        presence "Indicates a overflow node is configured.";
        description
          "Configuring the tunnel overflow detection";
        leaf overflow-threshold-percent {
          type uint32 {
            range "1..100";
          }
          units "percentage";
          mandatory true;
          description
            "Bandwidth change percent to trigger an
             overflow";
        }
        leaf overflow-threshold-value {
          type uint32 {
            range "10..4294967295";
          }
          units "kbit/s";
          mandatory true;
          description
            "Bandwidth change value to trigger an overflow
             (kbps)";
        }
        leaf overflow-threshold-limit {
          type uint32 {
            range "1..10";
          }
          mandatory true;
          description
            "Number of consecutive collections exceeding
             threshold";
        }
      }
      container bandwidth-limits {
        presence "Indicates a bandwidth-limits node is configured.";
        description
          "Set min/max bandwidth auto-bw can apply on a
           tunnel";
        leaf bandwidth-min-limit {
          type uint32 {
            range "0..4294967295";
          }
          mandatory true;
          description
            "Set minimum bandwidth auto-bw can apply on a
             tunnel";
        }
        leaf bandwidth-max-limit {
          type uint32 {
            range "0..4294967295";
          }
          mandatory true;
          description
            "Set maximum bandwidth auto-bw can apply on a
             tunnel";
        }
      }
      container adjustment-threshold {
        presence "Indicates a adjustment-threshold node is configured.";
        description
          "Set the bandwidth change threshold to trigger
           adjustment";
        leaf adjustment-threshold-percent {
          type uint32 {
            range "1..100";
          }
          units "percentage";
          mandatory true;
          description
            "Bandwidth change percent to trigger adjustment";
        }
        leaf adjustment-threshold-value {
          type uint32 {
            range "10..4294967295";
          }
          units "kbit/s";
          mandatory true;
          description
            "Bandwidth change value to trigger adjustment
             (kbps)";
        }
      }
      container auto-capacity {
        description
          "Tunnel auto-capacity configuration data";
        leaf nominal-bandwidth {
          type uint32 {
            range "0..4294967295";
          }
          units "kbit/s";
          description
            "Bandwidth value used to compute the desired
             number of tunnels for auto-capacity";
        }
        leaf enable {
          type boolean;
          description
            "Enable auto-capacityThe object must be set
             before any other auto capacity configuration
             is supplied for the tunnel,and must be the
             last auto-capacity configuration object to be
             removed.";
        }
        leaf clones-minimum {
          type uint32 {
            range "0..63";
          }
          default "0";
          description
            "Lower limit on the number of clones can be
             created for the tunnel";
        }
        leaf split-bandwidth {
          type uint32 {
            range "0..4294967295";
          }
          units "kbit/s";
          description
            "Upper bandwidth limit that causes the tunnel
             to be split";
        }
        leaf merge-bandwidth {
          type uint32 {
            range "0..4294967295";
          }
          units "kbit/s";
          description
            "Lower bandwidth limit that causes the tunnel
             to be merged";
        }
        leaf clones-maximum {
          type uint32 {
            range "0..63";
          }
          default "63";
          description
            "Upper limit on the number of clones can be
             created for the tunnel";
        }
      }
      leaf underflow-enable {
        type boolean;
        description
          "Enable auto bandwidth underflow detection";
      }
      leaf resignal-last-bandwidth-time-out {
        type uint32 {
          range "1..3600000";
        }
        units "second";
        description
          "Set the tunnel auto-bw resignal last bandwidth
           time-out in seconds";
      }
      leaf enabled {
        type boolean;
        description
          "This object is only valid for tunnel interfaces
           and it controls whether that interface has
           auto-bw enabled on it or not.The object must be
           set before any other auto-bw configuration is
           supplied for the interface, and must be the
           last auto-bw configuration object to be removed
           .";
      }
      leaf application-frequency {
        type uint32 {
          range "5..10080";
        }
        units "minute";
        description
          "Set the tunnel auto-bw application frequency in
           minutes";
      }
      leaf overflow-enable {
        type boolean;
        description
          "Enable auto bandwidth overflow detection";
      }
      uses ncs_rpc_notif_COLLECTION-ONLY;
    }
  }

  grouping ncs_rpc_notif_RECORD-ROUTE {
    description
      "Common node of tunnel-attributes,
       tunnel-te-attributes, auto-mesh-attribute,
       auto-backup-attribute, gmpls-unitunnel-head,
       p2mpte-attribute, tunnel-head";
    leaf record-route {
      type empty;
      description
        "Record the route used by the tunnel";
    }
  }

  grouping ncs_rpc_notif_OOR-ACCEPT-LSP-MIN-BANDWIDTH {
    description
      "Common node of oor-green-state, oor-yellow-state,
       oor-red-state";
    leaf oor-accept-lsp-min-bandwidth {
      type uint32;
      units "kbit/s";
      default "0";
      description
        "Only accept LSPs with at least the specified
         bandwidth (in kbps).";
    }
  }

  grouping ncs_rpc_notif_LOGGING {
    description
      "Common node of tunnel-te-attributes,
       tunnel-attributes, p2p-te-attribute";
    container logging {
      description
        "Log tunnel LSP messages";
      leaf lsp-switch-over-change-message {
        type empty;
        description
          "Log tunnel messages for bandwidth change";
      }
      leaf all {
        type empty;
        description
          "Log all events for a tunnel";
      }
      leaf record-route-messsage {
        type empty;
        description
          "Log tunnel record-route messages";
      }
      leaf bfd-state-message {
        type empty;
        description
          "Enable BFD session state change alarm";
      }
      uses ncs_rpc_notif_BANDWIDTH-CHANGE-MESSAGE;
      uses ncs_rpc_notif_REOPTIMIZE-ATTEMPTS-MESSAGE;
      uses ncs_rpc_notif_REROUTE-MESSSAGE;
      uses ncs_rpc_notif_STATE-MESSAGE;
      uses ncs_rpc_notif_INSUFFICIENT-BW-MESSAGE;
      uses ncs_rpc_notif_REOPTIMIZED-MESSAGE;
      uses ncs_rpc_notif_PCALC-FAILURE-MESSAGE;
    }
  }

  grouping ncs_rpc_notif_MPLS-MTE-TUNNEL-CFG-LOGGING {
    description
      "Common node of tunnel-te-attributes,
       tunnel-attributes, p2p-te-attributeCommon node of
       mte-tunnel-attributes, p2mpte-attribute";
    container logging {
      description
        "Log tunnel LSP messages";
      leaf insufficient-bw-message {
        type empty;
        description
          "Log tunnel messages for insufficient bandwidth";
      }
      leaf reoptimized-message {
        type empty;
        description
          "Log tunnel reoptimized messages";
      }
      leaf bandwidth-change-message {
        type empty;
        description
          "Log tunnel bandwidth change messages";
      }
      leaf all {
        type empty;
        description
          "Log all events for a tunnel";
      }
      leaf pcalc-failure-message {
        type empty;
        description
          "Enable logging for path-calculation failures";
      }
      leaf state-message {
        type empty;
        description
          "Log tunnel state messages";
      }
      leaf reoptimize-attempts-message {
        type empty;
        description
          "Log tunnel reoptimization attempts messages";
      }
      leaf sub-lsp-state-message {
        type empty;
        description
          "Log all tunnel sub-LSP state messages";
      }
      leaf reroute-messsage {
        type empty;
        description
          "Log tunnel rereoute messages";
      }
    }
  }

  grouping ncs_rpc_notif_COLLECTION-ONLY {
    description
      "Common node of auto-bandwidth,
       auto-mesh-attribute";
    leaf collection-only {
      type empty;
      description
        "Enable bandwidth collection only, no auto-bw
         adjustment";
    }
  }

  grouping ncs_rpc_notif_PCE {
    description
      "Common node of path-option-attribute,
       p2p-te-attribute";
    container pce {
      description
        "Configure pce properties";
      container bidirectional {
        presence "Indicates a bidirectional node is configured.";
        description
          "Bidirectional parameters";
        leaf bd-source-address {
          type inet:ipv4-address-no-zone;
          mandatory true;
          description
            "Bidirectional Source IP Address";
        }
        leaf bd-group-id {
          type uint32 {
            range "1..4294967295";
          }
          mandatory true;
          description
            "Bidirectional Group ID";
        }
      }
      container disjoint-path {
        presence "Indicates a disjoint-path node is configured.";
        description
          "Disjoint path parameters";
        leaf dp-source-address {
          type inet:ipv4-address-no-zone;
          mandatory true;
          description
            "Disjoint Path Source IP Address";
        }
        leaf dp-type {
          type uint32 {
            range "1..3";
          }
          mandatory true;
          description
            "Disjoint Path Type";
        }
        leaf dp-group-id {
          type uint32 {
            range "1..4294967295";
          }
          mandatory true;
          description
            "Disjoint Path Group ID";
        }
      }
      leaf enable {
        type empty;
        description
          "Always set to true";
      }
    }
  }

  grouping ncs_rpc_notif_DESTINATION {
    description
      "Common node of tunnel-te-attributes,
       tunnel-attributes";
    leaf destination {
      type inet:ipv4-address-no-zone;
      description
        "Set the destination of the tunnel";
    }
  }

  grouping ncs_rpc_notif_STATE-MESSAGE {
    description
      "Common node of logging, logging,
       auto-backup-logging, auto-mesh-logging";
    leaf state-message {
      type empty;
      description
        "Log tunnel state messages";
    }
  }

  grouping ncs_rpc_notif_LOAD-SHARE {
    description
      "Common node of tunnel-attributes,
       tunnel-te-attributes, auto-mesh-attribute";
    leaf load-share {
      type uint32 {
        range "1..4294967295";
      }
      description
        "Tunnel loadsharing metric";
    }
  }

  grouping ncs_rpc_notif_PATH-SELECTION {
    description
      "Common node of auto-mesh-attribute, xro-attribute
       , auto-backup-attribute, p2mpte-attribute,
       otn-pp-attribute";
    container path-selection {
      description
        "Configure path selection properties";
      leaf enable {
        type empty;
        description
          "Enable path selection";
      }
    }
  }

  grouping ncs_rpc_notif_SIGNALLED-NAME {
    description
      "Common node of tunnel-te-attributes,
       gmpls-unitunnel-head, tunnel-head";
    leaf signalled-name {
      type string {
        length "1..254";
      }
      description
        "The name of the tunnel to be included in
         signalling messages";
    }
  }

  grouping ncs_rpc_notif_REOPTIMIZED-MESSAGE {
    description
      "Common node of logging, auto-backup-logging,
       auto-mesh-logging";
    leaf reoptimized-message {
      type empty;
      description
        "Log tunnel reoptimized messages";
    }
  }

  grouping ncs_rpc_notif_NEW-STYLE-AFFINITY-TABLE {
    description
      "Common node of logging, auto-backup-logging,
       auto-mesh-loggingCommon node of tunnel-attributes
       , tunnel-te-attributes, path-option-attribute,
       auto-backup-attribute, auto-mesh-attribute,
       p2mpte-attribute, p2p-te-attribute";
    container new-style-affinity-affinity-types {
      description
        "Tunnel new style affinity attributes table";
      list new-style-affinity-affinity-type {
        key "affinity-type";
        description
          "Tunnel new style affinity attribute";
        leaf affinity-type {
          type Mpls-te-tunnel-affinity;
          description
            "The type of the affinity entry";
        }
      }
      list new-style-affinity-affinity-type-affinity1 {
        key "affinity-type affinity1";
        description
          "Tunnel new style affinity attribute";
        leaf affinity-type {
          type Mpls-te-tunnel-affinity;
          description
            "The type of the affinity entry";
        }
        leaf affinity1 {
          type xr:Cisco-ios-xr-string;
          description
            "The name of the first affinity";
        }
      }
      list new-style-affinity-affinity-type-affinity1-affinity2 {
        key "affinity-type affinity1 affinity2";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
      }
      list new-style-affinity-affinity-type-affinity1-affinity2-affinity3 {
        key "affinity-type affinity1 affinity2 affinity3";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
      }
      list new-style-affinity-affinity-type-affinity1-affinity2-affinity3-affinity4 {
        key "affinity-type affinity1 affinity2 affinity3 affinity4";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
        leaf affinity4 {
          type xr:Cisco-ios-xr-string;
          description
            "The name of the fourth affinity";
        }
      }
      list new-style-affinity-affinity-type-affinity1-affinity2-affinity3-affinity4-affinity5 {
        key "affinity-type affinity1 affinity2 affinity3 affinity4 affinity5";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
        leaf affinity4 {
          type xr:Cisco-ios-xr-string;
          description
            "The name of the fourth affinity";
        }
        leaf affinity5 {
          type xr:Cisco-ios-xr-string;
          description
            "The name of the fifth affinity";
        }
      }
      list new-style-affinity-affinity-type-affinity1-affinity2-affinity3-affinity4-affinity5-affinity6 {
        key "affinity-type affinity1 affinity2 affinity3 affinity4 affinity5 affinity6";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
        leaf affinity4 {
          type xr:Cisco-ios-xr-string;
          description
            "The name of the fourth affinity";
        }
        leaf affinity5 {
          type xr:Cisco-ios-xr-string;
          description
            "The name of the fifth affinity";
        }
        leaf affinity6 {
          type xr:Cisco-ios-xr-string;
          description
            "The name of the sixth affinity";
        }
      }
      list new-style-affinity-affinity-type-affinity1-affinity2-affinity3-affinity4-affinity5-affinity6-affinity7 {
        key "affinity-type affinity1 affinity2 affinity3 affinity4 affinity5 affinity6 affinity7";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
        leaf affinity4 {
          type xr:Cisco-ios-xr-string;
          description
            "The name of the fourth affinity";
        }
        leaf affinity5 {
          type xr:Cisco-ios-xr-string;
          description
            "The name of the fifth affinity";
        }
        leaf affinity6 {
          type xr:Cisco-ios-xr-string;
          description
            "The name of the sixth affinity";
        }
        leaf affinity7 {
          type xr:Cisco-ios-xr-string;
          description
            "The name of the seventh affinity";
        }
      }
      list new-style-affinity-affinity-type-affinity1-affinity2-affinity3-affinity4-affinity5-affinity6-affinity7-affinity8 {
        key "affinity-type affinity1 affinity2 affinity3 affinity4 affinity5 affinity6 affinity7 affinity8";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
        leaf affinity4 {
          type xr:Cisco-ios-xr-string;
          description
            "The name of the fourth affinity";
        }
        leaf affinity5 {
          type xr:Cisco-ios-xr-string;
          description
            "The name of the fifth affinity";
        }
        leaf affinity6 {
          type xr:Cisco-ios-xr-string;
          description
            "The name of the sixth affinity";
        }
        leaf affinity7 {
          type xr:Cisco-ios-xr-string;
          description
            "The name of the seventh affinity";
        }
        leaf affinity8 {
          type xr:Cisco-ios-xr-string;
          description
            "The name of the eighth affinity";
        }
      }
      list new-style-affinity-affinity-type-affinity1-affinity2-affinity3-affinity4-affinity5-affinity6-affinity7-affinity8-affinity9 {
        key "affinity-type affinity1 affinity2 affinity3 affinity4 affinity5 affinity6 affinity7 affinity8 affinity9";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
        leaf affinity4 {
          type xr:Cisco-ios-xr-string;
          description
            "The name of the fourth affinity";
        }
        leaf affinity5 {
          type xr:Cisco-ios-xr-string;
          description
            "The name of the fifth affinity";
        }
        leaf affinity6 {
          type xr:Cisco-ios-xr-string;
          description
            "The name of the sixth affinity";
        }
        leaf affinity7 {
          type xr:Cisco-ios-xr-string;
          description
            "The name of the seventh affinity";
        }
        leaf affinity8 {
          type xr:Cisco-ios-xr-string;
          description
            "The name of the eighth affinity";
        }
        leaf affinity9 {
          type xr:Cisco-ios-xr-string;
          description
            "The name of the nineth affinity";
        }
      }
      list new-style-affinity-affinity-type-affinity1-affinity2-affinity3-affinity4-affinity5-affinity6-affinity7-affinity8-affinity9-affinity10 {
        key "affinity-type affinity1 affinity2 affinity3 affinity4 affinity5 affinity6 affinity7 affinity8 affinity9 affinity10";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
        leaf affinity4 {
          type xr:Cisco-ios-xr-string;
          description
            "The name of the fourth affinity";
        }
        leaf affinity5 {
          type xr:Cisco-ios-xr-string;
          description
            "The name of the fifth affinity";
        }
        leaf affinity6 {
          type xr:Cisco-ios-xr-string;
          description
            "The name of the sixth affinity";
        }
        leaf affinity7 {
          type xr:Cisco-ios-xr-string;
          description
            "The name of the seventh affinity";
        }
        leaf affinity8 {
          type xr:Cisco-ios-xr-string;
          description
            "The name of the eighth affinity";
        }
        leaf affinity9 {
          type xr:Cisco-ios-xr-string;
          description
            "The name of the nineth affinity";
        }
        leaf affinity10 {
          type xr:Cisco-ios-xr-string;
          description
            "The name of the tenth affinity";
        }
      }
    }
  }

  grouping ncs_rpc_notif_FAST-REROUTE {
    description
      "Common node of tunnel-attributes,
       tunnel-te-attributes, auto-mesh-attribute,
       p2mpte-attribute";
    container fast-reroute {
      presence "Indicates a fast-reroute node is configured.";
      description
        "Specify MPLS tunnel can be fast-rerouted";
      leaf bandwidth-protection {
        type uint32 {
          range "0..1";
        }
        mandatory true;
        description
          "Bandwidth Protection";
      }
      leaf node-protection {
        type uint32 {
          range "0..1";
        }
        mandatory true;
        description
          "Node Protection";
      }
    }
  }

  grouping ncs_rpc_notif_TUNNEL-RANGE {
    description
      "Common node of backup, mesh, p2mp-auto-tunnel,
       p2p-auto-tunnel, pcc";
    container tunnel-range {
      presence "Indicates a tunnel-range node is configured.";
      description
        "Configure tunnel ID range for auto-tunnel
         features";
      leaf min-tunnel-id {
        type uint32 {
          range "0..65535";
        }
        mandatory true;
        description
          "Minimum tunnel ID for auto-tunnels";
      }
      leaf max-tunnel-id {
        type uint32 {
          range "0..65535";
        }
        mandatory true;
        description
          "Maximum tunnel ID for auto-tunnels";
      }
    }
  }

  grouping ncs_rpc_notif_ENABLE {
    description
      "Common node of path-selection,
       att-path-option-path-selection";
    leaf enable {
      type empty;
      description
        "Enter path selection configuration";
    }
  }

  grouping ncs_rpc_notif_AUTOROUTE {
    description
      "Common node of tunnel-attributes,
       tunnel-te-attributes";
    container autoroute {
      description
        "Parameters for IGP routing over tunnel";
      container autoroute-announce {
        description
          "Announce tunnel to IGP";
        container exclude-traffic {
          description
            "Exclude traffic on autorouted tunnel";
          leaf segment-routing {
            type empty;
            description
              "Exclude tunnel in IGP for SR prefixes";
          }
        }
        container metric {
          description
            "Specify MPLS tunnel metric";
          leaf metric-type {
            type Mpls-te-autoroute-metric;
            description
              "Autoroute tunnel metric type";
          }
          leaf absolute-metric {
            when "../metric-type = 'absolute'" {
              tailf:xpath-root 3;
              description
                "../MetricType = Absolute";
            }
            type uint32 {
              range "1..2147483647";
            }
            description
              "The absolute metric value";
          }
          leaf relative-metric {
            when "../metric-type = 'relative'" {
              tailf:xpath-root 3;
              description
                "../MetricType = Relative";
            }
            type int32 {
              range "-10..10";
            }
            description
              "The value of the adjustment";
          }
          leaf constant-metric {
            when "../metric-type = 'constant'" {
              tailf:xpath-root 3;
              description
                "../MetricType = Constant";
            }
            type uint32 {
              range "1..2147483647";
            }
            description
              "The constant metric value";
          }
        }
        leaf enable {
          type empty;
          description
            "Enable autoroute announce";
        }
        leaf include-ipv6 {
          type empty;
          description
            "Specify that the tunnel should be an IPv6
             autoroute announce also";
        }
      }
      container destinations {
        description
          "Tunnel Autoroute Destination(s)";
        list destination {
          key "destination-address";
          description
            "Destination address to add in RIB";
          leaf destination-address {
            type inet:ipv4-address-no-zone;
            description
              "IP address of destination";
          }
        }
      }
    }
  }

  grouping ncs_rpc_notif_OOR-NODE-PROTECTION-DISABLE {
    description
      "Common node of oor-green-state, oor-yellow-state,
       oor-red-state";
    leaf oor-node-protection-disable {
      type empty;
      description
        "Disable FRR node-protection when the link is in
         this OOR State";
    }
  }

  grouping ncs_rpc_notif_REROUTE-MESSSAGE {
    description
      "Common node of logging, auto-mesh-logging";
    leaf reroute-messsage {
      type empty;
      description
        "Log tunnel rereoute messages";
    }
  }

  grouping ncs_rpc_notif_CACHE-TIMER {
    description
      "Common node of mpls-te-mib, mpls-frr-mib,
       mpls-p2mp-mib, mpls-te-ext-mib,
       mpls-te-ext-std-mib";
    leaf cache-timer {
      type uint32 {
        range "0..600";
      }
      units "second";
      default "60";
      description
        "Configure the cache time for the mib.";
    }
  }

  grouping ncs_rpc_notif_PATH-SELECTION-METRIC {
    description
      "Common node of tunnel-attributes,
       tunnel-te-attributes";
    leaf path-selection-metric {
      type Mpls-te-path-selection-metric;
      description
        "Path selection metric to use in path calculation";
    }
  }

  grouping ncs_rpc_notif_PASSWORD {
    description
      "Common node of peer, pce-attributes";
    leaf password {
      type xr:Proprietary-password;
      description
        "MD5 password";
    }
  }

  grouping ncs_rpc_notif_BANDWIDTH {
    description
      "Common node of tunnel-attributes,
       tunnel-te-attributes, auto-mesh-attribute,
       path-option-attribute, p2mpte-attribute";
    container bandwidth {
      presence "Indicates a bandwidth node is configured.";
      description
        "Tunnel bandwidth requirement";
      leaf dste-type {
        type Mpls-te-bandwidth-dste;
        mandatory true;
        description
          "DSTE-standard flag";
      }
      leaf class-or-pool-type {
        type uint32 {
          range "0..1";
        }
        mandatory true;
        description
          "Class type for the bandwidth allocation";
      }
      leaf bandwidth {
        type uint32 {
          range "0..4294967295";
        }
        units "kbit/s";
        mandatory true;
        description
          "The value of the bandwidth reserved by this
           tunnel in kbps";
      }
    }
  }

  grouping ncs_rpc_notif_INTERFACE-BANDWIDTH {
    description
      "Common node of auto-mesh-attribute,
       p2mpte-attribute";
    leaf interface-bandwidth {
      type uint32 {
        range "0..4294967295";
      }
      units "kbit/s";
      description
        "The bandwidth of the interface in kbps";
    }
  }

  grouping ncs_rpc_notif_FORWARD-CLASS {
    description
      "Common node of tunnel-attributes,
       tunnel-te-attributes, auto-mesh-attribute";
    leaf forward-class {
      type uint32 {
        range "0..7";
      }
      description
        "Forward class value";
    }
  }

  grouping ncs_rpc_notif_INSUFFICIENT-BW-MESSAGE {
    description
      "Common node of logging, auto-mesh-logging";
    leaf insufficient-bw-message {
      type empty;
      description
        "Log tunnel messages for insufficient bandwidth";
    }
  }

  grouping ncs_rpc_notif_PATH-SELECTION-DELAY-LIMIT {
    description
      "Common node of tunnel-path-selection,
       att-path-option-path-selection";
    leaf path-selection-delay-limit {
      type uint32 {
        range "1..4294967295";
      }
      description
        "Path selection delay limit (usec) configuration
         for this specific tunnel";
    }
  }

  grouping ncs_rpc_notif_OOR-METRIC-TE-PENALTY {
    description
      "Common node of oor-green-state, oor-yellow-state,
       oor-red-state";
    leaf oor-metric-te-penalty {
      type uint32;
      default "0";
      description
        "Penalty applied to the TE metric of a link in
         OOR state";
    }
  }

  grouping ncs_rpc_notif_KEYCHAIN {
    description
      "Common node of peer, pce-attributes";
    leaf keychain {
      type string {
        length "1..32";
      }
      description
        "Keychain based authentication";
    }
  }

  grouping ncs_rpc_notif_FORWARDING-ADJACENCY {
    description
      "Common node of tunnel-attributes,
       tunnel-te-attributes";
    container forwarding-adjacency {
      description
        "Forwarding adjacency announcement to IGP";
      leaf enable {
        type empty;
        description
          "Enable forwarding adjacency";
      }
      leaf include-ipv6 {
        type empty;
        description
          "Specify that the tunnel should be an IPv6
           forwarding adjacency also";
      }
      leaf hold-time {
        type uint32 {
          range "0..20000";
        }
        description
          "Specify the holdtime for the tunnel as
           forwarding adjacency";
      }
    }
  }

  grouping ncs_rpc_notif_ALL-TRANSIT-LSP-THRESHOLD {
    description
      "Common node of lsp-oor-yellow-state,
       lsp-oor-red-state";
    leaf all-transit-lsp-threshold {
      type uint32;
      description
        "Threshold for all transit LSPs";
    }
  }

  grouping ncs_rpc_notif_PRIORITY {
    description
      "Common node of tunnel-te-attributes,
       tunnel-attributes, auto-mesh-attribute,
       gmpls-unitunnel-head, auto-backup-attribute,
       p2mpte-attribute";
    container priority {
      presence "Indicates a priority node is configured.";
      description
        "Tunnel Setup and Hold Priorities";
      leaf setup-priority {
        type uint32 {
          range "0..7";
        }
        mandatory true;
        description
          "Setup Priority";
      }
      leaf hold-priority {
        type uint32 {
          range "0..7";
        }
        mandatory true;
        description
          "Hold Priority";
      }
    }
  }

  grouping live_ncs_OOR-ACCEPT-REOPT-LSP {
    description
      "Common node of oor-green-state, oor-yellow-state,
       oor-red-state";
    leaf oor-accept-reopt-lsp {
      type empty;
      description
        "Allow the setup of reoptimized LSPs over the
         link in this OOR State";
    }
  }

  grouping live_ncs_PCALC-FAILURE-MESSAGE {
    description
      "Common node of logging, auto-mesh-logging";
    leaf pcalc-failure-message {
      type empty;
      description
        "Enable logging for path-calculation failures";
    }
  }

  grouping live_ncs_POLICY-CLASSES {
    description
      "Common node of tunnel-te-attributes,
       auto-mesh-attribute, auto-backup-attribute";
    container policy-classes {
      description
        "Policy classes for PBTS";
      leaf-list policy-class {
        type Mpls-te-policy-class-range;
        // NCS drop max-elements statement
        description
          "Array of Policy class";
      }
    }
  }

  grouping live_ncs_UNPROTECTED-TRANSIT-LSP-THRESHOLD {
    description
      "Common node of lsp-oor-yellow-state,
       lsp-oor-red-state";
    leaf unprotected-transit-lsp-threshold {
      type uint32;
      description
        "Threshold for unprotected transit LSPs";
    }
  }

  grouping live_ncs_AFFINITY-MASK {
    description
      "Common node of tunnel-te-attributes,
       tunnel-attributes, auto-mesh-attribute,
       auto-backup-attribute, path-option-attribute,
       p2mpte-attribute, p2p-te-attribute";
    container affinity-mask {
      presence "Indicates a affinity-mask node is configured.";
      description
        "Set the affinity flags and mask";
      leaf affinity {
        type xr:Hex-integer;
        // NCS drop mandatory statement
        description
          "Affinity flags";
      }
      leaf mask {
        type xr:Hex-integer;
        // NCS drop mandatory statement
        description
          "Affinity mask";
      }
    }
  }

  grouping live_ncs_BANDWIDTH-CHANGE-MESSAGE {
    description
      "Common node of logging, auto-backup-logging,
       auto-mesh-logging";
    leaf bandwidth-change-message {
      type empty;
      description
        "Log tunnel messages for bandwidth change";
    }
  }

  grouping live_ncs_REOPTIMIZE-ATTEMPTS-MESSAGE {
    description
      "Common node of logging, auto-backup-logging,
       auto-mesh-logging";
    leaf reoptimize-attempts-message {
      type empty;
      description
        "Log tunnel reoptimization attempts messages";
    }
  }

  grouping live_ncs_OOR-AVAILABLE-BANDWIDTH-PERCENTAGE {
    description
      "Common node of oor-green-state, oor-yellow-state,
       oor-red-state";
    leaf oor-available-bandwidth-percentage {
      type uint32 {
        range "0..100";
      }
      units "percentage";
      // NCS drop default statement
      description
        "Flood a specific percentage of the available
         bandwidth";
    }
  }

  grouping live_ncs_TIMERS {
    description
      "Common node of backup, mesh";
    container timers {
      description
        "Configure auto-tunnel backup timers value";
      container removal {
        description
          "Configure auto-tunnel backup removal timers
           value";
        leaf unused {
          type uint32 {
            range "0..10080";
          }
          units "minute";
          // NCS drop default statement
          description
            "Auto-tunnel backup unused timeout in minutes
             (0=never timeout)";
        }
      }
    }
  }

  grouping live_ncs_TUNNEL-PATH-SELECTION {
    description
      "Common node of tunnel-te-attributes,
       tunnel-attributes";
    container tunnel-path-selection {
      description
        "Configure path selection properties";
      leaf tiebreaker {
        type Mpls-te-path-selection-tiebreaker;
        description
          "CSPF tiebreaker to use in path calculation";
      }
      leaf path-selection-hop-limit {
        type uint32 {
          range "1..255";
        }
        description
          "Path selection hop limit configuration for this
           specific tunnel";
      }
      uses live_ncs_PATH-SELECTION-DELAY-LIMIT;
      uses live_ncs_INVALIDATION;
      uses live_ncs_PATH-SELECTION-COST-LIMIT;
    }
  }

  grouping live_ncs_INVALIDATION {
    description
      "Common node of tunnel-te-attributes,
       tunnel-attributesCommon node of
       tunnel-path-selection,
       att-path-option-path-selection";
    container invalidation {
      presence "enable invalidation";
      description
        "Deprecated";
      leaf path-invalidation-timeout {
        type uint32 {
          range "0..60000";
        }
        description
          "Path Invalidation Timeout";
      }
      leaf path-invalidation-action {
        type Path-invalidation-action;
        description
          "Path Invalidation Action";
      }
    }
  }

  grouping live_ncs_PRECEDENCE {
    description
      "Common node of peer, pce-attributes";
    leaf precedence {
      type uint32 {
        range "0..255";
      }
      description
        "Precedence order";
    }
  }

  grouping live_ncs_SOFT-PREEMPTION {
    description
      "Common node of tunnel-attributes,
       tunnel-te-attributes, auto-mesh-attribute";
    leaf soft-preemption {
      type empty;
      description
        "Enable the soft-preemption feature on the tunnel";
    }
  }

  grouping live_ncs_PATH-SELECTION-COST-LIMIT {
    description
      "Common node of tunnel-path-selection,
       att-path-option-path-selection";
    leaf path-selection-cost-limit {
      type uint32 {
        range "1..4294967295";
      }
      description
        "Path selection cost limit configuration for this
         specific tunnel";
    }
  }

  grouping live_ncs_AUTO-BANDWIDTH {
    description
      "Common node of tunnel-attributes,
       tunnel-te-attributes";
    container auto-bandwidth {
      description
        "Tunnel Interface Auto-bandwidth configuration
         data";
      container underflow {
        presence "Indicates a underflow node is configured.";
        description
          "Configuring the tunnel underflow detection";
        leaf underflow-threshold-percent {
          type uint32 {
            range "1..100";
          }
          units "percentage";
          // NCS drop mandatory statement
          description
            "Bandwidth change percent to trigger an
             underflow";
        }
        leaf underflow-threshold-value {
          type uint32 {
            range "10..4294967295";
          }
          units "kbit/s";
          // NCS drop mandatory statement
          description
            "Bandwidth change value to trigger an underflow
             (kbps)";
        }
        leaf underflow-threshold-limit {
          type uint32 {
            range "1..10";
          }
          // NCS drop mandatory statement
          description
            "Number of consecutive collections exceeding
             threshold";
        }
      }
      container overflow {
        presence "Indicates a overflow node is configured.";
        description
          "Configuring the tunnel overflow detection";
        leaf overflow-threshold-percent {
          type uint32 {
            range "1..100";
          }
          units "percentage";
          // NCS drop mandatory statement
          description
            "Bandwidth change percent to trigger an
             overflow";
        }
        leaf overflow-threshold-value {
          type uint32 {
            range "10..4294967295";
          }
          units "kbit/s";
          // NCS drop mandatory statement
          description
            "Bandwidth change value to trigger an overflow
             (kbps)";
        }
        leaf overflow-threshold-limit {
          type uint32 {
            range "1..10";
          }
          // NCS drop mandatory statement
          description
            "Number of consecutive collections exceeding
             threshold";
        }
      }
      container bandwidth-limits {
        presence "Indicates a bandwidth-limits node is configured.";
        description
          "Set min/max bandwidth auto-bw can apply on a
           tunnel";
        leaf bandwidth-min-limit {
          type uint32 {
            range "0..4294967295";
          }
          // NCS drop mandatory statement
          description
            "Set minimum bandwidth auto-bw can apply on a
             tunnel";
        }
        leaf bandwidth-max-limit {
          type uint32 {
            range "0..4294967295";
          }
          // NCS drop mandatory statement
          description
            "Set maximum bandwidth auto-bw can apply on a
             tunnel";
        }
      }
      container adjustment-threshold {
        presence "Indicates a adjustment-threshold node is configured.";
        description
          "Set the bandwidth change threshold to trigger
           adjustment";
        leaf adjustment-threshold-percent {
          type uint32 {
            range "1..100";
          }
          units "percentage";
          // NCS drop mandatory statement
          description
            "Bandwidth change percent to trigger adjustment";
        }
        leaf adjustment-threshold-value {
          type uint32 {
            range "10..4294967295";
          }
          units "kbit/s";
          // NCS drop mandatory statement
          description
            "Bandwidth change value to trigger adjustment
             (kbps)";
        }
      }
      container auto-capacity {
        description
          "Tunnel auto-capacity configuration data";
        leaf nominal-bandwidth {
          type uint32 {
            range "0..4294967295";
          }
          units "kbit/s";
          description
            "Bandwidth value used to compute the desired
             number of tunnels for auto-capacity";
        }
        leaf enable {
          type boolean;
          description
            "Enable auto-capacityThe object must be set
             before any other auto capacity configuration
             is supplied for the tunnel,and must be the
             last auto-capacity configuration object to be
             removed.";
        }
        leaf clones-minimum {
          type uint32 {
            range "0..63";
          }
          // NCS drop default statement
          description
            "Lower limit on the number of clones can be
             created for the tunnel";
        }
        leaf split-bandwidth {
          type uint32 {
            range "0..4294967295";
          }
          units "kbit/s";
          description
            "Upper bandwidth limit that causes the tunnel
             to be split";
        }
        leaf merge-bandwidth {
          type uint32 {
            range "0..4294967295";
          }
          units "kbit/s";
          description
            "Lower bandwidth limit that causes the tunnel
             to be merged";
        }
        leaf clones-maximum {
          type uint32 {
            range "0..63";
          }
          // NCS drop default statement
          description
            "Upper limit on the number of clones can be
             created for the tunnel";
        }
      }
      leaf underflow-enable {
        type boolean;
        description
          "Enable auto bandwidth underflow detection";
      }
      leaf resignal-last-bandwidth-time-out {
        type uint32 {
          range "1..3600000";
        }
        units "second";
        description
          "Set the tunnel auto-bw resignal last bandwidth
           time-out in seconds";
      }
      leaf enabled {
        type boolean;
        description
          "This object is only valid for tunnel interfaces
           and it controls whether that interface has
           auto-bw enabled on it or not.The object must be
           set before any other auto-bw configuration is
           supplied for the interface, and must be the
           last auto-bw configuration object to be removed
           .";
      }
      leaf application-frequency {
        type uint32 {
          range "5..10080";
        }
        units "minute";
        description
          "Set the tunnel auto-bw application frequency in
           minutes";
      }
      leaf overflow-enable {
        type boolean;
        description
          "Enable auto bandwidth overflow detection";
      }
      uses live_ncs_COLLECTION-ONLY;
    }
  }

  grouping live_ncs_RECORD-ROUTE {
    description
      "Common node of tunnel-attributes,
       tunnel-te-attributes, auto-mesh-attribute,
       auto-backup-attribute, gmpls-unitunnel-head,
       p2mpte-attribute, tunnel-head";
    leaf record-route {
      type empty;
      description
        "Record the route used by the tunnel";
    }
  }

  grouping live_ncs_OOR-ACCEPT-LSP-MIN-BANDWIDTH {
    description
      "Common node of oor-green-state, oor-yellow-state,
       oor-red-state";
    leaf oor-accept-lsp-min-bandwidth {
      type uint32;
      units "kbit/s";
      // NCS drop default statement
      description
        "Only accept LSPs with at least the specified
         bandwidth (in kbps).";
    }
  }

  grouping live_ncs_LOGGING {
    description
      "Common node of tunnel-te-attributes,
       tunnel-attributes, p2p-te-attribute";
    container logging {
      description
        "Log tunnel LSP messages";
      leaf lsp-switch-over-change-message {
        type empty;
        description
          "Log tunnel messages for bandwidth change";
      }
      leaf all {
        type empty;
        description
          "Log all events for a tunnel";
      }
      leaf record-route-messsage {
        type empty;
        description
          "Log tunnel record-route messages";
      }
      leaf bfd-state-message {
        type empty;
        description
          "Enable BFD session state change alarm";
      }
      uses live_ncs_BANDWIDTH-CHANGE-MESSAGE;
      uses live_ncs_REOPTIMIZE-ATTEMPTS-MESSAGE;
      uses live_ncs_REROUTE-MESSSAGE;
      uses live_ncs_STATE-MESSAGE;
      uses live_ncs_INSUFFICIENT-BW-MESSAGE;
      uses live_ncs_REOPTIMIZED-MESSAGE;
      uses live_ncs_PCALC-FAILURE-MESSAGE;
    }
  }

  grouping live_ncs_MPLS-MTE-TUNNEL-CFG-LOGGING {
    description
      "Common node of tunnel-te-attributes,
       tunnel-attributes, p2p-te-attributeCommon node of
       mte-tunnel-attributes, p2mpte-attribute";
    container logging {
      description
        "Log tunnel LSP messages";
      leaf insufficient-bw-message {
        type empty;
        description
          "Log tunnel messages for insufficient bandwidth";
      }
      leaf reoptimized-message {
        type empty;
        description
          "Log tunnel reoptimized messages";
      }
      leaf bandwidth-change-message {
        type empty;
        description
          "Log tunnel bandwidth change messages";
      }
      leaf all {
        type empty;
        description
          "Log all events for a tunnel";
      }
      leaf pcalc-failure-message {
        type empty;
        description
          "Enable logging for path-calculation failures";
      }
      leaf state-message {
        type empty;
        description
          "Log tunnel state messages";
      }
      leaf reoptimize-attempts-message {
        type empty;
        description
          "Log tunnel reoptimization attempts messages";
      }
      leaf sub-lsp-state-message {
        type empty;
        description
          "Log all tunnel sub-LSP state messages";
      }
      leaf reroute-messsage {
        type empty;
        description
          "Log tunnel rereoute messages";
      }
    }
  }

  grouping live_ncs_COLLECTION-ONLY {
    description
      "Common node of auto-bandwidth,
       auto-mesh-attribute";
    leaf collection-only {
      type empty;
      description
        "Enable bandwidth collection only, no auto-bw
         adjustment";
    }
  }

  grouping live_ncs_PCE {
    description
      "Common node of path-option-attribute,
       p2p-te-attribute";
    container pce {
      description
        "Configure pce properties";
      container bidirectional {
        presence "Indicates a bidirectional node is configured.";
        description
          "Bidirectional parameters";
        leaf bd-source-address {
          type inet:ipv4-address-no-zone;
          // NCS drop mandatory statement
          description
            "Bidirectional Source IP Address";
        }
        leaf bd-group-id {
          type uint32 {
            range "1..4294967295";
          }
          // NCS drop mandatory statement
          description
            "Bidirectional Group ID";
        }
      }
      container disjoint-path {
        presence "Indicates a disjoint-path node is configured.";
        description
          "Disjoint path parameters";
        leaf dp-source-address {
          type inet:ipv4-address-no-zone;
          // NCS drop mandatory statement
          description
            "Disjoint Path Source IP Address";
        }
        leaf dp-type {
          type uint32 {
            range "1..3";
          }
          // NCS drop mandatory statement
          description
            "Disjoint Path Type";
        }
        leaf dp-group-id {
          type uint32 {
            range "1..4294967295";
          }
          // NCS drop mandatory statement
          description
            "Disjoint Path Group ID";
        }
      }
      leaf enable {
        type empty;
        description
          "Always set to true";
      }
    }
  }

  grouping live_ncs_DESTINATION {
    description
      "Common node of tunnel-te-attributes,
       tunnel-attributes";
    leaf destination {
      type inet:ipv4-address-no-zone;
      description
        "Set the destination of the tunnel";
    }
  }

  grouping live_ncs_STATE-MESSAGE {
    description
      "Common node of logging, logging,
       auto-backup-logging, auto-mesh-logging";
    leaf state-message {
      type empty;
      description
        "Log tunnel state messages";
    }
  }

  grouping live_ncs_LOAD-SHARE {
    description
      "Common node of tunnel-attributes,
       tunnel-te-attributes, auto-mesh-attribute";
    leaf load-share {
      type uint32 {
        range "1..4294967295";
      }
      description
        "Tunnel loadsharing metric";
    }
  }

  grouping live_ncs_PATH-SELECTION {
    description
      "Common node of auto-mesh-attribute, xro-attribute
       , auto-backup-attribute, p2mpte-attribute,
       otn-pp-attribute";
    container path-selection {
      description
        "Configure path selection properties";
      leaf enable {
        type empty;
        description
          "Enable path selection";
      }
    }
  }

  grouping live_ncs_SIGNALLED-NAME {
    description
      "Common node of tunnel-te-attributes,
       gmpls-unitunnel-head, tunnel-head";
    leaf signalled-name {
      type string {
        length "1..254";
      }
      description
        "The name of the tunnel to be included in
         signalling messages";
    }
  }

  grouping live_ncs_REOPTIMIZED-MESSAGE {
    description
      "Common node of logging, auto-backup-logging,
       auto-mesh-logging";
    leaf reoptimized-message {
      type empty;
      description
        "Log tunnel reoptimized messages";
    }
  }

  grouping live_ncs_NEW-STYLE-AFFINITY-TABLE {
    description
      "Common node of logging, auto-backup-logging,
       auto-mesh-loggingCommon node of tunnel-attributes
       , tunnel-te-attributes, path-option-attribute,
       auto-backup-attribute, auto-mesh-attribute,
       p2mpte-attribute, p2p-te-attribute";
    container new-style-affinity-affinity-types {
      description
        "Tunnel new style affinity attributes table";
      list new-style-affinity-affinity-type {
        key "affinity-type";
        description
          "Tunnel new style affinity attribute";
        leaf affinity-type {
          type Mpls-te-tunnel-affinity;
          description
            "The type of the affinity entry";
        }
      }
      list new-style-affinity-affinity-type-affinity1 {
        key "affinity-type affinity1";
        description
          "Tunnel new style affinity attribute";
        leaf affinity-type {
          type Mpls-te-tunnel-affinity;
          description
            "The type of the affinity entry";
        }
        leaf affinity1 {
          type xr:Cisco-ios-xr-string;
          description
            "The name of the first affinity";
        }
      }
      list new-style-affinity-affinity-type-affinity1-affinity2 {
        key "affinity-type affinity1 affinity2";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
      }
      list new-style-affinity-affinity-type-affinity1-affinity2-affinity3 {
        key "affinity-type affinity1 affinity2 affinity3";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
      }
      list new-style-affinity-affinity-type-affinity1-affinity2-affinity3-affinity4 {
        key "affinity-type affinity1 affinity2 affinity3 affinity4";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
        leaf affinity4 {
          type xr:Cisco-ios-xr-string;
          description
            "The name of the fourth affinity";
        }
      }
      list new-style-affinity-affinity-type-affinity1-affinity2-affinity3-affinity4-affinity5 {
        key "affinity-type affinity1 affinity2 affinity3 affinity4 affinity5";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
        leaf affinity4 {
          type xr:Cisco-ios-xr-string;
          description
            "The name of the fourth affinity";
        }
        leaf affinity5 {
          type xr:Cisco-ios-xr-string;
          description
            "The name of the fifth affinity";
        }
      }
      list new-style-affinity-affinity-type-affinity1-affinity2-affinity3-affinity4-affinity5-affinity6 {
        key "affinity-type affinity1 affinity2 affinity3 affinity4 affinity5 affinity6";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
        leaf affinity4 {
          type xr:Cisco-ios-xr-string;
          description
            "The name of the fourth affinity";
        }
        leaf affinity5 {
          type xr:Cisco-ios-xr-string;
          description
            "The name of the fifth affinity";
        }
        leaf affinity6 {
          type xr:Cisco-ios-xr-string;
          description
            "The name of the sixth affinity";
        }
      }
      list new-style-affinity-affinity-type-affinity1-affinity2-affinity3-affinity4-affinity5-affinity6-affinity7 {
        key "affinity-type affinity1 affinity2 affinity3 affinity4 affinity5 affinity6 affinity7";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
        leaf affinity4 {
          type xr:Cisco-ios-xr-string;
          description
            "The name of the fourth affinity";
        }
        leaf affinity5 {
          type xr:Cisco-ios-xr-string;
          description
            "The name of the fifth affinity";
        }
        leaf affinity6 {
          type xr:Cisco-ios-xr-string;
          description
            "The name of the sixth affinity";
        }
        leaf affinity7 {
          type xr:Cisco-ios-xr-string;
          description
            "The name of the seventh affinity";
        }
      }
      list new-style-affinity-affinity-type-affinity1-affinity2-affinity3-affinity4-affinity5-affinity6-affinity7-affinity8 {
        key "affinity-type affinity1 affinity2 affinity3 affinity4 affinity5 affinity6 affinity7 affinity8";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
        leaf affinity4 {
          type xr:Cisco-ios-xr-string;
          description
            "The name of the fourth affinity";
        }
        leaf affinity5 {
          type xr:Cisco-ios-xr-string;
          description
            "The name of the fifth affinity";
        }
        leaf affinity6 {
          type xr:Cisco-ios-xr-string;
          description
            "The name of the sixth affinity";
        }
        leaf affinity7 {
          type xr:Cisco-ios-xr-string;
          description
            "The name of the seventh affinity";
        }
        leaf affinity8 {
          type xr:Cisco-ios-xr-string;
          description
            "The name of the eighth affinity";
        }
      }
      list new-style-affinity-affinity-type-affinity1-affinity2-affinity3-affinity4-affinity5-affinity6-affinity7-affinity8-affinity9 {
        key "affinity-type affinity1 affinity2 affinity3 affinity4 affinity5 affinity6 affinity7 affinity8 affinity9";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
        leaf affinity4 {
          type xr:Cisco-ios-xr-string;
          description
            "The name of the fourth affinity";
        }
        leaf affinity5 {
          type xr:Cisco-ios-xr-string;
          description
            "The name of the fifth affinity";
        }
        leaf affinity6 {
          type xr:Cisco-ios-xr-string;
          description
            "The name of the sixth affinity";
        }
        leaf affinity7 {
          type xr:Cisco-ios-xr-string;
          description
            "The name of the seventh affinity";
        }
        leaf affinity8 {
          type xr:Cisco-ios-xr-string;
          description
            "The name of the eighth affinity";
        }
        leaf affinity9 {
          type xr:Cisco-ios-xr-string;
          description
            "The name of the nineth affinity";
        }
      }
      list new-style-affinity-affinity-type-affinity1-affinity2-affinity3-affinity4-affinity5-affinity6-affinity7-affinity8-affinity9-affinity10 {
        key "affinity-type affinity1 affinity2 affinity3 affinity4 affinity5 affinity6 affinity7 affinity8 affinity9 affinity10";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
        leaf affinity4 {
          type xr:Cisco-ios-xr-string;
          description
            "The name of the fourth affinity";
        }
        leaf affinity5 {
          type xr:Cisco-ios-xr-string;
          description
            "The name of the fifth affinity";
        }
        leaf affinity6 {
          type xr:Cisco-ios-xr-string;
          description
            "The name of the sixth affinity";
        }
        leaf affinity7 {
          type xr:Cisco-ios-xr-string;
          description
            "The name of the seventh affinity";
        }
        leaf affinity8 {
          type xr:Cisco-ios-xr-string;
          description
            "The name of the eighth affinity";
        }
        leaf affinity9 {
          type xr:Cisco-ios-xr-string;
          description
            "The name of the nineth affinity";
        }
        leaf affinity10 {
          type xr:Cisco-ios-xr-string;
          description
            "The name of the tenth affinity";
        }
      }
    }
  }

  grouping live_ncs_FAST-REROUTE {
    description
      "Common node of tunnel-attributes,
       tunnel-te-attributes, auto-mesh-attribute,
       p2mpte-attribute";
    container fast-reroute {
      presence "Indicates a fast-reroute node is configured.";
      description
        "Specify MPLS tunnel can be fast-rerouted";
      leaf bandwidth-protection {
        type uint32 {
          range "0..1";
        }
        // NCS drop mandatory statement
        description
          "Bandwidth Protection";
      }
      leaf node-protection {
        type uint32 {
          range "0..1";
        }
        // NCS drop mandatory statement
        description
          "Node Protection";
      }
    }
  }

  grouping live_ncs_TUNNEL-RANGE {
    description
      "Common node of backup, mesh, p2mp-auto-tunnel,
       p2p-auto-tunnel, pcc";
    container tunnel-range {
      presence "Indicates a tunnel-range node is configured.";
      description
        "Configure tunnel ID range for auto-tunnel
         features";
      leaf min-tunnel-id {
        type uint32 {
          range "0..65535";
        }
        // NCS drop mandatory statement
        description
          "Minimum tunnel ID for auto-tunnels";
      }
      leaf max-tunnel-id {
        type uint32 {
          range "0..65535";
        }
        // NCS drop mandatory statement
        description
          "Maximum tunnel ID for auto-tunnels";
      }
    }
  }

  grouping live_ncs_ENABLE {
    description
      "Common node of path-selection,
       att-path-option-path-selection";
    leaf enable {
      type empty;
      description
        "Enter path selection configuration";
    }
  }

  grouping live_ncs_AUTOROUTE {
    description
      "Common node of tunnel-attributes,
       tunnel-te-attributes";
    container autoroute {
      description
        "Parameters for IGP routing over tunnel";
      container autoroute-announce {
        description
          "Announce tunnel to IGP";
        container exclude-traffic {
          description
            "Exclude traffic on autorouted tunnel";
          leaf segment-routing {
            type empty;
            description
              "Exclude tunnel in IGP for SR prefixes";
          }
        }
        container metric {
          description
            "Specify MPLS tunnel metric";
          leaf metric-type {
            type Mpls-te-autoroute-metric;
            description
              "Autoroute tunnel metric type";
          }
          leaf absolute-metric {
            // NCS drop when statement
            type uint32 {
              range "1..2147483647";
            }
            description
              "The absolute metric value";
          }
          leaf relative-metric {
            // NCS drop when statement
            type int32 {
              range "-10..10";
            }
            description
              "The value of the adjustment";
          }
          leaf constant-metric {
            // NCS drop when statement
            type uint32 {
              range "1..2147483647";
            }
            description
              "The constant metric value";
          }
        }
        leaf enable {
          type empty;
          description
            "Enable autoroute announce";
        }
        leaf include-ipv6 {
          type empty;
          description
            "Specify that the tunnel should be an IPv6
             autoroute announce also";
        }
      }
      container destinations {
        description
          "Tunnel Autoroute Destination(s)";
        list destination {
          key "destination-address";
          description
            "Destination address to add in RIB";
          leaf destination-address {
            type inet:ipv4-address-no-zone;
            description
              "IP address of destination";
          }
        }
      }
    }
  }

  grouping live_ncs_OOR-NODE-PROTECTION-DISABLE {
    description
      "Common node of oor-green-state, oor-yellow-state,
       oor-red-state";
    leaf oor-node-protection-disable {
      type empty;
      description
        "Disable FRR node-protection when the link is in
         this OOR State";
    }
  }

  grouping live_ncs_REROUTE-MESSSAGE {
    description
      "Common node of logging, auto-mesh-logging";
    leaf reroute-messsage {
      type empty;
      description
        "Log tunnel rereoute messages";
    }
  }

  grouping live_ncs_CACHE-TIMER {
    description
      "Common node of mpls-te-mib, mpls-frr-mib,
       mpls-p2mp-mib, mpls-te-ext-mib,
       mpls-te-ext-std-mib";
    leaf cache-timer {
      type uint32 {
        range "0..600";
      }
      units "second";
      // NCS drop default statement
      description
        "Configure the cache time for the mib.";
    }
  }

  grouping live_ncs_PATH-SELECTION-METRIC {
    description
      "Common node of tunnel-attributes,
       tunnel-te-attributes";
    leaf path-selection-metric {
      type Mpls-te-path-selection-metric;
      description
        "Path selection metric to use in path calculation";
    }
  }

  grouping live_ncs_PASSWORD {
    description
      "Common node of peer, pce-attributes";
    leaf password {
      type xr:Proprietary-password;
      description
        "MD5 password";
    }
  }

  grouping live_ncs_BANDWIDTH {
    description
      "Common node of tunnel-attributes,
       tunnel-te-attributes, auto-mesh-attribute,
       path-option-attribute, p2mpte-attribute";
    container bandwidth {
      presence "Indicates a bandwidth node is configured.";
      description
        "Tunnel bandwidth requirement";
      leaf dste-type {
        type Mpls-te-bandwidth-dste;
        // NCS drop mandatory statement
        description
          "DSTE-standard flag";
      }
      leaf class-or-pool-type {
        type uint32 {
          range "0..1";
        }
        // NCS drop mandatory statement
        description
          "Class type for the bandwidth allocation";
      }
      leaf bandwidth {
        type uint32 {
          range "0..4294967295";
        }
        units "kbit/s";
        // NCS drop mandatory statement
        description
          "The value of the bandwidth reserved by this
           tunnel in kbps";
      }
    }
  }

  grouping live_ncs_INTERFACE-BANDWIDTH {
    description
      "Common node of auto-mesh-attribute,
       p2mpte-attribute";
    leaf interface-bandwidth {
      type uint32 {
        range "0..4294967295";
      }
      units "kbit/s";
      description
        "The bandwidth of the interface in kbps";
    }
  }

  grouping live_ncs_FORWARD-CLASS {
    description
      "Common node of tunnel-attributes,
       tunnel-te-attributes, auto-mesh-attribute";
    leaf forward-class {
      type uint32 {
        range "0..7";
      }
      description
        "Forward class value";
    }
  }

  grouping live_ncs_INSUFFICIENT-BW-MESSAGE {
    description
      "Common node of logging, auto-mesh-logging";
    leaf insufficient-bw-message {
      type empty;
      description
        "Log tunnel messages for insufficient bandwidth";
    }
  }

  grouping live_ncs_PATH-SELECTION-DELAY-LIMIT {
    description
      "Common node of tunnel-path-selection,
       att-path-option-path-selection";
    leaf path-selection-delay-limit {
      type uint32 {
        range "1..4294967295";
      }
      description
        "Path selection delay limit (usec) configuration
         for this specific tunnel";
    }
  }

  grouping live_ncs_OOR-METRIC-TE-PENALTY {
    description
      "Common node of oor-green-state, oor-yellow-state,
       oor-red-state";
    leaf oor-metric-te-penalty {
      type uint32;
      // NCS drop default statement
      description
        "Penalty applied to the TE metric of a link in
         OOR state";
    }
  }

  grouping live_ncs_KEYCHAIN {
    description
      "Common node of peer, pce-attributes";
    leaf keychain {
      type string {
        length "1..32";
      }
      description
        "Keychain based authentication";
    }
  }

  grouping live_ncs_FORWARDING-ADJACENCY {
    description
      "Common node of tunnel-attributes,
       tunnel-te-attributes";
    container forwarding-adjacency {
      description
        "Forwarding adjacency announcement to IGP";
      leaf enable {
        type empty;
        description
          "Enable forwarding adjacency";
      }
      leaf include-ipv6 {
        type empty;
        description
          "Specify that the tunnel should be an IPv6
           forwarding adjacency also";
      }
      leaf hold-time {
        type uint32 {
          range "0..20000";
        }
        description
          "Specify the holdtime for the tunnel as
           forwarding adjacency";
      }
    }
  }

  grouping live_ncs_ALL-TRANSIT-LSP-THRESHOLD {
    description
      "Common node of lsp-oor-yellow-state,
       lsp-oor-red-state";
    leaf all-transit-lsp-threshold {
      type uint32;
      description
        "Threshold for all transit LSPs";
    }
  }

  grouping live_ncs_PRIORITY {
    description
      "Common node of tunnel-te-attributes,
       tunnel-attributes, auto-mesh-attribute,
       gmpls-unitunnel-head, auto-backup-attribute,
       p2mpte-attribute";
    container priority {
      presence "Indicates a priority node is configured.";
      description
        "Tunnel Setup and Hold Priorities";
      leaf setup-priority {
        type uint32 {
          range "0..7";
        }
        // NCS drop mandatory statement
        description
          "Setup Priority";
      }
      leaf hold-priority {
        type uint32 {
          range "0..7";
        }
        // NCS drop mandatory statement
        description
          "Hold Priority";
      }
    }
  }

  grouping OOR-ACCEPT-REOPT-LSP {
    description
      "Common node of oor-green-state, oor-yellow-state,
       oor-red-state";
    leaf oor-accept-reopt-lsp {
      type empty;
      description
        "Allow the setup of reoptimized LSPs over the
         link in this OOR State";
    }
  }

  grouping PCALC-FAILURE-MESSAGE {
    description
      "Common node of logging, auto-mesh-logging";
    leaf pcalc-failure-message {
      type empty;
      description
        "Enable logging for path-calculation failures";
    }
  }

  grouping POLICY-CLASSES {
    description
      "Common node of tunnel-te-attributes,
       auto-mesh-attribute, auto-backup-attribute";
    container policy-classes {
      description
        "Policy classes for PBTS";
      leaf-list policy-class {
        type Mpls-te-policy-class-range;
        max-elements 7;
        description
          "Array of Policy class";
      }
    }
  }

  grouping UNPROTECTED-TRANSIT-LSP-THRESHOLD {
    description
      "Common node of lsp-oor-yellow-state,
       lsp-oor-red-state";
    leaf unprotected-transit-lsp-threshold {
      type uint32;
      description
        "Threshold for unprotected transit LSPs";
    }
  }

  grouping AFFINITY-MASK {
    description
      "Common node of tunnel-te-attributes,
       tunnel-attributes, auto-mesh-attribute,
       auto-backup-attribute, path-option-attribute,
       p2mpte-attribute, p2p-te-attribute";
    container affinity-mask {
      presence "Indicates a affinity-mask node is configured.";
      description
        "Set the affinity flags and mask";
      leaf affinity {
        type xr:Hex-integer;
        mandatory true;
        description
          "Affinity flags";
      }
      leaf mask {
        type xr:Hex-integer;
        mandatory true;
        description
          "Affinity mask";
      }
    }
  }

  grouping BANDWIDTH-CHANGE-MESSAGE {
    description
      "Common node of logging, auto-backup-logging,
       auto-mesh-logging";
    leaf bandwidth-change-message {
      type empty;
      description
        "Log tunnel messages for bandwidth change";
    }
  }

  grouping REOPTIMIZE-ATTEMPTS-MESSAGE {
    description
      "Common node of logging, auto-backup-logging,
       auto-mesh-logging";
    leaf reoptimize-attempts-message {
      type empty;
      description
        "Log tunnel reoptimization attempts messages";
    }
  }

  grouping OOR-AVAILABLE-BANDWIDTH-PERCENTAGE {
    description
      "Common node of oor-green-state, oor-yellow-state,
       oor-red-state";
    leaf oor-available-bandwidth-percentage {
      type uint32 {
        range "0..100";
      }
      units "percentage";
      default "100";
      description
        "Flood a specific percentage of the available
         bandwidth";
    }
  }

  grouping TIMERS {
    description
      "Common node of backup, mesh";
    container timers {
      description
        "Configure auto-tunnel backup timers value";
      container removal {
        description
          "Configure auto-tunnel backup removal timers
           value";
        leaf unused {
          type uint32 {
            range "0..10080";
          }
          units "minute";
          default "3600";
          description
            "Auto-tunnel backup unused timeout in minutes
             (0=never timeout)";
        }
      }
    }
  }

  grouping TUNNEL-PATH-SELECTION {
    description
      "Common node of tunnel-te-attributes,
       tunnel-attributes";
    container tunnel-path-selection {
      description
        "Configure path selection properties";
      leaf tiebreaker {
        type Mpls-te-path-selection-tiebreaker;
        description
          "CSPF tiebreaker to use in path calculation";
      }
      leaf path-selection-hop-limit {
        type uint32 {
          range "1..255";
        }
        description
          "Path selection hop limit configuration for this
           specific tunnel";
      }
      uses PATH-SELECTION-DELAY-LIMIT;
      uses INVALIDATION;
      uses PATH-SELECTION-COST-LIMIT;
    }
  }

  grouping INVALIDATION {
    description
      "Common node of tunnel-te-attributes,
       tunnel-attributesCommon node of
       tunnel-path-selection,
       att-path-option-path-selection";
    container invalidation {
      presence "enable invalidation";
      description
        "Deprecated";
      leaf path-invalidation-timeout {
        type uint32 {
          range "0..60000";
        }
        description
          "Path Invalidation Timeout";
      }
      leaf path-invalidation-action {
        type Path-invalidation-action;
        description
          "Path Invalidation Action";
      }
    }
  }

  grouping PRECEDENCE {
    description
      "Common node of peer, pce-attributes";
    leaf precedence {
      type uint32 {
        range "0..255";
      }
      description
        "Precedence order";
    }
  }

  grouping SOFT-PREEMPTION {
    description
      "Common node of tunnel-attributes,
       tunnel-te-attributes, auto-mesh-attribute";
    leaf soft-preemption {
      type empty;
      description
        "Enable the soft-preemption feature on the tunnel";
    }
  }

  grouping PATH-SELECTION-COST-LIMIT {
    description
      "Common node of tunnel-path-selection,
       att-path-option-path-selection";
    leaf path-selection-cost-limit {
      type uint32 {
        range "1..4294967295";
      }
      description
        "Path selection cost limit configuration for this
         specific tunnel";
    }
  }

  grouping AUTO-BANDWIDTH {
    description
      "Common node of tunnel-attributes,
       tunnel-te-attributes";
    container auto-bandwidth {
      description
        "Tunnel Interface Auto-bandwidth configuration
         data";
      container underflow {
        presence "Indicates a underflow node is configured.";
        description
          "Configuring the tunnel underflow detection";
        leaf underflow-threshold-percent {
          type uint32 {
            range "1..100";
          }
          units "percentage";
          mandatory true;
          description
            "Bandwidth change percent to trigger an
             underflow";
        }
        leaf underflow-threshold-value {
          type uint32 {
            range "10..4294967295";
          }
          units "kbit/s";
          mandatory true;
          description
            "Bandwidth change value to trigger an underflow
             (kbps)";
        }
        leaf underflow-threshold-limit {
          type uint32 {
            range "1..10";
          }
          mandatory true;
          description
            "Number of consecutive collections exceeding
             threshold";
        }
      }
      container overflow {
        presence "Indicates a overflow node is configured.";
        description
          "Configuring the tunnel overflow detection";
        leaf overflow-threshold-percent {
          type uint32 {
            range "1..100";
          }
          units "percentage";
          mandatory true;
          description
            "Bandwidth change percent to trigger an
             overflow";
        }
        leaf overflow-threshold-value {
          type uint32 {
            range "10..4294967295";
          }
          units "kbit/s";
          mandatory true;
          description
            "Bandwidth change value to trigger an overflow
             (kbps)";
        }
        leaf overflow-threshold-limit {
          type uint32 {
            range "1..10";
          }
          mandatory true;
          description
            "Number of consecutive collections exceeding
             threshold";
        }
      }
      container bandwidth-limits {
        presence "Indicates a bandwidth-limits node is configured.";
        description
          "Set min/max bandwidth auto-bw can apply on a
           tunnel";
        leaf bandwidth-min-limit {
          type uint32 {
            range "0..4294967295";
          }
          mandatory true;
          description
            "Set minimum bandwidth auto-bw can apply on a
             tunnel";
        }
        leaf bandwidth-max-limit {
          type uint32 {
            range "0..4294967295";
          }
          mandatory true;
          description
            "Set maximum bandwidth auto-bw can apply on a
             tunnel";
        }
      }
      container adjustment-threshold {
        presence "Indicates a adjustment-threshold node is configured.";
        description
          "Set the bandwidth change threshold to trigger
           adjustment";
        leaf adjustment-threshold-percent {
          type uint32 {
            range "1..100";
          }
          units "percentage";
          mandatory true;
          description
            "Bandwidth change percent to trigger adjustment";
        }
        leaf adjustment-threshold-value {
          type uint32 {
            range "10..4294967295";
          }
          units "kbit/s";
          mandatory true;
          description
            "Bandwidth change value to trigger adjustment
             (kbps)";
        }
      }
      container auto-capacity {
        description
          "Tunnel auto-capacity configuration data";
        leaf nominal-bandwidth {
          type uint32 {
            range "0..4294967295";
          }
          units "kbit/s";
          description
            "Bandwidth value used to compute the desired
             number of tunnels for auto-capacity";
        }
        leaf enable {
          type boolean;
          description
            "Enable auto-capacityThe object must be set
             before any other auto capacity configuration
             is supplied for the tunnel,and must be the
             last auto-capacity configuration object to be
             removed.";
        }
        leaf clones-minimum {
          type uint32 {
            range "0..63";
          }
          default "0";
          description
            "Lower limit on the number of clones can be
             created for the tunnel";
        }
        leaf split-bandwidth {
          type uint32 {
            range "0..4294967295";
          }
          units "kbit/s";
          description
            "Upper bandwidth limit that causes the tunnel
             to be split";
        }
        leaf merge-bandwidth {
          type uint32 {
            range "0..4294967295";
          }
          units "kbit/s";
          description
            "Lower bandwidth limit that causes the tunnel
             to be merged";
        }
        leaf clones-maximum {
          type uint32 {
            range "0..63";
          }
          default "63";
          description
            "Upper limit on the number of clones can be
             created for the tunnel";
        }
      }
      leaf underflow-enable {
        type boolean;
        description
          "Enable auto bandwidth underflow detection";
      }
      leaf resignal-last-bandwidth-time-out {
        type uint32 {
          range "1..3600000";
        }
        units "second";
        description
          "Set the tunnel auto-bw resignal last bandwidth
           time-out in seconds";
      }
      leaf enabled {
        type boolean;
        description
          "This object is only valid for tunnel interfaces
           and it controls whether that interface has
           auto-bw enabled on it or not.The object must be
           set before any other auto-bw configuration is
           supplied for the interface, and must be the
           last auto-bw configuration object to be removed
           .";
      }
      leaf application-frequency {
        type uint32 {
          range "5..10080";
        }
        units "minute";
        description
          "Set the tunnel auto-bw application frequency in
           minutes";
      }
      leaf overflow-enable {
        type boolean;
        description
          "Enable auto bandwidth overflow detection";
      }
      uses COLLECTION-ONLY;
    }
  }

  grouping RECORD-ROUTE {
    description
      "Common node of tunnel-attributes,
       tunnel-te-attributes, auto-mesh-attribute,
       auto-backup-attribute, gmpls-unitunnel-head,
       p2mpte-attribute, tunnel-head";
    leaf record-route {
      type empty;
      description
        "Record the route used by the tunnel";
    }
  }

  grouping OOR-ACCEPT-LSP-MIN-BANDWIDTH {
    description
      "Common node of oor-green-state, oor-yellow-state,
       oor-red-state";
    leaf oor-accept-lsp-min-bandwidth {
      type uint32;
      units "kbit/s";
      default "0";
      description
        "Only accept LSPs with at least the specified
         bandwidth (in kbps).";
    }
  }

  grouping LOGGING {
    description
      "Common node of tunnel-te-attributes,
       tunnel-attributes, p2p-te-attribute";
    container logging {
      description
        "Log tunnel LSP messages";
      leaf lsp-switch-over-change-message {
        type empty;
        description
          "Log tunnel messages for bandwidth change";
      }
      leaf all {
        type empty;
        description
          "Log all events for a tunnel";
      }
      leaf record-route-messsage {
        type empty;
        description
          "Log tunnel record-route messages";
      }
      leaf bfd-state-message {
        type empty;
        description
          "Enable BFD session state change alarm";
      }
      uses BANDWIDTH-CHANGE-MESSAGE;
      uses REOPTIMIZE-ATTEMPTS-MESSAGE;
      uses REROUTE-MESSSAGE;
      uses STATE-MESSAGE;
      uses INSUFFICIENT-BW-MESSAGE;
      uses REOPTIMIZED-MESSAGE;
      uses PCALC-FAILURE-MESSAGE;
    }
  }

  grouping MPLS-MTE-TUNNEL-CFG-LOGGING {
    description
      "Common node of tunnel-te-attributes,
       tunnel-attributes, p2p-te-attributeCommon node of
       mte-tunnel-attributes, p2mpte-attribute";
    container logging {
      description
        "Log tunnel LSP messages";
      leaf insufficient-bw-message {
        type empty;
        description
          "Log tunnel messages for insufficient bandwidth";
      }
      leaf reoptimized-message {
        type empty;
        description
          "Log tunnel reoptimized messages";
      }
      leaf bandwidth-change-message {
        type empty;
        description
          "Log tunnel bandwidth change messages";
      }
      leaf all {
        type empty;
        description
          "Log all events for a tunnel";
      }
      leaf pcalc-failure-message {
        type empty;
        description
          "Enable logging for path-calculation failures";
      }
      leaf state-message {
        type empty;
        description
          "Log tunnel state messages";
      }
      leaf reoptimize-attempts-message {
        type empty;
        description
          "Log tunnel reoptimization attempts messages";
      }
      leaf sub-lsp-state-message {
        type empty;
        description
          "Log all tunnel sub-LSP state messages";
      }
      leaf reroute-messsage {
        type empty;
        description
          "Log tunnel rereoute messages";
      }
    }
  }

  grouping COLLECTION-ONLY {
    description
      "Common node of auto-bandwidth,
       auto-mesh-attribute";
    leaf collection-only {
      type empty;
      description
        "Enable bandwidth collection only, no auto-bw
         adjustment";
    }
  }

  grouping PCE {
    description
      "Common node of path-option-attribute,
       p2p-te-attribute";
    container pce {
      description
        "Configure pce properties";
      container bidirectional {
        presence "Indicates a bidirectional node is configured.";
        description
          "Bidirectional parameters";
        leaf bd-source-address {
          type inet:ipv4-address-no-zone;
          mandatory true;
          description
            "Bidirectional Source IP Address";
        }
        leaf bd-group-id {
          type uint32 {
            range "1..4294967295";
          }
          mandatory true;
          description
            "Bidirectional Group ID";
        }
      }
      container disjoint-path {
        presence "Indicates a disjoint-path node is configured.";
        description
          "Disjoint path parameters";
        leaf dp-source-address {
          type inet:ipv4-address-no-zone;
          mandatory true;
          description
            "Disjoint Path Source IP Address";
        }
        leaf dp-type {
          type uint32 {
            range "1..3";
          }
          mandatory true;
          description
            "Disjoint Path Type";
        }
        leaf dp-group-id {
          type uint32 {
            range "1..4294967295";
          }
          mandatory true;
          description
            "Disjoint Path Group ID";
        }
      }
      leaf enable {
        type empty;
        description
          "Always set to true";
      }
    }
  }

  grouping DESTINATION {
    description
      "Common node of tunnel-te-attributes,
       tunnel-attributes";
    leaf destination {
      type inet:ipv4-address-no-zone;
      description
        "Set the destination of the tunnel";
    }
  }

  grouping STATE-MESSAGE {
    description
      "Common node of logging, logging,
       auto-backup-logging, auto-mesh-logging";
    leaf state-message {
      type empty;
      description
        "Log tunnel state messages";
    }
  }

  grouping LOAD-SHARE {
    description
      "Common node of tunnel-attributes,
       tunnel-te-attributes, auto-mesh-attribute";
    leaf load-share {
      type uint32 {
        range "1..4294967295";
      }
      description
        "Tunnel loadsharing metric";
    }
  }

  grouping PATH-SELECTION {
    description
      "Common node of auto-mesh-attribute, xro-attribute
       , auto-backup-attribute, p2mpte-attribute,
       otn-pp-attribute";
    container path-selection {
      description
        "Configure path selection properties";
      leaf enable {
        type empty;
        description
          "Enable path selection";
      }
    }
  }

  grouping SIGNALLED-NAME {
    description
      "Common node of tunnel-te-attributes,
       gmpls-unitunnel-head, tunnel-head";
    leaf signalled-name {
      type string {
        length "1..254";
      }
      description
        "The name of the tunnel to be included in
         signalling messages";
    }
  }

  grouping REOPTIMIZED-MESSAGE {
    description
      "Common node of logging, auto-backup-logging,
       auto-mesh-logging";
    leaf reoptimized-message {
      type empty;
      description
        "Log tunnel reoptimized messages";
    }
  }

  grouping NEW-STYLE-AFFINITY-TABLE {
    description
      "Common node of logging, auto-backup-logging,
       auto-mesh-loggingCommon node of tunnel-attributes
       , tunnel-te-attributes, path-option-attribute,
       auto-backup-attribute, auto-mesh-attribute,
       p2mpte-attribute, p2p-te-attribute";
    container new-style-affinity-affinity-types {
      description
        "Tunnel new style affinity attributes table";
      list new-style-affinity-affinity-type {
        key "affinity-type";
        description
          "Tunnel new style affinity attribute";
        leaf affinity-type {
          type Mpls-te-tunnel-affinity;
          description
            "The type of the affinity entry";
        }
      }
      list new-style-affinity-affinity-type-affinity1 {
        key "affinity-type affinity1";
        description
          "Tunnel new style affinity attribute";
        leaf affinity-type {
          type Mpls-te-tunnel-affinity;
          description
            "The type of the affinity entry";
        }
        leaf affinity1 {
          type xr:Cisco-ios-xr-string;
          description
            "The name of the first affinity";
        }
      }
      list new-style-affinity-affinity-type-affinity1-affinity2 {
        key "affinity-type affinity1 affinity2";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
      }
      list new-style-affinity-affinity-type-affinity1-affinity2-affinity3 {
        key "affinity-type affinity1 affinity2 affinity3";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
      }
      list new-style-affinity-affinity-type-affinity1-affinity2-affinity3-affinity4 {
        key "affinity-type affinity1 affinity2 affinity3 affinity4";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
        leaf affinity4 {
          type xr:Cisco-ios-xr-string;
          description
            "The name of the fourth affinity";
        }
      }
      list new-style-affinity-affinity-type-affinity1-affinity2-affinity3-affinity4-affinity5 {
        key "affinity-type affinity1 affinity2 affinity3 affinity4 affinity5";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
        leaf affinity4 {
          type xr:Cisco-ios-xr-string;
          description
            "The name of the fourth affinity";
        }
        leaf affinity5 {
          type xr:Cisco-ios-xr-string;
          description
            "The name of the fifth affinity";
        }
      }
      list new-style-affinity-affinity-type-affinity1-affinity2-affinity3-affinity4-affinity5-affinity6 {
        key "affinity-type affinity1 affinity2 affinity3 affinity4 affinity5 affinity6";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
        leaf affinity4 {
          type xr:Cisco-ios-xr-string;
          description
            "The name of the fourth affinity";
        }
        leaf affinity5 {
          type xr:Cisco-ios-xr-string;
          description
            "The name of the fifth affinity";
        }
        leaf affinity6 {
          type xr:Cisco-ios-xr-string;
          description
            "The name of the sixth affinity";
        }
      }
      list new-style-affinity-affinity-type-affinity1-affinity2-affinity3-affinity4-affinity5-affinity6-affinity7 {
        key "affinity-type affinity1 affinity2 affinity3 affinity4 affinity5 affinity6 affinity7";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
        leaf affinity4 {
          type xr:Cisco-ios-xr-string;
          description
            "The name of the fourth affinity";
        }
        leaf affinity5 {
          type xr:Cisco-ios-xr-string;
          description
            "The name of the fifth affinity";
        }
        leaf affinity6 {
          type xr:Cisco-ios-xr-string;
          description
            "The name of the sixth affinity";
        }
        leaf affinity7 {
          type xr:Cisco-ios-xr-string;
          description
            "The name of the seventh affinity";
        }
      }
      list new-style-affinity-affinity-type-affinity1-affinity2-affinity3-affinity4-affinity5-affinity6-affinity7-affinity8 {
        key "affinity-type affinity1 affinity2 affinity3 affinity4 affinity5 affinity6 affinity7 affinity8";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
        leaf affinity4 {
          type xr:Cisco-ios-xr-string;
          description
            "The name of the fourth affinity";
        }
        leaf affinity5 {
          type xr:Cisco-ios-xr-string;
          description
            "The name of the fifth affinity";
        }
        leaf affinity6 {
          type xr:Cisco-ios-xr-string;
          description
            "The name of the sixth affinity";
        }
        leaf affinity7 {
          type xr:Cisco-ios-xr-string;
          description
            "The name of the seventh affinity";
        }
        leaf affinity8 {
          type xr:Cisco-ios-xr-string;
          description
            "The name of the eighth affinity";
        }
      }
      list new-style-affinity-affinity-type-affinity1-affinity2-affinity3-affinity4-affinity5-affinity6-affinity7-affinity8-affinity9 {
        key "affinity-type affinity1 affinity2 affinity3 affinity4 affinity5 affinity6 affinity7 affinity8 affinity9";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
        leaf affinity4 {
          type xr:Cisco-ios-xr-string;
          description
            "The name of the fourth affinity";
        }
        leaf affinity5 {
          type xr:Cisco-ios-xr-string;
          description
            "The name of the fifth affinity";
        }
        leaf affinity6 {
          type xr:Cisco-ios-xr-string;
          description
            "The name of the sixth affinity";
        }
        leaf affinity7 {
          type xr:Cisco-ios-xr-string;
          description
            "The name of the seventh affinity";
        }
        leaf affinity8 {
          type xr:Cisco-ios-xr-string;
          description
            "The name of the eighth affinity";
        }
        leaf affinity9 {
          type xr:Cisco-ios-xr-string;
          description
            "The name of the nineth affinity";
        }
      }
      list new-style-affinity-affinity-type-affinity1-affinity2-affinity3-affinity4-affinity5-affinity6-affinity7-affinity8-affinity9-affinity10 {
        key "affinity-type affinity1 affinity2 affinity3 affinity4 affinity5 affinity6 affinity7 affinity8 affinity9 affinity10";
        description
          "Tunnel new style affinity attribute";
        leaf affinity-type {
          type Mpls-te-tunnel-affinity;
          description
            "The type of the affinity entry";
        }
        leaf affinity1 {
          type xr:Cisco-ios-xr-string;
          description
            "The name of the first affinity";
        }
        leaf affinity2 {
          type xr:Cisco-ios-xr-string;
          description
            "The name of the second affinity";
        }
        leaf affinity3 {
          type xr:Cisco-ios-xr-string;
          description
            "The name of the third affinity";
        }
        leaf affinity4 {
          type xr:Cisco-ios-xr-string;
          description
            "The name of the fourth affinity";
        }
        leaf affinity5 {
          type xr:Cisco-ios-xr-string;
          description
            "The name of the fifth affinity";
        }
        leaf affinity6 {
          type xr:Cisco-ios-xr-string;
          description
            "The name of the sixth affinity";
        }
        leaf affinity7 {
          type xr:Cisco-ios-xr-string;
          description
            "The name of the seventh affinity";
        }
        leaf affinity8 {
          type xr:Cisco-ios-xr-string;
          description
            "The name of the eighth affinity";
        }
        leaf affinity9 {
          type xr:Cisco-ios-xr-string;
          description
            "The name of the nineth affinity";
        }
        leaf affinity10 {
          type xr:Cisco-ios-xr-string;
          description
            "The name of the tenth affinity";
        }
      }
    }
  }

  grouping FAST-REROUTE {
    description
      "Common node of tunnel-attributes,
       tunnel-te-attributes, auto-mesh-attribute,
       p2mpte-attribute";
    container fast-reroute {
      presence "Indicates a fast-reroute node is configured.";
      description
        "Specify MPLS tunnel can be fast-rerouted";
      leaf bandwidth-protection {
        type uint32 {
          range "0..1";
        }
        mandatory true;
        description
          "Bandwidth Protection";
      }
      leaf node-protection {
        type uint32 {
          range "0..1";
        }
        mandatory true;
        description
          "Node Protection";
      }
    }
  }

  grouping TUNNEL-RANGE {
    description
      "Common node of backup, mesh, p2mp-auto-tunnel,
       p2p-auto-tunnel, pcc";
    container tunnel-range {
      presence "Indicates a tunnel-range node is configured.";
      description
        "Configure tunnel ID range for auto-tunnel
         features";
      leaf min-tunnel-id {
        type uint32 {
          range "0..65535";
        }
        mandatory true;
        description
          "Minimum tunnel ID for auto-tunnels";
      }
      leaf max-tunnel-id {
        type uint32 {
          range "0..65535";
        }
        mandatory true;
        description
          "Maximum tunnel ID for auto-tunnels";
      }
    }
  }

  grouping ENABLE {
    description
      "Common node of path-selection,
       att-path-option-path-selection";
    leaf enable {
      type empty;
      description
        "Enter path selection configuration";
    }
  }

  grouping AUTOROUTE {
    description
      "Common node of tunnel-attributes,
       tunnel-te-attributes";
    container autoroute {
      description
        "Parameters for IGP routing over tunnel";
      container autoroute-announce {
        description
          "Announce tunnel to IGP";
        container exclude-traffic {
          description
            "Exclude traffic on autorouted tunnel";
          leaf segment-routing {
            type empty;
            description
              "Exclude tunnel in IGP for SR prefixes";
          }
        }
        container metric {
          description
            "Specify MPLS tunnel metric";
          leaf metric-type {
            type Mpls-te-autoroute-metric;
            description
              "Autoroute tunnel metric type";
          }
          leaf absolute-metric {
            when "../metric-type = 'absolute'" {
              tailf:xpath-root 3;
              description
                "../MetricType = Absolute";
            }
            type uint32 {
              range "1..2147483647";
            }
            description
              "The absolute metric value";
          }
          leaf relative-metric {
            when "../metric-type = 'relative'" {
              tailf:xpath-root 3;
              description
                "../MetricType = Relative";
            }
            type int32 {
              range "-10..10";
            }
            description
              "The value of the adjustment";
          }
          leaf constant-metric {
            when "../metric-type = 'constant'" {
              tailf:xpath-root 3;
              description
                "../MetricType = Constant";
            }
            type uint32 {
              range "1..2147483647";
            }
            description
              "The constant metric value";
          }
        }
        leaf enable {
          type empty;
          description
            "Enable autoroute announce";
        }
        leaf include-ipv6 {
          type empty;
          description
            "Specify that the tunnel should be an IPv6
             autoroute announce also";
        }
      }
      container destinations {
        description
          "Tunnel Autoroute Destination(s)";
        list destination {
          key "destination-address";
          description
            "Destination address to add in RIB";
          leaf destination-address {
            type inet:ipv4-address-no-zone;
            description
              "IP address of destination";
          }
        }
      }
    }
  }

  grouping OOR-NODE-PROTECTION-DISABLE {
    description
      "Common node of oor-green-state, oor-yellow-state,
       oor-red-state";
    leaf oor-node-protection-disable {
      type empty;
      description
        "Disable FRR node-protection when the link is in
         this OOR State";
    }
  }

  grouping REROUTE-MESSSAGE {
    description
      "Common node of logging, auto-mesh-logging";
    leaf reroute-messsage {
      type empty;
      description
        "Log tunnel rereoute messages";
    }
  }

  grouping CACHE-TIMER {
    description
      "Common node of mpls-te-mib, mpls-frr-mib,
       mpls-p2mp-mib, mpls-te-ext-mib,
       mpls-te-ext-std-mib";
    leaf cache-timer {
      type uint32 {
        range "0..600";
      }
      units "second";
      default "60";
      description
        "Configure the cache time for the mib.";
    }
  }

  grouping PATH-SELECTION-METRIC {
    description
      "Common node of tunnel-attributes,
       tunnel-te-attributes";
    leaf path-selection-metric {
      type Mpls-te-path-selection-metric;
      description
        "Path selection metric to use in path calculation";
    }
  }

  grouping PASSWORD {
    description
      "Common node of peer, pce-attributes";
    leaf password {
      type xr:Proprietary-password;
      description
        "MD5 password";
    }
  }

  grouping BANDWIDTH {
    description
      "Common node of tunnel-attributes,
       tunnel-te-attributes, auto-mesh-attribute,
       path-option-attribute, p2mpte-attribute";
    container bandwidth {
      presence "Indicates a bandwidth node is configured.";
      description
        "Tunnel bandwidth requirement";
      leaf dste-type {
        type Mpls-te-bandwidth-dste;
        mandatory true;
        description
          "DSTE-standard flag";
      }
      leaf class-or-pool-type {
        type uint32 {
          range "0..1";
        }
        mandatory true;
        description
          "Class type for the bandwidth allocation";
      }
      leaf bandwidth {
        type uint32 {
          range "0..4294967295";
        }
        units "kbit/s";
        mandatory true;
        description
          "The value of the bandwidth reserved by this
           tunnel in kbps";
      }
    }
  }

  grouping INTERFACE-BANDWIDTH {
    description
      "Common node of auto-mesh-attribute,
       p2mpte-attribute";
    leaf interface-bandwidth {
      type uint32 {
        range "0..4294967295";
      }
      units "kbit/s";
      description
        "The bandwidth of the interface in kbps";
    }
  }

  grouping FORWARD-CLASS {
    description
      "Common node of tunnel-attributes,
       tunnel-te-attributes, auto-mesh-attribute";
    leaf forward-class {
      type uint32 {
        range "0..7";
      }
      description
        "Forward class value";
    }
  }

  grouping INSUFFICIENT-BW-MESSAGE {
    description
      "Common node of logging, auto-mesh-logging";
    leaf insufficient-bw-message {
      type empty;
      description
        "Log tunnel messages for insufficient bandwidth";
    }
  }

  grouping PATH-SELECTION-DELAY-LIMIT {
    description
      "Common node of tunnel-path-selection,
       att-path-option-path-selection";
    leaf path-selection-delay-limit {
      type uint32 {
        range "1..4294967295";
      }
      description
        "Path selection delay limit (usec) configuration
         for this specific tunnel";
    }
  }

  grouping OOR-METRIC-TE-PENALTY {
    description
      "Common node of oor-green-state, oor-yellow-state,
       oor-red-state";
    leaf oor-metric-te-penalty {
      type uint32;
      default "0";
      description
        "Penalty applied to the TE metric of a link in
         OOR state";
    }
  }

  grouping KEYCHAIN {
    description
      "Common node of peer, pce-attributes";
    leaf keychain {
      type string {
        length "1..32";
      }
      description
        "Keychain based authentication";
    }
  }

  grouping FORWARDING-ADJACENCY {
    description
      "Common node of tunnel-attributes,
       tunnel-te-attributes";
    container forwarding-adjacency {
      description
        "Forwarding adjacency announcement to IGP";
      leaf enable {
        type empty;
        description
          "Enable forwarding adjacency";
      }
      leaf include-ipv6 {
        type empty;
        description
          "Specify that the tunnel should be an IPv6
           forwarding adjacency also";
      }
      leaf hold-time {
        type uint32 {
          range "0..20000";
        }
        description
          "Specify the holdtime for the tunnel as
           forwarding adjacency";
      }
    }
  }

  grouping ALL-TRANSIT-LSP-THRESHOLD {
    description
      "Common node of lsp-oor-yellow-state,
       lsp-oor-red-state";
    leaf all-transit-lsp-threshold {
      type uint32;
      description
        "Threshold for all transit LSPs";
    }
  }

  grouping PRIORITY {
    description
      "Common node of tunnel-te-attributes,
       tunnel-attributes, auto-mesh-attribute,
       gmpls-unitunnel-head, auto-backup-attribute,
       p2mpte-attribute";
    container priority {
      presence "Indicates a priority node is configured.";
      description
        "Tunnel Setup and Hold Priorities";
      leaf setup-priority {
        type uint32 {
          range "0..7";
        }
        mandatory true;
        description
          "Setup Priority";
      }
      leaf hold-priority {
        type uint32 {
          range "0..7";
        }
        mandatory true;
        description
          "Hold Priority";
      }
    }
  }

  augment "/ncs:devices/ncs:device/ncs:config" {
    container mpls-te {
      tailf:ncs-device-type "netconf";
      tailf:display-when "not(../../ncs:module) or ../../ncs:module[ncs:name='Cisco-IOS-XR-mpls-te-cfg']";
      description
        "The root of MPLS TE configuration";
      container diff-serv-traffic-engineering {
        description
          "Configure Diff-Serv Traffic-Engineering";
        container classes {
          description
            "Configure Diff-Serv Traffic-Engineering Classes";
          list class {
            key "class-number";
            description
              "DSTE class number";
            leaf class-number {
              type uint32 {
                range "0..7";
              }
              description
                "DS-TE class number";
            }
            leaf class-type {
              when "../unused = 'false'" {
                tailf:xpath-root 3;
                description
                  "../Unused = 'false'";
              }
              type uint32 {
                range "0..1";
              }
              default "1";
              description
                "Class type number";
            }
            leaf class-priority {
              when "../unused = 'false'" {
                tailf:xpath-root 3;
                description
                  "../Unused = 'false'";
              }
              type uint32 {
                range "0..7";
              }
              default "1";
              description
                "Class-type priority";
            }
            leaf unused {
              type boolean;
              description
                "TRUE to skip classtype and class priority
                 provisioning FALSE to provision them";
            }
          }
        }
        leaf bandwidth-constraint-model {
          type Bandwidth-constraint;
          description
            "Diff-Serv Traffic-Engineering Bandwidth
             Constraint Model";
        }
        leaf mode-ietf {
          type Ietf-mode;
          description
            "Diff-Serv Traffic-Engineering IETF mode";
        }
      }
      container named-tunnels {
        description
          "Configure MPLS TE tunnel";
        container tunnels {
          description
            "Configure MPLS TE tunnel";
          list tunnel {
            key "tunnel-name tunnel-type";
            description
              "Configure a MPLS TE tunnel";
            container tunnel-attributes {
              description
                "MPLS tunnel attributes";
              container path-setups {
                description
                  "Tunnel path setup table";
                list path-setup {
                  key "path-setup-name";
                  description
                    "Tunnel path setup";
                  container path-computation {
                    presence "Indicates a path-computation node is configured.";
                    description
                      "Path computation method";
                    leaf path-computation-method {
                      type Mpls-te-path-computation-method;
                      mandatory true;
                      description
                        "Path computation method";
                    }
                    leaf explicit-path-name {
                      type string;
                      description
                        "Explicit Path Name";
                    }
                    leaf path-computation-server {
                      type inet:ipv4-address-no-zone;
                      default "0.0.0.0";
                      description
                        "Path Computation Server Address";
                    }
                  }
                  leaf preference {
                    type uint32 {
                      range "0..255";
                    }
                    description
                      "Path preference level";
                  }
                  leaf path-setup-name {
                    type xr:Cisco-ios-xr-string;
                    description
                      "Path Name";
                  }
                }
              }
              leaf shutdown {
                type empty;
                description
                  "shutdown the tunnel";
              }
              uses FORWARD-CLASS;
              uses TUNNEL-PATH-SELECTION;
              uses AUTO-BANDWIDTH;
              uses PRIORITY;
              uses DESTINATION;
              uses RECORD-ROUTE;
              uses AFFINITY-MASK;
              uses FORWARDING-ADJACENCY;
              uses LOGGING;
              uses BANDWIDTH;
              uses AUTOROUTE;
              uses PATH-SELECTION-METRIC;
              uses NEW-STYLE-AFFINITY-TABLE;
              uses SOFT-PREEMPTION;
              uses FAST-REROUTE;
              uses LOAD-SHARE;
            }
            container tunnel-id {
              presence "Indicates a tunnel-id node is configured.";
              description
                "Set the tunnel ID";
              leaf tunnel-id-type {
                type Mpls-te-tunnel-id;
                mandatory true;
                description
                  "Tunnel ID Type";
              }
              leaf tunnel-id {
                type uint32 {
                  range "0..65535";
                }
                description
                  "Tunnel ID";
              }
            }
            leaf tunnel-name {
              type xr:Cisco-ios-xr-string {
                length "1..54";
              }
              description
                "Tunnel name";
            }
            leaf tunnel-type {
              type Mpls-te-config-tunnel;
              description
                "Tunnel Type";
            }
          }
        }
        leaf enable {
          type empty;
          description
            "Enable Named Tunnels";
        }
      }
      container gmpls-uni {
        description
          "GMPLS-UNI configuration";
        container timers {
          description
            "GMPLS-UNI timer configuration";
          container path-option-timers {
            description
              "GMPLS-UNI path-option timer configuration";
            container holddown {
              description
                "GMPLS-UNI path-option holddown timer
                 configuration";
              leaf minimum {
                type uint32 {
                  range "5..3600";
                }
                units "second";
                description
                  "Minimum holddown (seconds)";
              }
              leaf maximum {
                type uint32 {
                  range "5..3600";
                }
                units "second";
                description
                  "Maximum holddown (seconds)";
              }
            }
          }
        }
        container controllers {
          description
            "GMPLS-UNI controllers";
          list controller {
            key "controller-name";
            description
              "Configure a GMPLS controller";
            container announce {
              description
                "Announce discovered tunnel properties to
                 system";
              leaf srl-gs {
                type empty;
                description
                  "Enable announcement of discovered SRLGs";
              }
            }
            container controller-logging {
              description
                "Controller logging";
              leaf discovered-srlg-change-logging {
                type empty;
                description
                  "Enable logging of changes to of discovered
                   SRLGs";
              }
            }
            container gmpls-unitunnel-head {
              description
                "GMPLS-UNI tunnel-head properties";
              container path-options {
                description
                  "Path-option configuration";
                list path-option {
                  key "preference-level";
                  description
                    "A Path-option";
                  leaf preference-level {
                    type uint32 {
                      range "1..1000";
                    }
                    description
                      "Preference level for this path option";
                  }
                  leaf path-type {
                    type Mpls-te-path-option;
                    mandatory true;
                    description
                      "The type of the path option";
                  }
                  leaf path-id {
                    type uint32 {
                      range "1..65535";
                    }
                    default "1";
                    description
                      "The ID of the explicit path associated
                       with this option";
                  }
                  leaf path-name {
                    type string;
                    description
                      "The name of the explicit path associated
                       with this option";
                  }
                  leaf xro-type {
                    type Mpls-te-path-option-xro;
                    mandatory true;
                    description
                      "The route-exclusion type";
                  }
                  leaf xro-attribute-set-name {
                    type Attribute-set-name-length;
                    description
                      "The name of the XRO attribute set to be
                       used for this path-option";
                  }
                  leaf lockdown {
                    type Mpls-te-path-option-property;
                    mandatory true;
                    description
                      "Path option properties: must be Lockdown";
                  }
                  leaf verbatim {
                    type Mpls-te-path-option-property;
                    default "none";
                    description
                      "Path option properties: must be verbatim
                       if set";
                  }
                  leaf signaled-label {
                    type Mpls-te-signaled-label;
                    default "not-set";
                    description
                      "Signaled label type";
                  }
                  leaf dwdm-channel {
                    type uint32 {
                      range "1..89";
                    }
                    default "1";
                    description
                      "DWDM channel number";
                  }
                }
              }
              container recording {
                description
                  "Tunnel property recording";
                leaf srlg {
                  type empty;
                  description
                    "Enable SRLG-recording during signaling";
                }
              }
              container logging {
                description
                  "Tunnel event logging";
                uses STATE-MESSAGE;
              }
              leaf tunnel-id {
                type uint32 {
                  range "0..65535";
                }
                description
                  "GMPLS-UNI head tunnel-id";
              }
              leaf enable {
                type empty;
                description
                  "Set link as a GMPLS tunnel head";
              }
              leaf destination {
                type inet:ipv4-address-no-zone;
                description
                  "Set the destination of the tunnel";
              }
              uses PRIORITY;
              uses RECORD-ROUTE;
              uses SIGNALLED-NAME;
            }
            leaf enable {
              type empty;
              description
                "Enable GMPLS-UNI on the link";
            }
            leaf controller-name {
              type xr:Interface-name;
              description
                "Controller name";
            }
          }
        }
      }
      container global-attributes {
        description
          "Configure MPLS TE global attributes";
        container auto-tunnel {
          description
            "Configure auto-tunnels feature";
          container pcc {
            description
              "Configure auto-tunnel PCC (Path Computation
               Client) feature";
            uses TUNNEL-RANGE;
          }
          container p2p-auto-tunnel {
            description
              "Configure P2P auto-tunnel feature";
            uses TUNNEL-RANGE;
          }
          container backup {
            description
              "Configure auto-tunnel backup feature";
            leaf affinity-ignore {
              type empty;
              description
                "Ignore affinity during CSPF for auto backup
                 tunnels";
            }
            uses TIMERS;
            uses TUNNEL-RANGE;
          }
          container mesh {
            description
              "Configure auto-tunnel mesh feature";
            container mesh-groups {
              description
                "Configure auto-tunnel mesh group";
              list mesh-group {
                key "mesh-group-id";
                description
                  "Auto-mesh group identifier";
                leaf destination-list {
                  type Destination-list-name-length;
                  description
                    "The name of prefix-list to be applied to
                     this destination-list";
                }
                leaf disable {
                  type empty;
                  description
                    "Disables mesh group";
                }
                leaf attribute-set {
                  type Attribute-set-name-length;
                  description
                    "The name of auto-mesh attribute set to be
                     applied to this group";
                }
                leaf one-hop {
                  type empty;
                  description
                    "Automatically create tunnel to all
                     next-hops";
                }
                leaf mesh-group-id {
                  type Mesh-group-id;
                  description
                    "Mesh group ID";
                }
              }
            }
            uses TIMERS;
            uses TUNNEL-RANGE;
          }
          container p2mp-auto-tunnel {
            description
              "Configure P2MP auto-tunnel feature";
            uses TUNNEL-RANGE;
          }
        }
        container hardware-out-of-resource {
          description
            "Configure HW OOR processing in MPLS-TE";
          container oor-red-state {
            description
              "Configuration for HW OOR Red State";
            uses OOR-NODE-PROTECTION-DISABLE;
            uses OOR-AVAILABLE-BANDWIDTH-PERCENTAGE;
            uses OOR-ACCEPT-LSP-MIN-BANDWIDTH;
            uses OOR-ACCEPT-REOPT-LSP;
            uses OOR-METRIC-TE-PENALTY;
          }
          container oor-yellow-state {
            description
              "Configuration for HW OOR Yellow State";
            uses OOR-NODE-PROTECTION-DISABLE;
            uses OOR-AVAILABLE-BANDWIDTH-PERCENTAGE;
            uses OOR-ACCEPT-LSP-MIN-BANDWIDTH;
            uses OOR-ACCEPT-REOPT-LSP;
            uses OOR-METRIC-TE-PENALTY;
          }
          container oor-green-state {
            description
              "Configuration for HW OOR Green State";
            leaf oor-recovery-duration {
              type uint32 {
                range "0..10080";
              }
              units "minute";
              default "0";
              description
                "Period of time (minutes) during which the
                 action in Green state are applied. After this
                 period, the processing in TE goes back to
                 normal state";
            }
            uses OOR-NODE-PROTECTION-DISABLE;
            uses OOR-AVAILABLE-BANDWIDTH-PERCENTAGE;
            uses OOR-ACCEPT-LSP-MIN-BANDWIDTH;
            uses OOR-ACCEPT-REOPT-LSP;
            uses OOR-METRIC-TE-PENALTY;
          }
        }
        container secondary-router-ids {
          description
            "Configure MPLS TE Secondary Router ID";
          list secondary-router-id {
            key "secondary-router-id-value";
            description
              "Secondary Router ID";
            leaf secondary-router-id-value {
              type inet:ipv4-address-no-zone;
              description
                "Secondary TE Router ID";
            }
          }
        }
        container srlg {
          description
            "Configure SRLG values and MPLS-TE properties";
          container names {
            description
              "Configure SRLG identified by names";
            list name {
              key "srlg-name";
              description
                "SRLG name and its MPLS-TE properties";
              container static-srlg-members {
                description
                  "Configure static SRLG members list";
                list static-srlg-member {
                  key "from-address";
                  description
                    "A mapping of the local static SRLG member";
                  leaf from-address {
                    type inet:ipv4-address-no-zone;
                    description
                      "From address";
                  }
                  leaf to-address {
                    type inet:ipv4-address-no-zone;
                    mandatory true;
                    description
                      "To Addres";
                  }
                }
              }
              leaf admin-weight {
                type uint32;
                description
                  "Administrative weight for the SRLG value";
              }
              leaf srlg-name {
                type xr:Cisco-ios-xr-string {
                  length "1..64";
                }
                description
                  "SRLG membership name";
              }
            }
          }
          leaf default-admin-weight {
            type uint32;
            default "1";
            description
              "Default Admin weight any SRLG value that does
               not have one";
          }
          leaf enable {
            type empty;
            description
              "Enter SRLG property configuration";
          }
        }
        container queues {
          description
            "Configure MPLS TE route priority";
          list queue {
            key "role";
            description
              "Configure route priority queue value";
            leaf role {
              type Route-priority-role;
              description
                "Route Priority Tunnel Role";
            }
            leaf value {
              type uint32 {
                range "0..12";
              }
              mandatory true;
              description
                "Route priority queue value";
            }
          }
        }
        container mib {
          description
            "MPLS-TE MIB properties";
          leaf midpoint-lsp-stats-collection-disable {
            type empty;
            description
              "Disables mib midpoint LSP traffic stats
               collection";
          }
        }
        container attribute-set {
          description
            "Attribute AttributeSets";
          container path-option-attributes {
            description
              "Path Option Attribute-Set Table";
            list path-option-attribute {
              key "attribute-set-name";
              description
                "Path Option Attribute";
              container bfd-reverse-path {
                presence "Indicates a bfd-reverse-path node is configured.";
                description
                  "Configure BFD reverse path";
                leaf bfd-reverse-path-type {
                  type Bfd-reverse-path;
                  description
                    "BFD reverse path type";
                }
                leaf binding-label {
                  type uint32 {
                    range "0..1048575";
                  }
                  mandatory true;
                  description
                    "BFD reverse path binding label";
                }
              }
              container att-path-option-path-selection {
                description
                  "Configure path selection properties";
                leaf path-selection-exclude-list {
                  type string {
                    length "1..64";
                  }
                  description
                    "Path selection exclude list name
                     configuration";
                }
                uses ENABLE;
                uses PATH-SELECTION-DELAY-LIMIT;
                uses INVALIDATION;
                uses PATH-SELECTION-COST-LIMIT;
              }
              leaf attribute-set-name {
                type Attribute-set-name-length;
                description
                  "Attribute Set Name";
              }
              uses PCE;
              uses AFFINITY-MASK;
              uses BANDWIDTH;
              uses NEW-STYLE-AFFINITY-TABLE;
            }
          }
          container p2mpte-attributes {
            description
              "P2MP-TE Tunnel AttributeSets Table";
            list p2mpte-attribute {
              key "attribute-set-name";
              description
                "P2MP-TE Tunnel Attribute";
              leaf attribute-set-name {
                type Attribute-set-name-length;
                description
                  "Attribute Set Name";
              }
              uses INTERFACE-BANDWIDTH;
              uses PRIORITY;
              uses RECORD-ROUTE;
              uses AFFINITY-MASK;
              uses BANDWIDTH;
              uses PATH-SELECTION;
              uses NEW-STYLE-AFFINITY-TABLE;
              uses FAST-REROUTE;
              uses MPLS-MTE-TUNNEL-CFG-LOGGING;
            }
          }
          container p2p-te-attributes {
            description
              "P2P-TE Tunnel AttributeSets Table";
            list p2p-te-attribute {
              key "attribute-set-name";
              description
                "P2P-TE Tunnel Attribute";
              container path-selection {
                description
                  "Configure path selection properties";
                container segment-routing-prepend {
                  description
                    "Deprecated";
                  container indexes {
                    description
                      "Segment routing prepend index table";
                    list index {
                      key "index-number";
                      description
                        "Prepend index information";
                      leaf index-number {
                        type uint32 {
                          range "1..10";
                        }
                        description
                          "Index number";
                      }
                      leaf prepend-type {
                        type Sr-prepend;
                        default "none-type";
                        description
                          "Prepend type";
                      }
                      leaf mpls-label {
                        type uint32;
                        default "1048577";
                        description
                          "MPLS Label";
                      }
                    }
                  }
                  leaf enable {
                    type empty;
                    description
                      "Enter path selection segment routing
                       prepend submode";
                  }
                }
                container invalidation {
                  description
                    "Deprecated";
                  leaf invalidation-timer {
                    type uint32 {
                      range "0..60000";
                    }
                    units "millisecond";
                    description
                      "Path selection invalidation timer value
                       (milliseconds)";
                  }
                  leaf invalidation-timer-expire-type {
                    type Mpls-te-path-selection-invalidation-timer-expire;
                    default "tunnel-action-tear";
                    description
                      "Path selection invalidation timer expire
                       type";
                  }
                }
                leaf path-selection-metric {
                  type Mpls-te-path-selection-metric;
                  description
                    "Path selection metric to use in path
                     calculation";
                }
                leaf path-selection-segment-routing-adjacency-protection {
                  type Mpls-te-path-selection-segment-routing-adjacency-protection;
                  description
                    "Segment routing adjacency protection type
                     to use in path calculation";
                }
                uses ENABLE;
              }
              leaf attribute-set-name {
                type Attribute-set-name-length;
                description
                  "Attribute Set Name";
              }
              uses PCE;
              uses AFFINITY-MASK;
              uses LOGGING;
              uses NEW-STYLE-AFFINITY-TABLE;
            }
          }
          container auto-backup-attributes {
            description
              "Auto-backup Tunnel Attribute Table";
            list auto-backup-attribute {
              key "attribute-set-name";
              description
                "Auto-backup Tunnel Attribute";
              container signalled-name {
                description
                  "Signalled name";
                leaf name {
                  type string;
                  description
                    "Signalled name";
                }
                leaf source-type {
                  type Mpls-te-sig-name-option;
                  description
                    "Source address or name";
                }
                leaf protected-interface-type {
                  type Mpls-te-sig-name-option;
                  description
                    "Protected-interface address or name";
                }
                leaf mp-address {
                  type boolean;
                  description
                    "Set if merge-point address is to be
                     appended";
                }
              }
              container auto-backup-logging {
                description
                  "Log tunnel LSP messages";
                uses BANDWIDTH-CHANGE-MESSAGE;
                uses REOPTIMIZE-ATTEMPTS-MESSAGE;
                uses STATE-MESSAGE;
                uses REOPTIMIZED-MESSAGE;
              }
              leaf attribute-set-name {
                type Attribute-set-name-length;
                description
                  "Attribute Set Name";
              }
              uses PRIORITY;
              uses RECORD-ROUTE;
              uses AFFINITY-MASK;
              uses PATH-SELECTION;
              uses POLICY-CLASSES;
              uses NEW-STYLE-AFFINITY-TABLE;
            }
          }
          container otn-pp-attributes {
            description
              "OTN Path Protection Attributes table";
            list otn-pp-attribute {
              key "attribute-set-name";
              description
                "OTN Path Protection Attribute";
              container revert-schedule-names {
                description
                  "Specify APS revert schedule";
                list revert-schedule-name {
                  key "schedule-name";
                  description
                    "Name Identifier for revert schedule";
                  container schedule-duration {
                    presence "Indicates a schedule-duration node is configured.";
                    description
                      "Set duration in format hh:mm";
                    leaf hour {
                      type uint32 {
                        range "0..167";
                      }
                      mandatory true;
                      description
                        "Hour of day";
                    }
                    leaf minutes {
                      type uint32 {
                        range "0..59";
                      }
                      mandatory true;
                      description
                        "Minute of the hour";
                    }
                  }
                  container schedule-date {
                    presence "Indicates a schedule-date node is configured.";
                    description
                      "Set date in format hh:mm MMM DD YYYY";
                    leaf hour {
                      type uint32 {
                        range "0..23";
                      }
                      mandatory true;
                      description
                        "Hour of day";
                    }
                    leaf minutes {
                      type uint32 {
                        range "0..59";
                      }
                      mandatory true;
                      description
                        "Minute of the hour";
                    }
                    leaf month {
                      type uint32 {
                        range "0..11";
                      }
                      mandatory true;
                      description
                        "Month of the year";
                    }
                    leaf day {
                      type uint32 {
                        range "1..31";
                      }
                      mandatory true;
                      description
                        "Day of the month";
                    }
                    leaf year {
                      type uint32 {
                        range "2015..2035";
                      }
                      mandatory true;
                      description
                        "Year";
                    }
                  }
                  leaf revert-schedule-max-tries {
                    type uint32 {
                      range "1..2016";
                    }
                    description
                      "Revert Schedule Max tries";
                  }
                  leaf sch-name-enable {
                    type empty;
                    description
                      "Schedule name enable object";
                  }
                  leaf revert-schedule-frequency {
                    type uint32 {
                      range "1..3";
                    }
                    description
                      "Frequency set as Once, Daily, Weekly";
                  }
                  leaf schedule-name {
                    type xr:Cisco-ios-xr-string {
                      length "1..254";
                    }
                    description
                      "Enter 64 characters for revert schedule
                       name";
                  }
                }
              }
              container sub-network-connection-mode {
                description
                  "Sub-network connection mode";
                leaf connection-mode {
                  type Mpls-te-otn-snc-mode;
                  description
                    "The sub-network connection mode";
                }
                leaf connection-monitoring-mode {
                  type uint32 {
                    range "1..6";
                  }
                  description
                    "Tandem Connection Monitoring ID for the
                     interface";
                }
              }
              container timers {
                description
                  "Timers";
                leaf aps-wait-to-restore {
                  type uint32 {
                    range "0..720";
                  }
                  units "second";
                  description
                    "G.709 OTN path protection wait to restore
                     timer in seconds";
                }
                leaf aps-hold-off {
                  type uint32 {
                    range "100..10000";
                  }
                  units "millisecond";
                  description
                    "G.709 OTN path protection hold-off timer in
                     milliseconds";
                }
              }
              leaf aps-protection-mode {
                type Mpls-te-otn-aps-protection-mode;
                description
                  "The APS protecion mode";
              }
              leaf aps-restoration-style {
                type Mpls-te-otn-aps-restoration-style;
                description
                  "The APS restoration style";
              }
              leaf aps-protection-type {
                type Mpls-te-otn-aps-protection;
                description
                  "The APS protecion type";
              }
              leaf attribute-set-name {
                type Attribute-set-name-length;
                description
                  "Attribute Set Name";
              }
              uses PATH-SELECTION;
            }
          }
          container auto-mesh-attributes {
            description
              "Auto-mesh Tunnel AttributeSets Table";
            list auto-mesh-attribute {
              key "attribute-set-name";
              description
                "Auto-mesh Tunnel Attribute";
              container auto-mesh-logging {
                description
                  "Log tunnel LSP messages";
                uses BANDWIDTH-CHANGE-MESSAGE;
                uses REOPTIMIZE-ATTEMPTS-MESSAGE;
                uses REROUTE-MESSSAGE;
                uses STATE-MESSAGE;
                uses INSUFFICIENT-BW-MESSAGE;
                uses REOPTIMIZED-MESSAGE;
                uses PCALC-FAILURE-MESSAGE;
              }
              leaf autoroute-announce {
                type empty;
                description
                  "Enable autoroute announce";
              }
              leaf attribute-set-name {
                type Attribute-set-name-length;
                description
                  "Attribute Set Name";
              }
              uses INTERFACE-BANDWIDTH;
              uses FORWARD-CLASS;
              uses PRIORITY;
              uses RECORD-ROUTE;
              uses AFFINITY-MASK;
              uses BANDWIDTH;
              uses PATH-SELECTION;
              uses COLLECTION-ONLY;
              uses POLICY-CLASSES;
              uses NEW-STYLE-AFFINITY-TABLE;
              uses SOFT-PREEMPTION;
              uses FAST-REROUTE;
              uses LOAD-SHARE;
            }
          }
          container xro-attributes {
            description
              "XRO Tunnel Attributes table";
            list xro-attribute {
              key "attribute-set-name";
              description
                "XRO Attribute";
              container path-diversity {
                description
                  "Path diversity";
                container srlgs {
                  description
                    "SRLG-based path diversity";
                  list srlg {
                    key "srlg";
                    description
                      "SRLG-based path-diversity element";
                    leaf srlg {
                      type uint32 {
                        range "0..4294967295";
                      }
                      description
                        "SRLG";
                    }
                    leaf conformance {
                      type Mpls-te-path-diversity-conformance;
                      mandatory true;
                      description
                        "The diversity conformance requirements";
                    }
                  }
                }
                container lsp {
                  description
                    "LSP-based path diversity";
                  container fecs {
                    description
                      "FEC LSP-based path diversity";
                    list fec {
                      key "source destination tunnel-id extended-tunnel-id lsp-id";
                      description
                        "LSP-based path-diversity, referenced by
                         FEC";
                      leaf source {
                        type inet:ipv4-address-no-zone;
                        description
                          "Source address";
                      }
                      leaf destination {
                        type inet:ipv4-address-no-zone;
                        description
                          "Destination address";
                      }
                      leaf tunnel-id {
                        type uint32 {
                          range "0..65535";
                        }
                        description
                          "Tunnel id";
                      }
                      leaf extended-tunnel-id {
                        type inet:ipv4-address-no-zone;
                        description
                          "Extended tunnel-id";
                      }
                      leaf lsp-id {
                        type uint32 {
                          range "0..65535";
                        }
                        description
                          "LSP id";
                      }
                      leaf conformance {
                        type Mpls-te-path-diversity-conformance;
                        mandatory true;
                        description
                          "The diversity conformance requirements";
                      }
                    }
                  }
                }
              }
              leaf attribute-set-name {
                type Attribute-set-name-length;
                description
                  "Attribute Set Name";
              }
              uses PATH-SELECTION;
            }
          }
        }
        container bfd-over-lsp {
          description
            "BFD over MPLS TE Global Configurations";
          container tail {
            description
              "BFD over LSP Tail Global Configurations";
            leaf multiplier {
              type uint32 {
                range "3..10";
              }
              description
                "Specify BFD over LSP tail multiplier";
            }
            leaf minimum-interval {
              type uint32 {
                range "50..30000";
              }
              description
                "Specify BFD over LSP tail minimum interval";
            }
          }
          container head {
            description
              "BFD over LSP Head Global Configurations";
            leaf reopt-timeout {
              type uint32 {
                range "120..4294967295";
              }
              description
                "BFD session down reopt timeout";
            }
            leaf down-action {
              type Mpls-te-bfd-session-down-action;
              description
                "Specify BFD session down action";
            }
          }
        }
        container bandwidth-accounting {
          description
            "Bandwidth accounting configuration data";
          container application {
            description
              "Bandwidth accounting application configuration
               data";
            leaf application-enforced {
              type boolean;
              default "false";
              description
                "This object enables the application";
            }
            leaf application-interval {
              type uint32 {
                range "30..1800";
              }
              units "second";
              default "180";
              description
                "This object sets the application interval in
                 seconds for bandwidth accounting. Default to
                 180 seconds.";
            }
          }
          container account-flooding-threshold {
            description
              "This object sets the flooding threshold as
               percentage of total link bandwidth for
               bandwidth accounting. Default to 10%, 10%";
            leaf up-threshold {
              type Mpls-percent-range;
              units "percentage";
              default "10";
              description
                "Upward flooding Threshold in percentages of
                 total bandwidth";
            }
            leaf down-threshold {
              type Mpls-percent-range;
              units "percentage";
              default "10";
              description
                "Downward flooding Threshold in percentages of
                 total bandwidth";
            }
          }
          leaf sampling-interval {
            type uint32 {
              range "10..600";
            }
            units "second";
            default "60";
            description
              "This object sets the sampling interval in
               seconds for bandwidth accounting. Default to
               60 seconds.";
          }
          leaf adjustment-factor {
            type uint32 {
              range "0..200";
            }
            units "percentage";
            default "100";
            description
              "This object sets the percentage adjustment
               factor for the non RSVP-TE bandwidth
               accounting.  Default is 100%.";
          }
          leaf collection-type-rsvp-te {
            type boolean;
            default "false";
            description
              "This object enables the bandwidth accounting
               RSVP-TE sample collection.";
          }
          leaf enable {
            type empty;
            description
              "This object controls whether BW accounting is
               enabled. This object must be set before
               setting any other objects  under the
               BandwidthAccounting class.";
          }
        }
        container pce-attributes {
          description
            "Configuration MPLS TE PCE attributes";
          container pce-stateful {
            description
              "PCE Stateful";
            container stateful-timers {
              description
                "Configure Stateful PCE (Path Computation
                 Element) timers";
              leaf redelegation-timeout {
                type uint32 {
                  range "0..3600";
                }
                units "second";
                default "180";
                description
                  "Timer for static tunnel redelegation in
                   seconds, default is 180 seconds";
              }
              leaf state-timeout {
                type uint32 {
                  range "0..3600";
                }
                units "second";
                default "180";
                description
                  "State timeout for LSPs without delegation in
                   seconds, zero means immediate removal,
                   default is 180 seconds";
              }
            }
            leaf fast-repair {
              type empty;
              description
                "Enable reoptimization by PCC after path
                 failures";
            }
            leaf instantiation {
              type empty;
              description
                "PCE stateful instantiation capability";
            }
            leaf cisco-extension {
              type empty;
              description
                "Enable processing of PCEP Cisco extension";
            }
            leaf delegation {
              type empty;
              description
                "Delegate all statically configured tunnels";
            }
            leaf autoroute-announce {
              type empty;
              description
                "Enable autoroute announce for PCE
                 instantiated tunnels";
            }
            leaf report {
              type empty;
              description
                "Report all statically configured tunnels";
            }
            leaf enable {
              type empty;
              description
                "PCE stateful capability";
            }
          }
          container timer {
            description
              "Configure PCE (Path Computation Element)
               timers";
          }
          container peers {
            description
              "Configure PCE peers";
            list peer {
              key "pce-peer-address";
              description
                "PCE peer";
              leaf pce-peer-address {
                type inet:ipv4-address-no-zone;
                description
                  "Address of PCE Peer";
              }
              uses PASSWORD;
              uses KEYCHAIN;
              uses PRECEDENCE;
            }
          }
          container logging {
            description
              "Configure PCE (Path Computation Element)
               logging feature";
            container events {
              description
                "Configure logging events";
              leaf peer-status {
                type empty;
                description
                  "Peer status changes logging";
              }
            }
          }
          leaf request-timeout {
            type uint32 {
              range "5..100";
            }
            units "second";
            default "10";
            description
              "Request timeout value in seconds";
          }
          leaf reoptimize-period {
            type uint32 {
              range "60..604800";
            }
            units "second";
            default "60";
            description
              "PCE reoptimization period for PCE-based paths";
          }
          leaf address {
            type inet:ipv4-address-no-zone;
            description
              "Address of this PCE";
          }
          leaf deadtimer {
            type uint32 {
              range "0..255";
            }
            units "second";
            default "120";
            description
              "Deadtimer interval in seconds";
          }
          leaf keepalive {
            type uint32 {
              range "0..255";
            }
            units "second";
            default "30";
            description
              "Keepalive interval in seconds";
          }
          leaf keepalive-tolerance {
            type uint32 {
              range "0..255";
            }
            units "second";
            default "10";
            description
              "Keepalive interval tolerance in seconds";
          }
          leaf peer-source-addr {
            type inet:ipv4-address-no-zone;
            description
              "PCE Peer Source Address";
          }
          leaf speaker-entity-id {
            type string {
              length "1..256";
            }
            description
              "PCE speaker entity identifier";
          }
          leaf segment-routing {
            type empty;
            description
              "Always set to true";
          }
          uses PASSWORD;
          uses KEYCHAIN;
          uses PRECEDENCE;
        }
        container lsp-out-of-resource {
          description
            "Configure LSP OOR attributes in MPLS-TE";
          container lsp-oor-red-state {
            description
              "Configuration for LSP OOR Red/Major State";
            uses ALL-TRANSIT-LSP-THRESHOLD;
            uses UNPROTECTED-TRANSIT-LSP-THRESHOLD;
          }
          container lsp-oor-yellow-state {
            description
              "Configuration for LSP OOR Yellow/Minor State";
            uses ALL-TRANSIT-LSP-THRESHOLD;
            uses UNPROTECTED-TRANSIT-LSP-THRESHOLD;
          }
        }
        container soft-preemption {
          description
            "Soft preemption configuration data";
          leaf timeout {
            type uint32 {
              range "1..300";
            }
            units "second";
            default "60";
            description
              "This object sets the timeout in seconds before
               hard preemption is triggered.";
          }
          leaf frr-rewrite {
            type empty;
            description
              "This object controls whether FRR rewrite
               during soft preemption is enabled.";
          }
          leaf enable {
            type boolean;
            description
              "This object controls whether soft preemption
               is enabled. This object must be set before
               setting any other objects under the
               SoftPreemption class.";
          }
        }
        container fast-reroute {
          description
            "Configure fast reroute attributes";
          container timers {
            description
              "Configure fast reroute timers";
            leaf hold-backup {
              type uint32 {
                range "0..604800";
              }
              units "second";
              description
                "Seconds before backup declared UP (0 disables
                 hold-timer)";
            }
            leaf promotion {
              type uint32 {
                range "0..604800";
              }
              units "second";
              description
                "The value of the promotion timer in seconds";
            }
          }
        }
        container path-selection {
          description
            "Path selection configuration";
          container loose-metrics {
            description
              "Path selection Loose ERO Metric Class
               configuration";
            list loose-metric {
              key "class-type";
              description
                "Path selection Loose ERO Metric configuration";
              leaf class-type {
                type uint32 {
                  range "0..7";
                }
                description
                  "Path Selection class Type";
              }
              leaf metric-type {
                type Mpls-te-path-selection-metric;
                mandatory true;
                description
                  "Metric to use for ERO Expansion";
              }
            }
          }
          container invalidation {
            description
              "Deprecated";
            leaf path-invalidation-timeout {
              type uint32 {
                range "0..60000";
              }
              description
                "Path Invalidation Timeout";
            }
            leaf path-invalidation-action {
              type Path-invalidation-action;
              description
                "Path Invalidation Action";
            }
          }
          container ignore-overload-role {
            description
              "Path selection to ignore overload node during
               CSPF";
            leaf head {
              type boolean;
              description
                "Set if the OL-bit is to be applied to tunnel
                 heads";
            }
            leaf mid {
              type boolean;
              description
                "Set if the OL-bit is to be applied to tunnel
                 midpoints";
            }
            leaf tail {
              type boolean;
              description
                "Set if the OL-bit is to be applied to tunnel
                 tails";
            }
          }
          container loose-affinities {
            description
              "Path selection Loose ERO Affinity Class
               configuration";
            list loose-affinity {
              key "class-type";
              description
                "Path selection Loose ERO Affinity
                 configuration";
              leaf class-type {
                type uint32 {
                  range "0..7";
                }
                description
                  "Path Selection class Type";
              }
              leaf affinity {
                type xr:Hex-integer;
                description
                  "Affinity flags";
              }
              leaf mask {
                type xr:Hex-integer;
                description
                  "Affinity mask";
              }
            }
          }
          leaf cost-limit {
            type uint32 {
              range "1..4294967295";
            }
            description
              "Path selection cost limit configuration for
               all tunnels";
          }
          leaf tiebreaker {
            type Mpls-te-path-selection-tiebreaker;
            description
              "CSPF tiebreaker to use in path calculation";
          }
          leaf metric {
            type Mpls-te-path-selection-metric;
            description
              "Metric to use in path calculation";
          }
          leaf loose-domain-match {
            type boolean;
            description
              "Use only the IGP instance of the incoming
               interface";
          }
          leaf delay-limit {
            type uint32 {
              range "1..4294967295";
            }
            description
              "Path selection delay limit configuration for
               p2p tunnels (usec)";
          }
        }
        container affinity-mappings {
          description
            "Affinity Mapping Table configuration";
          list affinity-mapping {
            key "affinity-name";
            description
              "Affinity Mapping configuration";
            leaf affinity-name {
              type xr:Cisco-ios-xr-string {
                length "1..32";
              }
              description
                "Affinity Name";
            }
            leaf value-type {
              type Mpls-te-affinity-value;
              description
                "Affinity value type";
            }
            leaf value {
              type xr:Hex-integer;
              description
                "Affinity Value in Hex number or by Bit
                 position";
            }
          }
        }
        leaf log-nsr-status {
          type empty;
          description
            "Log NSR status messages";
        }
        leaf log-issu-status {
          type empty;
          description
            "Log ISSU status messages";
        }
        leaf reoptimize-link-up {
          type empty;
          description
            "Enable reoptimization based on link-up events";
        }
        leaf reoptimize-delay-cleanup-timer {
          type uint32 {
            range "0..300";
          }
          units "second";
          description
            "Reoptimization Delay Cleanup Value (seconds)";
        }
        leaf disable-reoptimize-affinity-failure {
          type empty;
          description
            "Disable reoptimization after affinity failures";
        }
        leaf maximum-tunnels {
          type uint32 {
            range "1..65536";
          }
          default "4096";
          description
            "The maximum number of tunnel heads that will be
             allowed.";
        }
        leaf link-holddown-timer {
          type uint32 {
            range "0..300";
          }
          units "second";
          default "10";
          description
            "Holddown time for links which had Path Errors
             in seconds";
        }
        leaf fault-oam {
          type empty;
          description
            "Enable Fault-OAM functionality for
             bidirectional tunnels";
        }
        leaf enable-unequal-load-balancing {
          type empty;
          description
            "Enable unequal load-balancing over tunnels to
             the same destination";
        }
        leaf log-tail {
          type empty;
          description
            "Log all tail tunnel events";
        }
        leaf reoptimize-delay-after-frr-timer {
          type uint32 {
            range "0..120";
          }
          units "second";
          description
            "Reoptimization Delay After FRR Value (seconds)";
        }
        leaf auto-bandwidth-collect-frequency {
          type uint32 {
            range "1..10080";
          }
          units "minute";
          default "5";
          description
            "Auto-bandwidth global collection frequency in
             minutes";
        }
        leaf reopt-delay-path-protect-switchover-timer {
          type uint32 {
            range "0..604800";
          }
          units "second";
          default "180";
          description
            "Seconds between path protect switchover and
             tunnel re-optimization. Set to 0 to disable";
        }
        leaf log-all {
          type empty;
          description
            "Always set to true";
        }
        leaf loose-path-retry-period {
          type uint32 {
            range "30..600";
          }
          default "120";
          description
            "Signalling retry for tunnels terminating
             outside the headend area";
        }
        leaf reoptimize-load-balancing {
          type empty;
          description
            "Load balance bandwidth during reoptimization";
        }
        leaf log-head {
          type empty;
          description
            "Log all head tunnel events";
        }
        leaf path-selection-ignore-overload {
          type empty;
          description
            "Deprecated - do not use";
        }
        leaf graceful-preemption-on-bandwidth-reduction {
          type empty;
          description
            "Enable graceful preemption when there is a
             bandwidth reduction";
        }
        leaf advertise-explicit-nulls {
          type empty;
          description
            "Enable explicit-null advertising to PHOP";
        }
        leaf reoptimize-delay-install-timer {
          type uint32 {
            range "0..3600";
          }
          units "second";
          description
            "Reoptimization Delay Install Value (seconds)";
        }
        leaf reoptimize-delay-after-affinity-failure-timer {
          type uint32 {
            range "1..604800";
          }
          units "second";
          description
            "Delay reoptimizing current LSP after affinity
             failures";
        }
        leaf log-frr-protection {
          type Mpls-te-log-frr-protection;
          description
            "Log FRR Protection messages";
        }
        leaf reoptimize-timer-frequency {
          type uint32 {
            range "0..604800";
          }
          units "second";
          default "3600";
          description
            "Reoptimize timers period in seconds";
        }
        leaf log-mid {
          type empty;
          description
            "Log all mid tunnel events";
        }
        leaf log-preemption {
          type empty;
          description
            "Log tunnel preemption messages";
        }
      }
      container transport-profile {
        description
          "MPLS transport profile configuration data";
        container fault {
          description
            "Fault management";
          container protection-trigger {
            description
              "OAM events that trigger protection switching";
            container ldi {
              description
                "Protection switching due to LDI event";
              leaf disable {
                type empty;
                description
                  "Disable protection switching due to LDI
                   event";
              }
            }
            container lkr {
              description
                "Protection switching due to LKR event";
              leaf disable {
                type empty;
                description
                  "Disable protection switching due to LKR
                   event";
              }
            }
            leaf ais {
              type empty;
              description
                "Enable protection switching due to AIS event";
            }
          }
          leaf wait-to-restore-interval {
            type uint32 {
              range "0..2147483647";
            }
            units "second";
            default "0";
            description
              "Waiting time before restoring working LSP";
          }
          leaf refresh-interval {
            type uint32 {
              range "1..20";
            }
            units "second";
            default "20";
            description
              "Periodic refresh interval for fault OAM
               messages";
          }
        }
        container alarm {
          description
            "Alarm management";
          container suppress-event {
            description
              "Suppress all tunnel/LSP alarms";
            leaf disable {
              type empty;
              description
                "Disable alarm suppression";
            }
          }
          leaf soak-time {
            type uint32 {
              range "0..10";
            }
            units "second";
            default "3";
            description
              "Duration of soaking alarms";
          }
          leaf enable-alarm {
            type empty;
            description
              "Enable Transport Profile Alarm";
          }
        }
        container bfd {
          description
            "Configure BFD parameters";
          container min-interval-standby {
            description
              "Hello interval for standby transport profile
               LSPs, either in milli-seconds or in
               micro-seconds";
            leaf interval-standby-ms {
              type uint32 {
                range "3..5000";
              }
              units "millisecond";
              description
                "Hello interval in milli-seconds";
            }
            leaf interval-standby-us {
              type uint32 {
                range "3000..5000000";
              }
              units "microsecond";
              description
                "Hello interval in micro-seconds";
            }
          }
          container min-interval {
            description
              "Hello interval, either in milli-seconds or in
               micro-seconds";
            leaf interval-ms {
              type uint32 {
                range "3..5000";
              }
              units "millisecond";
              description
                "Hello interval in milli-seconds";
            }
            leaf interval-us {
              type uint32 {
                range "3000..5000000";
              }
              units "microsecond";
              description
                "Hello interval in micro-seconds";
            }
          }
          leaf detection-multiplier-standby {
            type uint32 {
              range "2..10";
            }
            description
              "Detect multiplier for standby transport
               profile LSP";
          }
          leaf detection-multiplier {
            type uint32 {
              range "2..10";
            }
            description
              "Detect multiplier";
          }
        }
        container midpoints {
          description
            "MPLS-TP tunnel mid-point table";
          list midpoint {
            key "midpoint-name";
            description
              "Transport profile mid-point identifier";
            container source {
              presence "Indicates a source node is configured.";
              description
                "Node identifier, tunnel identifier and
                 optional global identifier of the source of
                 the LSP";
              leaf node-id {
                type inet:ipv4-address-no-zone;
                description
                  "Node identifier in IPv4 address format";
              }
              leaf tunnel-id {
                type uint32 {
                  range "0..65535";
                }
                mandatory true;
                description
                  "Tunnel identifier in numeric value";
              }
              leaf global-id {
                type uint32 {
                  range "1..65535";
                }
                description
                  "Global identifier in numeric value";
              }
            }
            container destination {
              presence "Indicates a destination node is configured.";
              description
                "Node identifier, tunnel identifier and
                 optional global identifier of the destination
                 of the LSP";
              leaf node-id {
                type inet:ipv4-address-no-zone;
                description
                  "Node identifier in IPv4 address format";
              }
              leaf tunnel-id {
                type uint32 {
                  range "0..65535";
                }
                mandatory true;
                description
                  "Tunnel identifier in numeric value";
              }
              leaf global-id {
                type uint32 {
                  range "1..65535";
                }
                description
                  "Global identifier in numeric value";
              }
            }
            container forward-lsp {
              description
                "Forward transport profile LSP";
              container forward-io-map {
                presence "Indicates a forward-io-map node is configured.";
                description
                  "Label cross-connect of forward transport
                   profile LSP";
                leaf in-label {
                  type uint32 {
                    range "16..4015";
                  }
                  description
                    "MPLS label";
                }
                leaf out-label {
                  type uint32 {
                    range "16..1048575";
                  }
                  mandatory true;
                  description
                    "Outgoing MPLS label";
                }
                leaf out-link {
                  type uint32 {
                    range "1..65535";
                  }
                  mandatory true;
                  description
                    "Transport profile identifier of outgoing
                     link";
                }
              }
              leaf forward-bandwidth {
                type uint32 {
                  range "0..4294967295";
                }
                units "kbit/s";
                description
                  "Bandwidth of forward transport profile LSP";
              }
            }
            container reverse-lsp {
              description
                "none";
              container reverse-io-map {
                presence "Indicates a reverse-io-map node is configured.";
                description
                  "Label cross-connect of reverse transport
                   profile LSP";
                leaf in-label {
                  type uint32 {
                    range "16..4015";
                  }
                  description
                    "MPLS label";
                }
                leaf out-label {
                  type uint32 {
                    range "16..1048575";
                  }
                  mandatory true;
                  description
                    "Outgoing MPLS label";
                }
                leaf out-link {
                  type uint32 {
                    range "1..65535";
                  }
                  mandatory true;
                  description
                    "Transport profile identifier of outgoing
                     link";
                }
              }
              leaf reverse-bandwidth {
                type uint32 {
                  range "0..4294967295";
                }
                units "kbit/s";
                description
                  "Bandwidth of reverse transport profile LSP";
              }
            }
            leaf tunnel-name {
              type string;
              description
                "Tunnel Name";
            }
            leaf lsp-protect {
              type empty;
              description
                "Enable LSP protection";
            }
            leaf lsp-id {
              type uint32 {
                range "0..65535";
              }
              description
                "Numeric identifier";
            }
            leaf midpoint-name {
              type xr:Cisco-ios-xr-string {
                length "1..64";
              }
              description
                "Name of mid-point";
            }
          }
        }
        leaf global-id {
          type uint32 {
            range "1..65535";
          }
          description
            "Transport profile global identifier";
        }
        leaf node-id {
          type inet:ipv4-address-no-zone;
          description
            "Node identifier in IPv4 address format";
        }
      }
      container interfaces {
        description
          "Configure MPLS TE interfaces";
        list interface {
          key "interface-name";
          description
            "Configure an MPLS TE interface";
          container transport-profile-link {
            description
              "MPLS transport profile capable link";
            container links {
              description
                "Transport profile link table";
              list link {
                key "link-id";
                description
                  "Transport profile link";
                leaf link-id {
                  type uint32 {
                    range "1..65535";
                  }
                  description
                    "Numeric link identifier";
                }
                leaf next-hop-type {
                  type Link-next-hop;
                  default "ipv4-address";
                  description
                    "Next hop type";
                }
                leaf next-hop-address {
                  when "../next-hop-type = 'ipv4-address'" {
                    tailf:xpath-root 3;
                    description
                      "../NextHopType = IPV4Address";
                  }
                  type inet:ipv4-address-no-zone;
                  description
                    "Next-hop address in IPv4 format";
                }
              }
            }
          }
          container lcac {
            description
              "LCAC specific MPLS interface configuration";
            container switchings {
              description
                "Set the te-link switching attributes";
              list switching {
                key "switching-id";
                description
                  "The te-link switching attributes";
                leaf encoding {
                  type Mpls-te-switching-encoding;
                  description
                    "Set the local encoding type";
                }
                leaf capability {
                  type Mpls-te-switching-cap;
                  description
                    "Set the local switching capability";
                }
                leaf switching-id {
                  type Mpls-te-switching-index;
                  description
                    "Switching index";
                }
              }
            }
            container flood-area {
              description
                "Set the IGP instance into which this
                 interface is to be flooded (GMPLS only)";
              leaf igp-type {
                type Mpls-lcac-flooding-igp;
                description
                  "IGP type";
              }
              leaf process-name {
                type xr:Cisco-ios-xr-string {
                  length "1..32";
                }
                description
                  "Process name";
              }
              leaf area-id {
                type uint32;
                description
                  "Area ID";
              }
            }
            container attribute-name-xr {
              description
                "Set the interface attribute names";
              leaf-list attribute-name {
                type string;
                max-elements 32;
                description
                  "Array of Attribute Names";
              }
            }
            container attribute-names {
              description
                "Attribute name table";
              list attribute-name {
                key "affinity-index";
                description
                  "Set the interface attribute names";
                leaf affinity-index {
                  type uint32 {
                    range "1..9";
                  }
                  description
                    "Specify the entry index";
                }
                leaf-list value {
                  type string;
                  min-elements 1;
                  max-elements 32;
                  description
                    "Array of Attribute Names";
                }
              }
            }
            container srlgs {
              description
                "Configure SRLG membership for the interface";
              list srlg {
                key "srlg-number";
                description
                  "SRLG membership number";
                leaf srlg-number {
                  type uint32 {
                    range "0..4294967295";
                  }
                  description
                    "SRLG membership number";
                }
              }
            }
            container up-thresholds {
              description
                "Set thresholds for increased resource
                 availability in %";
              leaf-list up-threshold {
                type Mpls-lcac-flooding-threshold-percent-range;
                units "percentage";
                max-elements 14;
                description
                  "Array of up threshold percentage";
              }
            }
            container down-thresholds {
              description
                "Set thresholds for decreased resource
                 availability in %";
              leaf-list down-threshold {
                type Mpls-lcac-flooding-threshold-percent-range;
                units "percentage";
                max-elements 14;
                description
                  "Array of down threshold percentage";
              }
            }
            leaf bfd {
              type empty;
              description
                "Enable use of Bidirectional Forwarding
                 Detection";
            }
            leaf fault-oam-lockout {
              type empty;
              description
                "Lockout protection on the interface for Flex
                 LSP";
            }
            leaf attribute-flags {
              type xr:Hex-integer;
              description
                "Set user defined interface attribute flags";
            }
            leaf enable {
              type empty;
              description
                "Enable MPLS-TE on the link";
            }
            leaf admin-weight {
              type uint32 {
                range "0..4294967295";
              }
              description
                "Set administrative weight for the interface";
            }
          }
          container global-attributes {
            description
              "MPLS TE global interface configuration";
            container backup-tunnels {
              description
                "Configure MPLS TE backup tunnels for this
                 interface";
              list backup-tunnel {
                key "tunnel-name";
                description
                  "Tunnel name";
                leaf tunnel-name {
                  type xr:Cisco-ios-xr-string {
                    length "1..54";
                  }
                  description
                    "Tunnel name";
                }
              }
            }
            container auto-tunnel {
              description
                "Auto tunnel configuration";
              container backup {
                description
                  "Auto tunnel backup configuration";
                container exclude {
                  description
                    "Auto-tunnel backup exclusion criteria";
                  leaf srlg-mode {
                    type Mpls-tesrlg-exclude;
                    description
                      "Set exclude SRLG mode for auto-tunnel
                       backup on this TE link";
                  }
                }
                leaf enable {
                  type empty;
                  description
                    "Enable auto-tunnel backup on this TE link";
                }
                leaf attribute-set {
                  type Attribute-set-name-length;
                  description
                    "The name of attribute set to be applied to
                     this auto backup lsp";
                }
                leaf next-hop-only {
                  type empty;
                  description
                    "Enable NHOP-only mode for auto-tunnel
                     backup on this TE link";
                }
              }
            }
            container backup-paths {
              description
                "Configure MPLS TE backup tunnels for this
                 interface";
              list backup-path {
                key "tunnel-number";
                description
                  "Tunnel interface number";
                leaf tunnel-number {
                  type uint32 {
                    range "0..65535";
                  }
                  description
                    "Tunnel interface number";
                }
              }
            }
          }
          leaf interface-name {
            type xr:Interface-name;
            description
              "Interface name";
          }
        }
      }
      container gmpls-nni {
        description
          "GMPLS-NNI configuration";
        container topology-instances {
          description
            "GMPLS-NNI topology instance table";
          list topology-instance {
            must 'ospf-int or ospfip-addr' {
              tailf:xpath-root 3;
              description
                "OSPFInt or OSPFIPAddr must be present.";
            }
            key "ospf-area-type igp-instance-name igp-type";
            description
              "GMPLS-NNI topology instance configuration";

            grouping TOPOLOGY-INSTANCE-CONTENT {
              description
                "TOPOLOGY INSTANCE CONTENT";
              container controllers {
                description
                  "GMPLS-NNI controllers";
                list controller {
                  key "controller-name";
                  description
                    "Configure a GMPLS NNI controller";
                  container tti-mode {
                    description
                      "Set tandem connection monitoring for the
                       interface";
                    leaf tti-mode-type {
                      type Gmplstti-mode;
                      description
                        "Type of Trail Trace Identifier";
                    }
                    leaf tcmid {
                      when "../tti-mode-type = 'tcm'" {
                        tailf:xpath-root 3;
                        description
                          "../TTIModeType = TCM";
                      }
                      type uint32 {
                        range "1..6";
                      }
                      description
                        "Tandem Connection Monitoring ID for the
                         interface";
                    }
                  }
                  container affinity-names {
                    description
                      "Set the interface affinity names";
                    leaf-list affinity-name {
                      type string;
                      max-elements 32;
                      description
                        "Array of Attribute Names";
                    }
                  }
                  leaf admin-weight {
                    type uint32 {
                      range "0..65535";
                    }
                    description
                      "Set administrative weight for the
                       interface";
                  }
                  leaf enable {
                    type empty;
                    description
                      "Enable GMPLS-NNI on the link";
                  }
                  leaf delay {
                    type uint32 {
                      range "1..16777215";
                    }
                    description
                      "Set link delay for the interface";
                  }
                  leaf controller-name {
                    type xr:Interface-name;
                    description
                      "Controller name";
                  }
                }
              }
            }
            leaf igp-type {
              type Mpls-te-igp-protocol;
              description
                "IGP type";
            }
            leaf igp-instance-name {
              type xr:Cisco-ios-xr-string {
                length "1..40";
              }
              description
                "Name of IGP instance";
            }
            leaf ospf-area-type {
              type Ospf-area-mode;
              description
                "OSPF area format";
            }
            list ospf-int {
              when "../ospf-area-type = 'ospf-int'" {
                tailf:xpath-root 3;
                description
                  "../OSPFAreaType = OSPFInt";
              }
              key "igp-area";
              description
                "ospf int";
              leaf igp-area {
                type uint32;
                description
                  "IGP area";
              }
              uses TOPOLOGY-INSTANCE-CONTENT;
            }
            list ospfip-addr {
              when "../ospf-area-type = 'ospfip-addr'" {
                tailf:xpath-root 3;
                description
                  "../OSPFAreaType = OSPFIPAddr";
              }
              key "address";
              description
                "ospfip addr";
              leaf address {
                type inet:ipv4-address-no-zone;
                description
                  "Area ID if in IP address format";
              }
              uses TOPOLOGY-INSTANCE-CONTENT;
            }
          }
        }
        container tunnel-heads {
          description
            "GMPLS-NNI tunnel-head table";
          list tunnel-head {
            key "tunnel-id";
            description
              "The configuration for a GMPLS NNI tunnel
               head-end";
            container signalled-bandwidth {
              description
                "The existence of this configuration indicates
                 the signalled bandwidth has been set for the
                 tunnel";
              leaf signalled-bandwidth-type {
                type Otn-signaled-bandwidth;
                description
                  "The g.709 signal type requested";
              }
              leaf bitrate {
                when "../signalled-bandwidth-type = 'od-uflex-cbr' or ../signalled-bandwidth-type = 'od-uflex-gfp-resize' or ../signalled-bandwidth-type = 'od-uflex-gfp-not-resize'" {
                  tailf:xpath-root 3;
                  description
                    "../SignalledBandwidthType = ODUflexCBR or
                     ../SignalledBandwidthType =
                     ODUflexGFPResize or .
                     ./SignalledBandwidthType =
                     ODUflexGFPNotResize";
                }
                type uint32;
                units "kbit/s";
                description
                  "Bitrate value in Kbps for ODUflex framing
                   type";
              }
              leaf od-uflex-framing-type {
                when "../signalled-bandwidth-type = 'od-uflex-cbr' or ../signalled-bandwidth-type = 'od-uflex-gfp-resize' or ../signalled-bandwidth-type = 'od-uflex-gfp-not-resize'" {
                  tailf:xpath-root 3;
                  description
                    "../SignalledBandwidthType = ODUflexCBR or
                     ../SignalledBandwidthType =
                     ODUflexGFPResize or .
                     ./SignalledBandwidthType =
                     ODUflexGFPNotResize";
                }
                type Otn-signaled-bandwidth-flex-framing;
                description
                  "Framing type in case of ODUflex signal type";
              }
            }
            container destination {
              description
                "The existence of this configuration indicates
                 the destination has been set for the tunnel";
              leaf destination {
                type inet:ipv4-address-no-zone;
                description
                  "IPV4 tunnel destination";
              }
              leaf destination-type {
                type Otn-destination;
                description
                  "Destination type whether it is unicast or
                   unnumbered";
              }
              leaf interface-if-index {
                type uint32;
                description
                  "Interface index of port";
              }
            }
            container protection-switching {
              description
                "The configuration for a GMPLS NNI tunnel
                 protection switch";
              leaf lockout {
                type Otn-protection-switch-lockout;
                description
                  "The configuration is used to prevent switch
                   over for a particular path type in tunnel";
              }
            }
            container logging {
              description
                "Tunnel event logging";
              leaf active-lsp-message {
                type empty;
                description
                  "Log all tunnel messages for changes in
                   Active LSP";
              }
              leaf homepath-state-message {
                type empty;
                description
                  "Log all messages for changes in state of
                   Homepath of Working LSP";
              }
              leaf signalling-state-message {
                type empty;
                description
                  "Log all tunnel sub-LSP state messages";
              }
              leaf path-change-message {
                type empty;
                description
                  "Log all tunnel messages for changes in
                   path-change";
              }
              leaf static-cross-connect-message {
                type empty;
                description
                  "Log all tunnel messages for static
                   cross-connect messages";
              }
              leaf tunnel-state-message {
                type empty;
                description
                  "Log all tunnel messages for changes in
                   tunnel-state";
              }
              leaf insufficient-bw-message {
                type empty;
                description
                  "Log tunnel messages for insufficient
                   bandwidth";
              }
            }
            container path-options {
              description
                "GMPLS NNI path options";
              list path-option {
                key "preference-level";
                description
                  "The existence of this configuration
                   indicates the path options have been set for
                   the tunnel";
                leaf preference-level {
                  type uint32 {
                    range "1..1000";
                  }
                  description
                    "Preference level for this path option";
                }
                leaf path-type {
                  type Mpls-te-path-option;
                  description
                    "The type of the path option";
                }
                leaf path-id {
                  type uint32 {
                    range "1..65535";
                  }
                  description
                    "The ID of the IP explicit path associated
                     with this option";
                }
                leaf path-name {
                  type string;
                  description
                    "The name of the IP explicit path associated
                     with this option";
                }
                leaf protected-by-preference-level {
                  type uint32 {
                    range "1..1001";
                  }
                  description
                    "Preference level of the protecting explicit
                     path. ";
                }
                leaf restore-by-preference-level {
                  type uint32 {
                    range "1..1000";
                  }
                  description
                    "Preference level of the restore path. ";
                }
                leaf xro-type {
                  type Mpls-te-path-option-xro;
                  mandatory true;
                  description
                    "The route-exclusion type";
                }
                leaf xro-attribute-set-name {
                  type Attribute-set-name-length;
                  description
                    "The name of the XRO attribute set to be
                     used for this path-option";
                }
                leaf affinity-attribute-set-name {
                  type Attribute-set-affinity-name-length;
                  description
                    "The name of the affinity attribute set to
                     be used for this path-option";
                }
                leaf lockdown {
                  type Mpls-te-path-option-property;
                  description
                    "Lockdown properties";
                }
              }
            }
            container static-uni {
              description
                "The existence of this configuration indicates
                 the static UNI endpoints have been set for
                 the tunnel";
              leaf ingress-controller-name {
                type xr:Cisco-ios-xr-string {
                  length "1..255";
                }
                description
                  "Name of  ingress controller";
              }
              leaf egress-controller-if-index {
                type uint32;
                description
                  "Interface index of Egress controller";
              }
              leaf ingress-type {
                type Otn-static-uni;
                description
                  "Ingress type whether it is xconnect or
                   terminated";
              }
              leaf egress-type {
                type Otn-static-uni;
                description
                  "Egress type whether it is xconnect or
                   terminated";
              }
            }
            leaf enable {
              type empty;
              description
                "The existence of this configuration indicates
                 the a new GMPLS NNI tunnel has been enabled";
            }
            leaf announce-srlg {
              type empty;
              description
                "Announce SRLG on term interface for the
                 tunnel";
            }
            leaf restore-lsp-shutdown {
              type empty;
              description
                "The existence of this configuration indicates
                 the restore LSP of tunnel is shutdown";
            }
            leaf current-lsp-shutdown {
              type empty;
              description
                "The existence of this configuration indicates
                 the current/working LSP of tunnel is shutdown";
            }
            leaf path-selection-metric {
              type Mpls-te-path-selection-metric;
              description
                "Path selection configuration for this
                 specific tunnel";
            }
            leaf payload {
              type Otn-payload;
              description
                "The existence of this configuration indicates
                 the Payload type have been set for the tunnel";
            }
            leaf standby-lsp-shutdown {
              type empty;
              description
                "The existence of this configuration indicates
                 the standby/protect LSP of tunnel is shutdown";
            }
            leaf shutdown {
              type empty;
              description
                "The existence of this configuration indicates
                 the tunnel is shutdown";
            }
            leaf path-protection-attribute-set-profile {
              type string {
                length "1..64";
              }
              description
                "The name of the path-protection profile to be
                 included in signalling messages";
            }
            leaf tunnel-id {
              type uint32 {
                range "0..65535";
              }
              description
                "Tunnel ID";
            }
            uses RECORD-ROUTE;
            uses SIGNALLED-NAME;
          }
        }
        leaf path-selection-metric {
          type Mpls-te-path-selection-metric;
          description
            "Path selection configuration for all gmpls nni
             tunnels";
        }
        leaf enable-gmpls-nni {
          type empty;
          description
            "Enable MPLS Traffic Engineering GMPLS-NNI";
        }
      }
      container lcac {
        description
          "LCAC specific MPLS global configuration";
        container bfd {
          description
            "BFD configuration";
          leaf interval {
            type uint32 {
              range "15..200";
            }
            units "millisecond";
            description
              "Hello interval for BFD sessions created by TE";
          }
          leaf detection-multiplier {
            type uint32 {
              range "2..10";
            }
            description
              "Detection multiplier for BFD sessions created
               by TE";
          }
        }
        container flooding-threshold {
          description
            "Configure flooding threshold as percentage of
             total link bandwidth.";
          leaf up-stream {
            type Mpls-percent-range;
            units "percentage";
            description
              "Upward flooding Threshold in percentages of
               total bandwidth";
          }
          leaf down-stream {
            type Mpls-percent-range;
            units "percentage";
            description
              "Downward flooding Threshold in percentages of
               total bandwidth";
          }
        }
        leaf bandwidth-hold-timer {
          type Mpls-lcac-bandwidth-hold-timer-range;
          units "second";
          description
            "Bandwidth hold timer value (seconds)";
        }
        leaf delay-preempt-bundle-capacity-timer {
          type uint32 {
            range "0..300";
          }
          units "second";
          description
            "Bundle capacity preemption timer value
             (seconds)";
        }
        leaf periodic-flooding-timer {
          type uint32 {
            range "0..3600";
          }
          units "second";
          description
            "Periodic flooding value (seconds)";
        }
      }
      leaf enable-traffic-engineering {
        type empty;
        description
          "Enable MPLS Traffic Engineering";
      }
    }
  }
  augment "/ncs:devices/ncs:device/ncs:live-status" {
    container mpls-te {
      tailf:ncs-device-type "netconf";
      tailf:display-when "not(../../ncs:module) or ../../ncs:module[ncs:name='Cisco-IOS-XR-mpls-te-cfg'] or (../../ncs:live-status-protocol[not(ncs:capability)]) or (../../ncs:live-status-protocol/ncs:capability/ncs:module[.='Cisco-IOS-XR-mpls-te-cfg'])";
      description
        "The root of MPLS TE configuration";
      container diff-serv-traffic-engineering {
        description
          "Configure Diff-Serv Traffic-Engineering";
        container classes {
          description
            "Configure Diff-Serv Traffic-Engineering Classes";
          list class {
            key "class-number";
            description
              "DSTE class number";
            leaf class-number {
              type uint32 {
                range "0..7";
              }
              description
                "DS-TE class number";
            }
            leaf class-type {
              // NCS drop when statement
              type uint32 {
                range "0..1";
              }
              // NCS drop default statement
              description
                "Class type number";
            }
            leaf class-priority {
              // NCS drop when statement
              type uint32 {
                range "0..7";
              }
              // NCS drop default statement
              description
                "Class-type priority";
            }
            leaf unused {
              type boolean;
              description
                "TRUE to skip classtype and class priority
                 provisioning FALSE to provision them";
            }
          }
        }
        leaf bandwidth-constraint-model {
          type Bandwidth-constraint;
          description
            "Diff-Serv Traffic-Engineering Bandwidth
             Constraint Model";
        }
        leaf mode-ietf {
          type Ietf-mode;
          description
            "Diff-Serv Traffic-Engineering IETF mode";
        }
      }
      container named-tunnels {
        description
          "Configure MPLS TE tunnel";
        container tunnels {
          description
            "Configure MPLS TE tunnel";
          list tunnel {
            key "tunnel-name tunnel-type";
            description
              "Configure a MPLS TE tunnel";
            container tunnel-attributes {
              description
                "MPLS tunnel attributes";
              container path-setups {
                description
                  "Tunnel path setup table";
                list path-setup {
                  key "path-setup-name";
                  description
                    "Tunnel path setup";
                  container path-computation {
                    presence "Indicates a path-computation node is configured.";
                    description
                      "Path computation method";
                    leaf path-computation-method {
                      type Mpls-te-path-computation-method;
                      // NCS drop mandatory statement
                      description
                        "Path computation method";
                    }
                    leaf explicit-path-name {
                      type string;
                      description
                        "Explicit Path Name";
                    }
                    leaf path-computation-server {
                      type inet:ipv4-address-no-zone;
                      // NCS drop default statement
                      description
                        "Path Computation Server Address";
                    }
                  }
                  leaf preference {
                    type uint32 {
                      range "0..255";
                    }
                    description
                      "Path preference level";
                  }
                  leaf path-setup-name {
                    type xr:Cisco-ios-xr-string;
                    description
                      "Path Name";
                  }
                }
              }
              leaf shutdown {
                type empty;
                description
                  "shutdown the tunnel";
              }
              uses live_ncs_FORWARD-CLASS;
              uses live_ncs_TUNNEL-PATH-SELECTION;
              uses live_ncs_AUTO-BANDWIDTH;
              uses live_ncs_PRIORITY;
              uses live_ncs_DESTINATION;
              uses live_ncs_RECORD-ROUTE;
              uses live_ncs_AFFINITY-MASK;
              uses live_ncs_FORWARDING-ADJACENCY;
              uses live_ncs_LOGGING;
              uses live_ncs_BANDWIDTH;
              uses live_ncs_AUTOROUTE;
              uses live_ncs_PATH-SELECTION-METRIC;
              uses live_ncs_NEW-STYLE-AFFINITY-TABLE;
              uses live_ncs_SOFT-PREEMPTION;
              uses live_ncs_FAST-REROUTE;
              uses live_ncs_LOAD-SHARE;
            }
            container tunnel-id {
              presence "Indicates a tunnel-id node is configured.";
              description
                "Set the tunnel ID";
              leaf tunnel-id-type {
                type Mpls-te-tunnel-id;
                // NCS drop mandatory statement
                description
                  "Tunnel ID Type";
              }
              leaf tunnel-id {
                type uint32 {
                  range "0..65535";
                }
                description
                  "Tunnel ID";
              }
            }
            leaf tunnel-name {
              type xr:Cisco-ios-xr-string {
                length "1..54";
              }
              description
                "Tunnel name";
            }
            leaf tunnel-type {
              type Mpls-te-config-tunnel;
              description
                "Tunnel Type";
            }
          }
        }
        leaf enable {
          type empty;
          description
            "Enable Named Tunnels";
        }
      }
      container gmpls-uni {
        description
          "GMPLS-UNI configuration";
        container timers {
          description
            "GMPLS-UNI timer configuration";
          container path-option-timers {
            description
              "GMPLS-UNI path-option timer configuration";
            container holddown {
              description
                "GMPLS-UNI path-option holddown timer
                 configuration";
              leaf minimum {
                type uint32 {
                  range "5..3600";
                }
                units "second";
                description
                  "Minimum holddown (seconds)";
              }
              leaf maximum {
                type uint32 {
                  range "5..3600";
                }
                units "second";
                description
                  "Maximum holddown (seconds)";
              }
            }
          }
        }
        container controllers {
          description
            "GMPLS-UNI controllers";
          list controller {
            key "controller-name";
            description
              "Configure a GMPLS controller";
            container announce {
              description
                "Announce discovered tunnel properties to
                 system";
              leaf srl-gs {
                type empty;
                description
                  "Enable announcement of discovered SRLGs";
              }
            }
            container controller-logging {
              description
                "Controller logging";
              leaf discovered-srlg-change-logging {
                type empty;
                description
                  "Enable logging of changes to of discovered
                   SRLGs";
              }
            }
            container gmpls-unitunnel-head {
              description
                "GMPLS-UNI tunnel-head properties";
              container path-options {
                description
                  "Path-option configuration";
                list path-option {
                  key "preference-level";
                  description
                    "A Path-option";
                  leaf preference-level {
                    type uint32 {
                      range "1..1000";
                    }
                    description
                      "Preference level for this path option";
                  }
                  leaf path-type {
                    type Mpls-te-path-option;
                    // NCS drop mandatory statement
                    description
                      "The type of the path option";
                  }
                  leaf path-id {
                    type uint32 {
                      range "1..65535";
                    }
                    // NCS drop default statement
                    description
                      "The ID of the explicit path associated
                       with this option";
                  }
                  leaf path-name {
                    type string;
                    description
                      "The name of the explicit path associated
                       with this option";
                  }
                  leaf xro-type {
                    type Mpls-te-path-option-xro;
                    // NCS drop mandatory statement
                    description
                      "The route-exclusion type";
                  }
                  leaf xro-attribute-set-name {
                    type Attribute-set-name-length;
                    description
                      "The name of the XRO attribute set to be
                       used for this path-option";
                  }
                  leaf lockdown {
                    type Mpls-te-path-option-property;
                    // NCS drop mandatory statement
                    description
                      "Path option properties: must be Lockdown";
                  }
                  leaf verbatim {
                    type Mpls-te-path-option-property;
                    // NCS drop default statement
                    description
                      "Path option properties: must be verbatim
                       if set";
                  }
                  leaf signaled-label {
                    type Mpls-te-signaled-label;
                    // NCS drop default statement
                    description
                      "Signaled label type";
                  }
                  leaf dwdm-channel {
                    type uint32 {
                      range "1..89";
                    }
                    // NCS drop default statement
                    description
                      "DWDM channel number";
                  }
                }
              }
              container recording {
                description
                  "Tunnel property recording";
                leaf srlg {
                  type empty;
                  description
                    "Enable SRLG-recording during signaling";
                }
              }
              container logging {
                description
                  "Tunnel event logging";
                uses live_ncs_STATE-MESSAGE;
              }
              leaf tunnel-id {
                type uint32 {
                  range "0..65535";
                }
                description
                  "GMPLS-UNI head tunnel-id";
              }
              leaf enable {
                type empty;
                description
                  "Set link as a GMPLS tunnel head";
              }
              leaf destination {
                type inet:ipv4-address-no-zone;
                description
                  "Set the destination of the tunnel";
              }
              uses live_ncs_PRIORITY;
              uses live_ncs_RECORD-ROUTE;
              uses live_ncs_SIGNALLED-NAME;
            }
            leaf enable {
              type empty;
              description
                "Enable GMPLS-UNI on the link";
            }
            leaf controller-name {
              type xr:Interface-name;
              description
                "Controller name";
            }
          }
        }
      }
      container global-attributes {
        description
          "Configure MPLS TE global attributes";
        container auto-tunnel {
          description
            "Configure auto-tunnels feature";
          container pcc {
            description
              "Configure auto-tunnel PCC (Path Computation
               Client) feature";
            uses live_ncs_TUNNEL-RANGE;
          }
          container p2p-auto-tunnel {
            description
              "Configure P2P auto-tunnel feature";
            uses live_ncs_TUNNEL-RANGE;
          }
          container backup {
            description
              "Configure auto-tunnel backup feature";
            leaf affinity-ignore {
              type empty;
              description
                "Ignore affinity during CSPF for auto backup
                 tunnels";
            }
            uses live_ncs_TIMERS;
            uses live_ncs_TUNNEL-RANGE;
          }
          container mesh {
            description
              "Configure auto-tunnel mesh feature";
            container mesh-groups {
              description
                "Configure auto-tunnel mesh group";
              list mesh-group {
                key "mesh-group-id";
                description
                  "Auto-mesh group identifier";
                leaf destination-list {
                  type Destination-list-name-length;
                  description
                    "The name of prefix-list to be applied to
                     this destination-list";
                }
                leaf disable {
                  type empty;
                  description
                    "Disables mesh group";
                }
                leaf attribute-set {
                  type Attribute-set-name-length;
                  description
                    "The name of auto-mesh attribute set to be
                     applied to this group";
                }
                leaf one-hop {
                  type empty;
                  description
                    "Automatically create tunnel to all
                     next-hops";
                }
                leaf mesh-group-id {
                  type Mesh-group-id;
                  description
                    "Mesh group ID";
                }
              }
            }
            uses live_ncs_TIMERS;
            uses live_ncs_TUNNEL-RANGE;
          }
          container p2mp-auto-tunnel {
            description
              "Configure P2MP auto-tunnel feature";
            uses live_ncs_TUNNEL-RANGE;
          }
        }
        container hardware-out-of-resource {
          description
            "Configure HW OOR processing in MPLS-TE";
          container oor-red-state {
            description
              "Configuration for HW OOR Red State";
            uses live_ncs_OOR-NODE-PROTECTION-DISABLE;
            uses live_ncs_OOR-AVAILABLE-BANDWIDTH-PERCENTAGE;
            uses live_ncs_OOR-ACCEPT-LSP-MIN-BANDWIDTH;
            uses live_ncs_OOR-ACCEPT-REOPT-LSP;
            uses live_ncs_OOR-METRIC-TE-PENALTY;
          }
          container oor-yellow-state {
            description
              "Configuration for HW OOR Yellow State";
            uses live_ncs_OOR-NODE-PROTECTION-DISABLE;
            uses live_ncs_OOR-AVAILABLE-BANDWIDTH-PERCENTAGE;
            uses live_ncs_OOR-ACCEPT-LSP-MIN-BANDWIDTH;
            uses live_ncs_OOR-ACCEPT-REOPT-LSP;
            uses live_ncs_OOR-METRIC-TE-PENALTY;
          }
          container oor-green-state {
            description
              "Configuration for HW OOR Green State";
            leaf oor-recovery-duration {
              type uint32 {
                range "0..10080";
              }
              units "minute";
              // NCS drop default statement
              description
                "Period of time (minutes) during which the
                 action in Green state are applied. After this
                 period, the processing in TE goes back to
                 normal state";
            }
            uses live_ncs_OOR-NODE-PROTECTION-DISABLE;
            uses live_ncs_OOR-AVAILABLE-BANDWIDTH-PERCENTAGE;
            uses live_ncs_OOR-ACCEPT-LSP-MIN-BANDWIDTH;
            uses live_ncs_OOR-ACCEPT-REOPT-LSP;
            uses live_ncs_OOR-METRIC-TE-PENALTY;
          }
        }
        container secondary-router-ids {
          description
            "Configure MPLS TE Secondary Router ID";
          list secondary-router-id {
            key "secondary-router-id-value";
            description
              "Secondary Router ID";
            leaf secondary-router-id-value {
              type inet:ipv4-address-no-zone;
              description
                "Secondary TE Router ID";
            }
          }
        }
        container srlg {
          description
            "Configure SRLG values and MPLS-TE properties";
          container names {
            description
              "Configure SRLG identified by names";
            list name {
              key "srlg-name";
              description
                "SRLG name and its MPLS-TE properties";
              container static-srlg-members {
                description
                  "Configure static SRLG members list";
                list static-srlg-member {
                  key "from-address";
                  description
                    "A mapping of the local static SRLG member";
                  leaf from-address {
                    type inet:ipv4-address-no-zone;
                    description
                      "From address";
                  }
                  leaf to-address {
                    type inet:ipv4-address-no-zone;
                    // NCS drop mandatory statement
                    description
                      "To Addres";
                  }
                }
              }
              leaf admin-weight {
                type uint32;
                description
                  "Administrative weight for the SRLG value";
              }
              leaf srlg-name {
                type xr:Cisco-ios-xr-string {
                  length "1..64";
                }
                description
                  "SRLG membership name";
              }
            }
          }
          leaf default-admin-weight {
            type uint32;
            // NCS drop default statement
            description
              "Default Admin weight any SRLG value that does
               not have one";
          }
          leaf enable {
            type empty;
            description
              "Enter SRLG property configuration";
          }
        }
        container queues {
          description
            "Configure MPLS TE route priority";
          list queue {
            key "role";
            description
              "Configure route priority queue value";
            leaf role {
              type Route-priority-role;
              description
                "Route Priority Tunnel Role";
            }
            leaf value {
              type uint32 {
                range "0..12";
              }
              // NCS drop mandatory statement
              description
                "Route priority queue value";
            }
          }
        }
        container mib {
          description
            "MPLS-TE MIB properties";
          leaf midpoint-lsp-stats-collection-disable {
            type empty;
            description
              "Disables mib midpoint LSP traffic stats
               collection";
          }
        }
        container attribute-set {
          description
            "Attribute AttributeSets";
          container path-option-attributes {
            description
              "Path Option Attribute-Set Table";
            list path-option-attribute {
              key "attribute-set-name";
              description
                "Path Option Attribute";
              container bfd-reverse-path {
                presence "Indicates a bfd-reverse-path node is configured.";
                description
                  "Configure BFD reverse path";
                leaf bfd-reverse-path-type {
                  type Bfd-reverse-path;
                  description
                    "BFD reverse path type";
                }
                leaf binding-label {
                  type uint32 {
                    range "0..1048575";
                  }
                  // NCS drop mandatory statement
                  description
                    "BFD reverse path binding label";
                }
              }
              container att-path-option-path-selection {
                description
                  "Configure path selection properties";
                leaf path-selection-exclude-list {
                  type string {
                    length "1..64";
                  }
                  description
                    "Path selection exclude list name
                     configuration";
                }
                uses live_ncs_ENABLE;
                uses live_ncs_PATH-SELECTION-DELAY-LIMIT;
                uses live_ncs_INVALIDATION;
                uses live_ncs_PATH-SELECTION-COST-LIMIT;
              }
              leaf attribute-set-name {
                type Attribute-set-name-length;
                description
                  "Attribute Set Name";
              }
              uses live_ncs_PCE;
              uses live_ncs_AFFINITY-MASK;
              uses live_ncs_BANDWIDTH;
              uses live_ncs_NEW-STYLE-AFFINITY-TABLE;
            }
          }
          container p2mpte-attributes {
            description
              "P2MP-TE Tunnel AttributeSets Table";
            list p2mpte-attribute {
              key "attribute-set-name";
              description
                "P2MP-TE Tunnel Attribute";
              leaf attribute-set-name {
                type Attribute-set-name-length;
                description
                  "Attribute Set Name";
              }
              uses live_ncs_INTERFACE-BANDWIDTH;
              uses live_ncs_PRIORITY;
              uses live_ncs_RECORD-ROUTE;
              uses live_ncs_AFFINITY-MASK;
              uses live_ncs_BANDWIDTH;
              uses live_ncs_PATH-SELECTION;
              uses live_ncs_NEW-STYLE-AFFINITY-TABLE;
              uses live_ncs_FAST-REROUTE;
              uses live_ncs_MPLS-MTE-TUNNEL-CFG-LOGGING;
            }
          }
          container p2p-te-attributes {
            description
              "P2P-TE Tunnel AttributeSets Table";
            list p2p-te-attribute {
              key "attribute-set-name";
              description
                "P2P-TE Tunnel Attribute";
              container path-selection {
                description
                  "Configure path selection properties";
                container segment-routing-prepend {
                  description
                    "Deprecated";
                  container indexes {
                    description
                      "Segment routing prepend index table";
                    list index {
                      key "index-number";
                      description
                        "Prepend index information";
                      leaf index-number {
                        type uint32 {
                          range "1..10";
                        }
                        description
                          "Index number";
                      }
                      leaf prepend-type {
                        type Sr-prepend;
                        // NCS drop default statement
                        description
                          "Prepend type";
                      }
                      leaf mpls-label {
                        type uint32;
                        // NCS drop default statement
                        description
                          "MPLS Label";
                      }
                    }
                  }
                  leaf enable {
                    type empty;
                    description
                      "Enter path selection segment routing
                       prepend submode";
                  }
                }
                container invalidation {
                  description
                    "Deprecated";
                  leaf invalidation-timer {
                    type uint32 {
                      range "0..60000";
                    }
                    units "millisecond";
                    description
                      "Path selection invalidation timer value
                       (milliseconds)";
                  }
                  leaf invalidation-timer-expire-type {
                    type Mpls-te-path-selection-invalidation-timer-expire;
                    // NCS drop default statement
                    description
                      "Path selection invalidation timer expire
                       type";
                  }
                }
                leaf path-selection-metric {
                  type Mpls-te-path-selection-metric;
                  description
                    "Path selection metric to use in path
                     calculation";
                }
                leaf path-selection-segment-routing-adjacency-protection {
                  type Mpls-te-path-selection-segment-routing-adjacency-protection;
                  description
                    "Segment routing adjacency protection type
                     to use in path calculation";
                }
                uses live_ncs_ENABLE;
              }
              leaf attribute-set-name {
                type Attribute-set-name-length;
                description
                  "Attribute Set Name";
              }
              uses live_ncs_PCE;
              uses live_ncs_AFFINITY-MASK;
              uses live_ncs_LOGGING;
              uses live_ncs_NEW-STYLE-AFFINITY-TABLE;
            }
          }
          container auto-backup-attributes {
            description
              "Auto-backup Tunnel Attribute Table";
            list auto-backup-attribute {
              key "attribute-set-name";
              description
                "Auto-backup Tunnel Attribute";
              container signalled-name {
                description
                  "Signalled name";
                leaf name {
                  type string;
                  description
                    "Signalled name";
                }
                leaf source-type {
                  type Mpls-te-sig-name-option;
                  description
                    "Source address or name";
                }
                leaf protected-interface-type {
                  type Mpls-te-sig-name-option;
                  description
                    "Protected-interface address or name";
                }
                leaf mp-address {
                  type boolean;
                  description
                    "Set if merge-point address is to be
                     appended";
                }
              }
              container auto-backup-logging {
                description
                  "Log tunnel LSP messages";
                uses live_ncs_BANDWIDTH-CHANGE-MESSAGE;
                uses live_ncs_REOPTIMIZE-ATTEMPTS-MESSAGE;
                uses live_ncs_STATE-MESSAGE;
                uses live_ncs_REOPTIMIZED-MESSAGE;
              }
              leaf attribute-set-name {
                type Attribute-set-name-length;
                description
                  "Attribute Set Name";
              }
              uses live_ncs_PRIORITY;
              uses live_ncs_RECORD-ROUTE;
              uses live_ncs_AFFINITY-MASK;
              uses live_ncs_PATH-SELECTION;
              uses live_ncs_POLICY-CLASSES;
              uses live_ncs_NEW-STYLE-AFFINITY-TABLE;
            }
          }
          container otn-pp-attributes {
            description
              "OTN Path Protection Attributes table";
            list otn-pp-attribute {
              key "attribute-set-name";
              description
                "OTN Path Protection Attribute";
              container revert-schedule-names {
                description
                  "Specify APS revert schedule";
                list revert-schedule-name {
                  key "schedule-name";
                  description
                    "Name Identifier for revert schedule";
                  container schedule-duration {
                    presence "Indicates a schedule-duration node is configured.";
                    description
                      "Set duration in format hh:mm";
                    leaf hour {
                      type uint32 {
                        range "0..167";
                      }
                      // NCS drop mandatory statement
                      description
                        "Hour of day";
                    }
                    leaf minutes {
                      type uint32 {
                        range "0..59";
                      }
                      // NCS drop mandatory statement
                      description
                        "Minute of the hour";
                    }
                  }
                  container schedule-date {
                    presence "Indicates a schedule-date node is configured.";
                    description
                      "Set date in format hh:mm MMM DD YYYY";
                    leaf hour {
                      type uint32 {
                        range "0..23";
                      }
                      // NCS drop mandatory statement
                      description
                        "Hour of day";
                    }
                    leaf minutes {
                      type uint32 {
                        range "0..59";
                      }
                      // NCS drop mandatory statement
                      description
                        "Minute of the hour";
                    }
                    leaf month {
                      type uint32 {
                        range "0..11";
                      }
                      // NCS drop mandatory statement
                      description
                        "Month of the year";
                    }
                    leaf day {
                      type uint32 {
                        range "1..31";
                      }
                      // NCS drop mandatory statement
                      description
                        "Day of the month";
                    }
                    leaf year {
                      type uint32 {
                        range "2015..2035";
                      }
                      // NCS drop mandatory statement
                      description
                        "Year";
                    }
                  }
                  leaf revert-schedule-max-tries {
                    type uint32 {
                      range "1..2016";
                    }
                    description
                      "Revert Schedule Max tries";
                  }
                  leaf sch-name-enable {
                    type empty;
                    description
                      "Schedule name enable object";
                  }
                  leaf revert-schedule-frequency {
                    type uint32 {
                      range "1..3";
                    }
                    description
                      "Frequency set as Once, Daily, Weekly";
                  }
                  leaf schedule-name {
                    type xr:Cisco-ios-xr-string {
                      length "1..254";
                    }
                    description
                      "Enter 64 characters for revert schedule
                       name";
                  }
                }
              }
              container sub-network-connection-mode {
                description
                  "Sub-network connection mode";
                leaf connection-mode {
                  type Mpls-te-otn-snc-mode;
                  description
                    "The sub-network connection mode";
                }
                leaf connection-monitoring-mode {
                  type uint32 {
                    range "1..6";
                  }
                  description
                    "Tandem Connection Monitoring ID for the
                     interface";
                }
              }
              container timers {
                description
                  "Timers";
                leaf aps-wait-to-restore {
                  type uint32 {
                    range "0..720";
                  }
                  units "second";
                  description
                    "G.709 OTN path protection wait to restore
                     timer in seconds";
                }
                leaf aps-hold-off {
                  type uint32 {
                    range "100..10000";
                  }
                  units "millisecond";
                  description
                    "G.709 OTN path protection hold-off timer in
                     milliseconds";
                }
              }
              leaf aps-protection-mode {
                type Mpls-te-otn-aps-protection-mode;
                description
                  "The APS protecion mode";
              }
              leaf aps-restoration-style {
                type Mpls-te-otn-aps-restoration-style;
                description
                  "The APS restoration style";
              }
              leaf aps-protection-type {
                type Mpls-te-otn-aps-protection;
                description
                  "The APS protecion type";
              }
              leaf attribute-set-name {
                type Attribute-set-name-length;
                description
                  "Attribute Set Name";
              }
              uses live_ncs_PATH-SELECTION;
            }
          }
          container auto-mesh-attributes {
            description
              "Auto-mesh Tunnel AttributeSets Table";
            list auto-mesh-attribute {
              key "attribute-set-name";
              description
                "Auto-mesh Tunnel Attribute";
              container auto-mesh-logging {
                description
                  "Log tunnel LSP messages";
                uses live_ncs_BANDWIDTH-CHANGE-MESSAGE;
                uses live_ncs_REOPTIMIZE-ATTEMPTS-MESSAGE;
                uses live_ncs_REROUTE-MESSSAGE;
                uses live_ncs_STATE-MESSAGE;
                uses live_ncs_INSUFFICIENT-BW-MESSAGE;
                uses live_ncs_REOPTIMIZED-MESSAGE;
                uses live_ncs_PCALC-FAILURE-MESSAGE;
              }
              leaf autoroute-announce {
                type empty;
                description
                  "Enable autoroute announce";
              }
              leaf attribute-set-name {
                type Attribute-set-name-length;
                description
                  "Attribute Set Name";
              }
              uses live_ncs_INTERFACE-BANDWIDTH;
              uses live_ncs_FORWARD-CLASS;
              uses live_ncs_PRIORITY;
              uses live_ncs_RECORD-ROUTE;
              uses live_ncs_AFFINITY-MASK;
              uses live_ncs_BANDWIDTH;
              uses live_ncs_PATH-SELECTION;
              uses live_ncs_COLLECTION-ONLY;
              uses live_ncs_POLICY-CLASSES;
              uses live_ncs_NEW-STYLE-AFFINITY-TABLE;
              uses live_ncs_SOFT-PREEMPTION;
              uses live_ncs_FAST-REROUTE;
              uses live_ncs_LOAD-SHARE;
            }
          }
          container xro-attributes {
            description
              "XRO Tunnel Attributes table";
            list xro-attribute {
              key "attribute-set-name";
              description
                "XRO Attribute";
              container path-diversity {
                description
                  "Path diversity";
                container srlgs {
                  description
                    "SRLG-based path diversity";
                  list srlg {
                    key "srlg";
                    description
                      "SRLG-based path-diversity element";
                    leaf srlg {
                      type uint32 {
                        range "0..4294967295";
                      }
                      description
                        "SRLG";
                    }
                    leaf conformance {
                      type Mpls-te-path-diversity-conformance;
                      // NCS drop mandatory statement
                      description
                        "The diversity conformance requirements";
                    }
                  }
                }
                container lsp {
                  description
                    "LSP-based path diversity";
                  container fecs {
                    description
                      "FEC LSP-based path diversity";
                    list fec {
                      key "source destination tunnel-id extended-tunnel-id lsp-id";
                      description
                        "LSP-based path-diversity, referenced by
                         FEC";
                      leaf source {
                        type inet:ipv4-address-no-zone;
                        description
                          "Source address";
                      }
                      leaf destination {
                        type inet:ipv4-address-no-zone;
                        description
                          "Destination address";
                      }
                      leaf tunnel-id {
                        type uint32 {
                          range "0..65535";
                        }
                        description
                          "Tunnel id";
                      }
                      leaf extended-tunnel-id {
                        type inet:ipv4-address-no-zone;
                        description
                          "Extended tunnel-id";
                      }
                      leaf lsp-id {
                        type uint32 {
                          range "0..65535";
                        }
                        description
                          "LSP id";
                      }
                      leaf conformance {
                        type Mpls-te-path-diversity-conformance;
                        // NCS drop mandatory statement
                        description
                          "The diversity conformance requirements";
                      }
                    }
                  }
                }
              }
              leaf attribute-set-name {
                type Attribute-set-name-length;
                description
                  "Attribute Set Name";
              }
              uses live_ncs_PATH-SELECTION;
            }
          }
        }
        container bfd-over-lsp {
          description
            "BFD over MPLS TE Global Configurations";
          container tail {
            description
              "BFD over LSP Tail Global Configurations";
            leaf multiplier {
              type uint32 {
                range "3..10";
              }
              description
                "Specify BFD over LSP tail multiplier";
            }
            leaf minimum-interval {
              type uint32 {
                range "50..30000";
              }
              description
                "Specify BFD over LSP tail minimum interval";
            }
          }
          container head {
            description
              "BFD over LSP Head Global Configurations";
            leaf reopt-timeout {
              type uint32 {
                range "120..4294967295";
              }
              description
                "BFD session down reopt timeout";
            }
            leaf down-action {
              type Mpls-te-bfd-session-down-action;
              description
                "Specify BFD session down action";
            }
          }
        }
        container bandwidth-accounting {
          description
            "Bandwidth accounting configuration data";
          container application {
            description
              "Bandwidth accounting application configuration
               data";
            leaf application-enforced {
              type boolean;
              // NCS drop default statement
              description
                "This object enables the application";
            }
            leaf application-interval {
              type uint32 {
                range "30..1800";
              }
              units "second";
              // NCS drop default statement
              description
                "This object sets the application interval in
                 seconds for bandwidth accounting. Default to
                 180 seconds.";
            }
          }
          container account-flooding-threshold {
            description
              "This object sets the flooding threshold as
               percentage of total link bandwidth for
               bandwidth accounting. Default to 10%, 10%";
            leaf up-threshold {
              type Mpls-percent-range;
              units "percentage";
              // NCS drop default statement
              description
                "Upward flooding Threshold in percentages of
                 total bandwidth";
            }
            leaf down-threshold {
              type Mpls-percent-range;
              units "percentage";
              // NCS drop default statement
              description
                "Downward flooding Threshold in percentages of
                 total bandwidth";
            }
          }
          leaf sampling-interval {
            type uint32 {
              range "10..600";
            }
            units "second";
            // NCS drop default statement
            description
              "This object sets the sampling interval in
               seconds for bandwidth accounting. Default to
               60 seconds.";
          }
          leaf adjustment-factor {
            type uint32 {
              range "0..200";
            }
            units "percentage";
            // NCS drop default statement
            description
              "This object sets the percentage adjustment
               factor for the non RSVP-TE bandwidth
               accounting.  Default is 100%.";
          }
          leaf collection-type-rsvp-te {
            type boolean;
            // NCS drop default statement
            description
              "This object enables the bandwidth accounting
               RSVP-TE sample collection.";
          }
          leaf enable {
            type empty;
            description
              "This object controls whether BW accounting is
               enabled. This object must be set before
               setting any other objects  under the
               BandwidthAccounting class.";
          }
        }
        container pce-attributes {
          description
            "Configuration MPLS TE PCE attributes";
          container pce-stateful {
            description
              "PCE Stateful";
            container stateful-timers {
              description
                "Configure Stateful PCE (Path Computation
                 Element) timers";
              leaf redelegation-timeout {
                type uint32 {
                  range "0..3600";
                }
                units "second";
                // NCS drop default statement
                description
                  "Timer for static tunnel redelegation in
                   seconds, default is 180 seconds";
              }
              leaf state-timeout {
                type uint32 {
                  range "0..3600";
                }
                units "second";
                // NCS drop default statement
                description
                  "State timeout for LSPs without delegation in
                   seconds, zero means immediate removal,
                   default is 180 seconds";
              }
            }
            leaf fast-repair {
              type empty;
              description
                "Enable reoptimization by PCC after path
                 failures";
            }
            leaf instantiation {
              type empty;
              description
                "PCE stateful instantiation capability";
            }
            leaf cisco-extension {
              type empty;
              description
                "Enable processing of PCEP Cisco extension";
            }
            leaf delegation {
              type empty;
              description
                "Delegate all statically configured tunnels";
            }
            leaf autoroute-announce {
              type empty;
              description
                "Enable autoroute announce for PCE
                 instantiated tunnels";
            }
            leaf report {
              type empty;
              description
                "Report all statically configured tunnels";
            }
            leaf enable {
              type empty;
              description
                "PCE stateful capability";
            }
          }
          container timer {
            description
              "Configure PCE (Path Computation Element)
               timers";
          }
          container peers {
            description
              "Configure PCE peers";
            list peer {
              key "pce-peer-address";
              description
                "PCE peer";
              leaf pce-peer-address {
                type inet:ipv4-address-no-zone;
                description
                  "Address of PCE Peer";
              }
              uses live_ncs_PASSWORD;
              uses live_ncs_KEYCHAIN;
              uses live_ncs_PRECEDENCE;
            }
          }
          container logging {
            description
              "Configure PCE (Path Computation Element)
               logging feature";
            container events {
              description
                "Configure logging events";
              leaf peer-status {
                type empty;
                description
                  "Peer status changes logging";
              }
            }
          }
          leaf request-timeout {
            type uint32 {
              range "5..100";
            }
            units "second";
            // NCS drop default statement
            description
              "Request timeout value in seconds";
          }
          leaf reoptimize-period {
            type uint32 {
              range "60..604800";
            }
            units "second";
            // NCS drop default statement
            description
              "PCE reoptimization period for PCE-based paths";
          }
          leaf address {
            type inet:ipv4-address-no-zone;
            description
              "Address of this PCE";
          }
          leaf deadtimer {
            type uint32 {
              range "0..255";
            }
            units "second";
            // NCS drop default statement
            description
              "Deadtimer interval in seconds";
          }
          leaf keepalive {
            type uint32 {
              range "0..255";
            }
            units "second";
            // NCS drop default statement
            description
              "Keepalive interval in seconds";
          }
          leaf keepalive-tolerance {
            type uint32 {
              range "0..255";
            }
            units "second";
            // NCS drop default statement
            description
              "Keepalive interval tolerance in seconds";
          }
          leaf peer-source-addr {
            type inet:ipv4-address-no-zone;
            description
              "PCE Peer Source Address";
          }
          leaf speaker-entity-id {
            type string {
              length "1..256";
            }
            description
              "PCE speaker entity identifier";
          }
          leaf segment-routing {
            type empty;
            description
              "Always set to true";
          }
          uses live_ncs_PASSWORD;
          uses live_ncs_KEYCHAIN;
          uses live_ncs_PRECEDENCE;
        }
        container lsp-out-of-resource {
          description
            "Configure LSP OOR attributes in MPLS-TE";
          container lsp-oor-red-state {
            description
              "Configuration for LSP OOR Red/Major State";
            uses live_ncs_ALL-TRANSIT-LSP-THRESHOLD;
            uses live_ncs_UNPROTECTED-TRANSIT-LSP-THRESHOLD;
          }
          container lsp-oor-yellow-state {
            description
              "Configuration for LSP OOR Yellow/Minor State";
            uses live_ncs_ALL-TRANSIT-LSP-THRESHOLD;
            uses live_ncs_UNPROTECTED-TRANSIT-LSP-THRESHOLD;
          }
        }
        container soft-preemption {
          description
            "Soft preemption configuration data";
          leaf timeout {
            type uint32 {
              range "1..300";
            }
            units "second";
            // NCS drop default statement
            description
              "This object sets the timeout in seconds before
               hard preemption is triggered.";
          }
          leaf frr-rewrite {
            type empty;
            description
              "This object controls whether FRR rewrite
               during soft preemption is enabled.";
          }
          leaf enable {
            type boolean;
            description
              "This object controls whether soft preemption
               is enabled. This object must be set before
               setting any other objects under the
               SoftPreemption class.";
          }
        }
        container fast-reroute {
          description
            "Configure fast reroute attributes";
          container timers {
            description
              "Configure fast reroute timers";
            leaf hold-backup {
              type uint32 {
                range "0..604800";
              }
              units "second";
              description
                "Seconds before backup declared UP (0 disables
                 hold-timer)";
            }
            leaf promotion {
              type uint32 {
                range "0..604800";
              }
              units "second";
              description
                "The value of the promotion timer in seconds";
            }
          }
        }
        container path-selection {
          description
            "Path selection configuration";
          container loose-metrics {
            description
              "Path selection Loose ERO Metric Class
               configuration";
            list loose-metric {
              key "class-type";
              description
                "Path selection Loose ERO Metric configuration";
              leaf class-type {
                type uint32 {
                  range "0..7";
                }
                description
                  "Path Selection class Type";
              }
              leaf metric-type {
                type Mpls-te-path-selection-metric;
                // NCS drop mandatory statement
                description
                  "Metric to use for ERO Expansion";
              }
            }
          }
          container invalidation {
            description
              "Deprecated";
            leaf path-invalidation-timeout {
              type uint32 {
                range "0..60000";
              }
              description
                "Path Invalidation Timeout";
            }
            leaf path-invalidation-action {
              type Path-invalidation-action;
              description
                "Path Invalidation Action";
            }
          }
          container ignore-overload-role {
            description
              "Path selection to ignore overload node during
               CSPF";
            leaf head {
              type boolean;
              description
                "Set if the OL-bit is to be applied to tunnel
                 heads";
            }
            leaf mid {
              type boolean;
              description
                "Set if the OL-bit is to be applied to tunnel
                 midpoints";
            }
            leaf tail {
              type boolean;
              description
                "Set if the OL-bit is to be applied to tunnel
                 tails";
            }
          }
          container loose-affinities {
            description
              "Path selection Loose ERO Affinity Class
               configuration";
            list loose-affinity {
              key "class-type";
              description
                "Path selection Loose ERO Affinity
                 configuration";
              leaf class-type {
                type uint32 {
                  range "0..7";
                }
                description
                  "Path Selection class Type";
              }
              leaf affinity {
                type xr:Hex-integer;
                description
                  "Affinity flags";
              }
              leaf mask {
                type xr:Hex-integer;
                description
                  "Affinity mask";
              }
            }
          }
          leaf cost-limit {
            type uint32 {
              range "1..4294967295";
            }
            description
              "Path selection cost limit configuration for
               all tunnels";
          }
          leaf tiebreaker {
            type Mpls-te-path-selection-tiebreaker;
            description
              "CSPF tiebreaker to use in path calculation";
          }
          leaf metric {
            type Mpls-te-path-selection-metric;
            description
              "Metric to use in path calculation";
          }
          leaf loose-domain-match {
            type boolean;
            description
              "Use only the IGP instance of the incoming
               interface";
          }
          leaf delay-limit {
            type uint32 {
              range "1..4294967295";
            }
            description
              "Path selection delay limit configuration for
               p2p tunnels (usec)";
          }
        }
        container affinity-mappings {
          description
            "Affinity Mapping Table configuration";
          list affinity-mapping {
            key "affinity-name";
            description
              "Affinity Mapping configuration";
            leaf affinity-name {
              type xr:Cisco-ios-xr-string {
                length "1..32";
              }
              description
                "Affinity Name";
            }
            leaf value-type {
              type Mpls-te-affinity-value;
              description
                "Affinity value type";
            }
            leaf value {
              type xr:Hex-integer;
              description
                "Affinity Value in Hex number or by Bit
                 position";
            }
          }
        }
        leaf log-nsr-status {
          type empty;
          description
            "Log NSR status messages";
        }
        leaf log-issu-status {
          type empty;
          description
            "Log ISSU status messages";
        }
        leaf reoptimize-link-up {
          type empty;
          description
            "Enable reoptimization based on link-up events";
        }
        leaf reoptimize-delay-cleanup-timer {
          type uint32 {
            range "0..300";
          }
          units "second";
          description
            "Reoptimization Delay Cleanup Value (seconds)";
        }
        leaf disable-reoptimize-affinity-failure {
          type empty;
          description
            "Disable reoptimization after affinity failures";
        }
        leaf maximum-tunnels {
          type uint32 {
            range "1..65536";
          }
          // NCS drop default statement
          description
            "The maximum number of tunnel heads that will be
             allowed.";
        }
        leaf link-holddown-timer {
          type uint32 {
            range "0..300";
          }
          units "second";
          // NCS drop default statement
          description
            "Holddown time for links which had Path Errors
             in seconds";
        }
        leaf fault-oam {
          type empty;
          description
            "Enable Fault-OAM functionality for
             bidirectional tunnels";
        }
        leaf enable-unequal-load-balancing {
          type empty;
          description
            "Enable unequal load-balancing over tunnels to
             the same destination";
        }
        leaf log-tail {
          type empty;
          description
            "Log all tail tunnel events";
        }
        leaf reoptimize-delay-after-frr-timer {
          type uint32 {
            range "0..120";
          }
          units "second";
          description
            "Reoptimization Delay After FRR Value (seconds)";
        }
        leaf auto-bandwidth-collect-frequency {
          type uint32 {
            range "1..10080";
          }
          units "minute";
          // NCS drop default statement
          description
            "Auto-bandwidth global collection frequency in
             minutes";
        }
        leaf reopt-delay-path-protect-switchover-timer {
          type uint32 {
            range "0..604800";
          }
          units "second";
          // NCS drop default statement
          description
            "Seconds between path protect switchover and
             tunnel re-optimization. Set to 0 to disable";
        }
        leaf log-all {
          type empty;
          description
            "Always set to true";
        }
        leaf loose-path-retry-period {
          type uint32 {
            range "30..600";
          }
          // NCS drop default statement
          description
            "Signalling retry for tunnels terminating
             outside the headend area";
        }
        leaf reoptimize-load-balancing {
          type empty;
          description
            "Load balance bandwidth during reoptimization";
        }
        leaf log-head {
          type empty;
          description
            "Log all head tunnel events";
        }
        leaf path-selection-ignore-overload {
          type empty;
          description
            "Deprecated - do not use";
        }
        leaf graceful-preemption-on-bandwidth-reduction {
          type empty;
          description
            "Enable graceful preemption when there is a
             bandwidth reduction";
        }
        leaf advertise-explicit-nulls {
          type empty;
          description
            "Enable explicit-null advertising to PHOP";
        }
        leaf reoptimize-delay-install-timer {
          type uint32 {
            range "0..3600";
          }
          units "second";
          description
            "Reoptimization Delay Install Value (seconds)";
        }
        leaf reoptimize-delay-after-affinity-failure-timer {
          type uint32 {
            range "1..604800";
          }
          units "second";
          description
            "Delay reoptimizing current LSP after affinity
             failures";
        }
        leaf log-frr-protection {
          type Mpls-te-log-frr-protection;
          description
            "Log FRR Protection messages";
        }
        leaf reoptimize-timer-frequency {
          type uint32 {
            range "0..604800";
          }
          units "second";
          // NCS drop default statement
          description
            "Reoptimize timers period in seconds";
        }
        leaf log-mid {
          type empty;
          description
            "Log all mid tunnel events";
        }
        leaf log-preemption {
          type empty;
          description
            "Log tunnel preemption messages";
        }
      }
      container transport-profile {
        description
          "MPLS transport profile configuration data";
        container fault {
          description
            "Fault management";
          container protection-trigger {
            description
              "OAM events that trigger protection switching";
            container ldi {
              description
                "Protection switching due to LDI event";
              leaf disable {
                type empty;
                description
                  "Disable protection switching due to LDI
                   event";
              }
            }
            container lkr {
              description
                "Protection switching due to LKR event";
              leaf disable {
                type empty;
                description
                  "Disable protection switching due to LKR
                   event";
              }
            }
            leaf ais {
              type empty;
              description
                "Enable protection switching due to AIS event";
            }
          }
          leaf wait-to-restore-interval {
            type uint32 {
              range "0..2147483647";
            }
            units "second";
            // NCS drop default statement
            description
              "Waiting time before restoring working LSP";
          }
          leaf refresh-interval {
            type uint32 {
              range "1..20";
            }
            units "second";
            // NCS drop default statement
            description
              "Periodic refresh interval for fault OAM
               messages";
          }
        }
        container alarm {
          description
            "Alarm management";
          container suppress-event {
            description
              "Suppress all tunnel/LSP alarms";
            leaf disable {
              type empty;
              description
                "Disable alarm suppression";
            }
          }
          leaf soak-time {
            type uint32 {
              range "0..10";
            }
            units "second";
            // NCS drop default statement
            description
              "Duration of soaking alarms";
          }
          leaf enable-alarm {
            type empty;
            description
              "Enable Transport Profile Alarm";
          }
        }
        container bfd {
          description
            "Configure BFD parameters";
          container min-interval-standby {
            description
              "Hello interval for standby transport profile
               LSPs, either in milli-seconds or in
               micro-seconds";
            leaf interval-standby-ms {
              type uint32 {
                range "3..5000";
              }
              units "millisecond";
              description
                "Hello interval in milli-seconds";
            }
            leaf interval-standby-us {
              type uint32 {
                range "3000..5000000";
              }
              units "microsecond";
              description
                "Hello interval in micro-seconds";
            }
          }
          container min-interval {
            description
              "Hello interval, either in milli-seconds or in
               micro-seconds";
            leaf interval-ms {
              type uint32 {
                range "3..5000";
              }
              units "millisecond";
              description
                "Hello interval in milli-seconds";
            }
            leaf interval-us {
              type uint32 {
                range "3000..5000000";
              }
              units "microsecond";
              description
                "Hello interval in micro-seconds";
            }
          }
          leaf detection-multiplier-standby {
            type uint32 {
              range "2..10";
            }
            description
              "Detect multiplier for standby transport
               profile LSP";
          }
          leaf detection-multiplier {
            type uint32 {
              range "2..10";
            }
            description
              "Detect multiplier";
          }
        }
        container midpoints {
          description
            "MPLS-TP tunnel mid-point table";
          list midpoint {
            key "midpoint-name";
            description
              "Transport profile mid-point identifier";
            container source {
              presence "Indicates a source node is configured.";
              description
                "Node identifier, tunnel identifier and
                 optional global identifier of the source of
                 the LSP";
              leaf node-id {
                type inet:ipv4-address-no-zone;
                description
                  "Node identifier in IPv4 address format";
              }
              leaf tunnel-id {
                type uint32 {
                  range "0..65535";
                }
                // NCS drop mandatory statement
                description
                  "Tunnel identifier in numeric value";
              }
              leaf global-id {
                type uint32 {
                  range "1..65535";
                }
                description
                  "Global identifier in numeric value";
              }
            }
            container destination {
              presence "Indicates a destination node is configured.";
              description
                "Node identifier, tunnel identifier and
                 optional global identifier of the destination
                 of the LSP";
              leaf node-id {
                type inet:ipv4-address-no-zone;
                description
                  "Node identifier in IPv4 address format";
              }
              leaf tunnel-id {
                type uint32 {
                  range "0..65535";
                }
                // NCS drop mandatory statement
                description
                  "Tunnel identifier in numeric value";
              }
              leaf global-id {
                type uint32 {
                  range "1..65535";
                }
                description
                  "Global identifier in numeric value";
              }
            }
            container forward-lsp {
              description
                "Forward transport profile LSP";
              container forward-io-map {
                presence "Indicates a forward-io-map node is configured.";
                description
                  "Label cross-connect of forward transport
                   profile LSP";
                leaf in-label {
                  type uint32 {
                    range "16..4015";
                  }
                  description
                    "MPLS label";
                }
                leaf out-label {
                  type uint32 {
                    range "16..1048575";
                  }
                  // NCS drop mandatory statement
                  description
                    "Outgoing MPLS label";
                }
                leaf out-link {
                  type uint32 {
                    range "1..65535";
                  }
                  // NCS drop mandatory statement
                  description
                    "Transport profile identifier of outgoing
                     link";
                }
              }
              leaf forward-bandwidth {
                type uint32 {
                  range "0..4294967295";
                }
                units "kbit/s";
                description
                  "Bandwidth of forward transport profile LSP";
              }
            }
            container reverse-lsp {
              description
                "none";
              container reverse-io-map {
                presence "Indicates a reverse-io-map node is configured.";
                description
                  "Label cross-connect of reverse transport
                   profile LSP";
                leaf in-label {
                  type uint32 {
                    range "16..4015";
                  }
                  description
                    "MPLS label";
                }
                leaf out-label {
                  type uint32 {
                    range "16..1048575";
                  }
                  // NCS drop mandatory statement
                  description
                    "Outgoing MPLS label";
                }
                leaf out-link {
                  type uint32 {
                    range "1..65535";
                  }
                  // NCS drop mandatory statement
                  description
                    "Transport profile identifier of outgoing
                     link";
                }
              }
              leaf reverse-bandwidth {
                type uint32 {
                  range "0..4294967295";
                }
                units "kbit/s";
                description
                  "Bandwidth of reverse transport profile LSP";
              }
            }
            leaf tunnel-name {
              type string;
              description
                "Tunnel Name";
            }
            leaf lsp-protect {
              type empty;
              description
                "Enable LSP protection";
            }
            leaf lsp-id {
              type uint32 {
                range "0..65535";
              }
              description
                "Numeric identifier";
            }
            leaf midpoint-name {
              type xr:Cisco-ios-xr-string {
                length "1..64";
              }
              description
                "Name of mid-point";
            }
          }
        }
        leaf global-id {
          type uint32 {
            range "1..65535";
          }
          description
            "Transport profile global identifier";
        }
        leaf node-id {
          type inet:ipv4-address-no-zone;
          description
            "Node identifier in IPv4 address format";
        }
      }
      container interfaces {
        description
          "Configure MPLS TE interfaces";
        list interface {
          key "interface-name";
          description
            "Configure an MPLS TE interface";
          container transport-profile-link {
            description
              "MPLS transport profile capable link";
            container links {
              description
                "Transport profile link table";
              list link {
                key "link-id";
                description
                  "Transport profile link";
                leaf link-id {
                  type uint32 {
                    range "1..65535";
                  }
                  description
                    "Numeric link identifier";
                }
                leaf next-hop-type {
                  type Link-next-hop;
                  // NCS drop default statement
                  description
                    "Next hop type";
                }
                leaf next-hop-address {
                  // NCS drop when statement
                  type inet:ipv4-address-no-zone;
                  description
                    "Next-hop address in IPv4 format";
                }
              }
            }
          }
          container lcac {
            description
              "LCAC specific MPLS interface configuration";
            container switchings {
              description
                "Set the te-link switching attributes";
              list switching {
                key "switching-id";
                description
                  "The te-link switching attributes";
                leaf encoding {
                  type Mpls-te-switching-encoding;
                  description
                    "Set the local encoding type";
                }
                leaf capability {
                  type Mpls-te-switching-cap;
                  description
                    "Set the local switching capability";
                }
                leaf switching-id {
                  type Mpls-te-switching-index;
                  description
                    "Switching index";
                }
              }
            }
            container flood-area {
              description
                "Set the IGP instance into which this
                 interface is to be flooded (GMPLS only)";
              leaf igp-type {
                type Mpls-lcac-flooding-igp;
                description
                  "IGP type";
              }
              leaf process-name {
                type xr:Cisco-ios-xr-string {
                  length "1..32";
                }
                description
                  "Process name";
              }
              leaf area-id {
                type uint32;
                description
                  "Area ID";
              }
            }
            container attribute-name-xr {
              description
                "Set the interface attribute names";
              leaf-list attribute-name {
                type string;
                // NCS drop max-elements statement
                description
                  "Array of Attribute Names";
              }
            }
            container attribute-names {
              description
                "Attribute name table";
              list attribute-name {
                key "affinity-index";
                description
                  "Set the interface attribute names";
                leaf affinity-index {
                  type uint32 {
                    range "1..9";
                  }
                  description
                    "Specify the entry index";
                }
                leaf-list value {
                  type string;
                  // NCS drop min-elements statement
                  // NCS drop max-elements statement
                  description
                    "Array of Attribute Names";
                }
              }
            }
            container srlgs {
              description
                "Configure SRLG membership for the interface";
              list srlg {
                key "srlg-number";
                description
                  "SRLG membership number";
                leaf srlg-number {
                  type uint32 {
                    range "0..4294967295";
                  }
                  description
                    "SRLG membership number";
                }
              }
            }
            container up-thresholds {
              description
                "Set thresholds for increased resource
                 availability in %";
              leaf-list up-threshold {
                type Mpls-lcac-flooding-threshold-percent-range;
                units "percentage";
                // NCS drop max-elements statement
                description
                  "Array of up threshold percentage";
              }
            }
            container down-thresholds {
              description
                "Set thresholds for decreased resource
                 availability in %";
              leaf-list down-threshold {
                type Mpls-lcac-flooding-threshold-percent-range;
                units "percentage";
                // NCS drop max-elements statement
                description
                  "Array of down threshold percentage";
              }
            }
            leaf bfd {
              type empty;
              description
                "Enable use of Bidirectional Forwarding
                 Detection";
            }
            leaf fault-oam-lockout {
              type empty;
              description
                "Lockout protection on the interface for Flex
                 LSP";
            }
            leaf attribute-flags {
              type xr:Hex-integer;
              description
                "Set user defined interface attribute flags";
            }
            leaf enable {
              type empty;
              description
                "Enable MPLS-TE on the link";
            }
            leaf admin-weight {
              type uint32 {
                range "0..4294967295";
              }
              description
                "Set administrative weight for the interface";
            }
          }
          container global-attributes {
            description
              "MPLS TE global interface configuration";
            container backup-tunnels {
              description
                "Configure MPLS TE backup tunnels for this
                 interface";
              list backup-tunnel {
                key "tunnel-name";
                description
                  "Tunnel name";
                leaf tunnel-name {
                  type xr:Cisco-ios-xr-string {
                    length "1..54";
                  }
                  description
                    "Tunnel name";
                }
              }
            }
            container auto-tunnel {
              description
                "Auto tunnel configuration";
              container backup {
                description
                  "Auto tunnel backup configuration";
                container exclude {
                  description
                    "Auto-tunnel backup exclusion criteria";
                  leaf srlg-mode {
                    type Mpls-tesrlg-exclude;
                    description
                      "Set exclude SRLG mode for auto-tunnel
                       backup on this TE link";
                  }
                }
                leaf enable {
                  type empty;
                  description
                    "Enable auto-tunnel backup on this TE link";
                }
                leaf attribute-set {
                  type Attribute-set-name-length;
                  description
                    "The name of attribute set to be applied to
                     this auto backup lsp";
                }
                leaf next-hop-only {
                  type empty;
                  description
                    "Enable NHOP-only mode for auto-tunnel
                     backup on this TE link";
                }
              }
            }
            container backup-paths {
              description
                "Configure MPLS TE backup tunnels for this
                 interface";
              list backup-path {
                key "tunnel-number";
                description
                  "Tunnel interface number";
                leaf tunnel-number {
                  type uint32 {
                    range "0..65535";
                  }
                  description
                    "Tunnel interface number";
                }
              }
            }
          }
          leaf interface-name {
            type xr:Interface-name;
            description
              "Interface name";
          }
        }
      }
      container gmpls-nni {
        description
          "GMPLS-NNI configuration";
        container topology-instances {
          description
            "GMPLS-NNI topology instance table";
          list topology-instance {
            // NCS drop must statement
            key "ospf-area-type igp-instance-name igp-type";
            description
              "GMPLS-NNI topology instance configuration";

            grouping TOPOLOGY-INSTANCE-CONTENT {
              description
                "TOPOLOGY INSTANCE CONTENT";
              container controllers {
                description
                  "GMPLS-NNI controllers";
                list controller {
                  key "controller-name";
                  description
                    "Configure a GMPLS NNI controller";
                  container tti-mode {
                    description
                      "Set tandem connection monitoring for the
                       interface";
                    leaf tti-mode-type {
                      type Gmplstti-mode;
                      description
                        "Type of Trail Trace Identifier";
                    }
                    leaf tcmid {
                      // NCS drop when statement
                      type uint32 {
                        range "1..6";
                      }
                      description
                        "Tandem Connection Monitoring ID for the
                         interface";
                    }
                  }
                  container affinity-names {
                    description
                      "Set the interface affinity names";
                    leaf-list affinity-name {
                      type string;
                      // NCS drop max-elements statement
                      description
                        "Array of Attribute Names";
                    }
                  }
                  leaf admin-weight {
                    type uint32 {
                      range "0..65535";
                    }
                    description
                      "Set administrative weight for the
                       interface";
                  }
                  leaf enable {
                    type empty;
                    description
                      "Enable GMPLS-NNI on the link";
                  }
                  leaf delay {
                    type uint32 {
                      range "1..16777215";
                    }
                    description
                      "Set link delay for the interface";
                  }
                  leaf controller-name {
                    type xr:Interface-name;
                    description
                      "Controller name";
                  }
                }
              }
            }
            leaf igp-type {
              type Mpls-te-igp-protocol;
              description
                "IGP type";
            }
            leaf igp-instance-name {
              type xr:Cisco-ios-xr-string {
                length "1..40";
              }
              description
                "Name of IGP instance";
            }
            leaf ospf-area-type {
              type Ospf-area-mode;
              description
                "OSPF area format";
            }
            list ospf-int {
              // NCS drop when statement
              key "igp-area";
              description
                "ospf int";
              leaf igp-area {
                type uint32;
                description
                  "IGP area";
              }
              uses TOPOLOGY-INSTANCE-CONTENT;
            }
            list ospfip-addr {
              // NCS drop when statement
              key "address";
              description
                "ospfip addr";
              leaf address {
                type inet:ipv4-address-no-zone;
                description
                  "Area ID if in IP address format";
              }
              uses TOPOLOGY-INSTANCE-CONTENT;
            }
          }
        }
        container tunnel-heads {
          description
            "GMPLS-NNI tunnel-head table";
          list tunnel-head {
            key "tunnel-id";
            description
              "The configuration for a GMPLS NNI tunnel
               head-end";
            container signalled-bandwidth {
              description
                "The existence of this configuration indicates
                 the signalled bandwidth has been set for the
                 tunnel";
              leaf signalled-bandwidth-type {
                type Otn-signaled-bandwidth;
                description
                  "The g.709 signal type requested";
              }
              leaf bitrate {
                // NCS drop when statement
                type uint32;
                units "kbit/s";
                description
                  "Bitrate value in Kbps for ODUflex framing
                   type";
              }
              leaf od-uflex-framing-type {
                // NCS drop when statement
                type Otn-signaled-bandwidth-flex-framing;
                description
                  "Framing type in case of ODUflex signal type";
              }
            }
            container destination {
              description
                "The existence of this configuration indicates
                 the destination has been set for the tunnel";
              leaf destination {
                type inet:ipv4-address-no-zone;
                description
                  "IPV4 tunnel destination";
              }
              leaf destination-type {
                type Otn-destination;
                description
                  "Destination type whether it is unicast or
                   unnumbered";
              }
              leaf interface-if-index {
                type uint32;
                description
                  "Interface index of port";
              }
            }
            container protection-switching {
              description
                "The configuration for a GMPLS NNI tunnel
                 protection switch";
              leaf lockout {
                type Otn-protection-switch-lockout;
                description
                  "The configuration is used to prevent switch
                   over for a particular path type in tunnel";
              }
            }
            container logging {
              description
                "Tunnel event logging";
              leaf active-lsp-message {
                type empty;
                description
                  "Log all tunnel messages for changes in
                   Active LSP";
              }
              leaf homepath-state-message {
                type empty;
                description
                  "Log all messages for changes in state of
                   Homepath of Working LSP";
              }
              leaf signalling-state-message {
                type empty;
                description
                  "Log all tunnel sub-LSP state messages";
              }
              leaf path-change-message {
                type empty;
                description
                  "Log all tunnel messages for changes in
                   path-change";
              }
              leaf static-cross-connect-message {
                type empty;
                description
                  "Log all tunnel messages for static
                   cross-connect messages";
              }
              leaf tunnel-state-message {
                type empty;
                description
                  "Log all tunnel messages for changes in
                   tunnel-state";
              }
              leaf insufficient-bw-message {
                type empty;
                description
                  "Log tunnel messages for insufficient
                   bandwidth";
              }
            }
            container path-options {
              description
                "GMPLS NNI path options";
              list path-option {
                key "preference-level";
                description
                  "The existence of this configuration
                   indicates the path options have been set for
                   the tunnel";
                leaf preference-level {
                  type uint32 {
                    range "1..1000";
                  }
                  description
                    "Preference level for this path option";
                }
                leaf path-type {
                  type Mpls-te-path-option;
                  description
                    "The type of the path option";
                }
                leaf path-id {
                  type uint32 {
                    range "1..65535";
                  }
                  description
                    "The ID of the IP explicit path associated
                     with this option";
                }
                leaf path-name {
                  type string;
                  description
                    "The name of the IP explicit path associated
                     with this option";
                }
                leaf protected-by-preference-level {
                  type uint32 {
                    range "1..1001";
                  }
                  description
                    "Preference level of the protecting explicit
                     path. ";
                }
                leaf restore-by-preference-level {
                  type uint32 {
                    range "1..1000";
                  }
                  description
                    "Preference level of the restore path. ";
                }
                leaf xro-type {
                  type Mpls-te-path-option-xro;
                  // NCS drop mandatory statement
                  description
                    "The route-exclusion type";
                }
                leaf xro-attribute-set-name {
                  type Attribute-set-name-length;
                  description
                    "The name of the XRO attribute set to be
                     used for this path-option";
                }
                leaf affinity-attribute-set-name {
                  type Attribute-set-affinity-name-length;
                  description
                    "The name of the affinity attribute set to
                     be used for this path-option";
                }
                leaf lockdown {
                  type Mpls-te-path-option-property;
                  description
                    "Lockdown properties";
                }
              }
            }
            container static-uni {
              description
                "The existence of this configuration indicates
                 the static UNI endpoints have been set for
                 the tunnel";
              leaf ingress-controller-name {
                type xr:Cisco-ios-xr-string {
                  length "1..255";
                }
                description
                  "Name of  ingress controller";
              }
              leaf egress-controller-if-index {
                type uint32;
                description
                  "Interface index of Egress controller";
              }
              leaf ingress-type {
                type Otn-static-uni;
                description
                  "Ingress type whether it is xconnect or
                   terminated";
              }
              leaf egress-type {
                type Otn-static-uni;
                description
                  "Egress type whether it is xconnect or
                   terminated";
              }
            }
            leaf enable {
              type empty;
              description
                "The existence of this configuration indicates
                 the a new GMPLS NNI tunnel has been enabled";
            }
            leaf announce-srlg {
              type empty;
              description
                "Announce SRLG on term interface for the
                 tunnel";
            }
            leaf restore-lsp-shutdown {
              type empty;
              description
                "The existence of this configuration indicates
                 the restore LSP of tunnel is shutdown";
            }
            leaf current-lsp-shutdown {
              type empty;
              description
                "The existence of this configuration indicates
                 the current/working LSP of tunnel is shutdown";
            }
            leaf path-selection-metric {
              type Mpls-te-path-selection-metric;
              description
                "Path selection configuration for this
                 specific tunnel";
            }
            leaf payload {
              type Otn-payload;
              description
                "The existence of this configuration indicates
                 the Payload type have been set for the tunnel";
            }
            leaf standby-lsp-shutdown {
              type empty;
              description
                "The existence of this configuration indicates
                 the standby/protect LSP of tunnel is shutdown";
            }
            leaf shutdown {
              type empty;
              description
                "The existence of this configuration indicates
                 the tunnel is shutdown";
            }
            leaf path-protection-attribute-set-profile {
              type string {
                length "1..64";
              }
              description
                "The name of the path-protection profile to be
                 included in signalling messages";
            }
            leaf tunnel-id {
              type uint32 {
                range "0..65535";
              }
              description
                "Tunnel ID";
            }
            uses live_ncs_RECORD-ROUTE;
            uses live_ncs_SIGNALLED-NAME;
          }
        }
        leaf path-selection-metric {
          type Mpls-te-path-selection-metric;
          description
            "Path selection configuration for all gmpls nni
             tunnels";
        }
        leaf enable-gmpls-nni {
          type empty;
          description
            "Enable MPLS Traffic Engineering GMPLS-NNI";
        }
      }
      container lcac {
        description
          "LCAC specific MPLS global configuration";
        container bfd {
          description
            "BFD configuration";
          leaf interval {
            type uint32 {
              range "15..200";
            }
            units "millisecond";
            description
              "Hello interval for BFD sessions created by TE";
          }
          leaf detection-multiplier {
            type uint32 {
              range "2..10";
            }
            description
              "Detection multiplier for BFD sessions created
               by TE";
          }
        }
        container flooding-threshold {
          description
            "Configure flooding threshold as percentage of
             total link bandwidth.";
          leaf up-stream {
            type Mpls-percent-range;
            units "percentage";
            description
              "Upward flooding Threshold in percentages of
               total bandwidth";
          }
          leaf down-stream {
            type Mpls-percent-range;
            units "percentage";
            description
              "Downward flooding Threshold in percentages of
               total bandwidth";
          }
        }
        leaf bandwidth-hold-timer {
          type Mpls-lcac-bandwidth-hold-timer-range;
          units "second";
          description
            "Bandwidth hold timer value (seconds)";
        }
        leaf delay-preempt-bundle-capacity-timer {
          type uint32 {
            range "0..300";
          }
          units "second";
          description
            "Bundle capacity preemption timer value
             (seconds)";
        }
        leaf periodic-flooding-timer {
          type uint32 {
            range "0..3600";
          }
          units "second";
          description
            "Periodic flooding value (seconds)";
        }
      }
      leaf enable-traffic-engineering {
        type empty;
        description
          "Enable MPLS Traffic Engineering";
      }
    }
  }
  augment "/ncs:devices/ncs:template/ncs:ned-id/ncs:config" {
    container mpls-te {
      description
        "The root of MPLS TE configuration";
      container diff-serv-traffic-engineering {
        description
          "Configure Diff-Serv Traffic-Engineering";
        container classes {
          description
            "Configure Diff-Serv Traffic-Engineering Classes";
          list class {
            // NCS patched for predictable order
            ordered-by user;
            key "class-number";
            description
              "DSTE class number";
            leaf class-number {
              type string;
              description
                "DS-TE class number";
            }
            leaf class-type {
              // NCS drop when statement
              type string;
              // NCS drop default statement
              description
                "Class type number";
            }
            leaf class-priority {
              // NCS drop when statement
              type string;
              // NCS drop default statement
              description
                "Class-type priority";
            }
            leaf unused {
              type string;
              description
                "TRUE to skip classtype and class priority
                 provisioning FALSE to provision them";
            }
          }
        }
        leaf bandwidth-constraint-model {
          type string;
          description
            "Diff-Serv Traffic-Engineering Bandwidth
             Constraint Model";
        }
        leaf mode-ietf {
          type string;
          description
            "Diff-Serv Traffic-Engineering IETF mode";
        }
      }
      container named-tunnels {
        description
          "Configure MPLS TE tunnel";
        container tunnels {
          description
            "Configure MPLS TE tunnel";
          list tunnel {
            // NCS patched for predictable order
            ordered-by user;
            key "tunnel-name tunnel-type";
            description
              "Configure a MPLS TE tunnel";
            container tunnel-attributes {
              description
                "MPLS tunnel attributes";
              container path-setups {
                description
                  "Tunnel path setup table";
                list path-setup {
                  // NCS patched for predictable order
                  ordered-by user;
                  key "path-setup-name";
                  description
                    "Tunnel path setup";
                  container path-computation {
                    presence "Indicates a path-computation node is configured.";
                    description
                      "Path computation method";
                    leaf path-computation-method {
                      type string;
                      // NCS drop mandatory statement
                      description
                        "Path computation method";
                    }
                    leaf explicit-path-name {
                      type string;
                      description
                        "Explicit Path Name";
                    }
                    leaf path-computation-server {
                      type string;
                      // NCS drop default statement
                      description
                        "Path Computation Server Address";
                    }
                  }
                  leaf preference {
                    type string;
                    description
                      "Path preference level";
                  }
                  leaf path-setup-name {
                    type string;
                    description
                      "Path Name";
                  }
                }
              }
              leaf shutdown {
                type empty;
                description
                  "shutdown the tunnel";
              }
              uses ncs_template_FORWARD-CLASS;
              uses ncs_template_TUNNEL-PATH-SELECTION;
              uses ncs_template_AUTO-BANDWIDTH;
              uses ncs_template_PRIORITY;
              uses ncs_template_DESTINATION;
              uses ncs_template_RECORD-ROUTE;
              uses ncs_template_AFFINITY-MASK;
              uses ncs_template_FORWARDING-ADJACENCY;
              uses ncs_template_LOGGING;
              uses ncs_template_BANDWIDTH;
              uses ncs_template_AUTOROUTE;
              uses ncs_template_PATH-SELECTION-METRIC;
              uses ncs_template_NEW-STYLE-AFFINITY-TABLE;
              uses ncs_template_SOFT-PREEMPTION;
              uses ncs_template_FAST-REROUTE;
              uses ncs_template_LOAD-SHARE;
            }
            container tunnel-id {
              presence "Indicates a tunnel-id node is configured.";
              description
                "Set the tunnel ID";
              leaf tunnel-id-type {
                type string;
                // NCS drop mandatory statement
                description
                  "Tunnel ID Type";
              }
              leaf tunnel-id {
                type string;
                description
                  "Tunnel ID";
              }
            }
            leaf tunnel-name {
              type string;
              description
                "Tunnel name";
            }
            leaf tunnel-type {
              type string;
              description
                "Tunnel Type";
            }
          }
        }
        leaf enable {
          type empty;
          description
            "Enable Named Tunnels";
        }
      }
      container gmpls-uni {
        description
          "GMPLS-UNI configuration";
        container timers {
          description
            "GMPLS-UNI timer configuration";
          container path-option-timers {
            description
              "GMPLS-UNI path-option timer configuration";
            container holddown {
              description
                "GMPLS-UNI path-option holddown timer
                 configuration";
              leaf minimum {
                type string;
                units "second";
                description
                  "Minimum holddown (seconds)";
              }
              leaf maximum {
                type string;
                units "second";
                description
                  "Maximum holddown (seconds)";
              }
            }
          }
        }
        container controllers {
          description
            "GMPLS-UNI controllers";
          list controller {
            // NCS patched for predictable order
            ordered-by user;
            key "controller-name";
            description
              "Configure a GMPLS controller";
            container announce {
              description
                "Announce discovered tunnel properties to
                 system";
              leaf srl-gs {
                type empty;
                description
                  "Enable announcement of discovered SRLGs";
              }
            }
            container controller-logging {
              description
                "Controller logging";
              leaf discovered-srlg-change-logging {
                type empty;
                description
                  "Enable logging of changes to of discovered
                   SRLGs";
              }
            }
            container gmpls-unitunnel-head {
              description
                "GMPLS-UNI tunnel-head properties";
              container path-options {
                description
                  "Path-option configuration";
                list path-option {
                  // NCS patched for predictable order
                  ordered-by user;
                  key "preference-level";
                  description
                    "A Path-option";
                  leaf preference-level {
                    type string;
                    description
                      "Preference level for this path option";
                  }
                  leaf path-type {
                    type string;
                    // NCS drop mandatory statement
                    description
                      "The type of the path option";
                  }
                  leaf path-id {
                    type string;
                    // NCS drop default statement
                    description
                      "The ID of the explicit path associated
                       with this option";
                  }
                  leaf path-name {
                    type string;
                    description
                      "The name of the explicit path associated
                       with this option";
                  }
                  leaf xro-type {
                    type string;
                    // NCS drop mandatory statement
                    description
                      "The route-exclusion type";
                  }
                  leaf xro-attribute-set-name {
                    type string;
                    description
                      "The name of the XRO attribute set to be
                       used for this path-option";
                  }
                  leaf lockdown {
                    type string;
                    // NCS drop mandatory statement
                    description
                      "Path option properties: must be Lockdown";
                  }
                  leaf verbatim {
                    type string;
                    // NCS drop default statement
                    description
                      "Path option properties: must be verbatim
                       if set";
                  }
                  leaf signaled-label {
                    type string;
                    // NCS drop default statement
                    description
                      "Signaled label type";
                  }
                  leaf dwdm-channel {
                    type string;
                    // NCS drop default statement
                    description
                      "DWDM channel number";
                  }
                }
              }
              container recording {
                description
                  "Tunnel property recording";
                leaf srlg {
                  type empty;
                  description
                    "Enable SRLG-recording during signaling";
                }
              }
              container logging {
                description
                  "Tunnel event logging";
                uses ncs_template_STATE-MESSAGE;
              }
              leaf tunnel-id {
                type string;
                description
                  "GMPLS-UNI head tunnel-id";
              }
              leaf enable {
                type empty;
                description
                  "Set link as a GMPLS tunnel head";
              }
              leaf destination {
                type string;
                description
                  "Set the destination of the tunnel";
              }
              uses ncs_template_PRIORITY;
              uses ncs_template_RECORD-ROUTE;
              uses ncs_template_SIGNALLED-NAME;
            }
            leaf enable {
              type empty;
              description
                "Enable GMPLS-UNI on the link";
            }
            leaf controller-name {
              type string;
              description
                "Controller name";
            }
          }
        }
      }
      container global-attributes {
        description
          "Configure MPLS TE global attributes";
        container auto-tunnel {
          description
            "Configure auto-tunnels feature";
          container pcc {
            description
              "Configure auto-tunnel PCC (Path Computation
               Client) feature";
            uses ncs_template_TUNNEL-RANGE;
          }
          container p2p-auto-tunnel {
            description
              "Configure P2P auto-tunnel feature";
            uses ncs_template_TUNNEL-RANGE;
          }
          container backup {
            description
              "Configure auto-tunnel backup feature";
            leaf affinity-ignore {
              type empty;
              description
                "Ignore affinity during CSPF for auto backup
                 tunnels";
            }
            uses ncs_template_TIMERS;
            uses ncs_template_TUNNEL-RANGE;
          }
          container mesh {
            description
              "Configure auto-tunnel mesh feature";
            container mesh-groups {
              description
                "Configure auto-tunnel mesh group";
              list mesh-group {
                // NCS patched for predictable order
                ordered-by user;
                key "mesh-group-id";
                description
                  "Auto-mesh group identifier";
                leaf destination-list {
                  type string;
                  description
                    "The name of prefix-list to be applied to
                     this destination-list";
                }
                leaf disable {
                  type empty;
                  description
                    "Disables mesh group";
                }
                leaf attribute-set {
                  type string;
                  description
                    "The name of auto-mesh attribute set to be
                     applied to this group";
                }
                leaf one-hop {
                  type empty;
                  description
                    "Automatically create tunnel to all
                     next-hops";
                }
                leaf mesh-group-id {
                  type string;
                  description
                    "Mesh group ID";
                }
              }
            }
            uses ncs_template_TIMERS;
            uses ncs_template_TUNNEL-RANGE;
          }
          container p2mp-auto-tunnel {
            description
              "Configure P2MP auto-tunnel feature";
            uses ncs_template_TUNNEL-RANGE;
          }
        }
        container hardware-out-of-resource {
          description
            "Configure HW OOR processing in MPLS-TE";
          container oor-red-state {
            description
              "Configuration for HW OOR Red State";
            uses ncs_template_OOR-NODE-PROTECTION-DISABLE;
            uses ncs_template_OOR-AVAILABLE-BANDWIDTH-PERCENTAGE;
            uses ncs_template_OOR-ACCEPT-LSP-MIN-BANDWIDTH;
            uses ncs_template_OOR-ACCEPT-REOPT-LSP;
            uses ncs_template_OOR-METRIC-TE-PENALTY;
          }
          container oor-yellow-state {
            description
              "Configuration for HW OOR Yellow State";
            uses ncs_template_OOR-NODE-PROTECTION-DISABLE;
            uses ncs_template_OOR-AVAILABLE-BANDWIDTH-PERCENTAGE;
            uses ncs_template_OOR-ACCEPT-LSP-MIN-BANDWIDTH;
            uses ncs_template_OOR-ACCEPT-REOPT-LSP;
            uses ncs_template_OOR-METRIC-TE-PENALTY;
          }
          container oor-green-state {
            description
              "Configuration for HW OOR Green State";
            leaf oor-recovery-duration {
              type string;
              units "minute";
              // NCS drop default statement
              description
                "Period of time (minutes) during which the
                 action in Green state are applied. After this
                 period, the processing in TE goes back to
                 normal state";
            }
            uses ncs_template_OOR-NODE-PROTECTION-DISABLE;
            uses ncs_template_OOR-AVAILABLE-BANDWIDTH-PERCENTAGE;
            uses ncs_template_OOR-ACCEPT-LSP-MIN-BANDWIDTH;
            uses ncs_template_OOR-ACCEPT-REOPT-LSP;
            uses ncs_template_OOR-METRIC-TE-PENALTY;
          }
        }
        container secondary-router-ids {
          description
            "Configure MPLS TE Secondary Router ID";
          list secondary-router-id {
            // NCS patched for predictable order
            ordered-by user;
            key "secondary-router-id-value";
            description
              "Secondary Router ID";
            leaf secondary-router-id-value {
              type string;
              description
                "Secondary TE Router ID";
            }
          }
        }
        container srlg {
          description
            "Configure SRLG values and MPLS-TE properties";
          container names {
            description
              "Configure SRLG identified by names";
            list name {
              // NCS patched for predictable order
              ordered-by user;
              key "srlg-name";
              description
                "SRLG name and its MPLS-TE properties";
              container static-srlg-members {
                description
                  "Configure static SRLG members list";
                list static-srlg-member {
                  // NCS patched for predictable order
                  ordered-by user;
                  key "from-address";
                  description
                    "A mapping of the local static SRLG member";
                  leaf from-address {
                    type string;
                    description
                      "From address";
                  }
                  leaf to-address {
                    type string;
                    // NCS drop mandatory statement
                    description
                      "To Addres";
                  }
                }
              }
              leaf admin-weight {
                type string;
                description
                  "Administrative weight for the SRLG value";
              }
              leaf srlg-name {
                type string;
                description
                  "SRLG membership name";
              }
            }
          }
          leaf default-admin-weight {
            type string;
            // NCS drop default statement
            description
              "Default Admin weight any SRLG value that does
               not have one";
          }
          leaf enable {
            type empty;
            description
              "Enter SRLG property configuration";
          }
        }
        container queues {
          description
            "Configure MPLS TE route priority";
          list queue {
            // NCS patched for predictable order
            ordered-by user;
            key "role";
            description
              "Configure route priority queue value";
            leaf role {
              type string;
              description
                "Route Priority Tunnel Role";
            }
            leaf value {
              type string;
              // NCS drop mandatory statement
              description
                "Route priority queue value";
            }
          }
        }
        container mib {
          description
            "MPLS-TE MIB properties";
          leaf midpoint-lsp-stats-collection-disable {
            type empty;
            description
              "Disables mib midpoint LSP traffic stats
               collection";
          }
        }
        container attribute-set {
          description
            "Attribute AttributeSets";
          container path-option-attributes {
            description
              "Path Option Attribute-Set Table";
            list path-option-attribute {
              // NCS patched for predictable order
              ordered-by user;
              key "attribute-set-name";
              description
                "Path Option Attribute";
              container bfd-reverse-path {
                presence "Indicates a bfd-reverse-path node is configured.";
                description
                  "Configure BFD reverse path";
                leaf bfd-reverse-path-type {
                  type string;
                  description
                    "BFD reverse path type";
                }
                leaf binding-label {
                  type string;
                  // NCS drop mandatory statement
                  description
                    "BFD reverse path binding label";
                }
              }
              container att-path-option-path-selection {
                description
                  "Configure path selection properties";
                leaf path-selection-exclude-list {
                  type string;
                  description
                    "Path selection exclude list name
                     configuration";
                }
                uses ncs_template_ENABLE;
                uses ncs_template_PATH-SELECTION-DELAY-LIMIT;
                uses ncs_template_INVALIDATION;
                uses ncs_template_PATH-SELECTION-COST-LIMIT;
              }
              leaf attribute-set-name {
                type string;
                description
                  "Attribute Set Name";
              }
              uses ncs_template_PCE;
              uses ncs_template_AFFINITY-MASK;
              uses ncs_template_BANDWIDTH;
              uses ncs_template_NEW-STYLE-AFFINITY-TABLE;
            }
          }
          container p2mpte-attributes {
            description
              "P2MP-TE Tunnel AttributeSets Table";
            list p2mpte-attribute {
              // NCS patched for predictable order
              ordered-by user;
              key "attribute-set-name";
              description
                "P2MP-TE Tunnel Attribute";
              leaf attribute-set-name {
                type string;
                description
                  "Attribute Set Name";
              }
              uses ncs_template_INTERFACE-BANDWIDTH;
              uses ncs_template_PRIORITY;
              uses ncs_template_RECORD-ROUTE;
              uses ncs_template_AFFINITY-MASK;
              uses ncs_template_BANDWIDTH;
              uses ncs_template_PATH-SELECTION;
              uses ncs_template_NEW-STYLE-AFFINITY-TABLE;
              uses ncs_template_FAST-REROUTE;
              uses ncs_template_MPLS-MTE-TUNNEL-CFG-LOGGING;
            }
          }
          container p2p-te-attributes {
            description
              "P2P-TE Tunnel AttributeSets Table";
            list p2p-te-attribute {
              // NCS patched for predictable order
              ordered-by user;
              key "attribute-set-name";
              description
                "P2P-TE Tunnel Attribute";
              container path-selection {
                description
                  "Configure path selection properties";
                container segment-routing-prepend {
                  description
                    "Deprecated";
                  container indexes {
                    description
                      "Segment routing prepend index table";
                    list index {
                      // NCS patched for predictable order
                      ordered-by user;
                      key "index-number";
                      description
                        "Prepend index information";
                      leaf index-number {
                        type string;
                        description
                          "Index number";
                      }
                      leaf prepend-type {
                        type string;
                        // NCS drop default statement
                        description
                          "Prepend type";
                      }
                      leaf mpls-label {
                        type string;
                        // NCS drop default statement
                        description
                          "MPLS Label";
                      }
                    }
                  }
                  leaf enable {
                    type empty;
                    description
                      "Enter path selection segment routing
                       prepend submode";
                  }
                }
                container invalidation {
                  description
                    "Deprecated";
                  leaf invalidation-timer {
                    type string;
                    units "millisecond";
                    description
                      "Path selection invalidation timer value
                       (milliseconds)";
                  }
                  leaf invalidation-timer-expire-type {
                    type string;
                    // NCS drop default statement
                    description
                      "Path selection invalidation timer expire
                       type";
                  }
                }
                leaf path-selection-metric {
                  type string;
                  description
                    "Path selection metric to use in path
                     calculation";
                }
                leaf path-selection-segment-routing-adjacency-protection {
                  type string;
                  description
                    "Segment routing adjacency protection type
                     to use in path calculation";
                }
                uses ncs_template_ENABLE;
              }
              leaf attribute-set-name {
                type string;
                description
                  "Attribute Set Name";
              }
              uses ncs_template_PCE;
              uses ncs_template_AFFINITY-MASK;
              uses ncs_template_LOGGING;
              uses ncs_template_NEW-STYLE-AFFINITY-TABLE;
            }
          }
          container auto-backup-attributes {
            description
              "Auto-backup Tunnel Attribute Table";
            list auto-backup-attribute {
              // NCS patched for predictable order
              ordered-by user;
              key "attribute-set-name";
              description
                "Auto-backup Tunnel Attribute";
              container signalled-name {
                description
                  "Signalled name";
                leaf name {
                  type string;
                  description
                    "Signalled name";
                }
                leaf source-type {
                  type string;
                  description
                    "Source address or name";
                }
                leaf protected-interface-type {
                  type string;
                  description
                    "Protected-interface address or name";
                }
                leaf mp-address {
                  type string;
                  description
                    "Set if merge-point address is to be
                     appended";
                }
              }
              container auto-backup-logging {
                description
                  "Log tunnel LSP messages";
                uses ncs_template_BANDWIDTH-CHANGE-MESSAGE;
                uses ncs_template_REOPTIMIZE-ATTEMPTS-MESSAGE;
                uses ncs_template_STATE-MESSAGE;
                uses ncs_template_REOPTIMIZED-MESSAGE;
              }
              leaf attribute-set-name {
                type string;
                description
                  "Attribute Set Name";
              }
              uses ncs_template_PRIORITY;
              uses ncs_template_RECORD-ROUTE;
              uses ncs_template_AFFINITY-MASK;
              uses ncs_template_PATH-SELECTION;
              uses ncs_template_POLICY-CLASSES;
              uses ncs_template_NEW-STYLE-AFFINITY-TABLE;
            }
          }
          container otn-pp-attributes {
            description
              "OTN Path Protection Attributes table";
            list otn-pp-attribute {
              // NCS patched for predictable order
              ordered-by user;
              key "attribute-set-name";
              description
                "OTN Path Protection Attribute";
              container revert-schedule-names {
                description
                  "Specify APS revert schedule";
                list revert-schedule-name {
                  // NCS patched for predictable order
                  ordered-by user;
                  key "schedule-name";
                  description
                    "Name Identifier for revert schedule";
                  container schedule-duration {
                    presence "Indicates a schedule-duration node is configured.";
                    description
                      "Set duration in format hh:mm";
                    leaf hour {
                      type string;
                      // NCS drop mandatory statement
                      description
                        "Hour of day";
                    }
                    leaf minutes {
                      type string;
                      // NCS drop mandatory statement
                      description
                        "Minute of the hour";
                    }
                  }
                  container schedule-date {
                    presence "Indicates a schedule-date node is configured.";
                    description
                      "Set date in format hh:mm MMM DD YYYY";
                    leaf hour {
                      type string;
                      // NCS drop mandatory statement
                      description
                        "Hour of day";
                    }
                    leaf minutes {
                      type string;
                      // NCS drop mandatory statement
                      description
                        "Minute of the hour";
                    }
                    leaf month {
                      type string;
                      // NCS drop mandatory statement
                      description
                        "Month of the year";
                    }
                    leaf day {
                      type string;
                      // NCS drop mandatory statement
                      description
                        "Day of the month";
                    }
                    leaf year {
                      type string;
                      // NCS drop mandatory statement
                      description
                        "Year";
                    }
                  }
                  leaf revert-schedule-max-tries {
                    type string;
                    description
                      "Revert Schedule Max tries";
                  }
                  leaf sch-name-enable {
                    type empty;
                    description
                      "Schedule name enable object";
                  }
                  leaf revert-schedule-frequency {
                    type string;
                    description
                      "Frequency set as Once, Daily, Weekly";
                  }
                  leaf schedule-name {
                    type string;
                    description
                      "Enter 64 characters for revert schedule
                       name";
                  }
                }
              }
              container sub-network-connection-mode {
                description
                  "Sub-network connection mode";
                leaf connection-mode {
                  type string;
                  description
                    "The sub-network connection mode";
                }
                leaf connection-monitoring-mode {
                  type string;
                  description
                    "Tandem Connection Monitoring ID for the
                     interface";
                }
              }
              container timers {
                description
                  "Timers";
                leaf aps-wait-to-restore {
                  type string;
                  units "second";
                  description
                    "G.709 OTN path protection wait to restore
                     timer in seconds";
                }
                leaf aps-hold-off {
                  type string;
                  units "millisecond";
                  description
                    "G.709 OTN path protection hold-off timer in
                     milliseconds";
                }
              }
              leaf aps-protection-mode {
                type string;
                description
                  "The APS protecion mode";
              }
              leaf aps-restoration-style {
                type string;
                description
                  "The APS restoration style";
              }
              leaf aps-protection-type {
                type string;
                description
                  "The APS protecion type";
              }
              leaf attribute-set-name {
                type string;
                description
                  "Attribute Set Name";
              }
              uses ncs_template_PATH-SELECTION;
            }
          }
          container auto-mesh-attributes {
            description
              "Auto-mesh Tunnel AttributeSets Table";
            list auto-mesh-attribute {
              // NCS patched for predictable order
              ordered-by user;
              key "attribute-set-name";
              description
                "Auto-mesh Tunnel Attribute";
              container auto-mesh-logging {
                description
                  "Log tunnel LSP messages";
                uses ncs_template_BANDWIDTH-CHANGE-MESSAGE;
                uses ncs_template_REOPTIMIZE-ATTEMPTS-MESSAGE;
                uses ncs_template_REROUTE-MESSSAGE;
                uses ncs_template_STATE-MESSAGE;
                uses ncs_template_INSUFFICIENT-BW-MESSAGE;
                uses ncs_template_REOPTIMIZED-MESSAGE;
                uses ncs_template_PCALC-FAILURE-MESSAGE;
              }
              leaf autoroute-announce {
                type empty;
                description
                  "Enable autoroute announce";
              }
              leaf attribute-set-name {
                type string;
                description
                  "Attribute Set Name";
              }
              uses ncs_template_INTERFACE-BANDWIDTH;
              uses ncs_template_FORWARD-CLASS;
              uses ncs_template_PRIORITY;
              uses ncs_template_RECORD-ROUTE;
              uses ncs_template_AFFINITY-MASK;
              uses ncs_template_BANDWIDTH;
              uses ncs_template_PATH-SELECTION;
              uses ncs_template_COLLECTION-ONLY;
              uses ncs_template_POLICY-CLASSES;
              uses ncs_template_NEW-STYLE-AFFINITY-TABLE;
              uses ncs_template_SOFT-PREEMPTION;
              uses ncs_template_FAST-REROUTE;
              uses ncs_template_LOAD-SHARE;
            }
          }
          container xro-attributes {
            description
              "XRO Tunnel Attributes table";
            list xro-attribute {
              // NCS patched for predictable order
              ordered-by user;
              key "attribute-set-name";
              description
                "XRO Attribute";
              container path-diversity {
                description
                  "Path diversity";
                container srlgs {
                  description
                    "SRLG-based path diversity";
                  list srlg {
                    // NCS patched for predictable order
                    ordered-by user;
                    key "srlg";
                    description
                      "SRLG-based path-diversity element";
                    leaf srlg {
                      type string;
                      description
                        "SRLG";
                    }
                    leaf conformance {
                      type string;
                      // NCS drop mandatory statement
                      description
                        "The diversity conformance requirements";
                    }
                  }
                }
                container lsp {
                  description
                    "LSP-based path diversity";
                  container fecs {
                    description
                      "FEC LSP-based path diversity";
                    list fec {
                      // NCS patched for predictable order
                      ordered-by user;
                      key "source destination tunnel-id extended-tunnel-id lsp-id";
                      description
                        "LSP-based path-diversity, referenced by
                         FEC";
                      leaf source {
                        type string;
                        description
                          "Source address";
                      }
                      leaf destination {
                        type string;
                        description
                          "Destination address";
                      }
                      leaf tunnel-id {
                        type string;
                        description
                          "Tunnel id";
                      }
                      leaf extended-tunnel-id {
                        type string;
                        description
                          "Extended tunnel-id";
                      }
                      leaf lsp-id {
                        type string;
                        description
                          "LSP id";
                      }
                      leaf conformance {
                        type string;
                        // NCS drop mandatory statement
                        description
                          "The diversity conformance requirements";
                      }
                    }
                  }
                }
              }
              leaf attribute-set-name {
                type string;
                description
                  "Attribute Set Name";
              }
              uses ncs_template_PATH-SELECTION;
            }
          }
        }
        container bfd-over-lsp {
          description
            "BFD over MPLS TE Global Configurations";
          container tail {
            description
              "BFD over LSP Tail Global Configurations";
            leaf multiplier {
              type string;
              description
                "Specify BFD over LSP tail multiplier";
            }
            leaf minimum-interval {
              type string;
              description
                "Specify BFD over LSP tail minimum interval";
            }
          }
          container head {
            description
              "BFD over LSP Head Global Configurations";
            leaf reopt-timeout {
              type string;
              description
                "BFD session down reopt timeout";
            }
            leaf down-action {
              type string;
              description
                "Specify BFD session down action";
            }
          }
        }
        container bandwidth-accounting {
          description
            "Bandwidth accounting configuration data";
          container application {
            description
              "Bandwidth accounting application configuration
               data";
            leaf application-enforced {
              type string;
              // NCS drop default statement
              description
                "This object enables the application";
            }
            leaf application-interval {
              type string;
              units "second";
              // NCS drop default statement
              description
                "This object sets the application interval in
                 seconds for bandwidth accounting. Default to
                 180 seconds.";
            }
          }
          container account-flooding-threshold {
            description
              "This object sets the flooding threshold as
               percentage of total link bandwidth for
               bandwidth accounting. Default to 10%, 10%";
            leaf up-threshold {
              type string;
              units "percentage";
              // NCS drop default statement
              description
                "Upward flooding Threshold in percentages of
                 total bandwidth";
            }
            leaf down-threshold {
              type string;
              units "percentage";
              // NCS drop default statement
              description
                "Downward flooding Threshold in percentages of
                 total bandwidth";
            }
          }
          leaf sampling-interval {
            type string;
            units "second";
            // NCS drop default statement
            description
              "This object sets the sampling interval in
               seconds for bandwidth accounting. Default to
               60 seconds.";
          }
          leaf adjustment-factor {
            type string;
            units "percentage";
            // NCS drop default statement
            description
              "This object sets the percentage adjustment
               factor for the non RSVP-TE bandwidth
               accounting.  Default is 100%.";
          }
          leaf collection-type-rsvp-te {
            type string;
            // NCS drop default statement
            description
              "This object enables the bandwidth accounting
               RSVP-TE sample collection.";
          }
          leaf enable {
            type empty;
            description
              "This object controls whether BW accounting is
               enabled. This object must be set before
               setting any other objects  under the
               BandwidthAccounting class.";
          }
        }
        container pce-attributes {
          description
            "Configuration MPLS TE PCE attributes";
          container pce-stateful {
            description
              "PCE Stateful";
            container stateful-timers {
              description
                "Configure Stateful PCE (Path Computation
                 Element) timers";
              leaf redelegation-timeout {
                type string;
                units "second";
                // NCS drop default statement
                description
                  "Timer for static tunnel redelegation in
                   seconds, default is 180 seconds";
              }
              leaf state-timeout {
                type string;
                units "second";
                // NCS drop default statement
                description
                  "State timeout for LSPs without delegation in
                   seconds, zero means immediate removal,
                   default is 180 seconds";
              }
            }
            leaf fast-repair {
              type empty;
              description
                "Enable reoptimization by PCC after path
                 failures";
            }
            leaf instantiation {
              type empty;
              description
                "PCE stateful instantiation capability";
            }
            leaf cisco-extension {
              type empty;
              description
                "Enable processing of PCEP Cisco extension";
            }
            leaf delegation {
              type empty;
              description
                "Delegate all statically configured tunnels";
            }
            leaf autoroute-announce {
              type empty;
              description
                "Enable autoroute announce for PCE
                 instantiated tunnels";
            }
            leaf report {
              type empty;
              description
                "Report all statically configured tunnels";
            }
            leaf enable {
              type empty;
              description
                "PCE stateful capability";
            }
          }
          container timer {
            description
              "Configure PCE (Path Computation Element)
               timers";
          }
          container peers {
            description
              "Configure PCE peers";
            list peer {
              // NCS patched for predictable order
              ordered-by user;
              key "pce-peer-address";
              description
                "PCE peer";
              leaf pce-peer-address {
                type string;
                description
                  "Address of PCE Peer";
              }
              uses ncs_template_PASSWORD;
              uses ncs_template_KEYCHAIN;
              uses ncs_template_PRECEDENCE;
            }
          }
          container logging {
            description
              "Configure PCE (Path Computation Element)
               logging feature";
            container events {
              description
                "Configure logging events";
              leaf peer-status {
                type empty;
                description
                  "Peer status changes logging";
              }
            }
          }
          leaf request-timeout {
            type string;
            units "second";
            // NCS drop default statement
            description
              "Request timeout value in seconds";
          }
          leaf reoptimize-period {
            type string;
            units "second";
            // NCS drop default statement
            description
              "PCE reoptimization period for PCE-based paths";
          }
          leaf address {
            type string;
            description
              "Address of this PCE";
          }
          leaf deadtimer {
            type string;
            units "second";
            // NCS drop default statement
            description
              "Deadtimer interval in seconds";
          }
          leaf keepalive {
            type string;
            units "second";
            // NCS drop default statement
            description
              "Keepalive interval in seconds";
          }
          leaf keepalive-tolerance {
            type string;
            units "second";
            // NCS drop default statement
            description
              "Keepalive interval tolerance in seconds";
          }
          leaf peer-source-addr {
            type string;
            description
              "PCE Peer Source Address";
          }
          leaf speaker-entity-id {
            type string;
            description
              "PCE speaker entity identifier";
          }
          leaf segment-routing {
            type empty;
            description
              "Always set to true";
          }
          uses ncs_template_PASSWORD;
          uses ncs_template_KEYCHAIN;
          uses ncs_template_PRECEDENCE;
        }
        container lsp-out-of-resource {
          description
            "Configure LSP OOR attributes in MPLS-TE";
          container lsp-oor-red-state {
            description
              "Configuration for LSP OOR Red/Major State";
            uses ncs_template_ALL-TRANSIT-LSP-THRESHOLD;
            uses ncs_template_UNPROTECTED-TRANSIT-LSP-THRESHOLD;
          }
          container lsp-oor-yellow-state {
            description
              "Configuration for LSP OOR Yellow/Minor State";
            uses ncs_template_ALL-TRANSIT-LSP-THRESHOLD;
            uses ncs_template_UNPROTECTED-TRANSIT-LSP-THRESHOLD;
          }
        }
        container soft-preemption {
          description
            "Soft preemption configuration data";
          leaf timeout {
            type string;
            units "second";
            // NCS drop default statement
            description
              "This object sets the timeout in seconds before
               hard preemption is triggered.";
          }
          leaf frr-rewrite {
            type empty;
            description
              "This object controls whether FRR rewrite
               during soft preemption is enabled.";
          }
          leaf enable {
            type string;
            description
              "This object controls whether soft preemption
               is enabled. This object must be set before
               setting any other objects under the
               SoftPreemption class.";
          }
        }
        container fast-reroute {
          description
            "Configure fast reroute attributes";
          container timers {
            description
              "Configure fast reroute timers";
            leaf hold-backup {
              type string;
              units "second";
              description
                "Seconds before backup declared UP (0 disables
                 hold-timer)";
            }
            leaf promotion {
              type string;
              units "second";
              description
                "The value of the promotion timer in seconds";
            }
          }
        }
        container path-selection {
          description
            "Path selection configuration";
          container loose-metrics {
            description
              "Path selection Loose ERO Metric Class
               configuration";
            list loose-metric {
              // NCS patched for predictable order
              ordered-by user;
              key "class-type";
              description
                "Path selection Loose ERO Metric configuration";
              leaf class-type {
                type string;
                description
                  "Path Selection class Type";
              }
              leaf metric-type {
                type string;
                // NCS drop mandatory statement
                description
                  "Metric to use for ERO Expansion";
              }
            }
          }
          container invalidation {
            description
              "Deprecated";
            leaf path-invalidation-timeout {
              type string;
              description
                "Path Invalidation Timeout";
            }
            leaf path-invalidation-action {
              type string;
              description
                "Path Invalidation Action";
            }
          }
          container ignore-overload-role {
            description
              "Path selection to ignore overload node during
               CSPF";
            leaf head {
              type string;
              description
                "Set if the OL-bit is to be applied to tunnel
                 heads";
            }
            leaf mid {
              type string;
              description
                "Set if the OL-bit is to be applied to tunnel
                 midpoints";
            }
            leaf tail {
              type string;
              description
                "Set if the OL-bit is to be applied to tunnel
                 tails";
            }
          }
          container loose-affinities {
            description
              "Path selection Loose ERO Affinity Class
               configuration";
            list loose-affinity {
              // NCS patched for predictable order
              ordered-by user;
              key "class-type";
              description
                "Path selection Loose ERO Affinity
                 configuration";
              leaf class-type {
                type string;
                description
                  "Path Selection class Type";
              }
              leaf affinity {
                type string;
                description
                  "Affinity flags";
              }
              leaf mask {
                type string;
                description
                  "Affinity mask";
              }
            }
          }
          leaf cost-limit {
            type string;
            description
              "Path selection cost limit configuration for
               all tunnels";
          }
          leaf tiebreaker {
            type string;
            description
              "CSPF tiebreaker to use in path calculation";
          }
          leaf metric {
            type string;
            description
              "Metric to use in path calculation";
          }
          leaf loose-domain-match {
            type string;
            description
              "Use only the IGP instance of the incoming
               interface";
          }
          leaf delay-limit {
            type string;
            description
              "Path selection delay limit configuration for
               p2p tunnels (usec)";
          }
        }
        container affinity-mappings {
          description
            "Affinity Mapping Table configuration";
          list affinity-mapping {
            // NCS patched for predictable order
            ordered-by user;
            key "affinity-name";
            description
              "Affinity Mapping configuration";
            leaf affinity-name {
              type string;
              description
                "Affinity Name";
            }
            leaf value-type {
              type string;
              description
                "Affinity value type";
            }
            leaf value {
              type string;
              description
                "Affinity Value in Hex number or by Bit
                 position";
            }
          }
        }
        leaf log-nsr-status {
          type empty;
          description
            "Log NSR status messages";
        }
        leaf log-issu-status {
          type empty;
          description
            "Log ISSU status messages";
        }
        leaf reoptimize-link-up {
          type empty;
          description
            "Enable reoptimization based on link-up events";
        }
        leaf reoptimize-delay-cleanup-timer {
          type string;
          units "second";
          description
            "Reoptimization Delay Cleanup Value (seconds)";
        }
        leaf disable-reoptimize-affinity-failure {
          type empty;
          description
            "Disable reoptimization after affinity failures";
        }
        leaf maximum-tunnels {
          type string;
          // NCS drop default statement
          description
            "The maximum number of tunnel heads that will be
             allowed.";
        }
        leaf link-holddown-timer {
          type string;
          units "second";
          // NCS drop default statement
          description
            "Holddown time for links which had Path Errors
             in seconds";
        }
        leaf fault-oam {
          type empty;
          description
            "Enable Fault-OAM functionality for
             bidirectional tunnels";
        }
        leaf enable-unequal-load-balancing {
          type empty;
          description
            "Enable unequal load-balancing over tunnels to
             the same destination";
        }
        leaf log-tail {
          type empty;
          description
            "Log all tail tunnel events";
        }
        leaf reoptimize-delay-after-frr-timer {
          type string;
          units "second";
          description
            "Reoptimization Delay After FRR Value (seconds)";
        }
        leaf auto-bandwidth-collect-frequency {
          type string;
          units "minute";
          // NCS drop default statement
          description
            "Auto-bandwidth global collection frequency in
             minutes";
        }
        leaf reopt-delay-path-protect-switchover-timer {
          type string;
          units "second";
          // NCS drop default statement
          description
            "Seconds between path protect switchover and
             tunnel re-optimization. Set to 0 to disable";
        }
        leaf log-all {
          type empty;
          description
            "Always set to true";
        }
        leaf loose-path-retry-period {
          type string;
          // NCS drop default statement
          description
            "Signalling retry for tunnels terminating
             outside the headend area";
        }
        leaf reoptimize-load-balancing {
          type empty;
          description
            "Load balance bandwidth during reoptimization";
        }
        leaf log-head {
          type empty;
          description
            "Log all head tunnel events";
        }
        leaf path-selection-ignore-overload {
          type empty;
          description
            "Deprecated - do not use";
        }
        leaf graceful-preemption-on-bandwidth-reduction {
          type empty;
          description
            "Enable graceful preemption when there is a
             bandwidth reduction";
        }
        leaf advertise-explicit-nulls {
          type empty;
          description
            "Enable explicit-null advertising to PHOP";
        }
        leaf reoptimize-delay-install-timer {
          type string;
          units "second";
          description
            "Reoptimization Delay Install Value (seconds)";
        }
        leaf reoptimize-delay-after-affinity-failure-timer {
          type string;
          units "second";
          description
            "Delay reoptimizing current LSP after affinity
             failures";
        }
        leaf log-frr-protection {
          type string;
          description
            "Log FRR Protection messages";
        }
        leaf reoptimize-timer-frequency {
          type string;
          units "second";
          // NCS drop default statement
          description
            "Reoptimize timers period in seconds";
        }
        leaf log-mid {
          type empty;
          description
            "Log all mid tunnel events";
        }
        leaf log-preemption {
          type empty;
          description
            "Log tunnel preemption messages";
        }
      }
      container transport-profile {
        description
          "MPLS transport profile configuration data";
        container fault {
          description
            "Fault management";
          container protection-trigger {
            description
              "OAM events that trigger protection switching";
            container ldi {
              description
                "Protection switching due to LDI event";
              leaf disable {
                type empty;
                description
                  "Disable protection switching due to LDI
                   event";
              }
            }
            container lkr {
              description
                "Protection switching due to LKR event";
              leaf disable {
                type empty;
                description
                  "Disable protection switching due to LKR
                   event";
              }
            }
            leaf ais {
              type empty;
              description
                "Enable protection switching due to AIS event";
            }
          }
          leaf wait-to-restore-interval {
            type string;
            units "second";
            // NCS drop default statement
            description
              "Waiting time before restoring working LSP";
          }
          leaf refresh-interval {
            type string;
            units "second";
            // NCS drop default statement
            description
              "Periodic refresh interval for fault OAM
               messages";
          }
        }
        container alarm {
          description
            "Alarm management";
          container suppress-event {
            description
              "Suppress all tunnel/LSP alarms";
            leaf disable {
              type empty;
              description
                "Disable alarm suppression";
            }
          }
          leaf soak-time {
            type string;
            units "second";
            // NCS drop default statement
            description
              "Duration of soaking alarms";
          }
          leaf enable-alarm {
            type empty;
            description
              "Enable Transport Profile Alarm";
          }
        }
        container bfd {
          description
            "Configure BFD parameters";
          container min-interval-standby {
            description
              "Hello interval for standby transport profile
               LSPs, either in milli-seconds or in
               micro-seconds";
            leaf interval-standby-ms {
              type string;
              units "millisecond";
              description
                "Hello interval in milli-seconds";
            }
            leaf interval-standby-us {
              type string;
              units "microsecond";
              description
                "Hello interval in micro-seconds";
            }
          }
          container min-interval {
            description
              "Hello interval, either in milli-seconds or in
               micro-seconds";
            leaf interval-ms {
              type string;
              units "millisecond";
              description
                "Hello interval in milli-seconds";
            }
            leaf interval-us {
              type string;
              units "microsecond";
              description
                "Hello interval in micro-seconds";
            }
          }
          leaf detection-multiplier-standby {
            type string;
            description
              "Detect multiplier for standby transport
               profile LSP";
          }
          leaf detection-multiplier {
            type string;
            description
              "Detect multiplier";
          }
        }
        container midpoints {
          description
            "MPLS-TP tunnel mid-point table";
          list midpoint {
            // NCS patched for predictable order
            ordered-by user;
            key "midpoint-name";
            description
              "Transport profile mid-point identifier";
            container source {
              presence "Indicates a source node is configured.";
              description
                "Node identifier, tunnel identifier and
                 optional global identifier of the source of
                 the LSP";
              leaf node-id {
                type string;
                description
                  "Node identifier in IPv4 address format";
              }
              leaf tunnel-id {
                type string;
                // NCS drop mandatory statement
                description
                  "Tunnel identifier in numeric value";
              }
              leaf global-id {
                type string;
                description
                  "Global identifier in numeric value";
              }
            }
            container destination {
              presence "Indicates a destination node is configured.";
              description
                "Node identifier, tunnel identifier and
                 optional global identifier of the destination
                 of the LSP";
              leaf node-id {
                type string;
                description
                  "Node identifier in IPv4 address format";
              }
              leaf tunnel-id {
                type string;
                // NCS drop mandatory statement
                description
                  "Tunnel identifier in numeric value";
              }
              leaf global-id {
                type string;
                description
                  "Global identifier in numeric value";
              }
            }
            container forward-lsp {
              description
                "Forward transport profile LSP";
              container forward-io-map {
                presence "Indicates a forward-io-map node is configured.";
                description
                  "Label cross-connect of forward transport
                   profile LSP";
                leaf in-label {
                  type string;
                  description
                    "MPLS label";
                }
                leaf out-label {
                  type string;
                  // NCS drop mandatory statement
                  description
                    "Outgoing MPLS label";
                }
                leaf out-link {
                  type string;
                  // NCS drop mandatory statement
                  description
                    "Transport profile identifier of outgoing
                     link";
                }
              }
              leaf forward-bandwidth {
                type string;
                units "kbit/s";
                description
                  "Bandwidth of forward transport profile LSP";
              }
            }
            container reverse-lsp {
              description
                "none";
              container reverse-io-map {
                presence "Indicates a reverse-io-map node is configured.";
                description
                  "Label cross-connect of reverse transport
                   profile LSP";
                leaf in-label {
                  type string;
                  description
                    "MPLS label";
                }
                leaf out-label {
                  type string;
                  // NCS drop mandatory statement
                  description
                    "Outgoing MPLS label";
                }
                leaf out-link {
                  type string;
                  // NCS drop mandatory statement
                  description
                    "Transport profile identifier of outgoing
                     link";
                }
              }
              leaf reverse-bandwidth {
                type string;
                units "kbit/s";
                description
                  "Bandwidth of reverse transport profile LSP";
              }
            }
            leaf tunnel-name {
              type string;
              description
                "Tunnel Name";
            }
            leaf lsp-protect {
              type empty;
              description
                "Enable LSP protection";
            }
            leaf lsp-id {
              type string;
              description
                "Numeric identifier";
            }
            leaf midpoint-name {
              type string;
              description
                "Name of mid-point";
            }
          }
        }
        leaf global-id {
          type string;
          description
            "Transport profile global identifier";
        }
        leaf node-id {
          type string;
          description
            "Node identifier in IPv4 address format";
        }
      }
      container interfaces {
        description
          "Configure MPLS TE interfaces";
        list interface {
          // NCS patched for predictable order
          ordered-by user;
          key "interface-name";
          description
            "Configure an MPLS TE interface";
          container transport-profile-link {
            description
              "MPLS transport profile capable link";
            container links {
              description
                "Transport profile link table";
              list link {
                // NCS patched for predictable order
                ordered-by user;
                key "link-id";
                description
                  "Transport profile link";
                leaf link-id {
                  type string;
                  description
                    "Numeric link identifier";
                }
                leaf next-hop-type {
                  type string;
                  // NCS drop default statement
                  description
                    "Next hop type";
                }
                leaf next-hop-address {
                  // NCS drop when statement
                  type string;
                  description
                    "Next-hop address in IPv4 format";
                }
              }
            }
          }
          container lcac {
            description
              "LCAC specific MPLS interface configuration";
            container switchings {
              description
                "Set the te-link switching attributes";
              list switching {
                // NCS patched for predictable order
                ordered-by user;
                key "switching-id";
                description
                  "The te-link switching attributes";
                leaf encoding {
                  type string;
                  description
                    "Set the local encoding type";
                }
                leaf capability {
                  type string;
                  description
                    "Set the local switching capability";
                }
                leaf switching-id {
                  type string;
                  description
                    "Switching index";
                }
              }
            }
            container flood-area {
              description
                "Set the IGP instance into which this
                 interface is to be flooded (GMPLS only)";
              leaf igp-type {
                type string;
                description
                  "IGP type";
              }
              leaf process-name {
                type string;
                description
                  "Process name";
              }
              leaf area-id {
                type string;
                description
                  "Area ID";
              }
            }
            container attribute-name-xr {
              description
                "Set the interface attribute names";
              leaf-list attribute-name {
                // NCS patched for predictable order
                ordered-by user;
                type string;
                // NCS drop max-elements statement
                description
                  "Array of Attribute Names";
              }
            }
            container attribute-names {
              description
                "Attribute name table";
              list attribute-name {
                // NCS patched for predictable order
                ordered-by user;
                key "affinity-index";
                description
                  "Set the interface attribute names";
                leaf affinity-index {
                  type string;
                  description
                    "Specify the entry index";
                }
                leaf-list value {
                  // NCS patched for predictable order
                  ordered-by user;
                  type string;
                  // NCS drop min-elements statement
                  // NCS drop max-elements statement
                  description
                    "Array of Attribute Names";
                }
              }
            }
            container srlgs {
              description
                "Configure SRLG membership for the interface";
              list srlg {
                // NCS patched for predictable order
                ordered-by user;
                key "srlg-number";
                description
                  "SRLG membership number";
                leaf srlg-number {
                  type string;
                  description
                    "SRLG membership number";
                }
              }
            }
            container up-thresholds {
              description
                "Set thresholds for increased resource
                 availability in %";
              leaf-list up-threshold {
                // NCS patched for predictable order
                ordered-by user;
                type string;
                units "percentage";
                // NCS drop max-elements statement
                description
                  "Array of up threshold percentage";
              }
            }
            container down-thresholds {
              description
                "Set thresholds for decreased resource
                 availability in %";
              leaf-list down-threshold {
                // NCS patched for predictable order
                ordered-by user;
                type string;
                units "percentage";
                // NCS drop max-elements statement
                description
                  "Array of down threshold percentage";
              }
            }
            leaf bfd {
              type empty;
              description
                "Enable use of Bidirectional Forwarding
                 Detection";
            }
            leaf fault-oam-lockout {
              type empty;
              description
                "Lockout protection on the interface for Flex
                 LSP";
            }
            leaf attribute-flags {
              type string;
              description
                "Set user defined interface attribute flags";
            }
            leaf enable {
              type empty;
              description
                "Enable MPLS-TE on the link";
            }
            leaf admin-weight {
              type string;
              description
                "Set administrative weight for the interface";
            }
          }
          container global-attributes {
            description
              "MPLS TE global interface configuration";
            container backup-tunnels {
              description
                "Configure MPLS TE backup tunnels for this
                 interface";
              list backup-tunnel {
                // NCS patched for predictable order
                ordered-by user;
                key "tunnel-name";
                description
                  "Tunnel name";
                leaf tunnel-name {
                  type string;
                  description
                    "Tunnel name";
                }
              }
            }
            container auto-tunnel {
              description
                "Auto tunnel configuration";
              container backup {
                description
                  "Auto tunnel backup configuration";
                container exclude {
                  description
                    "Auto-tunnel backup exclusion criteria";
                  leaf srlg-mode {
                    type string;
                    description
                      "Set exclude SRLG mode for auto-tunnel
                       backup on this TE link";
                  }
                }
                leaf enable {
                  type empty;
                  description
                    "Enable auto-tunnel backup on this TE link";
                }
                leaf attribute-set {
                  type string;
                  description
                    "The name of attribute set to be applied to
                     this auto backup lsp";
                }
                leaf next-hop-only {
                  type empty;
                  description
                    "Enable NHOP-only mode for auto-tunnel
                     backup on this TE link";
                }
              }
            }
            container backup-paths {
              description
                "Configure MPLS TE backup tunnels for this
                 interface";
              list backup-path {
                // NCS patched for predictable order
                ordered-by user;
                key "tunnel-number";
                description
                  "Tunnel interface number";
                leaf tunnel-number {
                  type string;
                  description
                    "Tunnel interface number";
                }
              }
            }
          }
          leaf interface-name {
            type string;
            description
              "Interface name";
          }
        }
      }
      container gmpls-nni {
        description
          "GMPLS-NNI configuration";
        container topology-instances {
          description
            "GMPLS-NNI topology instance table";
          list topology-instance {
            // NCS patched for predictable order
            ordered-by user;
            // NCS drop must statement
            key "ospf-area-type igp-instance-name igp-type";
            description
              "GMPLS-NNI topology instance configuration";

            grouping TOPOLOGY-INSTANCE-CONTENT {
              description
                "TOPOLOGY INSTANCE CONTENT";
              container controllers {
                description
                  "GMPLS-NNI controllers";
                list controller {
                  // NCS patched for predictable order
                  ordered-by user;
                  key "controller-name";
                  description
                    "Configure a GMPLS NNI controller";
                  container tti-mode {
                    description
                      "Set tandem connection monitoring for the
                       interface";
                    leaf tti-mode-type {
                      type string;
                      description
                        "Type of Trail Trace Identifier";
                    }
                    leaf tcmid {
                      // NCS drop when statement
                      type string;
                      description
                        "Tandem Connection Monitoring ID for the
                         interface";
                    }
                  }
                  container affinity-names {
                    description
                      "Set the interface affinity names";
                    leaf-list affinity-name {
                      // NCS patched for predictable order
                      ordered-by user;
                      type string;
                      // NCS drop max-elements statement
                      description
                        "Array of Attribute Names";
                    }
                  }
                  leaf admin-weight {
                    type string;
                    description
                      "Set administrative weight for the
                       interface";
                  }
                  leaf enable {
                    type empty;
                    description
                      "Enable GMPLS-NNI on the link";
                  }
                  leaf delay {
                    type string;
                    description
                      "Set link delay for the interface";
                  }
                  leaf controller-name {
                    type string;
                    description
                      "Controller name";
                  }
                }
              }
            }
            leaf igp-type {
              type string;
              description
                "IGP type";
            }
            leaf igp-instance-name {
              type string;
              description
                "Name of IGP instance";
            }
            leaf ospf-area-type {
              type string;
              description
                "OSPF area format";
            }
            list ospf-int {
              // NCS patched for predictable order
              ordered-by user;
              // NCS drop when statement
              key "igp-area";
              description
                "ospf int";
              leaf igp-area {
                type string;
                description
                  "IGP area";
              }
              uses TOPOLOGY-INSTANCE-CONTENT;
            }
            list ospfip-addr {
              // NCS patched for predictable order
              ordered-by user;
              // NCS drop when statement
              key "address";
              description
                "ospfip addr";
              leaf address {
                type string;
                description
                  "Area ID if in IP address format";
              }
              uses TOPOLOGY-INSTANCE-CONTENT;
            }
          }
        }
        container tunnel-heads {
          description
            "GMPLS-NNI tunnel-head table";
          list tunnel-head {
            // NCS patched for predictable order
            ordered-by user;
            key "tunnel-id";
            description
              "The configuration for a GMPLS NNI tunnel
               head-end";
            container signalled-bandwidth {
              description
                "The existence of this configuration indicates
                 the signalled bandwidth has been set for the
                 tunnel";
              leaf signalled-bandwidth-type {
                type string;
                description
                  "The g.709 signal type requested";
              }
              leaf bitrate {
                // NCS drop when statement
                type string;
                units "kbit/s";
                description
                  "Bitrate value in Kbps for ODUflex framing
                   type";
              }
              leaf od-uflex-framing-type {
                // NCS drop when statement
                type string;
                description
                  "Framing type in case of ODUflex signal type";
              }
            }
            container destination {
              description
                "The existence of this configuration indicates
                 the destination has been set for the tunnel";
              leaf destination {
                type string;
                description
                  "IPV4 tunnel destination";
              }
              leaf destination-type {
                type string;
                description
                  "Destination type whether it is unicast or
                   unnumbered";
              }
              leaf interface-if-index {
                type string;
                description
                  "Interface index of port";
              }
            }
            container protection-switching {
              description
                "The configuration for a GMPLS NNI tunnel
                 protection switch";
              leaf lockout {
                type string;
                description
                  "The configuration is used to prevent switch
                   over for a particular path type in tunnel";
              }
            }
            container logging {
              description
                "Tunnel event logging";
              leaf active-lsp-message {
                type empty;
                description
                  "Log all tunnel messages for changes in
                   Active LSP";
              }
              leaf homepath-state-message {
                type empty;
                description
                  "Log all messages for changes in state of
                   Homepath of Working LSP";
              }
              leaf signalling-state-message {
                type empty;
                description
                  "Log all tunnel sub-LSP state messages";
              }
              leaf path-change-message {
                type empty;
                description
                  "Log all tunnel messages for changes in
                   path-change";
              }
              leaf static-cross-connect-message {
                type empty;
                description
                  "Log all tunnel messages for static
                   cross-connect messages";
              }
              leaf tunnel-state-message {
                type empty;
                description
                  "Log all tunnel messages for changes in
                   tunnel-state";
              }
              leaf insufficient-bw-message {
                type empty;
                description
                  "Log tunnel messages for insufficient
                   bandwidth";
              }
            }
            container path-options {
              description
                "GMPLS NNI path options";
              list path-option {
                // NCS patched for predictable order
                ordered-by user;
                key "preference-level";
                description
                  "The existence of this configuration
                   indicates the path options have been set for
                   the tunnel";
                leaf preference-level {
                  type string;
                  description
                    "Preference level for this path option";
                }
                leaf path-type {
                  type string;
                  description
                    "The type of the path option";
                }
                leaf path-id {
                  type string;
                  description
                    "The ID of the IP explicit path associated
                     with this option";
                }
                leaf path-name {
                  type string;
                  description
                    "The name of the IP explicit path associated
                     with this option";
                }
                leaf protected-by-preference-level {
                  type string;
                  description
                    "Preference level of the protecting explicit
                     path. ";
                }
                leaf restore-by-preference-level {
                  type string;
                  description
                    "Preference level of the restore path. ";
                }
                leaf xro-type {
                  type string;
                  // NCS drop mandatory statement
                  description
                    "The route-exclusion type";
                }
                leaf xro-attribute-set-name {
                  type string;
                  description
                    "The name of the XRO attribute set to be
                     used for this path-option";
                }
                leaf affinity-attribute-set-name {
                  type string;
                  description
                    "The name of the affinity attribute set to
                     be used for this path-option";
                }
                leaf lockdown {
                  type string;
                  description
                    "Lockdown properties";
                }
              }
            }
            container static-uni {
              description
                "The existence of this configuration indicates
                 the static UNI endpoints have been set for
                 the tunnel";
              leaf ingress-controller-name {
                type string;
                description
                  "Name of  ingress controller";
              }
              leaf egress-controller-if-index {
                type string;
                description
                  "Interface index of Egress controller";
              }
              leaf ingress-type {
                type string;
                description
                  "Ingress type whether it is xconnect or
                   terminated";
              }
              leaf egress-type {
                type string;
                description
                  "Egress type whether it is xconnect or
                   terminated";
              }
            }
            leaf enable {
              type empty;
              description
                "The existence of this configuration indicates
                 the a new GMPLS NNI tunnel has been enabled";
            }
            leaf announce-srlg {
              type empty;
              description
                "Announce SRLG on term interface for the
                 tunnel";
            }
            leaf restore-lsp-shutdown {
              type empty;
              description
                "The existence of this configuration indicates
                 the restore LSP of tunnel is shutdown";
            }
            leaf current-lsp-shutdown {
              type empty;
              description
                "The existence of this configuration indicates
                 the current/working LSP of tunnel is shutdown";
            }
            leaf path-selection-metric {
              type string;
              description
                "Path selection configuration for this
                 specific tunnel";
            }
            leaf payload {
              type string;
              description
                "The existence of this configuration indicates
                 the Payload type have been set for the tunnel";
            }
            leaf standby-lsp-shutdown {
              type empty;
              description
                "The existence of this configuration indicates
                 the standby/protect LSP of tunnel is shutdown";
            }
            leaf shutdown {
              type empty;
              description
                "The existence of this configuration indicates
                 the tunnel is shutdown";
            }
            leaf path-protection-attribute-set-profile {
              type string;
              description
                "The name of the path-protection profile to be
                 included in signalling messages";
            }
            leaf tunnel-id {
              type string;
              description
                "Tunnel ID";
            }
            uses ncs_template_RECORD-ROUTE;
            uses ncs_template_SIGNALLED-NAME;
          }
        }
        leaf path-selection-metric {
          type string;
          description
            "Path selection configuration for all gmpls nni
             tunnels";
        }
        leaf enable-gmpls-nni {
          type empty;
          description
            "Enable MPLS Traffic Engineering GMPLS-NNI";
        }
      }
      container lcac {
        description
          "LCAC specific MPLS global configuration";
        container bfd {
          description
            "BFD configuration";
          leaf interval {
            type string;
            units "millisecond";
            description
              "Hello interval for BFD sessions created by TE";
          }
          leaf detection-multiplier {
            type string;
            description
              "Detection multiplier for BFD sessions created
               by TE";
          }
        }
        container flooding-threshold {
          description
            "Configure flooding threshold as percentage of
             total link bandwidth.";
          leaf up-stream {
            type string;
            units "percentage";
            description
              "Upward flooding Threshold in percentages of
               total bandwidth";
          }
          leaf down-stream {
            type string;
            units "percentage";
            description
              "Downward flooding Threshold in percentages of
               total bandwidth";
          }
        }
        leaf bandwidth-hold-timer {
          type string;
          units "second";
          description
            "Bandwidth hold timer value (seconds)";
        }
        leaf delay-preempt-bundle-capacity-timer {
          type string;
          units "second";
          description
            "Bundle capacity preemption timer value
             (seconds)";
        }
        leaf periodic-flooding-timer {
          type string;
          units "second";
          description
            "Periodic flooding value (seconds)";
        }
      }
      leaf enable-traffic-engineering {
        type empty;
        description
          "Enable MPLS Traffic Engineering";
      }
    }
  }
  augment "/ncs:devices/ncs:template/ncs:ned-id/ncs:config/a1:interface-configurations/a1:interface-configuration" {
    container tunnel-te-attributes {
      description
        "MPLS tunnel attributes";
      container backup-bandwidth {
        description
          "Tunnel backup bandwidth requirement";
        leaf dste-type {
          type string;
          description
            "DSTE-standard flag";
        }
        leaf pool-type {
          type string;
          description
            "Backup bandwidth pool type, relevant only if
             DSTEType is PreStandardDSTE";
        }
        leaf class-type {
          type string;
          description
            "Backup bandwidth class type, relevant only if
             DSTEType is StandardDSTE";
        }
        leaf limit-type {
          type string;
          description
            "Backup bandwidth limit type";
        }
        leaf backup-bandwidth {
          type string;
          description
            "Backup bandwidth requested by this tunnel in
             kbps. Ignored if bandwidth limit type is
             unlimited.";
        }
      }
      container bfd-over-lsp {
        description
          "BFD over TE LSP";
        leaf dampening-initial-wait {
          type string;
          description
            "Initial delay in milliseconds (default 16000)";
        }
        leaf fast-detect {
          type string;
          description
            "Enable BFD Fast Detect On the tunnel";
        }
        leaf enable {
          type empty;
          description
            "Always set to true";
        }
        leaf multiplier {
          type string;
          description
            "Specify the multiplier for BFD failure
             detection";
        }
        leaf bringup-timeout {
          type string;
          description
            "Wait for session to come up in seconds
             (default 60)";
        }
        leaf periodic-ping-disable {
          type empty;
          description
            "Disable Periodic LSP Ping for BFD over LSP";
        }
        leaf dampening-secondary-wait {
          type string;
          description
            "Secondary delay in milliseconds (default
             20000)";
        }
        leaf periodic-ping-interval {
          type string;
          description
            "Periodic LSP Ping Interval in seconds (default
             120)";
        }
        leaf dampening-maximum-wait {
          type string;
          description
            "Maximum delay in milliseconds (default 600000)";
        }
        leaf minimum-interval {
          type string;
          description
            "Specify the minimum interval for BFD failure
             detection";
        }
        leaf encap-mode {
          type string;
          description
            "Specify BFD Encap Mode on the tunnel";
        }
      }
      container binding-segment-id-mpls {
        description
          "Allocate MPLS binding segment ID";
        leaf segment-id-type {
          type string;
          description
            "MPLS label value type";
        }
        leaf label-value {
          // NCS drop when statement
          type string;
          description
            "MPLS label";
        }
      }
      container tunnel-path-protection {
        description
          "MPLS tunnel path protected configs";
        leaf enable {
          type empty;
          description
            "Enable Path Protection";
        }
      }
      container path-option-protects {
        description
          "Tunnel path protection state";
        list path-option-protect {
          // NCS patched for predictable order
          ordered-by user;
          key "protection";
          description
            "Tunnel path protection";
          container path-options {
            description
              "Tunnel path options";
            list path-option {
              // NCS patched for predictable order
              ordered-by user;
              key "preference-level";
              description
                "A tunnel path option";
              leaf preference-level {
                type string;
                description
                  "Preference level for this path option";
              }
              leaf path-type {
                type string;
                // NCS drop mandatory statement
                description
                  "The type of the path option";
              }
              leaf path-id {
                type string;
                description
                  "The ID of the IP explicit path associated
                   with this option";
              }
              leaf path-name {
                type string;
                description
                  "The name of the IP explicit path associated
                   with this option";
              }
              leaf path-property {
                type string;
                // NCS drop default statement
                description
                  "Deprecated";
              }
              leaf interface {
                type string;
                description
                  "Deprecated";
              }
              leaf output-label {
                type string;
                // NCS drop default statement
                description
                  "Deprecated";
              }
              leaf destination {
                type string;
                // NCS drop default statement
                description
                  "Deprecated";
              }
              leaf lockdown {
                type string;
                // NCS drop default statement
                description
                  "Lockdown properties";
              }
              leaf verbatim {
                type string;
                // NCS drop default statement
                description
                  "Verbatim properties";
              }
              leaf pce {
                type string;
                // NCS drop default statement
                description
                  "PCE properties";
              }
              leaf pce-address {
                type string;
                // NCS drop default statement
                description
                  "PCE address";
              }
              leaf igp-type {
                type string;
                // NCS drop default statement
                description
                  "IGP type";
              }
              leaf igp-instance {
                type string;
                description
                  "IGP instance name";
              }
              leaf igp-area {
                type string;
                // NCS drop default statement
                description
                  "IGP area ID in integer format";
              }
              leaf igp-area-ip-address-id {
                type string;
                // NCS drop default statement
                description
                  "IGP area ID in IP address format";
              }
              leaf path-option-attribute-set-name {
                type string;
                description
                  "Path option attribute set name";
              }
              leaf protected-by-preference-level {
                type string;
                // NCS drop default statement
                description
                  "Preference level of the protecting explicit
                   path. Leave unset in order to not use an
                   explicit protecting path";
              }
              leaf segment-routing {
                type string;
                // NCS drop default statement
                description
                  "Deprecated";
              }
              leaf sticky {
                type string;
                // NCS drop default statement
                description
                  "Sticky properties";
              }
            }
          }
          leaf protection {
            type string;
            description
              "Protection type for this path";
          }
        }
      }
      container bidirectional {
        description
          "Tunnel Interface Bidirectional configuration
           data";
        container association-corouted-type {
          description
            "Association Corouted Type";
          container fault-oam {
            description
              "Tunnel Fault OAM";
            leaf enable {
              type empty;
              description
                "This object is only valid for bidirectional
                 tunnel interfaces and it controls whether
                 that interface has fault OAM enabled on it
                 or not.";
            }
          }
          leaf wrap-protection-enable {
            type empty;
            description
              "This object is only valid for bidirectional
               tunnel interfaces and it controls whether
               that interface has LSP Wrap protectionenabled
               on it or not.";
          }
          leaf enable {
            type empty;
            description
              "Controls whether association type is
               co-routed.";
          }
          leaf disable-protection-object {
            type empty;
            description
              "Disable signaling of RSVP Protection Object";
          }
        }
        container association-parameters {
          presence "Indicates a association-parameters node is configured.";
          description
            "Association ID, Source IP Address, and Global
             ID";
          leaf association-id {
            type string;
            // NCS drop mandatory statement
            description
              "Association ID";
          }
          leaf association-source-address {
            type string;
            // NCS drop mandatory statement
            description
              "Association Source IP Address";
          }
          leaf association-is-global-id-configured {
            type string;
            description
              "Is Association Global ID Configured";
          }
          leaf association-global-id {
            type string;
            description
              "Association Global ID";
          }
        }
        leaf enabled {
          type empty;
          description
            "This object is only valid for tunnel
             interfaces and it controls whether that
             interface has bidirectional enabled on it or
             not.";
        }
      }
      container admin-mode {
        description
          "Performs admin operations on the optical tunnel
           interface";
        leaf deactivate-tunnel {
          type empty;
          description
            "Performs signalling operation to deactivate
             optical tunnel";
        }
      }
      container switching {
        description
          "Specify tunnel LSPs switching capability
           descriptor";
        container transit {
          presence "Indicates a transit node is configured.";
          description
            "Specify transit switching descriptor
             parameters";
          leaf capability {
            type string;
            // NCS drop mandatory statement
            description
              "Switching capability";
          }
          leaf encoding {
            type string;
            description
              "LSP encoding";
          }
        }
        container endpoint {
          presence "Indicates a endpoint node is configured.";
          description
            "Specify end point switching descriptor
             parameters";
          leaf capability {
            type string;
            // NCS drop mandatory statement
            description
              "Switching capability";
          }
          leaf encoding {
            type string;
            description
              "LSP encoding";
          }
        }
      }
      container pce {
        description
          "PCE config";
        leaf enable {
          type empty;
          description
            "Always set to true";
        }
        leaf delegation {
          type empty;
          description
            "Enable PCE Delegation";
        }
      }
      uses ncs_template_FORWARD-CLASS;
      uses ncs_template_TUNNEL-PATH-SELECTION;
      uses ncs_template_AUTO-BANDWIDTH;
      uses ncs_template_PRIORITY;
      uses ncs_template_DESTINATION;
      uses ncs_template_RECORD-ROUTE;
      uses ncs_template_AFFINITY-MASK;
      uses ncs_template_FORWARDING-ADJACENCY;
      uses ncs_template_LOGGING;
      uses ncs_template_BANDWIDTH;
      uses ncs_template_AUTOROUTE;
      uses ncs_template_POLICY-CLASSES;
      uses ncs_template_PATH-SELECTION-METRIC;
      uses ncs_template_NEW-STYLE-AFFINITY-TABLE;
      uses ncs_template_SOFT-PREEMPTION;
      uses ncs_template_FAST-REROUTE;
      uses ncs_template_LOAD-SHARE;
      uses ncs_template_SIGNALLED-NAME;
    }
    description
      "This augment extends the configuration data of
       'Cisco-IOS-XR-ifmgr-cfg'";
  }
  augment "/ncs:devices/ncs:device/ncs:live-status/a1:interface-configurations/a1:interface-configuration" {
    container tunnel-te-attributes {
      tailf:ncs-device-type "netconf";
      tailf:display-when "not(../../../../ncs:module) or ../../../../ncs:module[ncs:name='Cisco-IOS-XR-mpls-te-cfg'] or (../../../../ncs:live-status-protocol[not(ncs:capability)]) or (../../../../ncs:live-status-protocol/ncs:capability/ncs:module[.='Cisco-IOS-XR-mpls-te-cfg'])";
      description
        "MPLS tunnel attributes";
      container backup-bandwidth {
        description
          "Tunnel backup bandwidth requirement";
        leaf dste-type {
          type Mpls-te-bandwidth-dste;
          description
            "DSTE-standard flag";
        }
        leaf pool-type {
          type Mpls-te-backup-bandwidth-pool;
          description
            "Backup bandwidth pool type, relevant only if
             DSTEType is PreStandardDSTE";
        }
        leaf class-type {
          type Mpls-te-backup-bandwidth-class;
          description
            "Backup bandwidth class type, relevant only if
             DSTEType is StandardDSTE";
        }
        leaf limit-type {
          type Mpls-te-bandwidth-limit;
          description
            "Backup bandwidth limit type";
        }
        leaf backup-bandwidth {
          type uint32 {
            range "1..4294967295";
          }
          description
            "Backup bandwidth requested by this tunnel in
             kbps. Ignored if bandwidth limit type is
             unlimited.";
        }
      }
      container bfd-over-lsp {
        description
          "BFD over TE LSP";
        leaf dampening-initial-wait {
          type uint32 {
            range "1..518400000";
          }
          description
            "Initial delay in milliseconds (default 16000)";
        }
        leaf fast-detect {
          type Mpls-tebfd-session;
          description
            "Enable BFD Fast Detect On the tunnel";
        }
        leaf enable {
          type empty;
          description
            "Always set to true";
        }
        leaf multiplier {
          type uint32 {
            range "3..10";
          }
          description
            "Specify the multiplier for BFD failure
             detection";
        }
        leaf bringup-timeout {
          type uint32 {
            range "10..3600";
          }
          description
            "Wait for session to come up in seconds
             (default 60)";
        }
        leaf periodic-ping-disable {
          type empty;
          description
            "Disable Periodic LSP Ping for BFD over LSP";
        }
        leaf dampening-secondary-wait {
          type uint32 {
            range "1..518400000";
          }
          description
            "Secondary delay in milliseconds (default
             20000)";
        }
        leaf periodic-ping-interval {
          type uint32 {
            range "60..3600";
          }
          description
            "Periodic LSP Ping Interval in seconds (default
             120)";
        }
        leaf dampening-maximum-wait {
          type uint32 {
            range "1..518400000";
          }
          description
            "Maximum delay in milliseconds (default 600000)";
        }
        leaf minimum-interval {
          type uint32 {
            range "3..30000";
          }
          description
            "Specify the minimum interval for BFD failure
             detection";
        }
        leaf encap-mode {
          type uint32 {
            range "0..1";
          }
          description
            "Specify BFD Encap Mode on the tunnel";
        }
      }
      container binding-segment-id-mpls {
        description
          "Allocate MPLS binding segment ID";
        leaf segment-id-type {
          type Binding-segment-id;
          description
            "MPLS label value type";
        }
        leaf label-value {
          // NCS drop when statement
          type uint32 {
            range "16..4015";
          }
          description
            "MPLS label";
        }
      }
      container tunnel-path-protection {
        description
          "MPLS tunnel path protected configs";
        leaf enable {
          type empty;
          description
            "Enable Path Protection";
        }
      }
      container path-option-protects {
        description
          "Tunnel path protection state";
        list path-option-protect {
          key "protection";
          description
            "Tunnel path protection";
          container path-options {
            description
              "Tunnel path options";
            list path-option {
              key "preference-level";
              description
                "A tunnel path option";
              leaf preference-level {
                type uint32 {
                  range "1..1000";
                }
                description
                  "Preference level for this path option";
              }
              leaf path-type {
                type Mpls-te-path-option;
                // NCS drop mandatory statement
                description
                  "The type of the path option";
              }
              leaf path-id {
                type uint32 {
                  range "1..65535";
                }
                description
                  "The ID of the IP explicit path associated
                   with this option";
              }
              leaf path-name {
                type string;
                description
                  "The name of the IP explicit path associated
                   with this option";
              }
              leaf path-property {
                type uint32;
                // NCS drop default statement
                description
                  "Deprecated";
              }
              leaf interface {
                type xr:Interface-name;
                description
                  "Deprecated";
              }
              leaf output-label {
                type uint32;
                // NCS drop default statement
                description
                  "Deprecated";
              }
              leaf destination {
                type inet:ipv4-address-no-zone;
                // NCS drop default statement
                description
                  "Deprecated";
              }
              leaf lockdown {
                type Mpls-te-path-option-property;
                // NCS drop default statement
                description
                  "Lockdown properties";
              }
              leaf verbatim {
                type Mpls-te-path-option-property;
                // NCS drop default statement
                description
                  "Verbatim properties";
              }
              leaf pce {
                type Mpls-te-path-option-property;
                // NCS drop default statement
                description
                  "PCE properties";
              }
              leaf pce-address {
                type inet:ipv4-address-no-zone;
                // NCS drop default statement
                description
                  "PCE address";
              }
              leaf igp-type {
                type Mpls-te-igp-protocol;
                // NCS drop default statement
                description
                  "IGP type";
              }
              leaf igp-instance {
                type string {
                  length "1..40";
                }
                description
                  "IGP instance name";
              }
              leaf igp-area {
                type uint32;
                // NCS drop default statement
                description
                  "IGP area ID in integer format";
              }
              leaf igp-area-ip-address-id {
                type inet:ipv4-address-no-zone;
                // NCS drop default statement
                description
                  "IGP area ID in IP address format";
              }
              leaf path-option-attribute-set-name {
                type string;
                description
                  "Path option attribute set name";
              }
              leaf protected-by-preference-level {
                type uint32 {
                  range "1..1000";
                }
                // NCS drop default statement
                description
                  "Preference level of the protecting explicit
                   path. Leave unset in order to not use an
                   explicit protecting path";
              }
              leaf segment-routing {
                type Mpls-te-path-option-property;
                // NCS drop default statement
                description
                  "Deprecated";
              }
              leaf sticky {
                type Mpls-te-path-option-property;
                // NCS drop default statement
                description
                  "Sticky properties";
              }
            }
          }
          leaf protection {
            type Mpls-te-path-option-protection;
            description
              "Protection type for this path";
          }
        }
      }
      container bidirectional {
        description
          "Tunnel Interface Bidirectional configuration
           data";
        container association-corouted-type {
          description
            "Association Corouted Type";
          container fault-oam {
            description
              "Tunnel Fault OAM";
            leaf enable {
              type empty;
              description
                "This object is only valid for bidirectional
                 tunnel interfaces and it controls whether
                 that interface has fault OAM enabled on it
                 or not.";
            }
          }
          leaf wrap-protection-enable {
            type empty;
            description
              "This object is only valid for bidirectional
               tunnel interfaces and it controls whether
               that interface has LSP Wrap protectionenabled
               on it or not.";
          }
          leaf enable {
            type empty;
            description
              "Controls whether association type is
               co-routed.";
          }
          leaf disable-protection-object {
            type empty;
            description
              "Disable signaling of RSVP Protection Object";
          }
        }
        container association-parameters {
          presence "Indicates a association-parameters node is configured.";
          description
            "Association ID, Source IP Address, and Global
             ID";
          leaf association-id {
            type uint32 {
              range "0..65535";
            }
            // NCS drop mandatory statement
            description
              "Association ID";
          }
          leaf association-source-address {
            type inet:ipv4-address-no-zone;
            // NCS drop mandatory statement
            description
              "Association Source IP Address";
          }
          leaf association-is-global-id-configured {
            type boolean;
            description
              "Is Association Global ID Configured";
          }
          leaf association-global-id {
            type uint32 {
              range "0..4294967295";
            }
            description
              "Association Global ID";
          }
        }
        leaf enabled {
          type empty;
          description
            "This object is only valid for tunnel
             interfaces and it controls whether that
             interface has bidirectional enabled on it or
             not.";
        }
      }
      container admin-mode {
        description
          "Performs admin operations on the optical tunnel
           interface";
        leaf deactivate-tunnel {
          type empty;
          description
            "Performs signalling operation to deactivate
             optical tunnel";
        }
      }
      container switching {
        description
          "Specify tunnel LSPs switching capability
           descriptor";
        container transit {
          presence "Indicates a transit node is configured.";
          description
            "Specify transit switching descriptor
             parameters";
          leaf capability {
            type Mpls-te-switching-cap;
            // NCS drop mandatory statement
            description
              "Switching capability";
          }
          leaf encoding {
            type Mpls-te-switching-encode;
            description
              "LSP encoding";
          }
        }
        container endpoint {
          presence "Indicates a endpoint node is configured.";
          description
            "Specify end point switching descriptor
             parameters";
          leaf capability {
            type Mpls-te-switching-cap;
            // NCS drop mandatory statement
            description
              "Switching capability";
          }
          leaf encoding {
            type Mpls-te-switching-encode;
            description
              "LSP encoding";
          }
        }
      }
      container pce {
        description
          "PCE config";
        leaf enable {
          type empty;
          description
            "Always set to true";
        }
        leaf delegation {
          type empty;
          description
            "Enable PCE Delegation";
        }
      }
      uses live_ncs_FORWARD-CLASS;
      uses live_ncs_TUNNEL-PATH-SELECTION;
      uses live_ncs_AUTO-BANDWIDTH;
      uses live_ncs_PRIORITY;
      uses live_ncs_DESTINATION;
      uses live_ncs_RECORD-ROUTE;
      uses live_ncs_AFFINITY-MASK;
      uses live_ncs_FORWARDING-ADJACENCY;
      uses live_ncs_LOGGING;
      uses live_ncs_BANDWIDTH;
      uses live_ncs_AUTOROUTE;
      uses live_ncs_POLICY-CLASSES;
      uses live_ncs_PATH-SELECTION-METRIC;
      uses live_ncs_NEW-STYLE-AFFINITY-TABLE;
      uses live_ncs_SOFT-PREEMPTION;
      uses live_ncs_FAST-REROUTE;
      uses live_ncs_LOAD-SHARE;
      uses live_ncs_SIGNALLED-NAME;
    }
    description
      "This augment extends the configuration data of
       'Cisco-IOS-XR-ifmgr-cfg'";
  }
  augment "/ncs:devices/ncs:device/ncs:config/a1:interface-configurations/a1:interface-configuration" {
    container tunnel-te-attributes {
      tailf:ncs-device-type "netconf";
      tailf:display-when "not(../../../../ncs:module) or ../../../../ncs:module[ncs:name='Cisco-IOS-XR-mpls-te-cfg']";
      description
        "MPLS tunnel attributes";
      container backup-bandwidth {
        description
          "Tunnel backup bandwidth requirement";
        leaf dste-type {
          type Mpls-te-bandwidth-dste;
          description
            "DSTE-standard flag";
        }
        leaf pool-type {
          type Mpls-te-backup-bandwidth-pool;
          description
            "Backup bandwidth pool type, relevant only if
             DSTEType is PreStandardDSTE";
        }
        leaf class-type {
          type Mpls-te-backup-bandwidth-class;
          description
            "Backup bandwidth class type, relevant only if
             DSTEType is StandardDSTE";
        }
        leaf limit-type {
          type Mpls-te-bandwidth-limit;
          description
            "Backup bandwidth limit type";
        }
        leaf backup-bandwidth {
          type uint32 {
            range "1..4294967295";
          }
          description
            "Backup bandwidth requested by this tunnel in
             kbps. Ignored if bandwidth limit type is
             unlimited.";
        }
      }
      container bfd-over-lsp {
        description
          "BFD over TE LSP";
        leaf dampening-initial-wait {
          type uint32 {
            range "1..518400000";
          }
          description
            "Initial delay in milliseconds (default 16000)";
        }
        leaf fast-detect {
          type Mpls-tebfd-session;
          description
            "Enable BFD Fast Detect On the tunnel";
        }
        leaf enable {
          type empty;
          description
            "Always set to true";
        }
        leaf multiplier {
          type uint32 {
            range "3..10";
          }
          description
            "Specify the multiplier for BFD failure
             detection";
        }
        leaf bringup-timeout {
          type uint32 {
            range "10..3600";
          }
          description
            "Wait for session to come up in seconds
             (default 60)";
        }
        leaf periodic-ping-disable {
          type empty;
          description
            "Disable Periodic LSP Ping for BFD over LSP";
        }
        leaf dampening-secondary-wait {
          type uint32 {
            range "1..518400000";
          }
          description
            "Secondary delay in milliseconds (default
             20000)";
        }
        leaf periodic-ping-interval {
          type uint32 {
            range "60..3600";
          }
          description
            "Periodic LSP Ping Interval in seconds (default
             120)";
        }
        leaf dampening-maximum-wait {
          type uint32 {
            range "1..518400000";
          }
          description
            "Maximum delay in milliseconds (default 600000)";
        }
        leaf minimum-interval {
          type uint32 {
            range "3..30000";
          }
          description
            "Specify the minimum interval for BFD failure
             detection";
        }
        leaf encap-mode {
          type uint32 {
            range "0..1";
          }
          description
            "Specify BFD Encap Mode on the tunnel";
        }
      }
      container binding-segment-id-mpls {
        description
          "Allocate MPLS binding segment ID";
        leaf segment-id-type {
          type Binding-segment-id;
          description
            "MPLS label value type";
        }
        leaf label-value {
          when "../segment-id-type = 'specified-label'" {
            tailf:xpath-root 3;
            description
              "../SegmentIDType = SpecifiedLabel";
          }
          type uint32 {
            range "16..4015";
          }
          description
            "MPLS label";
        }
      }
      container tunnel-path-protection {
        description
          "MPLS tunnel path protected configs";
        leaf enable {
          type empty;
          description
            "Enable Path Protection";
        }
      }
      container path-option-protects {
        description
          "Tunnel path protection state";
        list path-option-protect {
          key "protection";
          description
            "Tunnel path protection";
          container path-options {
            description
              "Tunnel path options";
            list path-option {
              key "preference-level";
              description
                "A tunnel path option";
              leaf preference-level {
                type uint32 {
                  range "1..1000";
                }
                description
                  "Preference level for this path option";
              }
              leaf path-type {
                type Mpls-te-path-option;
                mandatory true;
                description
                  "The type of the path option";
              }
              leaf path-id {
                type uint32 {
                  range "1..65535";
                }
                description
                  "The ID of the IP explicit path associated
                   with this option";
              }
              leaf path-name {
                type string;
                description
                  "The name of the IP explicit path associated
                   with this option";
              }
              leaf path-property {
                type uint32;
                default "0";
                description
                  "Deprecated";
              }
              leaf interface {
                type xr:Interface-name;
                description
                  "Deprecated";
              }
              leaf output-label {
                type uint32;
                default "0";
                description
                  "Deprecated";
              }
              leaf destination {
                type inet:ipv4-address-no-zone;
                default "0.0.0.0";
                description
                  "Deprecated";
              }
              leaf lockdown {
                type Mpls-te-path-option-property;
                default "none";
                description
                  "Lockdown properties";
              }
              leaf verbatim {
                type Mpls-te-path-option-property;
                default "none";
                description
                  "Verbatim properties";
              }
              leaf pce {
                type Mpls-te-path-option-property;
                default "none";
                description
                  "PCE properties";
              }
              leaf pce-address {
                type inet:ipv4-address-no-zone;
                default "0.0.0.0";
                description
                  "PCE address";
              }
              leaf igp-type {
                type Mpls-te-igp-protocol;
                default "none";
                description
                  "IGP type";
              }
              leaf igp-instance {
                type string {
                  length "1..40";
                }
                description
                  "IGP instance name";
              }
              leaf igp-area {
                type uint32;
                default "0";
                description
                  "IGP area ID in integer format";
              }
              leaf igp-area-ip-address-id {
                type inet:ipv4-address-no-zone;
                default "0.0.0.0";
                description
                  "IGP area ID in IP address format";
              }
              leaf path-option-attribute-set-name {
                type string;
                description
                  "Path option attribute set name";
              }
              leaf protected-by-preference-level {
                type uint32 {
                  range "1..1000";
                }
                default "1";
                description
                  "Preference level of the protecting explicit
                   path. Leave unset in order to not use an
                   explicit protecting path";
              }
              leaf segment-routing {
                type Mpls-te-path-option-property;
                default "none";
                description
                  "Deprecated";
              }
              leaf sticky {
                type Mpls-te-path-option-property;
                default "none";
                description
                  "Sticky properties";
              }
            }
          }
          leaf protection {
            type Mpls-te-path-option-protection;
            description
              "Protection type for this path";
          }
        }
      }
      container bidirectional {
        description
          "Tunnel Interface Bidirectional configuration
           data";
        container association-corouted-type {
          description
            "Association Corouted Type";
          container fault-oam {
            description
              "Tunnel Fault OAM";
            leaf enable {
              type empty;
              description
                "This object is only valid for bidirectional
                 tunnel interfaces and it controls whether
                 that interface has fault OAM enabled on it
                 or not.";
            }
          }
          leaf wrap-protection-enable {
            type empty;
            description
              "This object is only valid for bidirectional
               tunnel interfaces and it controls whether
               that interface has LSP Wrap protectionenabled
               on it or not.";
          }
          leaf enable {
            type empty;
            description
              "Controls whether association type is
               co-routed.";
          }
          leaf disable-protection-object {
            type empty;
            description
              "Disable signaling of RSVP Protection Object";
          }
        }
        container association-parameters {
          presence "Indicates a association-parameters node is configured.";
          description
            "Association ID, Source IP Address, and Global
             ID";
          leaf association-id {
            type uint32 {
              range "0..65535";
            }
            mandatory true;
            description
              "Association ID";
          }
          leaf association-source-address {
            type inet:ipv4-address-no-zone;
            mandatory true;
            description
              "Association Source IP Address";
          }
          leaf association-is-global-id-configured {
            type boolean;
            description
              "Is Association Global ID Configured";
          }
          leaf association-global-id {
            type uint32 {
              range "0..4294967295";
            }
            description
              "Association Global ID";
          }
        }
        leaf enabled {
          type empty;
          description
            "This object is only valid for tunnel
             interfaces and it controls whether that
             interface has bidirectional enabled on it or
             not.";
        }
      }
      container admin-mode {
        description
          "Performs admin operations on the optical tunnel
           interface";
        leaf deactivate-tunnel {
          type empty;
          description
            "Performs signalling operation to deactivate
             optical tunnel";
        }
      }
      container switching {
        description
          "Specify tunnel LSPs switching capability
           descriptor";
        container transit {
          presence "Indicates a transit node is configured.";
          description
            "Specify transit switching descriptor
             parameters";
          leaf capability {
            type Mpls-te-switching-cap;
            mandatory true;
            description
              "Switching capability";
          }
          leaf encoding {
            type Mpls-te-switching-encode;
            description
              "LSP encoding";
          }
        }
        container endpoint {
          presence "Indicates a endpoint node is configured.";
          description
            "Specify end point switching descriptor
             parameters";
          leaf capability {
            type Mpls-te-switching-cap;
            mandatory true;
            description
              "Switching capability";
          }
          leaf encoding {
            type Mpls-te-switching-encode;
            description
              "LSP encoding";
          }
        }
      }
      container pce {
        description
          "PCE config";
        leaf enable {
          type empty;
          description
            "Always set to true";
        }
        leaf delegation {
          type empty;
          description
            "Enable PCE Delegation";
        }
      }
      uses FORWARD-CLASS;
      uses TUNNEL-PATH-SELECTION;
      uses AUTO-BANDWIDTH;
      uses PRIORITY;
      uses DESTINATION;
      uses RECORD-ROUTE;
      uses AFFINITY-MASK;
      uses FORWARDING-ADJACENCY;
      uses LOGGING;
      uses BANDWIDTH;
      uses AUTOROUTE;
      uses POLICY-CLASSES;
      uses PATH-SELECTION-METRIC;
      uses NEW-STYLE-AFFINITY-TABLE;
      uses SOFT-PREEMPTION;
      uses FAST-REROUTE;
      uses LOAD-SHARE;
      uses SIGNALLED-NAME;
    }
    description
      "This augment extends the configuration data of
       'Cisco-IOS-XR-ifmgr-cfg'";
  }
  augment "/ncs:devices/ncs:template/ncs:ned-id/ncs:config/a1:interface-configurations/a1:interface-configuration" {
    container transport-profile-tunnel {
      description
        "MPLS-TP tunnel attributes";
      container bfd {
        description
          "Configure BFD parameters";
        container min-interval {
          description
            "Hello interval, either in milli-seconds or in
             micro-seconds";
          leaf interval-ms {
            type string;
            description
              "Hello interval in milli-seconds";
          }
          leaf interval-us {
            type string;
            description
              "Hello interval in micro-seconds";
          }
        }
        container min-interval-standby {
          description
            "Hello interval for standby transport profile
             LSP, either in milli-seconds or in
             micro-seconds";
          leaf interval-standby-ms {
            type string;
            description
              "Hello interval in milli-seconds";
          }
          leaf interval-standby-us {
            type string;
            description
              "Hello interval in micro-seconds";
          }
        }
        leaf detection-multiplier {
          type string;
          description
            "Detect multiplier";
        }
        leaf enable {
          type empty;
          description
            "Configure BFD parameters";
        }
        leaf multiplier-standby {
          type string;
          description
            "Detect multiplier for standby transport
             profile LSP";
        }
      }
      container working-lsp {
        description
          "Working LSP";
        container out-label {
          presence "Indicates a out-label node is configured.";
          description
            "Outgoing MPLS label of the working LSP";
          leaf label {
            type string;
            description
              "MPLS label";
          }
          leaf link {
            type string;
            // NCS drop mandatory statement
            description
              "Transport profile identifier of outgoing link";
          }
        }
        leaf in-label {
          type string;
          description
            "Incoming MPLS label of the working LSP";
        }
        leaf lockout {
          type empty;
          description
            "Enable lockout of working LSP";
        }
        leaf lsp-id {
          type string;
          // NCS drop default statement
          description
            "LSP Identifier of the working LSP";
        }
      }
      container destination {
        description
          "Node identifier and optional global identifier
           and tunnel identifier at destination";
        leaf node-id {
          type string;
          description
            "Node identifier in IPv4 address format";
        }
        leaf global-id {
          type string;
          description
            "Numeric global identifier";
        }
        leaf tunnel-id {
          type string;
          description
            "Numeric tunnel identifier";
        }
      }
      container fault {
        description
          "Fault management";
        container protection-trigger {
          description
            "OAM events that trigger protection switching";
          leaf ldi {
            type string;
            description
              "Enable protection switching due to LDI event";
          }
          leaf ais {
            type string;
            description
              "Enable protection switching due to AIS event";
          }
          leaf lkr {
            type string;
            description
              "Enable protection switching due to LKR event";
          }
        }
        leaf enable {
          type empty;
          description
            "Enter transport profile tunnel fault
             configuration";
        }
      }
      container protect-lsp {
        description
          "Protect LSP";
        container out-label {
          presence "Indicates a out-label node is configured.";
          description
            "Outgoing MPLS label of the protect LSP";
          leaf label {
            type string;
            description
              "MPLS label";
          }
          leaf link {
            type string;
            // NCS drop mandatory statement
            description
              "Transport profile identifier of outgoing link";
          }
        }
        leaf in-label {
          type string;
          description
            "Incoming MPLS label of the protect LSP";
        }
        leaf lockout {
          type empty;
          description
            "Enable lockout of protect LSP";
        }
        leaf lsp-id {
          type string;
          // NCS drop default statement
          description
            "LSP Identifier of the protect LSP";
        }
      }
      leaf source {
        type string;
        description
          "Transport profile node identifier in IPv4
           address format";
      }
    }
    description
      "This augment extends the configuration data of
       'Cisco-IOS-XR-ifmgr-cfg'";
  }
  augment "/ncs:devices/ncs:device/ncs:live-status/a1:interface-configurations/a1:interface-configuration" {
    container transport-profile-tunnel {
      tailf:ncs-device-type "netconf";
      tailf:display-when "not(../../../../ncs:module) or ../../../../ncs:module[ncs:name='Cisco-IOS-XR-mpls-te-cfg'] or (../../../../ncs:live-status-protocol[not(ncs:capability)]) or (../../../../ncs:live-status-protocol/ncs:capability/ncs:module[.='Cisco-IOS-XR-mpls-te-cfg'])";
      description
        "MPLS-TP tunnel attributes";
      container bfd {
        description
          "Configure BFD parameters";
        container min-interval {
          description
            "Hello interval, either in milli-seconds or in
             micro-seconds";
          leaf interval-ms {
            type uint32 {
              range "3..5000";
            }
            description
              "Hello interval in milli-seconds";
          }
          leaf interval-us {
            type uint32 {
              range "3000..5000000";
            }
            description
              "Hello interval in micro-seconds";
          }
        }
        container min-interval-standby {
          description
            "Hello interval for standby transport profile
             LSP, either in milli-seconds or in
             micro-seconds";
          leaf interval-standby-ms {
            type uint32 {
              range "3..5000";
            }
            description
              "Hello interval in milli-seconds";
          }
          leaf interval-standby-us {
            type uint32 {
              range "3000..5000000";
            }
            description
              "Hello interval in micro-seconds";
          }
        }
        leaf detection-multiplier {
          type uint32 {
            range "2..10";
          }
          description
            "Detect multiplier";
        }
        leaf enable {
          type empty;
          description
            "Configure BFD parameters";
        }
        leaf multiplier-standby {
          type uint32 {
            range "2..10";
          }
          description
            "Detect multiplier for standby transport
             profile LSP";
        }
      }
      container working-lsp {
        description
          "Working LSP";
        container out-label {
          presence "Indicates a out-label node is configured.";
          description
            "Outgoing MPLS label of the working LSP";
          leaf label {
            type uint32 {
              range "16..1048575";
            }
            description
              "MPLS label";
          }
          leaf link {
            type uint32 {
              range "1..65535";
            }
            // NCS drop mandatory statement
            description
              "Transport profile identifier of outgoing link";
          }
        }
        leaf in-label {
          type uint32 {
            range "16..4015";
          }
          description
            "Incoming MPLS label of the working LSP";
        }
        leaf lockout {
          type empty;
          description
            "Enable lockout of working LSP";
        }
        leaf lsp-id {
          type uint32 {
            range "0..65535";
          }
          // NCS drop default statement
          description
            "LSP Identifier of the working LSP";
        }
      }
      container destination {
        description
          "Node identifier and optional global identifier
           and tunnel identifier at destination";
        leaf node-id {
          type inet:ipv4-address-no-zone;
          description
            "Node identifier in IPv4 address format";
        }
        leaf global-id {
          type uint32 {
            range "1..65535";
          }
          description
            "Numeric global identifier";
        }
        leaf tunnel-id {
          type uint32 {
            range "0..65535";
          }
          description
            "Numeric tunnel identifier";
        }
      }
      container fault {
        description
          "Fault management";
        container protection-trigger {
          description
            "OAM events that trigger protection switching";
          leaf ldi {
            type boolean;
            description
              "Enable protection switching due to LDI event";
          }
          leaf ais {
            type boolean;
            description
              "Enable protection switching due to AIS event";
          }
          leaf lkr {
            type boolean;
            description
              "Enable protection switching due to LKR event";
          }
        }
        leaf enable {
          type empty;
          description
            "Enter transport profile tunnel fault
             configuration";
        }
      }
      container protect-lsp {
        description
          "Protect LSP";
        container out-label {
          presence "Indicates a out-label node is configured.";
          description
            "Outgoing MPLS label of the protect LSP";
          leaf label {
            type uint32 {
              range "16..1048575";
            }
            description
              "MPLS label";
          }
          leaf link {
            type uint32 {
              range "1..65535";
            }
            // NCS drop mandatory statement
            description
              "Transport profile identifier of outgoing link";
          }
        }
        leaf in-label {
          type uint32 {
            range "16..4015";
          }
          description
            "Incoming MPLS label of the protect LSP";
        }
        leaf lockout {
          type empty;
          description
            "Enable lockout of protect LSP";
        }
        leaf lsp-id {
          type uint32 {
            range "0..65535";
          }
          // NCS drop default statement
          description
            "LSP Identifier of the protect LSP";
        }
      }
      leaf source {
        type inet:ipv4-address-no-zone;
        description
          "Transport profile node identifier in IPv4
           address format";
      }
    }
    description
      "This augment extends the configuration data of
       'Cisco-IOS-XR-ifmgr-cfg'";
  }
  augment "/ncs:devices/ncs:device/ncs:config/a1:interface-configurations/a1:interface-configuration" {
    container transport-profile-tunnel {
      tailf:ncs-device-type "netconf";
      tailf:display-when "not(../../../../ncs:module) or ../../../../ncs:module[ncs:name='Cisco-IOS-XR-mpls-te-cfg']";
      description
        "MPLS-TP tunnel attributes";
      container bfd {
        description
          "Configure BFD parameters";
        container min-interval {
          description
            "Hello interval, either in milli-seconds or in
             micro-seconds";
          leaf interval-ms {
            type uint32 {
              range "3..5000";
            }
            description
              "Hello interval in milli-seconds";
          }
          leaf interval-us {
            type uint32 {
              range "3000..5000000";
            }
            description
              "Hello interval in micro-seconds";
          }
        }
        container min-interval-standby {
          description
            "Hello interval for standby transport profile
             LSP, either in milli-seconds or in
             micro-seconds";
          leaf interval-standby-ms {
            type uint32 {
              range "3..5000";
            }
            description
              "Hello interval in milli-seconds";
          }
          leaf interval-standby-us {
            type uint32 {
              range "3000..5000000";
            }
            description
              "Hello interval in micro-seconds";
          }
        }
        leaf detection-multiplier {
          type uint32 {
            range "2..10";
          }
          description
            "Detect multiplier";
        }
        leaf enable {
          type empty;
          description
            "Configure BFD parameters";
        }
        leaf multiplier-standby {
          type uint32 {
            range "2..10";
          }
          description
            "Detect multiplier for standby transport
             profile LSP";
        }
      }
      container working-lsp {
        description
          "Working LSP";
        container out-label {
          presence "Indicates a out-label node is configured.";
          description
            "Outgoing MPLS label of the working LSP";
          leaf label {
            type uint32 {
              range "16..1048575";
            }
            description
              "MPLS label";
          }
          leaf link {
            type uint32 {
              range "1..65535";
            }
            mandatory true;
            description
              "Transport profile identifier of outgoing link";
          }
        }
        leaf in-label {
          type uint32 {
            range "16..4015";
          }
          description
            "Incoming MPLS label of the working LSP";
        }
        leaf lockout {
          type empty;
          description
            "Enable lockout of working LSP";
        }
        leaf lsp-id {
          type uint32 {
            range "0..65535";
          }
          default "0";
          description
            "LSP Identifier of the working LSP";
        }
      }
      container destination {
        description
          "Node identifier and optional global identifier
           and tunnel identifier at destination";
        leaf node-id {
          type inet:ipv4-address-no-zone;
          description
            "Node identifier in IPv4 address format";
        }
        leaf global-id {
          type uint32 {
            range "1..65535";
          }
          description
            "Numeric global identifier";
        }
        leaf tunnel-id {
          type uint32 {
            range "0..65535";
          }
          description
            "Numeric tunnel identifier";
        }
      }
      container fault {
        description
          "Fault management";
        container protection-trigger {
          description
            "OAM events that trigger protection switching";
          leaf ldi {
            type boolean;
            description
              "Enable protection switching due to LDI event";
          }
          leaf ais {
            type boolean;
            description
              "Enable protection switching due to AIS event";
          }
          leaf lkr {
            type boolean;
            description
              "Enable protection switching due to LKR event";
          }
        }
        leaf enable {
          type empty;
          description
            "Enter transport profile tunnel fault
             configuration";
        }
      }
      container protect-lsp {
        description
          "Protect LSP";
        container out-label {
          presence "Indicates a out-label node is configured.";
          description
            "Outgoing MPLS label of the protect LSP";
          leaf label {
            type uint32 {
              range "16..1048575";
            }
            description
              "MPLS label";
          }
          leaf link {
            type uint32 {
              range "1..65535";
            }
            mandatory true;
            description
              "Transport profile identifier of outgoing link";
          }
        }
        leaf in-label {
          type uint32 {
            range "16..4015";
          }
          description
            "Incoming MPLS label of the protect LSP";
        }
        leaf lockout {
          type empty;
          description
            "Enable lockout of protect LSP";
        }
        leaf lsp-id {
          type uint32 {
            range "0..65535";
          }
          default "1";
          description
            "LSP Identifier of the protect LSP";
        }
      }
      leaf source {
        type inet:ipv4-address-no-zone;
        description
          "Transport profile node identifier in IPv4
           address format";
      }
    }
    description
      "This augment extends the configuration data of
       'Cisco-IOS-XR-ifmgr-cfg'";
  }
  augment "/ncs:devices/ncs:template/ncs:ned-id/ncs:config/a1:interface-configurations/a1:interface-configuration" {
    container mte-tunnel-attributes {
      description
        "MPLS P2MP tunnel attributes";
      container destination-leafs {
        description
          "P2MP destination table";
        list destination-leaf {
          // NCS patched for predictable order
          ordered-by user;
          key "address";
          description
            "P2MP destination leaf";
          container s2l-logging {
            description
              "Log tunnel destination s2l messages";
            leaf s2l-reroute-messsage {
              type empty;
              description
                "Log tunnel destination s2l rereoute messages";
            }
            leaf s2l-insufficient-bw-messsage {
              type empty;
              description
                "Log tunnel destination s2l insufficient BW
                 messages";
            }
            leaf s2l-pcalc-failure-message {
              type empty;
              description
                "Enable logging for destination s2l
                 path-calculation failures";
            }
            leaf s2l-state-message {
              type empty;
              description
                "Log tunnel destination s2l state messages";
            }
          }
          container path-options {
            description
              "P2MP destination path-options attributes
               table";
            list path-option {
              // NCS patched for predictable order
              ordered-by user;
              key "preference-level";
              description
                "P2MP destination path option";
              leaf preference-level {
                type string;
                description
                  "Preference level for this path option";
              }
              leaf path-type {
                type string;
                description
                  "The type of the path option";
              }
              leaf path-id {
                type string;
                description
                  "The ID of the IP explicit path associated
                   with this option";
              }
              leaf path-name {
                type string;
                description
                  "The name of the IP explicit path associated
                   with this option";
              }
              leaf lockdown {
                type string;
                description
                  "Path option properties";
              }
              leaf verbatim {
                type string;
                description
                  "Path option properties";
              }
            }
          }
          leaf destination-disable {
            type empty;
            description
              "Disables P2MP destination";
          }
          leaf destination {
            type empty;
            description
              "Always set to true";
          }
          leaf address {
            type string;
            description
              "Address of P2MP destination";
          }
        }
      }
      container priority {
        presence "Indicates a priority node is configured.";
        description
          "P2MP tunnel setup and hold priorities";
        leaf setup-priority {
          type string;
          // NCS drop mandatory statement
          description
            "Setup Priority";
        }
        leaf hold-priority {
          type string;
          // NCS drop mandatory statement
          description
            "Hold Priority";
        }
      }
      container new-style-affinities {
        description
          "P2MP tunnel new style affinity attributes table";
        list new-style-affinity {
          // NCS patched for predictable order
          ordered-by user;
          key "affinity-type affinity1 affinity2 affinity3 affinity4 affinity5 affinity6 affinity7 affinity8 affinity9 affinity10";
          description
            "Tunnel new style affinity attribute";
          leaf affinity-type {
            type string;
            description
              "The type of the affinity entry";
          }
          leaf affinity1 {
            type string;
            description
              "The name of the first affinity";
          }
          leaf affinity2 {
            type string;
            description
              "The name of the second affinity";
          }
          leaf affinity3 {
            type string;
            description
              "The name of the third affinity";
          }
          leaf affinity4 {
            type string;
            description
              "The name of the fourth affinity";
          }
          leaf affinity5 {
            type string;
            description
              "The name of the fifth affinity";
          }
          leaf affinity6 {
            type string;
            description
              "The name of the sixth affinity";
          }
          leaf affinity7 {
            type string;
            description
              "The name of the seventh affinity";
          }
          leaf affinity8 {
            type string;
            description
              "The name of the eighth affinity";
          }
          leaf affinity9 {
            type string;
            description
              "The name of the nineth affinity";
          }
          leaf affinity10 {
            type string;
            description
              "The name of the tenth affinity";
          }
        }
      }
      container bandwidth {
        description
          "P2MP tunnel bandwidth requirement";
        leaf dste-type {
          type string;
          description
            "DSTE-standard flag";
        }
        leaf class-or-pool-type {
          type string;
          description
            "Class type for the bandwidth allocation";
        }
        leaf bandwidth {
          type string;
          description
            "The value of the bandwidth reserved by this
             tunnel in kbps";
        }
      }
      container affinity-mask {
        description
          "P2MP tunnel affinity and mask";
        leaf affinity {
          type string;
          description
            "Affinity flags";
        }
        leaf mask {
          type string;
          description
            "Affinity mask";
        }
      }
      leaf record-route {
        type empty;
        description
          "Record route used by individual P2MP S2L(s)";
      }
      leaf signalled-name {
        type string;
        description
          "The name of the P2MP tunnel to be included in
           signalling messages";
      }
      leaf path-selection-metric {
        type string;
        description
          "Path selection configuration for this specific
           tunnel";
      }
      leaf signalled-payload {
        type string;
        description
          "P2MP tunnel ipv6 signalled payload";
      }
      leaf fast-reroute {
        type empty;
        description
          "Specify P2MP tunnel can be fast-rerouted";
      }
      leaf impose-explicit-null {
        type empty;
        description
          "Impose an explicit null bellow the TE label";
      }
      uses ncs_template_MPLS-MTE-TUNNEL-CFG-LOGGING;
    }
    description
      "This augment extends the configuration data of
       'Cisco-IOS-XR-ifmgr-cfg'";
  }
  augment "/ncs:devices/ncs:device/ncs:live-status/a1:interface-configurations/a1:interface-configuration" {
    container mte-tunnel-attributes {
      tailf:ncs-device-type "netconf";
      tailf:display-when "not(../../../../ncs:module) or ../../../../ncs:module[ncs:name='Cisco-IOS-XR-mpls-te-cfg'] or (../../../../ncs:live-status-protocol[not(ncs:capability)]) or (../../../../ncs:live-status-protocol/ncs:capability/ncs:module[.='Cisco-IOS-XR-mpls-te-cfg'])";
      description
        "MPLS P2MP tunnel attributes";
      container destination-leafs {
        description
          "P2MP destination table";
        list destination-leaf {
          key "address";
          description
            "P2MP destination leaf";
          container s2l-logging {
            description
              "Log tunnel destination s2l messages";
            leaf s2l-reroute-messsage {
              type empty;
              description
                "Log tunnel destination s2l rereoute messages";
            }
            leaf s2l-insufficient-bw-messsage {
              type empty;
              description
                "Log tunnel destination s2l insufficient BW
                 messages";
            }
            leaf s2l-pcalc-failure-message {
              type empty;
              description
                "Enable logging for destination s2l
                 path-calculation failures";
            }
            leaf s2l-state-message {
              type empty;
              description
                "Log tunnel destination s2l state messages";
            }
          }
          container path-options {
            description
              "P2MP destination path-options attributes
               table";
            list path-option {
              key "preference-level";
              description
                "P2MP destination path option";
              leaf preference-level {
                type uint32 {
                  range "1..1000";
                }
                description
                  "Preference level for this path option";
              }
              leaf path-type {
                type Mpls-te-path-option;
                description
                  "The type of the path option";
              }
              leaf path-id {
                type uint32 {
                  range "1..65535";
                }
                description
                  "The ID of the IP explicit path associated
                   with this option";
              }
              leaf path-name {
                type string;
                description
                  "The name of the IP explicit path associated
                   with this option";
              }
              leaf lockdown {
                type Mpls-te-path-option-property;
                description
                  "Path option properties";
              }
              leaf verbatim {
                type Mpls-te-path-option-property;
                description
                  "Path option properties";
              }
            }
          }
          leaf destination-disable {
            type empty;
            description
              "Disables P2MP destination";
          }
          leaf destination {
            type empty;
            description
              "Always set to true";
          }
          leaf address {
            type inet:ipv4-address-no-zone;
            description
              "Address of P2MP destination";
          }
        }
      }
      container priority {
        presence "Indicates a priority node is configured.";
        description
          "P2MP tunnel setup and hold priorities";
        leaf setup-priority {
          type uint32 {
            range "0..7";
          }
          // NCS drop mandatory statement
          description
            "Setup Priority";
        }
        leaf hold-priority {
          type uint32 {
            range "0..7";
          }
          // NCS drop mandatory statement
          description
            "Hold Priority";
        }
      }
      container new-style-affinities {
        description
          "P2MP tunnel new style affinity attributes table";
        list new-style-affinity {
          key "affinity-type affinity1 affinity2 affinity3 affinity4 affinity5 affinity6 affinity7 affinity8 affinity9 affinity10";
          description
            "Tunnel new style affinity attribute";
          leaf affinity-type {
            type Mpls-te-tunnel-affinity;
            description
              "The type of the affinity entry";
          }
          leaf affinity1 {
            type xr:Cisco-ios-xr-string;
            description
              "The name of the first affinity";
          }
          leaf affinity2 {
            type xr:Cisco-ios-xr-string;
            description
              "The name of the second affinity";
          }
          leaf affinity3 {
            type xr:Cisco-ios-xr-string;
            description
              "The name of the third affinity";
          }
          leaf affinity4 {
            type xr:Cisco-ios-xr-string;
            description
              "The name of the fourth affinity";
          }
          leaf affinity5 {
            type xr:Cisco-ios-xr-string;
            description
              "The name of the fifth affinity";
          }
          leaf affinity6 {
            type xr:Cisco-ios-xr-string;
            description
              "The name of the sixth affinity";
          }
          leaf affinity7 {
            type xr:Cisco-ios-xr-string;
            description
              "The name of the seventh affinity";
          }
          leaf affinity8 {
            type xr:Cisco-ios-xr-string;
            description
              "The name of the eighth affinity";
          }
          leaf affinity9 {
            type xr:Cisco-ios-xr-string;
            description
              "The name of the nineth affinity";
          }
          leaf affinity10 {
            type xr:Cisco-ios-xr-string;
            description
              "The name of the tenth affinity";
          }
        }
      }
      container bandwidth {
        description
          "P2MP tunnel bandwidth requirement";
        leaf dste-type {
          type Mpls-te-bandwidth-dste;
          description
            "DSTE-standard flag";
        }
        leaf class-or-pool-type {
          type uint32 {
            range "0..1";
          }
          description
            "Class type for the bandwidth allocation";
        }
        leaf bandwidth {
          type uint32 {
            range "0..4294967295";
          }
          description
            "The value of the bandwidth reserved by this
             tunnel in kbps";
        }
      }
      container affinity-mask {
        description
          "P2MP tunnel affinity and mask";
        leaf affinity {
          type xr:Hex-integer;
          description
            "Affinity flags";
        }
        leaf mask {
          type xr:Hex-integer;
          description
            "Affinity mask";
        }
      }
      leaf record-route {
        type empty;
        description
          "Record route used by individual P2MP S2L(s)";
      }
      leaf signalled-name {
        type string {
          length "1..254";
        }
        description
          "The name of the P2MP tunnel to be included in
           signalling messages";
      }
      leaf path-selection-metric {
        type Mpls-te-path-selection-metric;
        description
          "Path selection configuration for this specific
           tunnel";
      }
      leaf signalled-payload {
        type xr:Hex-integer;
        description
          "P2MP tunnel ipv6 signalled payload";
      }
      leaf fast-reroute {
        type empty;
        description
          "Specify P2MP tunnel can be fast-rerouted";
      }
      leaf impose-explicit-null {
        type empty;
        description
          "Impose an explicit null bellow the TE label";
      }
      uses live_ncs_MPLS-MTE-TUNNEL-CFG-LOGGING;
    }
    description
      "This augment extends the configuration data of
       'Cisco-IOS-XR-ifmgr-cfg'";
  }
  augment "/ncs:devices/ncs:device/ncs:config/a1:interface-configurations/a1:interface-configuration" {
    container mte-tunnel-attributes {
      tailf:ncs-device-type "netconf";
      tailf:display-when "not(../../../../ncs:module) or ../../../../ncs:module[ncs:name='Cisco-IOS-XR-mpls-te-cfg']";
      description
        "MPLS P2MP tunnel attributes";
      container destination-leafs {
        description
          "P2MP destination table";
        list destination-leaf {
          key "address";
          description
            "P2MP destination leaf";
          container s2l-logging {
            description
              "Log tunnel destination s2l messages";
            leaf s2l-reroute-messsage {
              type empty;
              description
                "Log tunnel destination s2l rereoute messages";
            }
            leaf s2l-insufficient-bw-messsage {
              type empty;
              description
                "Log tunnel destination s2l insufficient BW
                 messages";
            }
            leaf s2l-pcalc-failure-message {
              type empty;
              description
                "Enable logging for destination s2l
                 path-calculation failures";
            }
            leaf s2l-state-message {
              type empty;
              description
                "Log tunnel destination s2l state messages";
            }
          }
          container path-options {
            description
              "P2MP destination path-options attributes
               table";
            list path-option {
              key "preference-level";
              description
                "P2MP destination path option";
              leaf preference-level {
                type uint32 {
                  range "1..1000";
                }
                description
                  "Preference level for this path option";
              }
              leaf path-type {
                type Mpls-te-path-option;
                description
                  "The type of the path option";
              }
              leaf path-id {
                type uint32 {
                  range "1..65535";
                }
                description
                  "The ID of the IP explicit path associated
                   with this option";
              }
              leaf path-name {
                type string;
                description
                  "The name of the IP explicit path associated
                   with this option";
              }
              leaf lockdown {
                type Mpls-te-path-option-property;
                description
                  "Path option properties";
              }
              leaf verbatim {
                type Mpls-te-path-option-property;
                description
                  "Path option properties";
              }
            }
          }
          leaf destination-disable {
            type empty;
            description
              "Disables P2MP destination";
          }
          leaf destination {
            type empty;
            description
              "Always set to true";
          }
          leaf address {
            type inet:ipv4-address-no-zone;
            description
              "Address of P2MP destination";
          }
        }
      }
      container priority {
        presence "Indicates a priority node is configured.";
        description
          "P2MP tunnel setup and hold priorities";
        leaf setup-priority {
          type uint32 {
            range "0..7";
          }
          mandatory true;
          description
            "Setup Priority";
        }
        leaf hold-priority {
          type uint32 {
            range "0..7";
          }
          mandatory true;
          description
            "Hold Priority";
        }
      }
      container new-style-affinities {
        description
          "P2MP tunnel new style affinity attributes table";
        list new-style-affinity {
          key "affinity-type affinity1 affinity2 affinity3 affinity4 affinity5 affinity6 affinity7 affinity8 affinity9 affinity10";
          description
            "Tunnel new style affinity attribute";
          leaf affinity-type {
            type Mpls-te-tunnel-affinity;
            description
              "The type of the affinity entry";
          }
          leaf affinity1 {
            type xr:Cisco-ios-xr-string;
            description
              "The name of the first affinity";
          }
          leaf affinity2 {
            type xr:Cisco-ios-xr-string;
            description
              "The name of the second affinity";
          }
          leaf affinity3 {
            type xr:Cisco-ios-xr-string;
            description
              "The name of the third affinity";
          }
          leaf affinity4 {
            type xr:Cisco-ios-xr-string;
            description
              "The name of the fourth affinity";
          }
          leaf affinity5 {
            type xr:Cisco-ios-xr-string;
            description
              "The name of the fifth affinity";
          }
          leaf affinity6 {
            type xr:Cisco-ios-xr-string;
            description
              "The name of the sixth affinity";
          }
          leaf affinity7 {
            type xr:Cisco-ios-xr-string;
            description
              "The name of the seventh affinity";
          }
          leaf affinity8 {
            type xr:Cisco-ios-xr-string;
            description
              "The name of the eighth affinity";
          }
          leaf affinity9 {
            type xr:Cisco-ios-xr-string;
            description
              "The name of the nineth affinity";
          }
          leaf affinity10 {
            type xr:Cisco-ios-xr-string;
            description
              "The name of the tenth affinity";
          }
        }
      }
      container bandwidth {
        description
          "P2MP tunnel bandwidth requirement";
        leaf dste-type {
          type Mpls-te-bandwidth-dste;
          description
            "DSTE-standard flag";
        }
        leaf class-or-pool-type {
          type uint32 {
            range "0..1";
          }
          description
            "Class type for the bandwidth allocation";
        }
        leaf bandwidth {
          type uint32 {
            range "0..4294967295";
          }
          description
            "The value of the bandwidth reserved by this
             tunnel in kbps";
        }
      }
      container affinity-mask {
        description
          "P2MP tunnel affinity and mask";
        leaf affinity {
          type xr:Hex-integer;
          description
            "Affinity flags";
        }
        leaf mask {
          type xr:Hex-integer;
          description
            "Affinity mask";
        }
      }
      leaf record-route {
        type empty;
        description
          "Record route used by individual P2MP S2L(s)";
      }
      leaf signalled-name {
        type string {
          length "1..254";
        }
        description
          "The name of the P2MP tunnel to be included in
           signalling messages";
      }
      leaf path-selection-metric {
        type Mpls-te-path-selection-metric;
        description
          "Path selection configuration for this specific
           tunnel";
      }
      leaf signalled-payload {
        type xr:Hex-integer;
        description
          "P2MP tunnel ipv6 signalled payload";
      }
      leaf fast-reroute {
        type empty;
        description
          "Specify P2MP tunnel can be fast-rerouted";
      }
      leaf impose-explicit-null {
        type empty;
        description
          "Impose an explicit null bellow the TE label";
      }
      uses MPLS-MTE-TUNNEL-CFG-LOGGING;
    }
    description
      "This augment extends the configuration data of
       'Cisco-IOS-XR-ifmgr-cfg'";
  }
  augment "/ncs:devices/ncs:template/ncs:ned-id/ncs:config/a2:mib" {
    container mpls-te-mib {
      description
        "MPLS TE MIB configuration";
      leaf cache-garbage-collect-timer {
        type string;
        units "second";
        // NCS drop default statement
        description
          "Configure the cache garbage collector time for
           the mib.";
      }
      uses ncs_template_CACHE-TIMER;
    }
    description
      "This augment extends the configuration data of
       'Cisco-IOS-XR-snmp-agent-cfg'";
  }
  augment "/ncs:devices/ncs:device/ncs:live-status/a2:mib" {
    container mpls-te-mib {
      tailf:ncs-device-type "netconf";
      tailf:display-when "not(../../../ncs:module) or ../../../ncs:module[ncs:name='Cisco-IOS-XR-mpls-te-cfg'] or (../../../ncs:live-status-protocol[not(ncs:capability)]) or (../../../ncs:live-status-protocol/ncs:capability/ncs:module[.='Cisco-IOS-XR-mpls-te-cfg'])";
      description
        "MPLS TE MIB configuration";
      leaf cache-garbage-collect-timer {
        type uint32 {
          range "0..3600";
        }
        units "second";
        // NCS drop default statement
        description
          "Configure the cache garbage collector time for
           the mib.";
      }
      uses live_ncs_CACHE-TIMER;
    }
    description
      "This augment extends the configuration data of
       'Cisco-IOS-XR-snmp-agent-cfg'";
  }
  augment "/ncs:devices/ncs:device/ncs:config/a2:mib" {
    container mpls-te-mib {
      tailf:ncs-device-type "netconf";
      tailf:display-when "not(../../../ncs:module) or ../../../ncs:module[ncs:name='Cisco-IOS-XR-mpls-te-cfg']";
      description
        "MPLS TE MIB configuration";
      leaf cache-garbage-collect-timer {
        type uint32 {
          range "0..3600";
        }
        units "second";
        default "1800";
        description
          "Configure the cache garbage collector time for
           the mib.";
      }
      uses CACHE-TIMER;
    }
    description
      "This augment extends the configuration data of
       'Cisco-IOS-XR-snmp-agent-cfg'";
  }
  augment "/ncs:devices/ncs:template/ncs:ned-id/ncs:config/a2:mib" {
    container mpls-p2mp-mib {
      description
        "MPLS P2MP MIB configuration";
      uses ncs_template_CACHE-TIMER;
    }
    description
      "This augment extends the configuration data of
       'Cisco-IOS-XR-snmp-agent-cfg'";
  }
  augment "/ncs:devices/ncs:device/ncs:live-status/a2:mib" {
    container mpls-p2mp-mib {
      tailf:ncs-device-type "netconf";
      tailf:display-when "not(../../../ncs:module) or ../../../ncs:module[ncs:name='Cisco-IOS-XR-mpls-te-cfg'] or (../../../ncs:live-status-protocol[not(ncs:capability)]) or (../../../ncs:live-status-protocol/ncs:capability/ncs:module[.='Cisco-IOS-XR-mpls-te-cfg'])";
      description
        "MPLS P2MP MIB configuration";
      uses live_ncs_CACHE-TIMER;
    }
    description
      "This augment extends the configuration data of
       'Cisco-IOS-XR-snmp-agent-cfg'";
  }
  augment "/ncs:devices/ncs:device/ncs:config/a2:mib" {
    container mpls-p2mp-mib {
      tailf:ncs-device-type "netconf";
      tailf:display-when "not(../../../ncs:module) or ../../../ncs:module[ncs:name='Cisco-IOS-XR-mpls-te-cfg']";
      description
        "MPLS P2MP MIB configuration";
      uses CACHE-TIMER;
    }
    description
      "This augment extends the configuration data of
       'Cisco-IOS-XR-snmp-agent-cfg'";
  }
  augment "/ncs:devices/ncs:template/ncs:ned-id/ncs:config/a2:mib" {
    container mpls-te-ext-std-mib {
      description
        "MPLS TE EXT STD MIB configuration";
      uses ncs_template_CACHE-TIMER;
    }
    description
      "This augment extends the configuration data of
       'Cisco-IOS-XR-snmp-agent-cfg'";
  }
  augment "/ncs:devices/ncs:device/ncs:live-status/a2:mib" {
    container mpls-te-ext-std-mib {
      tailf:ncs-device-type "netconf";
      tailf:display-when "not(../../../ncs:module) or ../../../ncs:module[ncs:name='Cisco-IOS-XR-mpls-te-cfg'] or (../../../ncs:live-status-protocol[not(ncs:capability)]) or (../../../ncs:live-status-protocol/ncs:capability/ncs:module[.='Cisco-IOS-XR-mpls-te-cfg'])";
      description
        "MPLS TE EXT STD MIB configuration";
      uses live_ncs_CACHE-TIMER;
    }
    description
      "This augment extends the configuration data of
       'Cisco-IOS-XR-snmp-agent-cfg'";
  }
  augment "/ncs:devices/ncs:device/ncs:config/a2:mib" {
    container mpls-te-ext-std-mib {
      tailf:ncs-device-type "netconf";
      tailf:display-when "not(../../../ncs:module) or ../../../ncs:module[ncs:name='Cisco-IOS-XR-mpls-te-cfg']";
      description
        "MPLS TE EXT STD MIB configuration";
      uses CACHE-TIMER;
    }
    description
      "This augment extends the configuration data of
       'Cisco-IOS-XR-snmp-agent-cfg'";
  }
  augment "/ncs:devices/ncs:template/ncs:ned-id/ncs:config/a2:mib" {
    container mpls-te-ext-mib {
      description
        "MPLS TE EXT MIB configuration";
      uses ncs_template_CACHE-TIMER;
    }
    description
      "This augment extends the configuration data of
       'Cisco-IOS-XR-snmp-agent-cfg'";
  }
  augment "/ncs:devices/ncs:device/ncs:live-status/a2:mib" {
    container mpls-te-ext-mib {
      tailf:ncs-device-type "netconf";
      tailf:display-when "not(../../../ncs:module) or ../../../ncs:module[ncs:name='Cisco-IOS-XR-mpls-te-cfg'] or (../../../ncs:live-status-protocol[not(ncs:capability)]) or (../../../ncs:live-status-protocol/ncs:capability/ncs:module[.='Cisco-IOS-XR-mpls-te-cfg'])";
      description
        "MPLS TE EXT MIB configuration";
      uses live_ncs_CACHE-TIMER;
    }
    description
      "This augment extends the configuration data of
       'Cisco-IOS-XR-snmp-agent-cfg'";
  }
  augment "/ncs:devices/ncs:device/ncs:config/a2:mib" {
    container mpls-te-ext-mib {
      tailf:ncs-device-type "netconf";
      tailf:display-when "not(../../../ncs:module) or ../../../ncs:module[ncs:name='Cisco-IOS-XR-mpls-te-cfg']";
      description
        "MPLS TE EXT MIB configuration";
      uses CACHE-TIMER;
    }
    description
      "This augment extends the configuration data of
       'Cisco-IOS-XR-snmp-agent-cfg'";
  }
  augment "/ncs:devices/ncs:template/ncs:ned-id/ncs:config/a2:mib" {
    container mpls-frr-mib {
      description
        "FRR MIB configuration";
      uses ncs_template_CACHE-TIMER;
    }
    description
      "This augment extends the configuration data of
       'Cisco-IOS-XR-snmp-agent-cfg'";
  }
  augment "/ncs:devices/ncs:device/ncs:live-status/a2:mib" {
    container mpls-frr-mib {
      tailf:ncs-device-type "netconf";
      tailf:display-when "not(../../../ncs:module) or ../../../ncs:module[ncs:name='Cisco-IOS-XR-mpls-te-cfg'] or (../../../ncs:live-status-protocol[not(ncs:capability)]) or (../../../ncs:live-status-protocol/ncs:capability/ncs:module[.='Cisco-IOS-XR-mpls-te-cfg'])";
      description
        "FRR MIB configuration";
      uses live_ncs_CACHE-TIMER;
    }
    description
      "This augment extends the configuration data of
       'Cisco-IOS-XR-snmp-agent-cfg'";
  }
  augment "/ncs:devices/ncs:device/ncs:config/a2:mib" {
    container mpls-frr-mib {
      tailf:ncs-device-type "netconf";
      tailf:display-when "not(../../../ncs:module) or ../../../ncs:module[ncs:name='Cisco-IOS-XR-mpls-te-cfg']";
      description
        "FRR MIB configuration";
      uses CACHE-TIMER;
    }
    description
      "This augment extends the configuration data of
       'Cisco-IOS-XR-snmp-agent-cfg'";
  }
  augment "/ncs:devices/ncs:template/ncs:ned-id/ncs:config/a2:snmp/a2:notification" {
    container mpls-te-p2mp {
      description
        "CISCO-MPLS-TE-P2MP-STD-MIB notification
         configuration";
      leaf up {
        type empty;
        description
          "Enable cmplsTeP2mpTunnelDestUp notification";
      }
      leaf down {
        type empty;
        description
          "Enable cmplsTeP2mpTunnelDestDown notification";
      }
    }
    description
      "This augment extends the configuration data of
       'Cisco-IOS-XR-snmp-agent-cfg'";
  }
  augment "/ncs:devices/ncs:device/ncs:live-status/a2:snmp/a2:notification" {
    container mpls-te-p2mp {
      tailf:ncs-device-type "netconf";
      tailf:display-when "not(../../../../ncs:module) or ../../../../ncs:module[ncs:name='Cisco-IOS-XR-mpls-te-cfg'] or (../../../../ncs:live-status-protocol[not(ncs:capability)]) or (../../../../ncs:live-status-protocol/ncs:capability/ncs:module[.='Cisco-IOS-XR-mpls-te-cfg'])";
      description
        "CISCO-MPLS-TE-P2MP-STD-MIB notification
         configuration";
      leaf up {
        type empty;
        description
          "Enable cmplsTeP2mpTunnelDestUp notification";
      }
      leaf down {
        type empty;
        description
          "Enable cmplsTeP2mpTunnelDestDown notification";
      }
    }
    description
      "This augment extends the configuration data of
       'Cisco-IOS-XR-snmp-agent-cfg'";
  }
  augment "/ncs:devices/ncs:device/ncs:config/a2:snmp/a2:notification" {
    container mpls-te-p2mp {
      tailf:ncs-device-type "netconf";
      tailf:display-when "not(../../../../ncs:module) or ../../../../ncs:module[ncs:name='Cisco-IOS-XR-mpls-te-cfg']";
      description
        "CISCO-MPLS-TE-P2MP-STD-MIB notification
         configuration";
      leaf up {
        type empty;
        description
          "Enable cmplsTeP2mpTunnelDestUp notification";
      }
      leaf down {
        type empty;
        description
          "Enable cmplsTeP2mpTunnelDestDown notification";
      }
    }
    description
      "This augment extends the configuration data of
       'Cisco-IOS-XR-snmp-agent-cfg'";
  }
  augment "/ncs:devices/ncs:template/ncs:ned-id/ncs:config/a2:snmp/a2:notification" {
    container mpls-te {
      description
        "MPLS-TE-STD-MIB notification configuration";
      container cisco-extension {
        description
          "CISCO-MPLS-TE-STD-EXT-MIB notification
           configuration";
        leaf preempt {
          type empty;
          description
            "Enable cmplsTunnelPreempt notification";
        }
        leaf insufficient-bandwidth {
          type empty;
          description
            "Enable cmplsTunnelInsuffBW notification";
        }
        leaf re-route-pending-clear {
          type empty;
          description
            "Enable cmplsTunnelReRoutePendingClear
             notification";
        }
        leaf bringup-fail {
          type empty;
          description
            "Enable cmplsTunnelBringupFail notification";
        }
        leaf re-route-pending {
          type empty;
          description
            "Enable cmplsTunnelReRoutePending notification";
        }
      }
      leaf cisco {
        type empty;
        description
          "Enable MPLS TE tunnel Cisco format (default
           IETF) notification";
      }
      leaf up {
        type empty;
        description
          "Enable mplsTunnelUp notification";
      }
      leaf reoptimize {
        type empty;
        description
          "Enable mplsTunnelReoptimized notification";
      }
      leaf reroute {
        type empty;
        description
          "Enable mplsTunnelRerouted notification";
      }
      leaf down {
        type empty;
        description
          "Enable mplsTunnelDown notification";
      }
    }
    description
      "This augment extends the configuration data of
       'Cisco-IOS-XR-snmp-agent-cfg'";
  }
  augment "/ncs:devices/ncs:device/ncs:live-status/a2:snmp/a2:notification" {
    container mpls-te {
      tailf:ncs-device-type "netconf";
      tailf:display-when "not(../../../../ncs:module) or ../../../../ncs:module[ncs:name='Cisco-IOS-XR-mpls-te-cfg'] or (../../../../ncs:live-status-protocol[not(ncs:capability)]) or (../../../../ncs:live-status-protocol/ncs:capability/ncs:module[.='Cisco-IOS-XR-mpls-te-cfg'])";
      description
        "MPLS-TE-STD-MIB notification configuration";
      container cisco-extension {
        description
          "CISCO-MPLS-TE-STD-EXT-MIB notification
           configuration";
        leaf preempt {
          type empty;
          description
            "Enable cmplsTunnelPreempt notification";
        }
        leaf insufficient-bandwidth {
          type empty;
          description
            "Enable cmplsTunnelInsuffBW notification";
        }
        leaf re-route-pending-clear {
          type empty;
          description
            "Enable cmplsTunnelReRoutePendingClear
             notification";
        }
        leaf bringup-fail {
          type empty;
          description
            "Enable cmplsTunnelBringupFail notification";
        }
        leaf re-route-pending {
          type empty;
          description
            "Enable cmplsTunnelReRoutePending notification";
        }
      }
      leaf cisco {
        type empty;
        description
          "Enable MPLS TE tunnel Cisco format (default
           IETF) notification";
      }
      leaf up {
        type empty;
        description
          "Enable mplsTunnelUp notification";
      }
      leaf reoptimize {
        type empty;
        description
          "Enable mplsTunnelReoptimized notification";
      }
      leaf reroute {
        type empty;
        description
          "Enable mplsTunnelRerouted notification";
      }
      leaf down {
        type empty;
        description
          "Enable mplsTunnelDown notification";
      }
    }
    description
      "This augment extends the configuration data of
       'Cisco-IOS-XR-snmp-agent-cfg'";
  }
  augment "/ncs:devices/ncs:device/ncs:config/a2:snmp/a2:notification" {
    container mpls-te {
      tailf:ncs-device-type "netconf";
      tailf:display-when "not(../../../../ncs:module) or ../../../../ncs:module[ncs:name='Cisco-IOS-XR-mpls-te-cfg']";
      description
        "MPLS-TE-STD-MIB notification configuration";
      container cisco-extension {
        description
          "CISCO-MPLS-TE-STD-EXT-MIB notification
           configuration";
        leaf preempt {
          type empty;
          description
            "Enable cmplsTunnelPreempt notification";
        }
        leaf insufficient-bandwidth {
          type empty;
          description
            "Enable cmplsTunnelInsuffBW notification";
        }
        leaf re-route-pending-clear {
          type empty;
          description
            "Enable cmplsTunnelReRoutePendingClear
             notification";
        }
        leaf bringup-fail {
          type empty;
          description
            "Enable cmplsTunnelBringupFail notification";
        }
        leaf re-route-pending {
          type empty;
          description
            "Enable cmplsTunnelReRoutePending notification";
        }
      }
      leaf cisco {
        type empty;
        description
          "Enable MPLS TE tunnel Cisco format (default
           IETF) notification";
      }
      leaf up {
        type empty;
        description
          "Enable mplsTunnelUp notification";
      }
      leaf reoptimize {
        type empty;
        description
          "Enable mplsTunnelReoptimized notification";
      }
      leaf reroute {
        type empty;
        description
          "Enable mplsTunnelRerouted notification";
      }
      leaf down {
        type empty;
        description
          "Enable mplsTunnelDown notification";
      }
    }
    description
      "This augment extends the configuration data of
       'Cisco-IOS-XR-snmp-agent-cfg'";
  }
  augment "/ncs:devices/ncs:template/ncs:ned-id/ncs:config/a2:snmp/a2:notification" {
    container mpls-frr {
      description
        "CISCO-IETF-FRR-MIB notification configuration";
      leaf unprotected {
        type empty;
        description
          "Enable cmplsFrrUnProtected notification";
      }
      leaf enable {
        type empty;
        description
          "Enable cmplsFrrMIB notifications";
      }
      leaf protected {
        type empty;
        description
          "Enable cmplsFrrProtected notification";
      }
    }
    description
      "This augment extends the configuration data of
       'Cisco-IOS-XR-snmp-agent-cfg'";
  }
  augment "/ncs:devices/ncs:device/ncs:live-status/a2:snmp/a2:notification" {
    container mpls-frr {
      tailf:ncs-device-type "netconf";
      tailf:display-when "not(../../../../ncs:module) or ../../../../ncs:module[ncs:name='Cisco-IOS-XR-mpls-te-cfg'] or (../../../../ncs:live-status-protocol[not(ncs:capability)]) or (../../../../ncs:live-status-protocol/ncs:capability/ncs:module[.='Cisco-IOS-XR-mpls-te-cfg'])";
      description
        "CISCO-IETF-FRR-MIB notification configuration";
      leaf unprotected {
        type empty;
        description
          "Enable cmplsFrrUnProtected notification";
      }
      leaf enable {
        type empty;
        description
          "Enable cmplsFrrMIB notifications";
      }
      leaf protected {
        type empty;
        description
          "Enable cmplsFrrProtected notification";
      }
    }
    description
      "This augment extends the configuration data of
       'Cisco-IOS-XR-snmp-agent-cfg'";
  }
  augment "/ncs:devices/ncs:device/ncs:config/a2:snmp/a2:notification" {
    container mpls-frr {
      tailf:ncs-device-type "netconf";
      tailf:display-when "not(../../../../ncs:module) or ../../../../ncs:module[ncs:name='Cisco-IOS-XR-mpls-te-cfg']";
      description
        "CISCO-IETF-FRR-MIB notification configuration";
      leaf unprotected {
        type empty;
        description
          "Enable cmplsFrrUnProtected notification";
      }
      leaf enable {
        type empty;
        description
          "Enable cmplsFrrMIB notifications";
      }
      leaf protected {
        type empty;
        description
          "Enable cmplsFrrProtected notification";
      }
    }
    description
      "This augment extends the configuration data of
       'Cisco-IOS-XR-snmp-agent-cfg'";
  }
}
