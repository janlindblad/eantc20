module Cisco-IOS-XR-tunnel-l2tun-cfg {
  // Generated by yanger -t ncs
  tailf:mount-id f5500-nc-1.0:f5500-nc-1.0;
  tailf:ncs-device-type "netconf";

  namespace "http://cisco.com/ns/yang/Cisco-IOS-XR-tunnel-l2tun-cfg";
  prefix Cisco-IOS-XR-tunnel-l2tun-cfg;

  import Cisco-IOS-XR-types {
    prefix xr;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR tunnel-l2tun package configuration.

     This module contains definitions
     for the following management objects:
       l2tp: L2TPv3 class used for L2VPNs

     Copyright (c) 2013-2018 by Cisco Systems, Inc.
     All rights reserved.";

  revision 2017-09-07 {
    description
      "Fixed type translation error.";
  }
  revision 2015-11-09 {
    description
      "IOS XR 6.0 revision.";
  }

  typedef L2tp-digest-hash-method {
    type enumeration {
      enum "md5" {
        value 1;
        description
          "MD5";
      }
      enum "sha1" {
        value 2;
        description
          "SHA1";
      }
    }
    description
      "L2tp digest hash method";
  }

  typedef L2tp-hash-method {
    type enumeration {
      enum "md5" {
        value 1;
        description
          "MD5";
      }
      enum "sha1" {
        value 2;
        description
          "SHA1";
      }
      enum "none" {
        value 3;
        description
          "None";
      }
    }
    description
      "L2tp hash method";
  }

  typedef L2tp-no-user {
    type uint32 {
      range "0..4294967295";
    }
    description
      "L2tp no user";
  }

  grouping ncs_template_TIMEOUT {
    description
      "Common node of initial, retransmit";
    container timeout {
      description
        "Set timeout value range";
      leaf minimum {
        type string;
        description
          "Specify minimum timeout";
      }
      leaf maximum {
        type string;
        description
          "Specify maximum timeout";
      }
    }
  }

  grouping ncs_rpc_notif_TIMEOUT {
    description
      "Common node of initial, retransmit";
    container timeout {
      description
        "Set timeout value range";
      leaf minimum {
        type uint32 {
          range "1..8";
        }
        description
          "Specify minimum timeout";
      }
      leaf maximum {
        type uint32 {
          range "1..8";
        }
        description
          "Specify maximum timeout";
      }
    }
  }

  grouping live_ncs_TIMEOUT {
    description
      "Common node of initial, retransmit";
    container timeout {
      description
        "Set timeout value range";
      leaf minimum {
        type uint32 {
          range "1..8";
        }
        description
          "Specify minimum timeout";
      }
      leaf maximum {
        type uint32 {
          range "1..8";
        }
        description
          "Specify maximum timeout";
      }
    }
  }

  grouping TIMEOUT {
    description
      "Common node of initial, retransmit";
    container timeout {
      description
        "Set timeout value range";
      leaf minimum {
        type uint32 {
          range "1..8";
        }
        description
          "Specify minimum timeout";
      }
      leaf maximum {
        type uint32 {
          range "1..8";
        }
        description
          "Specify maximum timeout";
      }
    }
  }

  augment "/ncs:devices/ncs:device/ncs:config" {
    container l2tp {
      tailf:ncs-device-type "netconf";
      tailf:display-when "not(../../ncs:module) or ../../ncs:module[ncs:name='Cisco-IOS-XR-tunnel-l2tun-cfg']";
      description
        "L2TPv3 class used for L2VPNs";
      container classes {
        description
          "List of classes";
        list class {
          key "class-name";
          description
            "Configuration for a specific class";
          container security {
            description
              "Security check";
            container ip {
              description
                "Security check for IP";
              leaf address-check {
                type empty;
                description
                  "Enable IP address check for L2TP packets";
              }
            }
          }
          container retransmit {
            description
              "Control message retransmission parameters";
            container initial {
              description
                "Set retries and timeouts for initial";
              leaf retry {
                type uint32 {
                  range "1..1000";
                }
                description
                  "Specify the retry number";
              }
              uses TIMEOUT;
            }
            leaf retry {
              type uint32 {
                range "5..1000";
              }
              description
                "Specify retransmit retry count";
            }
            uses TIMEOUT;
          }
          container tunnel {
            description
              "l2TP tunnel";
            leaf accounting {
              type string;
              description
                "Tunnel accounting";
            }
          }
          container digest {
            description
              "Message digest authentication for the L2TP
               control connection";
            container secrets {
              description
                "Set shared secret for message digest";
              list secret {
                key "secret-name";
                description
                  "The encrypted user secret and hash method";
                leaf secret-name {
                  type xr:Cisco-ios-xr-string;
                  description
                    "Specify the encrypted user secret";
                }
                leaf hash {
                  type L2tp-hash-method;
                  mandatory true;
                  description
                    "Specify hash method";
                }
              }
            }
            leaf hash {
              type L2tp-digest-hash-method;
              description
                "Specify hash method";
            }
            leaf check-disable {
              type empty;
              description
                "Disable digest checking";
            }
          }
          container ip {
            description
              "IP TOS value";
            leaf tos {
              type uint32 {
                range "0..255";
              }
              description
                "IP TOS value (decimal)";
            }
          }
          leaf host-name {
            type string;
            description
              "Local hostname for control connection
               authentication";
          }
          leaf hidden {
            type empty;
            description
              "Specify to hide AVPs in outgoing control
               messages";
          }
          leaf hello-interval {
            type uint32 {
              range "0..1000";
            }
            units "second";
            description
              "Specify interval (in seconds)";
          }
          leaf timeout-setup {
            type uint32 {
              range "60..6000";
            }
            units "second";
            description
              "Time permitted to set up a control connection";
          }
          leaf receive-window {
            type uint32 {
              range "1..16384";
            }
            units "byte";
            description
              "Receive window size for the control connection";
          }
          leaf congestion-control {
            type empty;
            description
              "Congestion control enabled";
          }
          leaf timeout-no-user {
            type L2tp-no-user;
            units "second";
            description
              "Timeout value for no-user in seconds";
          }
          leaf authentication {
            type uint32;
            description
              "Authenticate the L2TP control connection";
          }
          leaf enable {
            type empty;
            description
              "Enable L2TPv3 class used for L2VPNs";
          }
          leaf password {
            type xr:Proprietary-password;
            description
              "Specify the password for control channel
               authentication";
          }
          leaf class-name {
            type xr:Cisco-ios-xr-string {
              length "1..31";
            }
            description
              "Specify the class name. Regexp:
               ^[a-z0-9A-Z][-_.a-z0-9A-Z]*$";
          }
        }
      }
    }
  }
  augment "/ncs:devices/ncs:device/ncs:live-status" {
    container l2tp {
      tailf:ncs-device-type "netconf";
      tailf:display-when "not(../../ncs:module) or ../../ncs:module[ncs:name='Cisco-IOS-XR-tunnel-l2tun-cfg'] or (../../ncs:live-status-protocol[not(ncs:capability)]) or (../../ncs:live-status-protocol/ncs:capability/ncs:module[.='Cisco-IOS-XR-tunnel-l2tun-cfg'])";
      description
        "L2TPv3 class used for L2VPNs";
      container classes {
        description
          "List of classes";
        list class {
          key "class-name";
          description
            "Configuration for a specific class";
          container security {
            description
              "Security check";
            container ip {
              description
                "Security check for IP";
              leaf address-check {
                type empty;
                description
                  "Enable IP address check for L2TP packets";
              }
            }
          }
          container retransmit {
            description
              "Control message retransmission parameters";
            container initial {
              description
                "Set retries and timeouts for initial";
              leaf retry {
                type uint32 {
                  range "1..1000";
                }
                description
                  "Specify the retry number";
              }
              uses live_ncs_TIMEOUT;
            }
            leaf retry {
              type uint32 {
                range "5..1000";
              }
              description
                "Specify retransmit retry count";
            }
            uses live_ncs_TIMEOUT;
          }
          container tunnel {
            description
              "l2TP tunnel";
            leaf accounting {
              type string;
              description
                "Tunnel accounting";
            }
          }
          container digest {
            description
              "Message digest authentication for the L2TP
               control connection";
            container secrets {
              description
                "Set shared secret for message digest";
              list secret {
                key "secret-name";
                description
                  "The encrypted user secret and hash method";
                leaf secret-name {
                  type xr:Cisco-ios-xr-string;
                  description
                    "Specify the encrypted user secret";
                }
                leaf hash {
                  type L2tp-hash-method;
                  // NCS drop mandatory statement
                  description
                    "Specify hash method";
                }
              }
            }
            leaf hash {
              type L2tp-digest-hash-method;
              description
                "Specify hash method";
            }
            leaf check-disable {
              type empty;
              description
                "Disable digest checking";
            }
          }
          container ip {
            description
              "IP TOS value";
            leaf tos {
              type uint32 {
                range "0..255";
              }
              description
                "IP TOS value (decimal)";
            }
          }
          leaf host-name {
            type string;
            description
              "Local hostname for control connection
               authentication";
          }
          leaf hidden {
            type empty;
            description
              "Specify to hide AVPs in outgoing control
               messages";
          }
          leaf hello-interval {
            type uint32 {
              range "0..1000";
            }
            units "second";
            description
              "Specify interval (in seconds)";
          }
          leaf timeout-setup {
            type uint32 {
              range "60..6000";
            }
            units "second";
            description
              "Time permitted to set up a control connection";
          }
          leaf receive-window {
            type uint32 {
              range "1..16384";
            }
            units "byte";
            description
              "Receive window size for the control connection";
          }
          leaf congestion-control {
            type empty;
            description
              "Congestion control enabled";
          }
          leaf timeout-no-user {
            type L2tp-no-user;
            units "second";
            description
              "Timeout value for no-user in seconds";
          }
          leaf authentication {
            type uint32;
            description
              "Authenticate the L2TP control connection";
          }
          leaf enable {
            type empty;
            description
              "Enable L2TPv3 class used for L2VPNs";
          }
          leaf password {
            type xr:Proprietary-password;
            description
              "Specify the password for control channel
               authentication";
          }
          leaf class-name {
            type xr:Cisco-ios-xr-string {
              length "1..31";
            }
            description
              "Specify the class name. Regexp:
               ^[a-z0-9A-Z][-_.a-z0-9A-Z]*$";
          }
        }
      }
    }
  }
  augment "/ncs:devices/ncs:template/ncs:ned-id/ncs:config" {
    container l2tp {
      description
        "L2TPv3 class used for L2VPNs";
      container classes {
        description
          "List of classes";
        list class {
          // NCS patched for predictable order
          ordered-by user;
          key "class-name";
          description
            "Configuration for a specific class";
          container security {
            description
              "Security check";
            container ip {
              description
                "Security check for IP";
              leaf address-check {
                type empty;
                description
                  "Enable IP address check for L2TP packets";
              }
            }
          }
          container retransmit {
            description
              "Control message retransmission parameters";
            container initial {
              description
                "Set retries and timeouts for initial";
              leaf retry {
                type string;
                description
                  "Specify the retry number";
              }
              uses ncs_template_TIMEOUT;
            }
            leaf retry {
              type string;
              description
                "Specify retransmit retry count";
            }
            uses ncs_template_TIMEOUT;
          }
          container tunnel {
            description
              "l2TP tunnel";
            leaf accounting {
              type string;
              description
                "Tunnel accounting";
            }
          }
          container digest {
            description
              "Message digest authentication for the L2TP
               control connection";
            container secrets {
              description
                "Set shared secret for message digest";
              list secret {
                // NCS patched for predictable order
                ordered-by user;
                key "secret-name";
                description
                  "The encrypted user secret and hash method";
                leaf secret-name {
                  type string;
                  description
                    "Specify the encrypted user secret";
                }
                leaf hash {
                  type string;
                  // NCS drop mandatory statement
                  description
                    "Specify hash method";
                }
              }
            }
            leaf hash {
              type string;
              description
                "Specify hash method";
            }
            leaf check-disable {
              type empty;
              description
                "Disable digest checking";
            }
          }
          container ip {
            description
              "IP TOS value";
            leaf tos {
              type string;
              description
                "IP TOS value (decimal)";
            }
          }
          leaf host-name {
            type string;
            description
              "Local hostname for control connection
               authentication";
          }
          leaf hidden {
            type empty;
            description
              "Specify to hide AVPs in outgoing control
               messages";
          }
          leaf hello-interval {
            type string;
            units "second";
            description
              "Specify interval (in seconds)";
          }
          leaf timeout-setup {
            type string;
            units "second";
            description
              "Time permitted to set up a control connection";
          }
          leaf receive-window {
            type string;
            units "byte";
            description
              "Receive window size for the control connection";
          }
          leaf congestion-control {
            type empty;
            description
              "Congestion control enabled";
          }
          leaf timeout-no-user {
            type string;
            units "second";
            description
              "Timeout value for no-user in seconds";
          }
          leaf authentication {
            type string;
            description
              "Authenticate the L2TP control connection";
          }
          leaf enable {
            type empty;
            description
              "Enable L2TPv3 class used for L2VPNs";
          }
          leaf password {
            type string;
            description
              "Specify the password for control channel
               authentication";
          }
          leaf class-name {
            type string;
            description
              "Specify the class name. Regexp:
               ^[a-z0-9A-Z][-_.a-z0-9A-Z]*$";
          }
        }
      }
    }
  }
}
