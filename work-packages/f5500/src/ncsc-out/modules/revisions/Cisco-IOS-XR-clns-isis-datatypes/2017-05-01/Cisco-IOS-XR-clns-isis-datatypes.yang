module Cisco-IOS-XR-clns-isis-datatypes {
  // Generated by yanger -t ncs
  tailf:mount-id f5500-nc-1.0:f5500-nc-1.0;
  tailf:ncs-device-type "netconf";

  namespace "http://cisco.com/ns/yang/Cisco-IOS-XR-clns-isis-datatypes";
  prefix Cisco-IOS-XR-clns-isis-datatypes;

  import Cisco-IOS-XR-types {
    prefix xr;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of generally useful
     derived YANG data types.

     Copyright (c) 2013-2018 by Cisco Systems, Inc.
     All rights reserved.";

  revision 2017-05-01 {
    description
      "Fixing backward compatibility error in module.";
  }
  revision 2015-11-09 {
    description
      "IOS XR 6.0 revision.";
  }

  typedef Isis-topology-name {
    type xr:Cisco-ios-xr-string {
      length "1..32";
    }
    description
      "Isis topology name";
  }

  typedef Isis-sub-address-family {
    type enumeration {
      enum "unicast" {
        value 0;
        description
          "Unicast";
      }
      enum "multicast" {
        value 1;
        description
          "Multicast";
      }
    }
    description
      "Isis sub address family";
  }

  typedef Isis-link-group-name {
    type xr:Cisco-ios-xr-string {
      length "1..40";
    }
    description
      "Isis link group name";
  }

  typedef Isis-internal-level {
    type enumeration {
      enum "not-set" {
        value 0;
        description
          "Level not set";
      }
      enum "level1" {
        value 1;
        description
          "Level1";
      }
      enum "level2" {
        value 2;
        description
          "Level2";
      }
    }
    description
      "Isis internal level";
  }

  typedef Isis-instance-name {
    type xr:Cisco-ios-xr-string {
      length "1..36";
    }
    description
      "Isis instance name";
  }

  typedef Isis-locator-name {
    type xr:Cisco-ios-xr-string {
      length "1..60";
    }
    description
      "Isis locator name";
  }

  typedef Isis-ipv4-prefix-length {
    type uint32 {
      range "0..32";
    }
    description
      "Isis ipv4 prefix length";
  }

  typedef Isis-ipv6-prefix-length {
    type uint32 {
      range "0..128";
    }
    description
      "Isis ipv6 prefix length";
  }

  typedef Isis-address-family {
    type enumeration {
      enum "ipv4" {
        value 0;
        description
          "IPv4";
      }
      enum "ipv6" {
        value 1;
        description
          "IPv6";
      }
    }
    description
      "Isis address family";
  }
}
