submodule Cisco-IOS-XR-ip-tcp-oper-sub5 {
  // Generated by yanger -t ncs
  tailf:mount-id f5500-nc-1.0:f5500-nc-1.0;

  belongs-to Cisco-IOS-XR-ip-tcp-oper {
    prefix Cisco-IOS-XR-ip-tcp-oper-sub5;
  }

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This submodule contains a collection of YANG definitions
     for Cisco IOS-XR ip-tcp package operational data.

     Copyright (c) 2013-2018 by Cisco Systems, Inc.
     All rights reserved.";

  revision 2018-11-01 {
    description
      "Added socket async double free prevention count in tcp statistics summary";
  }
  revision 2018-02-14 {
    description
      "PCB_ID argument is passed in string format.";
  }
  revision 2018-02-14 {
    description
      "Added support for TCP-AO feature.";
  }
  revision 2017-05-01 {
    description
      "Fixing backward compatibility error in module.";
  }
  revision 2016-02-26 {
    description
      "Descriptions updated.";
  }
  revision 2015-11-09 {
    description
      "IOS XR 6.0 revision.";
  }

  grouping ncs_template_TRANSP-CLIENT-STATS-BAG {
    description
      "Aggregated statistics of a transport client";
    leaf client-jid {
      type string;
      description
        "Job ID of the transport client";
    }
    leaf client-name {
      type string;
      description
        "Transport client name";
    }
    leaf ipv4-received-packets {
      type string;
      description
        "Total IPv4 packets received from client";
    }
    leaf ipv4-sent-packets {
      type string;
      description
        "Total IPv4 packets sent to client";
    }
    leaf ipv6-received-packets {
      type string;
      description
        "Total IPv6 packets received from app";
    }
    leaf ipv6-sent-packets {
      type string;
      description
        "Total IPv6 packets sent to app";
    }
  }

  grouping ncs_rpc_notif_TRANSP-CLIENT-STATS-BAG {
    description
      "Aggregated statistics of a transport client";
    leaf client-jid {
      type int32;
      description
        "Job ID of the transport client";
    }
    leaf client-name {
      type string {
        length "0..21";
      }
      description
        "Transport client name";
    }
    leaf ipv4-received-packets {
      type uint32;
      description
        "Total IPv4 packets received from client";
    }
    leaf ipv4-sent-packets {
      type uint32;
      description
        "Total IPv4 packets sent to client";
    }
    leaf ipv6-received-packets {
      type uint32;
      description
        "Total IPv6 packets received from app";
    }
    leaf ipv6-sent-packets {
      type uint32;
      description
        "Total IPv6 packets sent to app";
    }
  }

  grouping live_ncs_TRANSP-CLIENT-STATS-BAG {
    description
      "Aggregated statistics of a transport client";
    leaf client-jid {
      type int32;
      description
        "Job ID of the transport client";
    }
    leaf client-name {
      type string {
        length "0..21";
      }
      description
        "Transport client name";
    }
    leaf ipv4-received-packets {
      type uint32;
      description
        "Total IPv4 packets received from client";
    }
    leaf ipv4-sent-packets {
      type uint32;
      description
        "Total IPv4 packets sent to client";
    }
    leaf ipv6-received-packets {
      type uint32;
      description
        "Total IPv6 packets received from app";
    }
    leaf ipv6-sent-packets {
      type uint32;
      description
        "Total IPv6 packets sent to app";
    }
  }

  grouping TRANSP-CLIENT-STATS-BAG {
    description
      "Aggregated statistics of a transport client";
    leaf client-jid {
      type int32;
      description
        "Job ID of the transport client";
    }
    leaf client-name {
      type string {
        length "0..21";
      }
      description
        "Transport client name";
    }
    leaf ipv4-received-packets {
      type uint32;
      description
        "Total IPv4 packets received from client";
    }
    leaf ipv4-sent-packets {
      type uint32;
      description
        "Total IPv4 packets sent to client";
    }
    leaf ipv6-received-packets {
      type uint32;
      description
        "Total IPv6 packets received from app";
    }
    leaf ipv6-sent-packets {
      type uint32;
      description
        "Total IPv6 packets sent to app";
    }
  }
}
