module notifications {
  // Generated by yanger -t ncs
  tailf:mount-id f5500-nc-1.0:f5500-nc-1.0;
  tailf:ncs-device-type "netconf";

  namespace "urn:ietf:params:xml:ns:netconf:notification:1.0";
  prefix notifications;

  import ietf-yang-types {
    prefix yang;
  }
  import "f5500-nc-1.0" {
    prefix "f5500-nc-1.0";
  }
  import tailf-ncs {
    prefix ncs;
  }
  import tailf-common {
    prefix tailf;
  }

  organization
    "IETF NETCONF WG";
  contact
    "netconf@ops.ietf.org";
  description
    "Conversion of the 'ncEvent' XSD in the
     NETCONF Notifications RFC.";

  revision 2008-07-14 {
    description
      "Initial revision.";
    reference "RFC 5277: NETCONF Event Notifications";
  }

  typedef streamNameType {
    type string;
    description
      "The name of an event stream.";
  }

  augment "/ncs:devices/ncs:device/ncs:rpc" {
    container rpc-create-subscription {
      tailf:ncs-device-type "netconf";
      tailf:display-when "not(../../ncs:module) or ../../ncs:module[ncs:name='notifications']";
      tailf:action create-subscription {
        tailf:actionpoint ncsproxy {
          tailf:internal;
        }
        description
          "The command to create a notification subscription. It
           takes as argument the name of the notification stream
           and filter. Both of those options limit the content of
           the subscription. In addition, there are two time-related
           parameters, startTime and stopTime, which can be used to
           select the time interval of interest to the notification
           replay feature.";
        input {
          leaf stream {
            type streamNameType;
            default "NETCONF";
            description
              "An optional parameter that indicates which stream of
               events is of interest. If not present, then events in the
               default NETCONF stream will be sent.";
          }
          anyxml filter {
            description
              "An optional parameter that indicates which subset of all
               possible events is of interest. The format of this
               parameter is the same as that of the filter parameter
               in the NETCONF protocol operations. If not present,
               all events not precluded by other parameters will
               be sent.";
          }
          leaf startTime {
            type yang:date-and-time;
            description
              "A parameter used to trigger the replay feature and
               indicates that the replay should start at the time
               specified. If start time is not present, this is not a
               replay subscription.";
          }
          leaf stopTime {
            type yang:date-and-time;
            description
              "An optional parameter used with the optional replay
               feature to indicate the newest notifications of
               interest. If stop time is not present, the notifications
               will continue until the subscription is terminated.
               Must be used with startTime.";
          }
        }
      }
    }
  }
  augment "/ncs:devices/ncs:device-group/ncs:ned-id/ncs:rpc" {
    container rpc-create-subscription {
      tailf:ncs-device-type "netconf";
      tailf:display-when "/ncs:devices/ncs:device[ncs:name=current()/../../../ncs:member]/ncs:module[ncs:name='notifications']";
      tailf:action create-subscription {
        tailf:actionpoint ncsproxy {
          tailf:internal;
        }
        description
          "The command to create a notification subscription. It
           takes as argument the name of the notification stream
           and filter. Both of those options limit the content of
           the subscription. In addition, there are two time-related
           parameters, startTime and stopTime, which can be used to
           select the time interval of interest to the notification
           replay feature.";
        input {
          leaf stream {
            type streamNameType;
            default "NETCONF";
            description
              "An optional parameter that indicates which stream of
               events is of interest. If not present, then events in the
               default NETCONF stream will be sent.";
          }
          anyxml filter {
            description
              "An optional parameter that indicates which subset of all
               possible events is of interest. The format of this
               parameter is the same as that of the filter parameter
               in the NETCONF protocol operations. If not present,
               all events not precluded by other parameters will
               be sent.";
          }
          leaf startTime {
            type yang:date-and-time;
            description
              "A parameter used to trigger the replay feature and
               indicates that the replay should start at the time
               specified. If start time is not present, this is not a
               replay subscription.";
          }
          leaf stopTime {
            type yang:date-and-time;
            description
              "An optional parameter used with the optional replay
               feature to indicate the newest notifications of
               interest. If stop time is not present, the notifications
               will continue until the subscription is terminated.
               Must be used with startTime.";
          }
        }
      }
    }
  }
}
