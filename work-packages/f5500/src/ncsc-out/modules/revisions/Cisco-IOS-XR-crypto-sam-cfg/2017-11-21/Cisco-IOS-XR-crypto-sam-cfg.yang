module Cisco-IOS-XR-crypto-sam-cfg {
  // Generated by yanger -t ncs
  tailf:mount-id f5500-nc-1.0:f5500-nc-1.0;
  tailf:ncs-device-type "netconf";

  namespace "http://cisco.com/ns/yang/Cisco-IOS-XR-crypto-sam-cfg";
  prefix Cisco-IOS-XR-crypto-sam-cfg;

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR crypto-sam package configuration.

     This module contains definitions
     for the following management objects:
       sam: Software Authentication Manager (SAM) Config

     Copyright (c) 2013-2018 by Cisco Systems, Inc.
     All rights reserved.";

  revision 2017-11-21 {
    description
      "Resolving dependency issue with SAM";
  }
  revision 2015-01-07 {
    description
      "IOS XR 5.3.1 revision.";
  }

  typedef Crypto-sam-action {
    type enumeration {
      enum "proceed" {
        value 1;
        description
          "To respond YES to the SAM prompt";
      }
      enum "terminate" {
        value 2;
        description
          "To respond NO to the SAM prompt";
      }
    }
    description
      "Crypto sam action";
  }

  augment "/ncs:devices/ncs:device/ncs:config" {
    container sam {
      tailf:ncs-device-type "netconf";
      tailf:display-when "not(../../ncs:module) or ../../ncs:module[ncs:name='Cisco-IOS-XR-crypto-sam-cfg']";
      description
        "Software Authentication Manager (SAM) Config";
      container prompt-interval {
        presence "Indicates a prompt-interval node is configured.";
        description
          "Set prompt interval at reboot time";
        leaf action {
          type Crypto-sam-action;
          mandatory true;
          description
            "Respond to SAM prompt either Proceed/Terminate";
        }
        leaf prompt-time {
          type uint32 {
            range "0..300";
          }
          units "second";
          mandatory true;
          description
            "Prompt time from 0 - 300 seconds";
        }
      }
    }
  }
  augment "/ncs:devices/ncs:device/ncs:live-status" {
    container sam {
      tailf:ncs-device-type "netconf";
      tailf:display-when "not(../../ncs:module) or ../../ncs:module[ncs:name='Cisco-IOS-XR-crypto-sam-cfg'] or (../../ncs:live-status-protocol[not(ncs:capability)]) or (../../ncs:live-status-protocol/ncs:capability/ncs:module[.='Cisco-IOS-XR-crypto-sam-cfg'])";
      description
        "Software Authentication Manager (SAM) Config";
      container prompt-interval {
        presence "Indicates a prompt-interval node is configured.";
        description
          "Set prompt interval at reboot time";
        leaf action {
          type Crypto-sam-action;
          // NCS drop mandatory statement
          description
            "Respond to SAM prompt either Proceed/Terminate";
        }
        leaf prompt-time {
          type uint32 {
            range "0..300";
          }
          units "second";
          // NCS drop mandatory statement
          description
            "Prompt time from 0 - 300 seconds";
        }
      }
    }
  }
  augment "/ncs:devices/ncs:template/ncs:ned-id/ncs:config" {
    container sam {
      description
        "Software Authentication Manager (SAM) Config";
      container prompt-interval {
        presence "Indicates a prompt-interval node is configured.";
        description
          "Set prompt interval at reboot time";
        leaf action {
          type string;
          // NCS drop mandatory statement
          description
            "Respond to SAM prompt either Proceed/Terminate";
        }
        leaf prompt-time {
          type string;
          units "second";
          // NCS drop mandatory statement
          description
            "Prompt time from 0 - 300 seconds";
        }
      }
    }
  }
}
