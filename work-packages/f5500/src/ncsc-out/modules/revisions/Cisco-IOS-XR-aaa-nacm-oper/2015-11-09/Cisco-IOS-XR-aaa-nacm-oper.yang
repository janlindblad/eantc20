module Cisco-IOS-XR-aaa-nacm-oper {
  // Generated by yanger -t ncs
  tailf:mount-id f5500-nc-1.0:f5500-nc-1.0;
  tailf:ncs-device-type "netconf";

  namespace "http://cisco.com/ns/yang/Cisco-IOS-XR-aaa-nacm-oper";
  prefix Cisco-IOS-XR-aaa-nacm-oper;

  import Cisco-IOS-XR-types {
    prefix xr;
  }
  include Cisco-IOS-XR-aaa-nacm-oper-sub1 {
    revision-date 2015-11-09;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR aaa-nacm package operational data.

     This module contains definitions
     for the following management objects:
       aaa-nacm: AAA Nacm Information

     Copyright (c) 2013-2018 by Cisco Systems, Inc.
     All rights reserved.";

  revision 2015-11-09 {
    description
      "IOS XR 6.0 revision.";
  }

  augment "/ncs:devices/ncs:device/ncs:config" {
    // NCS drop config false container 'aaa-nacm'
  }
  augment "/ncs:devices/ncs:device/ncs:live-status" {
    container aaa-nacm {
      tailf:ncs-device-type "netconf";
      tailf:display-when "not(../../ncs:module) or ../../ncs:module[ncs:name='Cisco-IOS-XR-aaa-nacm-oper'] or (../../ncs:live-status-protocol[not(ncs:capability)]) or (../../ncs:live-status-protocol/ncs:capability/ncs:module[.='Cisco-IOS-XR-aaa-nacm-oper'])";
      description
        "AAA Nacm Information";
      container counters {
        description
          "AAA NACM summary";
        uses live_ncs_NACM-COUNTERS;
      }
      container users {
        description
          "AAA NACM User summary";
        list user {
          key "user";
          description
            "AAA NACM User detail";
          leaf user {
            type xr:Cisco-ios-xr-string {
              length "1..256";
            }
            description
              "User";
          }
          uses live_ncs_NACM-USER-DETAIL;
        }
      }
      container summary {
        description
          "AAA NACM summary";
        uses live_ncs_NACM-SUMMARY;
      }
      container rules {
        description
          "AAA NACM Rulelist summary";
        list rule {
          description
            "AAA NACM Rulelist detail";
          container rulelist-rules {
            description
              "AAA NACM Rulelist detail";
            list rulelist-rule {
              key "rule";
              description
                "AAA NACM Rulelist detail";
              leaf rule {
                type xr:Cisco-ios-xr-string {
                  length "1..256";
                }
                description
                  "Rule";
              }
              uses live_ncs_NACM-RULE-DETAIL;
            }
          }
          leaf ordering-index {
            type xr:Cisco-ios-xr-string {
              length "1..256";
            }
            description
              "Rulelist Ordering Index";
          }
          leaf rulelist-name {
            type xr:Cisco-ios-xr-string {
              length "1..256";
            }
            description
              "Rulelist Name";
          }
        }
      }
      container groups {
        description
          "AAA NACM Group summary";
        list group {
          key "group";
          description
            "AAA NACM Group detail";
          leaf group {
            type xr:Cisco-ios-xr-string {
              length "1..256";
            }
            description
              "Group";
          }
          uses live_ncs_NACM-GROUP-DETAIL;
        }
      }
    }
  }
  augment "/ncs:devices/ncs:template/ncs:ned-id/ncs:config" {
    // NCS drop config false container 'aaa-nacm'
  }
}
