module Cisco-IOS-XR-lpts-ifib-oper {
  // Generated by yanger -t ncs
  tailf:mount-id f5500-nc-1.0:f5500-nc-1.0;
  tailf:ncs-device-type "netconf";

  namespace "http://cisco.com/ns/yang/Cisco-IOS-XR-lpts-ifib-oper";
  prefix Cisco-IOS-XR-lpts-ifib-oper;

  import Cisco-IOS-XR-types {
    prefix xr;
  }
  include Cisco-IOS-XR-lpts-ifib-oper-sub1 {
    revision-date 2017-09-07;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR lpts-ifib package operational data.

     This module contains definitions
     for the following management objects:
       lpts-ifib: lpts ifib database

     Copyright (c) 2013-2018 by Cisco Systems, Inc.
     All rights reserved.";

  revision 2017-09-07 {
    description
      "Fixed type translation error.";
  }
  revision 2015-11-09 {
    description
      "IOS XR 6.0 revision.";
  }

  augment "/ncs:devices/ncs:device/ncs:config" {
    // NCS drop config false container 'lpts-ifib'
  }
  augment "/ncs:devices/ncs:device/ncs:live-status" {
    container lpts-ifib {
      tailf:ncs-device-type "netconf";
      tailf:display-when "not(../../ncs:module) or ../../ncs:module[ncs:name='Cisco-IOS-XR-lpts-ifib-oper'] or (../../ncs:live-status-protocol[not(ncs:capability)]) or (../../ncs:live-status-protocol/ncs:capability/ncs:module[.='Cisco-IOS-XR-lpts-ifib-oper'])";
      description
        "lpts ifib database";
      container nodes {
        description
          "Node ifib database";
        list node {
          key "node-name";
          description
            "Per node slice ";
          container slice-ids {
            description
              "Slice specific";
            list slice-id {
              key "slice-name";
              description
                "slice types";
              leaf slice-name {
                type xr:Cisco-ios-xr-string;
                description
                  "Type value";
              }
              list entry {
                key "entry";
                description
                  "Data for single pre-ifib entry";
                leaf entry {
                  type uint32;
                  description
                    "Single Pre-ifib entry";
                }
                uses live_ncs_FM-IFIB-ENTRY;
              }
            }
          }
          leaf node-name {
            type xr:Node-id;
            description
              "The node name";
          }
        }
      }
    }
  }
  augment "/ncs:devices/ncs:template/ncs:ned-id/ncs:config" {
    // NCS drop config false container 'lpts-ifib'
  }
}
