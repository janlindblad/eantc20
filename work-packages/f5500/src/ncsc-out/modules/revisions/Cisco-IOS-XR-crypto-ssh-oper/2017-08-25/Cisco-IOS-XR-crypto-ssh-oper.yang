module Cisco-IOS-XR-crypto-ssh-oper {
  // Generated by yanger -t ncs
  tailf:mount-id f5500-nc-1.0:f5500-nc-1.0;
  tailf:ncs-device-type "netconf";

  namespace "http://cisco.com/ns/yang/Cisco-IOS-XR-crypto-ssh-oper";
  prefix Cisco-IOS-XR-crypto-ssh-oper;

  import Cisco-IOS-XR-types {
    prefix xr;
  }
  include Cisco-IOS-XR-crypto-ssh-oper-sub1 {
    revision-date 2017-08-25;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR crypto-ssh package operational data.

     This module contains definitions
     for the following management objects:
       ssh1: Crypto Secure Shell(SSH) data
       ssh: ssh

     Copyright (c) 2013-2018 by Cisco Systems, Inc.
     All rights reserved.";

  revision 2017-08-25 {
    description
      "Introducing show ssh history CLI.";
  }
  revision 2017-05-01 {
    description
      "Fixing backward compatibility error in module.";
  }
  revision 2015-06-02 {
    description
      "IOS XR 5.3.2 revision.";
  }
  revision 2015-01-07 {
    description
      "IOS XR 5.3.1 revision.";
  }

  augment "/ncs:devices/ncs:device/ncs:config" {
    // NCS drop config false container ssh1
    // NCS drop config false container ssh
  }
  augment "/ncs:devices/ncs:device/ncs:live-status" {
    container ssh1 {
      tailf:ncs-device-type "netconf";
      tailf:display-when "not(../../ncs:module) or ../../ncs:module[ncs:name='Cisco-IOS-XR-crypto-ssh-oper'] or (../../ncs:live-status-protocol[not(ncs:capability)]) or (../../ncs:live-status-protocol/ncs:capability/ncs:module[.='Cisco-IOS-XR-crypto-ssh-oper'])";
      description
        "Crypto Secure Shell(SSH) data";
      container kex {
        description
          "key exchange method data";
        container nodes {
          description
            "Node-specific ssh session details";
          list node {
            key "node-name";
            description
              "SSH session details for a particular node";
            leaf node-name {
              type xr:Node-id;
              description
                "Node name";
            }
            uses live_ncs_SSH-SESSION-DETAIL;
          }
        }
      }
    }
    container ssh {
      tailf:ncs-device-type "netconf";
      tailf:display-when "not(../../ncs:module) or ../../ncs:module[ncs:name='Cisco-IOS-XR-crypto-ssh-oper'] or (../../ncs:live-status-protocol[not(ncs:capability)]) or (../../ncs:live-status-protocol/ncs:capability/ncs:module[.='Cisco-IOS-XR-crypto-ssh-oper'])";
      description
        "ssh";
      container session {
        description
          "Crypto SSH session";
        container rekey {
          description
            "SSH session rekey information";
          uses live_ncs_SSH-SESSION-REKEY;
        }
        container history-detail {
          description
            "SSH session history detail information";
          uses live_ncs_SSH-SESSION-DETAIL;
        }
        container brief {
          description
            "SSH session brief information";
          uses live_ncs_SSH-SESSION-BRIEF;
        }
        container history {
          description
            "SSH session history information";
          uses live_ncs_SSH-SESSION-HISTORY;
        }
        container detail {
          description
            "SSH session detail information";
          uses live_ncs_SSH-SESSION-DETAIL;
        }
      }
    }
  }
  augment "/ncs:devices/ncs:template/ncs:ned-id/ncs:config" {
    // NCS drop config false container ssh1
    // NCS drop config false container ssh
  }
}
