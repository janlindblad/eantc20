module Cisco-IOS-XR-controller-optics-oper {
  // Generated by yanger -t ncs
  tailf:mount-id f5500-nc-1.0:f5500-nc-1.0;
  tailf:ncs-device-type "netconf";

  namespace "http://cisco.com/ns/yang/Cisco-IOS-XR-controller-optics-oper";
  prefix Cisco-IOS-XR-controller-optics-oper;

  import Cisco-IOS-XR-types {
    prefix xr;
  }
  include Cisco-IOS-XR-controller-optics-oper-sub1 {
    revision-date 2017-09-07;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR controller-optics package operational data.

     This module contains definitions
     for the following management objects:
       optics-oper: Optics operational data

     Copyright (c) 2013-2018 by Cisco Systems, Inc.
     All rights reserved.";

  revision 2017-09-07 {
    description
      "Fixed type translation error.";
  }
  revision 2017-05-01 {
    description
      "Fixing backward compatibility error in module.";
  }
  revision 2015-11-09 {
    description
      "IOS XR 6.0 revision.";
  }

  augment "/ncs:devices/ncs:device/ncs:config" {
    // NCS drop config false container 'optics-oper'
  }
  augment "/ncs:devices/ncs:device/ncs:live-status" {
    container optics-oper {
      tailf:ncs-device-type "netconf";
      tailf:display-when "not(../../ncs:module) or ../../ncs:module[ncs:name='Cisco-IOS-XR-controller-optics-oper'] or (../../ncs:live-status-protocol[not(ncs:capability)]) or (../../ncs:live-status-protocol/ncs:capability/ncs:module[.='Cisco-IOS-XR-controller-optics-oper'])";
      description
        "Optics operational data";
      container optics-ports {
        description
          "All Optics Port operational data";
        list optics-port {
          key "name";
          description
            "Optics operational data";
          container optics-dwdm-carrier-channel-map {
            description
              "Optics operational data";
            uses live_ncs_OPTICS-EDM-WAVE-INFO;
          }
          container ots-spectrum-info {
            description
              "Ots Spectrum Operational data";
            uses live_ncs_OPTICS-EDM-SPECTRUM-INFO;
          }
          container optics-dwdm-carrier-channel-map-flexi {
            description
              "Optics operational data";
            uses live_ncs_OPTICS-EDM-WAVE-INFO;
          }
          container optics-info {
            description
              "Optics operational data";
            uses live_ncs_OPTICS-EDM-INFO;
          }
          container optics-lanes {
            description
              "All Optics Port operational data";
            list optics-lane {
              key "number";
              description
                "Lane Information";
              leaf number {
                type uint32;
                description
                  "Lane Index";
              }
              uses live_ncs_OPTICS-EDM-LANE-DATA;
            }
          }
          container optics-db-info {
            description
              "Optics operational data";
            uses live_ncs_OPTICS-DB-INFO;
          }
          leaf name {
            type xr:Interface-name;
            description
              "Port name";
          }
        }
      }
    }
  }
  augment "/ncs:devices/ncs:template/ncs:ned-id/ncs:config" {
    // NCS drop config false container 'optics-oper'
  }
}
