module Cisco-IOS-XR-infra-ltrace-cfg {
  // Generated by yanger -t ncs
  tailf:mount-id f5500-nc-1.0:f5500-nc-1.0;
  tailf:ncs-device-type "netconf";

  namespace "http://cisco.com/ns/yang/Cisco-IOS-XR-infra-ltrace-cfg";
  prefix Cisco-IOS-XR-infra-ltrace-cfg;

  import Cisco-IOS-XR-config-mda-cfg {
    prefix node;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR infra-ltrace package configuration.

     This YANG module augments the
       Cisco-IOS-XR-config-mda-cfg
     module with configuration data.

     Copyright (c) 2013-2018 by Cisco Systems, Inc.
     All rights reserved.";

  revision 2015-11-09 {
    description
      "IOS XR 6.0 revision.";
  }

  typedef Infra-ltrace-scale {
    type enumeration {
      enum "0" {
        value 0;
        description
          "Use platform-defined scale-factor";
      }
      enum "1" {
        value 1;
        description
          "Do not scale down ltrace memory request";
      }
      enum "2" {
        value 2;
        description
          "Scale down ltrace memory request by 2";
      }
      enum "4" {
        value 4;
        description
          "Scale down ltrace memory request by 4";
      }
      enum "8" {
        value 8;
        description
          "Scale down ltrace memory request by 8";
      }
      enum "16" {
        value 16;
        description
          "Scale down ltrace memory request by 16";
      }
    }
    description
      "Infra ltrace scale";
  }

  typedef Infra-ltrace-mode {
    type enumeration {
      enum "static" {
        value 1;
        description
          "Set ltrace memory allocation to static mode";
      }
      enum "dynamic" {
        value 2;
        description
          "Set ltrace memory allocation to dynamic mode";
      }
    }
    description
      "Infra ltrace mode";
  }

  grouping ncs_template_NODE-CFG {
    description
      "active/preconfigured nodes configuration";
    container ltrace {
      description
        "Ltrace Memory configuration";
      container allocation-params {
        description
          "Select Ltrace mode and scale-factor";
        leaf mode {
          type string;
          description
            "Select an allocation mode (static:1, dynamic
             :2)";
        }
        leaf scale-factor {
          type string;
          description
            "Select a scaling down factor";
        }
      }
    }
  }

  grouping ncs_rpc_notif_NODE-CFG {
    description
      "active/preconfigured nodes configuration";
    container ltrace {
      description
        "Ltrace Memory configuration";
      container allocation-params {
        description
          "Select Ltrace mode and scale-factor";
        leaf mode {
          type Infra-ltrace-mode;
          description
            "Select an allocation mode (static:1, dynamic
             :2)";
        }
        leaf scale-factor {
          type Infra-ltrace-scale;
          description
            "Select a scaling down factor";
        }
      }
    }
  }

  grouping live_ncs_NODE-CFG {
    description
      "active/preconfigured nodes configuration";
    container ltrace {
      description
        "Ltrace Memory configuration";
      container allocation-params {
        description
          "Select Ltrace mode and scale-factor";
        leaf mode {
          type Infra-ltrace-mode;
          description
            "Select an allocation mode (static:1, dynamic
             :2)";
        }
        leaf scale-factor {
          type Infra-ltrace-scale;
          description
            "Select a scaling down factor";
        }
      }
    }
  }

  grouping NODE-CFG {
    description
      "active/preconfigured nodes configuration";
    container ltrace {
      description
        "Ltrace Memory configuration";
      container allocation-params {
        description
          "Select Ltrace mode and scale-factor";
        leaf mode {
          type Infra-ltrace-mode;
          description
            "Select an allocation mode (static:1, dynamic
             :2)";
        }
        leaf scale-factor {
          type Infra-ltrace-scale;
          description
            "Select a scaling down factor";
        }
      }
    }
  }

  augment "/ncs:devices/ncs:template/ncs:ned-id/ncs:config/node:active-nodes/node:active-node" {
    uses ncs_template_NODE-CFG;
    description
      "This augment extends active nodes configuration";
  }
  augment "/ncs:devices/ncs:device/ncs:live-status/node:active-nodes/node:active-node" {
    uses live_ncs_NODE-CFG {
      refine ltrace {
        tailf:ncs-device-type "netconf";
        tailf:display-when "not(../../../../ncs:module) or ../../../../ncs:module[ncs:name='Cisco-IOS-XR-infra-ltrace-cfg'] or (../../../../ncs:live-status-protocol[not(ncs:capability)]) or (../../../../ncs:live-status-protocol/ncs:capability/ncs:module[.='Cisco-IOS-XR-infra-ltrace-cfg'])";
      }
    }
    description
      "This augment extends active nodes configuration";
  }
  augment "/ncs:devices/ncs:device/ncs:config/node:active-nodes/node:active-node" {
    uses NODE-CFG {
      refine ltrace {
        tailf:ncs-device-type "netconf";
        tailf:display-when "not(../../../../ncs:module) or ../../../../ncs:module[ncs:name='Cisco-IOS-XR-infra-ltrace-cfg']";
      }
    }
    description
      "This augment extends active nodes configuration";
  }
  augment "/ncs:devices/ncs:template/ncs:ned-id/ncs:config/node:preconfigured-nodes/node:preconfigured-node" {
    uses ncs_template_NODE-CFG;
    description
      "This augment extends preconfigured nodes
       configuration";
  }
  augment "/ncs:devices/ncs:device/ncs:live-status/node:preconfigured-nodes/node:preconfigured-node" {
    uses live_ncs_NODE-CFG {
      refine ltrace {
        tailf:ncs-device-type "netconf";
        tailf:display-when "not(../../../../ncs:module) or ../../../../ncs:module[ncs:name='Cisco-IOS-XR-infra-ltrace-cfg'] or (../../../../ncs:live-status-protocol[not(ncs:capability)]) or (../../../../ncs:live-status-protocol/ncs:capability/ncs:module[.='Cisco-IOS-XR-infra-ltrace-cfg'])";
      }
    }
    description
      "This augment extends preconfigured nodes
       configuration";
  }
  augment "/ncs:devices/ncs:device/ncs:config/node:preconfigured-nodes/node:preconfigured-node" {
    uses NODE-CFG {
      refine ltrace {
        tailf:ncs-device-type "netconf";
        tailf:display-when "not(../../../../ncs:module) or ../../../../ncs:module[ncs:name='Cisco-IOS-XR-infra-ltrace-cfg']";
      }
    }
    description
      "This augment extends preconfigured nodes
       configuration";
  }
}
