module Cisco-IOS-XR-group-cfg {
  // Generated by yanger -t ncs
  tailf:mount-id f5500-nc-1.0:f5500-nc-1.0;
  tailf:ncs-device-type "netconf";

  namespace "http://cisco.com/ns/yang/Cisco-IOS-XR-group-cfg";
  prefix Cisco-IOS-XR-group-cfg;

  import Cisco-IOS-XR-types {
    prefix xr;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 W Tasman Drive
     San Jose, CA 95134

     Tel: +1 1800 553-NETS

     E-mail: cs-yang@cisco.com";
  description
    "This module contains IOS-XR group YANG data
     for flexible cli groups

     Copyright (c) 2013-2016 by Cisco Systems, Inc.
     All rights reserved.";

  revision 2016-04-29 {
    description
      "Initial revision.";
  }

  augment "/ncs:devices/ncs:device/ncs:config" {
    container groups {
      tailf:ncs-device-type "netconf";
      tailf:display-when "not(../../ncs:module) or ../../ncs:module[ncs:name='Cisco-IOS-XR-group-cfg']";
      description
        "config groups";
      list group {
        key "group-name";
        description
          "Group config definition";
        leaf group-name {
          type xr:Cisco-ios-xr-string {
            length "0..32";
          }
          description
            "Group name";
        }
      }
    }
    container apply-groups {
      tailf:ncs-device-type "netconf";
      tailf:display-when "not(../../ncs:module) or ../../ncs:module[ncs:name='Cisco-IOS-XR-group-cfg']";
      description
        "apply groups";
      leaf apply-group {
        type xr:Cisco-ios-xr-string;
        description
          "apply-group name";
      }
    }
  }
  augment "/ncs:devices/ncs:device/ncs:live-status" {
    container groups {
      tailf:ncs-device-type "netconf";
      tailf:display-when "not(../../ncs:module) or ../../ncs:module[ncs:name='Cisco-IOS-XR-group-cfg'] or (../../ncs:live-status-protocol[not(ncs:capability)]) or (../../ncs:live-status-protocol/ncs:capability/ncs:module[.='Cisco-IOS-XR-group-cfg'])";
      description
        "config groups";
      list group {
        key "group-name";
        description
          "Group config definition";
        leaf group-name {
          type xr:Cisco-ios-xr-string {
            length "0..32";
          }
          description
            "Group name";
        }
      }
    }
    container apply-groups {
      tailf:ncs-device-type "netconf";
      tailf:display-when "not(../../ncs:module) or ../../ncs:module[ncs:name='Cisco-IOS-XR-group-cfg'] or (../../ncs:live-status-protocol[not(ncs:capability)]) or (../../ncs:live-status-protocol/ncs:capability/ncs:module[.='Cisco-IOS-XR-group-cfg'])";
      description
        "apply groups";
      leaf apply-group {
        type xr:Cisco-ios-xr-string;
        description
          "apply-group name";
      }
    }
  }
  augment "/ncs:devices/ncs:template/ncs:ned-id/ncs:config" {
    container groups {
      description
        "config groups";
      list group {
        // NCS patched for predictable order
        ordered-by user;
        key "group-name";
        description
          "Group config definition";
        leaf group-name {
          type string;
          description
            "Group name";
        }
      }
    }
    container apply-groups {
      description
        "apply groups";
      leaf apply-group {
        type string;
        description
          "apply-group name";
      }
    }
  }
}
