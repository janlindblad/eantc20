module cisco-xr-ietf-netconf-monitoring-deviations {
  // Generated by yanger -t ncs
  tailf:mount-id f5500-nc-1.0:f5500-nc-1.0;
  tailf:ncs-device-type "netconf";

  namespace "http://cisco.com/ns/yang/cisco-xr-ietf-netconf-monitoring-deviations";
  prefix cisco-xr-ietf-netconf-monitoring-deviations;

  import ietf-netconf-monitoring {
    prefix ncm;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a set of deviations of IETF netconf monitoring data
     model set for Cisco IOS-XR.

     Copyright (c) 2016, 2018 by Cisco Systems, Inc.
     All rights reserved.";

  revision 2018-04-09 {
    description
      "We now support sessions and statistics and these have been removed
       from the deviations";
  }
  revision 2016-02-16 {
    description
      "Initial revision applicable to IOS-XR 6.0.1 and older releases";
  }

  deviation "/ncs:devices/ncs:device/ncs:live-status/ncm:netconf-state/ncm:capabilities" {
    deviate not-supported;
  }
  deviation "/ncs:devices/ncs:device/ncs:live-status/ncm:netconf-state/ncm:datastores" {
    deviate not-supported;
  }
}
