module Cisco-IOS-XR-fretta-grid-svr-oper {
  // Generated by yanger -t ncs
  tailf:mount-id f5500-nc-1.0:f5500-nc-1.0;
  tailf:ncs-device-type "netconf";

  namespace "http://cisco.com/ns/yang/Cisco-IOS-XR-fretta-grid-svr-oper";
  prefix Cisco-IOS-XR-fretta-grid-svr-oper;

  import Cisco-IOS-XR-types {
    prefix xr;
  }
  include Cisco-IOS-XR-fretta-grid-svr-oper-sub1 {
    revision-date 2015-11-09;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR fretta-grid-svr package operational data.

     This module contains definitions
     for the following management objects:
       grid: GRID operational data

     Copyright (c) 2013-2018 by Cisco Systems, Inc.
     All rights reserved.";

  revision 2015-11-09 {
    description
      "IOS XR 6.0 revision.";
  }

  augment "/ncs:devices/ncs:device/ncs:config" {
    // NCS drop config false container grid
  }
  augment "/ncs:devices/ncs:device/ncs:live-status" {
    container grid {
      tailf:ncs-device-type "netconf";
      tailf:display-when "not(../../ncs:module) or ../../ncs:module[ncs:name='Cisco-IOS-XR-fretta-grid-svr-oper'] or (../../ncs:live-status-protocol[not(ncs:capability)]) or (../../ncs:live-status-protocol/ncs:capability/ncs:module[.='Cisco-IOS-XR-fretta-grid-svr-oper'])";
      description
        "GRID operational data";
      container nodes {
        description
          "Table of nodes";
        list node {
          key "node-name";
          description
            "Operational data for a particular node";
          container client-xr {
            description
              "GRID Client Table";
            list client {
              key "client-name";
              description
                "GRID Client Database";
              leaf client-name {
                type xr:Cisco-ios-xr-string;
                description
                  "Client name";
              }
              uses live_ncs_GRID-SVR-SHOW-CLIENT;
            }
          }
          container clients {
            description
              "GRID Client Consistency Check";
            list client {
              key "client-name";
              description
                "GRID Client Consistency Check";
              leaf client-name {
                type xr:Cisco-ios-xr-string;
                description
                  "Client name";
              }
              uses live_ncs_GRID-SVR-SHOW-CLIENT;
            }
          }
          leaf node-name {
            type xr:Node-id;
            description
              "Node ID";
          }
        }
      }
    }
  }
  augment "/ncs:devices/ncs:template/ncs:ned-id/ncs:config" {
    // NCS drop config false container grid
  }
}
