module Cisco-IOS-XR-aaa-protocol-radius-cfg {
  // Generated by yanger -t ncs
  tailf:mount-id f5500-nc-1.0:f5500-nc-1.0;
  tailf:ncs-device-type "netconf";

  namespace "http://cisco.com/ns/yang/Cisco-IOS-XR-aaa-protocol-radius-cfg";
  prefix Cisco-IOS-XR-aaa-protocol-radius-cfg;

  import ietf-inet-types {
    prefix inet;
  }
  import Cisco-IOS-XR-types {
    prefix xr;
  }
  import Cisco-IOS-XR-aaa-locald-cfg {
    prefix a1;
  }
  import Cisco-IOS-XR-aaa-lib-cfg {
    prefix a2;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR aaa-protocol-radius package configuration.

     This YANG module augments the
       Cisco-IOS-XR-aaa-locald-cfg,
       Cisco-IOS-XR-aaa-lib-cfg
     modules with configuration data.

     Copyright (c) 2013-2018 by Cisco Systems, Inc.
     All rights reserved.";

  revision 2017-09-07 {
    description
      "Fixed type translation error.";
  }
  revision 2017-05-01 {
    description
      "Fixing backward compatibility error in module.";
  }
  revision 2015-11-09 {
    description
      "IOS XR 6.0 revision.";
  }

  typedef Aaa-radius-retransmit-with-disable {
    type uint32 {
      range "0..100";
    }
    description
      "Aaa radius retransmit with disable";
  }

  typedef Aaa-config {
    type enumeration {
      enum "false" {
        value 0;
        description
          "False";
      }
      enum "true" {
        value 1;
        description
          "True";
      }
    }
    description
      "Aaa config";
  }

  typedef Aaa-throttle-access {
    type uint32 {
      range "0..65535";
    }
    description
      "Aaa throttle access";
  }

  typedef Aaa-radius-retransmit {
    type uint32 {
      range "1..100";
    }
    description
      "Aaa radius retransmit";
  }

  typedef Aaa-radius-dead-detect-time {
    type uint32 {
      range "1..120";
    }
    description
      "Aaa radius dead detect time";
  }

  typedef Aaa-direction {
    type enumeration {
      enum "inbound" {
        value 0;
        description
          "Inbound";
      }
      enum "outbound" {
        value 1;
        description
          "Outbound";
      }
    }
    description
      "Aaa direction";
  }

  typedef Aaa-radius-idle-time {
    type uint32 {
      range "1..60";
    }
    description
      "Aaa radius idle time";
  }

  typedef Aaa-throttle-accounting {
    type uint32 {
      range "0..65535";
    }
    description
      "Aaa throttle accounting";
  }

  typedef Aaa-radius-dead-time {
    type uint32 {
      range "1..1440";
    }
    description
      "Aaa radius dead time";
  }

  typedef Aaa-radius-dead-detect-tries {
    type uint32 {
      range "1..100";
    }
    description
      "Aaa radius dead detect tries";
  }

  typedef Aaa-throttle-access-timeout {
    type uint32 {
      range "1..10";
    }
    description
      "Aaa throttle access timeout";
  }

  typedef Aaa-select-key {
    type enumeration {
      enum "server-key" {
        value 1;
        description
          "Server key";
      }
      enum "session-key" {
        value 2;
        description
          "Session  key";
      }
    }
    description
      "Aaa select key";
  }

  typedef Aaa-authentication {
    type enumeration {
      enum "all" {
        value 101;
        description
          "All";
      }
      enum "any" {
        value 102;
        description
          "Any";
      }
      enum "session-key" {
        value 103;
        description
          "Session key";
      }
    }
    description
      "Aaa authentication";
  }

  typedef Aaa-action {
    type enumeration {
      enum "accept" {
        value 1;
        description
          "Accept";
      }
      enum "reject" {
        value 2;
        description
          "Reject";
      }
    }
    description
      "Aaa action";
  }

  typedef Aaa-dscp-value {
    type union {
      type enumeration {
        enum "af11" {
          value 10;
          description
            "Match packets with AF11 DSCP";
        }
        enum "af12" {
          value 12;
          description
            "Match packets with AF12 DSCP";
        }
        enum "af13" {
          value 14;
          description
            "Match packets with AF13 DSCP";
        }
        enum "af21" {
          value 18;
          description
            "Match packets with AF21 DSCP";
        }
        enum "af22" {
          value 20;
          description
            "Match packets with AF22 DSCP";
        }
        enum "af23" {
          value 22;
          description
            "Match packets with AF23 DSCP";
        }
        enum "af31" {
          value 26;
          description
            "Match packets with AF31 DSCP";
        }
        enum "af32" {
          value 28;
          description
            "Match packets with AF32 DSCP";
        }
        enum "af33" {
          value 30;
          description
            "Match packets with AF33 DSCP";
        }
        enum "af41" {
          value 34;
          description
            "Match packets with AF41 DSCP";
        }
        enum "af42" {
          value 36;
          description
            "Match packets with AF42 DSCP";
        }
        enum "af43" {
          value 38;
          description
            "Match packets with AF43 DSCP";
        }
        enum "cs1" {
          value 8;
          description
            "Match packets with CS1 DSCP";
        }
        enum "cs2" {
          value 16;
          description
            "Match packets with CS2 DSCP";
        }
        enum "cs3" {
          value 24;
          description
            "Match packets with CS3 DSCP";
        }
        enum "cs4" {
          value 32;
          description
            "Match packets with CS4 DSCP";
        }
        enum "cs5" {
          value 40;
          description
            "Match packets with CS5 DSCP";
        }
        enum "cs6" {
          value 48;
          description
            "Match packets with CS6 DSCP";
        }
        enum "cs7" {
          value 56;
          description
            "Match packets with CS7 DSCP";
        }
        enum "default" {
          value 0;
          description
            "Match packets with 0000 DSCP";
        }
        enum "ef" {
          value 46;
          description
            "Match packets with EF DSCP";
        }
      }
      type uint32 {
        range "0..63";
      }
    }
    description
      "Aaa dscp value";
  }

  typedef Aaa-radius-timeout {
    type uint32 {
      range "1..1000";
    }
    description
      "Aaa radius timeout";
  }

  grouping ncs_template_IGNORE-ACCOUNTING-PORT {
    description
      "Common node of radius, host";
    leaf ignore-accounting-port {
      type string;
      description
        "Time to wait for a RADIUS server to reply";
    }
  }

  grouping ncs_template_IDLE-TIME {
    description
      "Common node of radius, host";
    leaf idle-time {
      type string;
      // NCS drop default statement
      description
        "Idle time for RADIUS server";
    }
  }

  grouping ncs_template_USERNAME {
    description
      "Common node of radius, host";
    leaf username {
      type string;
      description
        "Username to be tested for automated testing";
    }
  }

  grouping ncs_template_REPLY {
    description
      "Common node of authorization, accounting";
    container reply {
      description
        "Specify a filter in server group";
      leaf action {
        type string;
        description
          "Specify the attribute list type accept or
           reject";
      }
      leaf attribute-list-name {
        type string;
        description
          "Name of RADIUS attribute list";
      }
    }
  }

  grouping ncs_template_DSCP {
    description
      "Common node of ipv4, ipv6";
    leaf dscp {
      type string;
      description
        "Specify the DSCP value";
    }
  }

  grouping ncs_template_SERVER-KEY {
    description
      "Common node of client, dynamic-authorization";
    leaf server-key {
      type string;
      description
        "RADIUS CoA client encryption key";
    }
  }

  grouping ncs_template_IGNORE-AUTH-PORT {
    description
      "Common node of radius, host";
    leaf ignore-auth-port {
      type string;
      description
        "Time to wait for a RADIUS server to reply";
    }
  }

  grouping ncs_template_REQUEST {
    description
      "Common node of authorization, accounting";
    container request {
      description
        "Specify a filter in server group";
      leaf action {
        type string;
        description
          "Specify the attribute list type accept or
           reject";
      }
      leaf attribute-list-name {
        type string;
        description
          "Name of RADIUS attribute list";
      }
    }
  }

  grouping ncs_rpc_notif_IGNORE-ACCOUNTING-PORT {
    description
      "Common node of radius, host";
    leaf ignore-accounting-port {
      type boolean;
      description
        "Time to wait for a RADIUS server to reply";
    }
  }

  grouping ncs_rpc_notif_IDLE-TIME {
    description
      "Common node of radius, host";
    leaf idle-time {
      type Aaa-radius-timeout;
      default "5";
      description
        "Idle time for RADIUS server";
    }
  }

  grouping ncs_rpc_notif_USERNAME {
    description
      "Common node of radius, host";
    leaf username {
      type string;
      description
        "Username to be tested for automated testing";
    }
  }

  grouping ncs_rpc_notif_REPLY {
    description
      "Common node of authorization, accounting";
    container reply {
      description
        "Specify a filter in server group";
      leaf action {
        type Aaa-action;
        description
          "Specify the attribute list type accept or
           reject";
      }
      leaf attribute-list-name {
        type string;
        description
          "Name of RADIUS attribute list";
      }
    }
  }

  grouping ncs_rpc_notif_DSCP {
    description
      "Common node of ipv4, ipv6";
    leaf dscp {
      type Aaa-dscp-value;
      description
        "Specify the DSCP value";
    }
  }

  grouping ncs_rpc_notif_SERVER-KEY {
    description
      "Common node of client, dynamic-authorization";
    leaf server-key {
      type xr:Proprietary-password;
      description
        "RADIUS CoA client encryption key";
    }
  }

  grouping ncs_rpc_notif_IGNORE-AUTH-PORT {
    description
      "Common node of radius, host";
    leaf ignore-auth-port {
      type boolean;
      description
        "Time to wait for a RADIUS server to reply";
    }
  }

  grouping ncs_rpc_notif_REQUEST {
    description
      "Common node of authorization, accounting";
    container request {
      description
        "Specify a filter in server group";
      leaf action {
        type Aaa-action;
        description
          "Specify the attribute list type accept or
           reject";
      }
      leaf attribute-list-name {
        type string;
        description
          "Name of RADIUS attribute list";
      }
    }
  }

  grouping live_ncs_IGNORE-ACCOUNTING-PORT {
    description
      "Common node of radius, host";
    leaf ignore-accounting-port {
      type boolean;
      description
        "Time to wait for a RADIUS server to reply";
    }
  }

  grouping live_ncs_IDLE-TIME {
    description
      "Common node of radius, host";
    leaf idle-time {
      type Aaa-radius-timeout;
      // NCS drop default statement
      description
        "Idle time for RADIUS server";
    }
  }

  grouping live_ncs_USERNAME {
    description
      "Common node of radius, host";
    leaf username {
      type string;
      description
        "Username to be tested for automated testing";
    }
  }

  grouping live_ncs_REPLY {
    description
      "Common node of authorization, accounting";
    container reply {
      description
        "Specify a filter in server group";
      leaf action {
        type Aaa-action;
        description
          "Specify the attribute list type accept or
           reject";
      }
      leaf attribute-list-name {
        type string;
        description
          "Name of RADIUS attribute list";
      }
    }
  }

  grouping live_ncs_DSCP {
    description
      "Common node of ipv4, ipv6";
    leaf dscp {
      type Aaa-dscp-value;
      description
        "Specify the DSCP value";
    }
  }

  grouping live_ncs_SERVER-KEY {
    description
      "Common node of client, dynamic-authorization";
    leaf server-key {
      type xr:Proprietary-password;
      description
        "RADIUS CoA client encryption key";
    }
  }

  grouping live_ncs_IGNORE-AUTH-PORT {
    description
      "Common node of radius, host";
    leaf ignore-auth-port {
      type boolean;
      description
        "Time to wait for a RADIUS server to reply";
    }
  }

  grouping live_ncs_REQUEST {
    description
      "Common node of authorization, accounting";
    container request {
      description
        "Specify a filter in server group";
      leaf action {
        type Aaa-action;
        description
          "Specify the attribute list type accept or
           reject";
      }
      leaf attribute-list-name {
        type string;
        description
          "Name of RADIUS attribute list";
      }
    }
  }

  grouping IGNORE-ACCOUNTING-PORT {
    description
      "Common node of radius, host";
    leaf ignore-accounting-port {
      type boolean;
      description
        "Time to wait for a RADIUS server to reply";
    }
  }

  grouping IDLE-TIME {
    description
      "Common node of radius, host";
    leaf idle-time {
      type Aaa-radius-timeout;
      default "5";
      description
        "Idle time for RADIUS server";
    }
  }

  grouping USERNAME {
    description
      "Common node of radius, host";
    leaf username {
      type string;
      description
        "Username to be tested for automated testing";
    }
  }

  grouping REPLY {
    description
      "Common node of authorization, accounting";
    container reply {
      description
        "Specify a filter in server group";
      leaf action {
        type Aaa-action;
        description
          "Specify the attribute list type accept or
           reject";
      }
      leaf attribute-list-name {
        type string;
        description
          "Name of RADIUS attribute list";
      }
    }
  }

  grouping DSCP {
    description
      "Common node of ipv4, ipv6";
    leaf dscp {
      type Aaa-dscp-value;
      description
        "Specify the DSCP value";
    }
  }

  grouping SERVER-KEY {
    description
      "Common node of client, dynamic-authorization";
    leaf server-key {
      type xr:Proprietary-password;
      description
        "RADIUS CoA client encryption key";
    }
  }

  grouping IGNORE-AUTH-PORT {
    description
      "Common node of radius, host";
    leaf ignore-auth-port {
      type boolean;
      description
        "Time to wait for a RADIUS server to reply";
    }
  }

  grouping REQUEST {
    description
      "Common node of authorization, accounting";
    container request {
      description
        "Specify a filter in server group";
      leaf action {
        type Aaa-action;
        description
          "Specify the attribute list type accept or
           reject";
      }
      leaf attribute-list-name {
        type string;
        description
          "Name of RADIUS attribute list";
      }
    }
  }

  augment "/ncs:devices/ncs:template/ncs:ned-id/ncs:config/a2:aaa" {
    container radius {
      description
        "Remote Access Dial-In User Service";
      container hosts {
        description
          "List of RADIUS servers";
        list host {
          // NCS patched for predictable order
          ordered-by user;
          key "ordering-index ip-address auth-port-number acct-port-number";
          description
            "Instance of a RADIUS server";
          leaf host-retransmit {
            type string;
            // NCS drop default statement
            description
              "Number of times to retransmit a request to
               the RADIUS server";
          }
          leaf host-timeout {
            type string;
            // NCS drop default statement
            description
              "Time to wait for a RADIUS server to reply";
          }
          leaf host-key {
            type string;
            description
              "RADIUS encryption key";
          }
          leaf ordering-index {
            type string;
            description
              "This is used to sort the servers in the order
               of precedence";
          }
          leaf ip-address {
            type string;
            description
              "IP address of RADIUS server";
          }
          leaf auth-port-number {
            type string;
            description
              "Authentication Port number (standard port
               1645)";
          }
          leaf acct-port-number {
            type string;
            description
              "Accounting Port number (standard port 1646)";
          }
          uses ncs_template_IGNORE-ACCOUNTING-PORT;
          uses ncs_template_IDLE-TIME;
          uses ncs_template_USERNAME;
          uses ncs_template_IGNORE-AUTH-PORT;
        }
      }
      container dead-criteria {
        description
          "RADIUS server dead criteria";
        leaf tries {
          type string;
          description
            "The number of consecutive timeouts the router
             must experience in order to mark the server as
             dead. All transmissions, including the initial
             transmit and all retransmits, will be counted";
        }
        leaf time {
          type string;
          description
            "The minimum amount of time which must elapse
             since the router last received a valid RADIUS
             packet from the server prior to marking it
             dead";
        }
      }
      container disallow {
        description
          "disallow null-username";
        leaf null-username {
          type string;
          description
            "Disallow null-username";
        }
      }
      container ipv6 {
        description
          "IPv6 configuration";
        uses ncs_template_DSCP;
      }
      container dynamic-authorization {
        description
          "RADIUS dynamic authorization";
        container clients {

          grouping CLIENT-CONTENT {
            description
              "CLIENT CONTENT";
            uses ncs_template_SERVER-KEY;
          }
          list client {
            // NCS patched for predictable order
            ordered-by user;
            key "ip-address";
            description
              "Client data";
            leaf ip-address {
              type string;
              description
                "IP address of COA client";
            }
            uses CLIENT-CONTENT;
          }
          list client-vrf-name {
            // NCS patched for predictable order
            ordered-by user;
            key "vrf-name ip-address";
            description
              "Client data";
            leaf vrf-name {
              type string;
              description
                "VRF name";
            }
            leaf ip-address {
              type string;
              description
                "IP address of COA client";
            }
            uses CLIENT-CONTENT;
          }
          description
            "Client data";
        }
        leaf ignore {
          type string;
          description
            "Ignore option for server key or session key";
        }
        leaf port {
          type string;
          description
            "Specify the COA server port to listen on";
        }
        leaf authentication-type {
          type string;
          description
            "RADIUS  dynamic  authorization  type";
        }
        uses ncs_template_SERVER-KEY;
      }
      container load-balance-options {
        description
          "Radius load-balancing options";
        container load-balance-method {
          description
            "Method by which the next host will be picked";
          container batch-size {
            description
              "Batch size for selection of the server";
            leaf batch-size {
              type string;
              // NCS drop default statement
              description
                "Batch size for selection of the server";
            }
            leaf ignore-preferred-server {
              type string;
              // NCS drop default statement
              description
                "Disable preferred server for this Server
                 Group";
            }
          }
        }
      }
      container vrfs {
        description
          "List of VRFs";
        list vrf {
          // NCS patched for predictable order
          ordered-by user;
          key "vrf-name";
          description
            "A VRF";
          leaf source-interface {
            type string;
            description
              "Specify interface for source address in
               RADIUS packets";
          }
          leaf vrf-name {
            type string;
            description
              "VRF name. Specify 'default' for defalut VRF";
          }
        }
      }
      container throttle {
        description
          "Radius throttling options";
        leaf access {
          type string;
          // NCS drop default statement
          description
            "To flow control the number of access requests
             sent to a radius server";
        }
        leaf accounting {
          type string;
          // NCS drop default statement
          description
            "To flow control the number of accounting
             requests sent to a radius server";
        }
        leaf access-timeout {
          type string;
          // NCS drop default statement
          description
            "Specify the number of timeouts exceeding which
             a throttled access request is dropped";
        }
      }
      container vsa {
        description
          "Unknown VSA (Vendor Specific Attribute) ignore
           configuration for RADIUS server";
        container attribute {
          description
            "Vendor Specific Attribute";
          container ignore {
            description
              "Ignore the VSA";
            leaf unknown {
              type empty;
              description
                "Ignore the VSA and no prefix will reject the
                 unknown VSA";
            }
          }
        }
      }
      container ipv4 {
        description
          "IPv4 configuration";
        uses ncs_template_DSCP;
      }
      container radius-attribute {
        description
          "attribute";
        container filter-id-11 {
          description
            "Filter-Id attribute configuration";
          container defaults {
            description
              "Set the attribute default direction";
            leaf direction {
              type string;
              description
                "Filtering is applied to
                 ingress(inbound)/egress(outbound) packets
                 only";
            }
          }
        }
        container acct-multi-session-id {
          description
            "Acct-Session-Id attribute(44)";
          container include-parent-session-id {
            description
              "Prepend Acct-Session-Id attribute with
               Nas-Port-Id";
            leaf config {
              type string;
              description
                "false/true";
            }
          }
        }
        container acct-session-id {
          description
            "Acct-Session-Id attribute(44)";
          container prepend-nas-port-id {
            description
              "Prepend Acct-Session-Id attribute with
               Nas-Port-Id";
            leaf config {
              type string;
              description
                "false/true";
            }
          }
        }
      }
      container attributes {
        description
          "Table of attribute list";
        list attribute {
          // NCS patched for predictable order
          ordered-by user;
          key "attribute-list-name";
          description
            "Attribute list name";
          container vendor-ids {
            description
              "Vendor Specific Attribute";
            list vendor-id {
              // NCS patched for predictable order
              ordered-by user;
              key "vendor-id";
              description
                "Vendor ID of vsa";
              leaf vendor-id {
                type string;
                description
                  "Vendor Id of vsa";
              }
              list vendor-type {
                // NCS patched for predictable order
                ordered-by user;
                key "vendor-type";
                description
                  "Vendor Type of vsa";
                leaf vendor-type {
                  type string;
                  description
                    "Vendor Type of vsa";
                }
                list attribute-name {
                  // NCS patched for predictable order
                  ordered-by user;
                  key "attribute-name";
                  description
                    "Attribute Name of vsa";
                  leaf attribute-name {
                    type string;
                    description
                      "Attribute Name of vsa";
                  }
                  list attribute-name-absent {
                    // NCS patched for predictable order
                    ordered-by user;
                    key "attribute-name-absent";
                    description
                      "AttributeName of vsa is absent";
                    leaf attribute-name-absent {
                      type string;
                      description
                        "AttributeName of vsa is absent";
                    }
                    list attribute-name-present {
                      // NCS patched for predictable order
                      ordered-by user;
                      key "attribute-name-present";
                      description
                        "AttributeName of vsa is present";
                      leaf attribute-name-present {
                        type string;
                        description
                          "AttributeName of vsa is present";
                      }
                    }
                  }
                }
              }
            }
          }
          leaf attribute {
            type string;
            description
              "Specify RADIUS attribute";
          }
          leaf attribute-list-name {
            type string;
            description
              "Attribute list name";
          }
        }
      }
      container source-port {
        description
          "Source port";
        leaf extended {
          type empty;
          description
            "Enable source-port extend ";
        }
      }
      leaf retransmit {
        type string;
        // NCS drop default statement
        description
          "Number of times to retransmit a request to the
           RADIUS server(0-Disable)";
      }
      leaf dead-time {
        type string;
        units "minute";
        description
          "This indicates the length of time (in minutes)
           for which a RADIUS server remains marked as
           dead";
      }
      leaf key {
        type string;
        description
          "RADIUS encryption key";
      }
      leaf timeout {
        type string;
        // NCS drop default statement
        description
          "Time to wait for a RADIUS server to reply";
      }
      uses ncs_template_IGNORE-ACCOUNTING-PORT;
      uses ncs_template_IDLE-TIME;
      uses ncs_template_USERNAME;
      uses ncs_template_IGNORE-AUTH-PORT;
    }
    description
      "This augment extends the configuration data of
       'Cisco-IOS-XR-aaa-lib-cfg'";
  }
  augment "/ncs:devices/ncs:device/ncs:live-status/a2:aaa" {
    container radius {
      tailf:ncs-device-type "netconf";
      tailf:display-when "not(../../../ncs:module) or ../../../ncs:module[ncs:name='Cisco-IOS-XR-aaa-protocol-radius-cfg'] or (../../../ncs:live-status-protocol[not(ncs:capability)]) or (../../../ncs:live-status-protocol/ncs:capability/ncs:module[.='Cisco-IOS-XR-aaa-protocol-radius-cfg'])";
      description
        "Remote Access Dial-In User Service";
      container hosts {
        description
          "List of RADIUS servers";
        list host {
          key "ordering-index ip-address auth-port-number acct-port-number";
          description
            "Instance of a RADIUS server";
          leaf host-retransmit {
            type Aaa-radius-retransmit;
            // NCS drop default statement
            description
              "Number of times to retransmit a request to
               the RADIUS server";
          }
          leaf host-timeout {
            type Aaa-radius-timeout;
            // NCS drop default statement
            description
              "Time to wait for a RADIUS server to reply";
          }
          leaf host-key {
            type xr:Proprietary-password;
            description
              "RADIUS encryption key";
          }
          leaf ordering-index {
            type uint32;
            description
              "This is used to sort the servers in the order
               of precedence";
          }
          leaf ip-address {
            type inet:ip-address-no-zone;
            description
              "IP address of RADIUS server";
          }
          leaf auth-port-number {
            type inet:port-number;
            description
              "Authentication Port number (standard port
               1645)";
          }
          leaf acct-port-number {
            type inet:port-number;
            description
              "Accounting Port number (standard port 1646)";
          }
          uses live_ncs_IGNORE-ACCOUNTING-PORT;
          uses live_ncs_IDLE-TIME;
          uses live_ncs_USERNAME;
          uses live_ncs_IGNORE-AUTH-PORT;
        }
      }
      container dead-criteria {
        description
          "RADIUS server dead criteria";
        leaf tries {
          type Aaa-radius-dead-detect-tries;
          description
            "The number of consecutive timeouts the router
             must experience in order to mark the server as
             dead. All transmissions, including the initial
             transmit and all retransmits, will be counted";
        }
        leaf time {
          type Aaa-radius-dead-detect-time;
          description
            "The minimum amount of time which must elapse
             since the router last received a valid RADIUS
             packet from the server prior to marking it
             dead";
        }
      }
      container disallow {
        description
          "disallow null-username";
        leaf null-username {
          type uint32;
          description
            "Disallow null-username";
        }
      }
      container ipv6 {
        description
          "IPv6 configuration";
        uses live_ncs_DSCP;
      }
      container dynamic-authorization {
        description
          "RADIUS dynamic authorization";
        container clients {

          grouping CLIENT-CONTENT {
            description
              "CLIENT CONTENT";
            uses live_ncs_SERVER-KEY;
          }
          list client {
            key "ip-address";
            description
              "Client data";
            leaf ip-address {
              type inet:ip-address-no-zone;
              description
                "IP address of COA client";
            }
            uses CLIENT-CONTENT;
          }
          list client-vrf-name {
            key "vrf-name ip-address";
            description
              "Client data";
            leaf vrf-name {
              type xr:Cisco-ios-xr-string;
              description
                "VRF name";
            }
            leaf ip-address {
              type inet:ip-address-no-zone;
              description
                "IP address of COA client";
            }
            uses CLIENT-CONTENT;
          }
          description
            "Client data";
        }
        leaf ignore {
          type Aaa-select-key;
          description
            "Ignore option for server key or session key";
        }
        leaf port {
          type uint32 {
            range "1000..5000";
          }
          description
            "Specify the COA server port to listen on";
        }
        leaf authentication-type {
          type Aaa-authentication;
          description
            "RADIUS  dynamic  authorization  type";
        }
        uses live_ncs_SERVER-KEY;
      }
      container load-balance-options {
        description
          "Radius load-balancing options";
        container load-balance-method {
          description
            "Method by which the next host will be picked";
          container batch-size {
            description
              "Batch size for selection of the server";
            leaf batch-size {
              type uint32 {
                range "1..1500";
              }
              // NCS drop default statement
              description
                "Batch size for selection of the server";
            }
            leaf ignore-preferred-server {
              type boolean;
              // NCS drop default statement
              description
                "Disable preferred server for this Server
                 Group";
            }
          }
        }
      }
      container vrfs {
        description
          "List of VRFs";
        list vrf {
          key "vrf-name";
          description
            "A VRF";
          leaf source-interface {
            type xr:Interface-name;
            description
              "Specify interface for source address in
               RADIUS packets";
          }
          leaf vrf-name {
            type xr:Cisco-ios-xr-string;
            description
              "VRF name. Specify 'default' for defalut VRF";
          }
        }
      }
      container throttle {
        description
          "Radius throttling options";
        leaf access {
          type Aaa-throttle-access;
          // NCS drop default statement
          description
            "To flow control the number of access requests
             sent to a radius server";
        }
        leaf accounting {
          type Aaa-throttle-accounting;
          // NCS drop default statement
          description
            "To flow control the number of accounting
             requests sent to a radius server";
        }
        leaf access-timeout {
          type Aaa-throttle-access-timeout;
          // NCS drop default statement
          description
            "Specify the number of timeouts exceeding which
             a throttled access request is dropped";
        }
      }
      container vsa {
        description
          "Unknown VSA (Vendor Specific Attribute) ignore
           configuration for RADIUS server";
        container attribute {
          description
            "Vendor Specific Attribute";
          container ignore {
            description
              "Ignore the VSA";
            leaf unknown {
              type empty;
              description
                "Ignore the VSA and no prefix will reject the
                 unknown VSA";
            }
          }
        }
      }
      container ipv4 {
        description
          "IPv4 configuration";
        uses live_ncs_DSCP;
      }
      container radius-attribute {
        description
          "attribute";
        container filter-id-11 {
          description
            "Filter-Id attribute configuration";
          container defaults {
            description
              "Set the attribute default direction";
            leaf direction {
              type Aaa-direction;
              description
                "Filtering is applied to
                 ingress(inbound)/egress(outbound) packets
                 only";
            }
          }
        }
        container acct-multi-session-id {
          description
            "Acct-Session-Id attribute(44)";
          container include-parent-session-id {
            description
              "Prepend Acct-Session-Id attribute with
               Nas-Port-Id";
            leaf config {
              type Aaa-config;
              description
                "false/true";
            }
          }
        }
        container acct-session-id {
          description
            "Acct-Session-Id attribute(44)";
          container prepend-nas-port-id {
            description
              "Prepend Acct-Session-Id attribute with
               Nas-Port-Id";
            leaf config {
              type Aaa-config;
              description
                "false/true";
            }
          }
        }
      }
      container attributes {
        description
          "Table of attribute list";
        list attribute {
          key "attribute-list-name";
          description
            "Attribute list name";
          container vendor-ids {
            description
              "Vendor Specific Attribute";
            list vendor-id {
              key "vendor-id";
              description
                "Vendor ID of vsa";
              leaf vendor-id {
                type uint32;
                description
                  "Vendor Id of vsa";
              }
              list vendor-type {
                key "vendor-type";
                description
                  "Vendor Type of vsa";
                leaf vendor-type {
                  type uint32;
                  description
                    "Vendor Type of vsa";
                }
                list attribute-name {
                  key "attribute-name";
                  description
                    "Attribute Name of vsa";
                  leaf attribute-name {
                    type xr:Cisco-ios-xr-string;
                    description
                      "Attribute Name of vsa";
                  }
                  list attribute-name-absent {
                    key "attribute-name-absent";
                    description
                      "AttributeName of vsa is absent";
                    leaf attribute-name-absent {
                      type uint32;
                      description
                        "AttributeName of vsa is absent";
                    }
                    list attribute-name-present {
                      key "attribute-name-present";
                      description
                        "AttributeName of vsa is present";
                      leaf attribute-name-present {
                        type uint32;
                        description
                          "AttributeName of vsa is present";
                      }
                    }
                  }
                }
              }
            }
          }
          leaf attribute {
            type string;
            description
              "Specify RADIUS attribute";
          }
          leaf attribute-list-name {
            type xr:Cisco-ios-xr-string;
            description
              "Attribute list name";
          }
        }
      }
      container source-port {
        description
          "Source port";
        leaf extended {
          type empty;
          description
            "Enable source-port extend ";
        }
      }
      leaf retransmit {
        type Aaa-radius-retransmit-with-disable;
        // NCS drop default statement
        description
          "Number of times to retransmit a request to the
           RADIUS server(0-Disable)";
      }
      leaf dead-time {
        type Aaa-radius-dead-time;
        units "minute";
        description
          "This indicates the length of time (in minutes)
           for which a RADIUS server remains marked as
           dead";
      }
      leaf key {
        type xr:Proprietary-password;
        description
          "RADIUS encryption key";
      }
      leaf timeout {
        type Aaa-radius-timeout;
        // NCS drop default statement
        description
          "Time to wait for a RADIUS server to reply";
      }
      uses live_ncs_IGNORE-ACCOUNTING-PORT;
      uses live_ncs_IDLE-TIME;
      uses live_ncs_USERNAME;
      uses live_ncs_IGNORE-AUTH-PORT;
    }
    description
      "This augment extends the configuration data of
       'Cisco-IOS-XR-aaa-lib-cfg'";
  }
  augment "/ncs:devices/ncs:device/ncs:config/a2:aaa" {
    container radius {
      tailf:ncs-device-type "netconf";
      tailf:display-when "not(../../../ncs:module) or ../../../ncs:module[ncs:name='Cisco-IOS-XR-aaa-protocol-radius-cfg']";
      description
        "Remote Access Dial-In User Service";
      container hosts {
        description
          "List of RADIUS servers";
        list host {
          key "ordering-index ip-address auth-port-number acct-port-number";
          description
            "Instance of a RADIUS server";
          leaf host-retransmit {
            type Aaa-radius-retransmit;
            default "3";
            description
              "Number of times to retransmit a request to
               the RADIUS server";
          }
          leaf host-timeout {
            type Aaa-radius-timeout;
            default "5";
            description
              "Time to wait for a RADIUS server to reply";
          }
          leaf host-key {
            type xr:Proprietary-password;
            description
              "RADIUS encryption key";
          }
          leaf ordering-index {
            type uint32;
            description
              "This is used to sort the servers in the order
               of precedence";
          }
          leaf ip-address {
            type inet:ip-address-no-zone;
            description
              "IP address of RADIUS server";
          }
          leaf auth-port-number {
            type inet:port-number;
            description
              "Authentication Port number (standard port
               1645)";
          }
          leaf acct-port-number {
            type inet:port-number;
            description
              "Accounting Port number (standard port 1646)";
          }
          uses IGNORE-ACCOUNTING-PORT;
          uses IDLE-TIME;
          uses USERNAME;
          uses IGNORE-AUTH-PORT;
        }
      }
      container dead-criteria {
        description
          "RADIUS server dead criteria";
        leaf tries {
          type Aaa-radius-dead-detect-tries;
          description
            "The number of consecutive timeouts the router
             must experience in order to mark the server as
             dead. All transmissions, including the initial
             transmit and all retransmits, will be counted";
        }
        leaf time {
          type Aaa-radius-dead-detect-time;
          description
            "The minimum amount of time which must elapse
             since the router last received a valid RADIUS
             packet from the server prior to marking it
             dead";
        }
      }
      container disallow {
        description
          "disallow null-username";
        leaf null-username {
          type uint32;
          description
            "Disallow null-username";
        }
      }
      container ipv6 {
        description
          "IPv6 configuration";
        uses DSCP;
      }
      container dynamic-authorization {
        description
          "RADIUS dynamic authorization";
        container clients {

          grouping CLIENT-CONTENT {
            description
              "CLIENT CONTENT";
            uses SERVER-KEY;
          }
          list client {
            key "ip-address";
            description
              "Client data";
            leaf ip-address {
              type inet:ip-address-no-zone;
              description
                "IP address of COA client";
            }
            uses CLIENT-CONTENT;
          }
          list client-vrf-name {
            key "vrf-name ip-address";
            description
              "Client data";
            leaf vrf-name {
              type xr:Cisco-ios-xr-string;
              description
                "VRF name";
            }
            leaf ip-address {
              type inet:ip-address-no-zone;
              description
                "IP address of COA client";
            }
            uses CLIENT-CONTENT;
          }
          description
            "Client data";
        }
        leaf ignore {
          type Aaa-select-key;
          description
            "Ignore option for server key or session key";
        }
        leaf port {
          type uint32 {
            range "1000..5000";
          }
          description
            "Specify the COA server port to listen on";
        }
        leaf authentication-type {
          type Aaa-authentication;
          description
            "RADIUS  dynamic  authorization  type";
        }
        uses SERVER-KEY;
      }
      container load-balance-options {
        description
          "Radius load-balancing options";
        container load-balance-method {
          description
            "Method by which the next host will be picked";
          container batch-size {
            description
              "Batch size for selection of the server";
            leaf batch-size {
              type uint32 {
                range "1..1500";
              }
              default "25";
              description
                "Batch size for selection of the server";
            }
            leaf ignore-preferred-server {
              type boolean;
              default "true";
              description
                "Disable preferred server for this Server
                 Group";
            }
          }
        }
      }
      container vrfs {
        description
          "List of VRFs";
        list vrf {
          key "vrf-name";
          description
            "A VRF";
          leaf source-interface {
            type xr:Interface-name;
            description
              "Specify interface for source address in
               RADIUS packets";
          }
          leaf vrf-name {
            type xr:Cisco-ios-xr-string;
            description
              "VRF name. Specify 'default' for defalut VRF";
          }
        }
      }
      container throttle {
        description
          "Radius throttling options";
        leaf access {
          type Aaa-throttle-access;
          default "0";
          description
            "To flow control the number of access requests
             sent to a radius server";
        }
        leaf accounting {
          type Aaa-throttle-accounting;
          default "0";
          description
            "To flow control the number of accounting
             requests sent to a radius server";
        }
        leaf access-timeout {
          type Aaa-throttle-access-timeout;
          default "3";
          description
            "Specify the number of timeouts exceeding which
             a throttled access request is dropped";
        }
      }
      container vsa {
        description
          "Unknown VSA (Vendor Specific Attribute) ignore
           configuration for RADIUS server";
        container attribute {
          description
            "Vendor Specific Attribute";
          container ignore {
            description
              "Ignore the VSA";
            leaf unknown {
              type empty;
              description
                "Ignore the VSA and no prefix will reject the
                 unknown VSA";
            }
          }
        }
      }
      container ipv4 {
        description
          "IPv4 configuration";
        uses DSCP;
      }
      container radius-attribute {
        description
          "attribute";
        container filter-id-11 {
          description
            "Filter-Id attribute configuration";
          container defaults {
            description
              "Set the attribute default direction";
            leaf direction {
              type Aaa-direction;
              description
                "Filtering is applied to
                 ingress(inbound)/egress(outbound) packets
                 only";
            }
          }
        }
        container acct-multi-session-id {
          description
            "Acct-Session-Id attribute(44)";
          container include-parent-session-id {
            description
              "Prepend Acct-Session-Id attribute with
               Nas-Port-Id";
            leaf config {
              type Aaa-config;
              description
                "false/true";
            }
          }
        }
        container acct-session-id {
          description
            "Acct-Session-Id attribute(44)";
          container prepend-nas-port-id {
            description
              "Prepend Acct-Session-Id attribute with
               Nas-Port-Id";
            leaf config {
              type Aaa-config;
              description
                "false/true";
            }
          }
        }
      }
      container attributes {
        description
          "Table of attribute list";
        list attribute {
          key "attribute-list-name";
          description
            "Attribute list name";
          container vendor-ids {
            description
              "Vendor Specific Attribute";
            list vendor-id {
              key "vendor-id";
              description
                "Vendor ID of vsa";
              leaf vendor-id {
                type uint32;
                description
                  "Vendor Id of vsa";
              }
              list vendor-type {
                key "vendor-type";
                description
                  "Vendor Type of vsa";
                leaf vendor-type {
                  type uint32;
                  description
                    "Vendor Type of vsa";
                }
                list attribute-name {
                  key "attribute-name";
                  description
                    "Attribute Name of vsa";
                  leaf attribute-name {
                    type xr:Cisco-ios-xr-string;
                    description
                      "Attribute Name of vsa";
                  }
                  list attribute-name-absent {
                    key "attribute-name-absent";
                    description
                      "AttributeName of vsa is absent";
                    leaf attribute-name-absent {
                      type uint32;
                      description
                        "AttributeName of vsa is absent";
                    }
                    list attribute-name-present {
                      key "attribute-name-present";
                      description
                        "AttributeName of vsa is present";
                      leaf attribute-name-present {
                        type uint32;
                        description
                          "AttributeName of vsa is present";
                      }
                    }
                  }
                }
              }
            }
          }
          leaf attribute {
            type string;
            description
              "Specify RADIUS attribute";
          }
          leaf attribute-list-name {
            type xr:Cisco-ios-xr-string;
            description
              "Attribute list name";
          }
        }
      }
      container source-port {
        description
          "Source port";
        leaf extended {
          type empty;
          description
            "Enable source-port extend ";
        }
      }
      leaf retransmit {
        type Aaa-radius-retransmit-with-disable;
        default "3";
        description
          "Number of times to retransmit a request to the
           RADIUS server(0-Disable)";
      }
      leaf dead-time {
        type Aaa-radius-dead-time;
        units "minute";
        description
          "This indicates the length of time (in minutes)
           for which a RADIUS server remains marked as
           dead";
      }
      leaf key {
        type xr:Proprietary-password;
        description
          "RADIUS encryption key";
      }
      leaf timeout {
        type Aaa-radius-timeout;
        default "5";
        description
          "Time to wait for a RADIUS server to reply";
      }
      uses IGNORE-ACCOUNTING-PORT;
      uses IDLE-TIME;
      uses USERNAME;
      uses IGNORE-AUTH-PORT;
    }
    description
      "This augment extends the configuration data of
       'Cisco-IOS-XR-aaa-lib-cfg'";
  }
  augment "/ncs:devices/ncs:template/ncs:ned-id/ncs:config/a2:aaa/a1:server-groups" {
    container radius-server-groups {
      description
        "RADIUS server group definition";
      list radius-server-group {
        // NCS patched for predictable order
        ordered-by user;
        key "server-group-name";
        description
          "RADIUS server group name";
        container accounting {
          description
            "List of filters in server group";
          uses ncs_template_REQUEST;
          uses ncs_template_REPLY;
        }
        container servers {
          description
            "List of RADIUS servers present in the group";
          list server {
            // NCS patched for predictable order
            ordered-by user;
            key "ordering-index ip-address auth-port-number acct-port-number";
            description
              "A server to include in the server group";
            leaf ordering-index {
              type string;
              description
                "This is used to sort the servers in the
                 order of precedence";
            }
            leaf ip-address {
              type string;
              description
                "IP address of RADIUS server";
            }
            leaf auth-port-number {
              type string;
              description
                "Authentication Port number (standard port
                 1645)";
            }
            leaf acct-port-number {
              type string;
              description
                "Accounting Port number (standard port 1646)";
            }
          }
        }
        container private-servers {
          description
            "List of private RADIUS servers present in the
             group";
          list private-server {
            // NCS patched for predictable order
            ordered-by user;
            key "ordering-index ip-address auth-port-number acct-port-number";
            description
              "A private server to include in the server
               group";
            leaf private-timeout {
              type string;
              // NCS drop default statement
              description
                "Time to wait for a RADIUS server to reply";
            }
            leaf ignore-accounting-port {
              type string;
              description
                "Ignore Accounting port";
            }
            leaf private-retransmit {
              type string;
              // NCS drop default statement
              description
                "Number of times to retransmit a request to
                 the RADIUS server";
            }
            leaf idle-time {
              type string;
              // NCS drop default statement
              description
                "Idle time for the radius Server";
            }
            leaf private-key {
              type string;
              description
                "RADIUS encryption key";
            }
            leaf username {
              type string;
              description
                "Username to be tested for automated testing";
            }
            leaf ignore-auth-port {
              type string;
              description
                "Ignore authentication Port";
            }
            leaf ordering-index {
              type string;
              description
                "This is used to sort the servers in the
                 order of precedence";
            }
            leaf ip-address {
              type string;
              description
                "IP address of RADIUS server";
            }
            leaf auth-port-number {
              type string;
              description
                "Authentication Port number (standard port
                 1645)";
            }
            leaf acct-port-number {
              type string;
              description
                "Accounting Port number (standard port 1646)";
            }
          }
        }
        container server-group-throttle {
          description
            "Radius throttling options";
          leaf access {
            type string;
            // NCS drop default statement
            description
              "To flow control the number of access requests
               sent to a radius server";
          }
          leaf accounting {
            type string;
            // NCS drop default statement
            description
              "To flow control the number of accounting
               requests sent to a radius server";
          }
          leaf access-timeout {
            type string;
            // NCS drop default statement
            description
              "Specify the number of timeouts exceeding
               which a throttled access request is dropped";
          }
        }
        container load-balance {
          description
            "Radius load-balancing options";
          container method {
            description
              "Method by which the next host will be picked";
            container name {
              description
                "Batch size for selection of the server";
              leaf least-outstanding {
                type string;
                // NCS drop default statement
                description
                  "Pick the server with the least transactions
                   outstanding";
              }
              leaf batch-size {
                type string;
                // NCS drop default statement
                description
                  "Batch size for selection of the server";
              }
              leaf ignore-preferred-server {
                type string;
                // NCS drop default statement
                description
                  "Disable preferred server for this Server
                   Group";
              }
            }
          }
        }
        container authorization {
          description
            "List of filters in server group";
          uses ncs_template_REQUEST;
          uses ncs_template_REPLY;
        }
        leaf dead-time {
          type string;
          units "minute";
          description
            "This indicates the length of time (in minutes)
             for which RADIUS servers present in this group
             remain marked as dead";
        }
        leaf source-interface {
          type string;
          description
            "Specify interface for source address in RADIUS
             packets";
        }
        leaf vrf {
          type string;
          description
            "Specify VRF name of RADIUS group";
        }
        leaf server-group-name {
          type string;
          description
            "RADIUS server group name";
        }
      }
    }
    description
      "This augment extends the configuration data of
       'Cisco-IOS-XR-aaa-locald-cfg'";
  }
  augment "/ncs:devices/ncs:device/ncs:live-status/a2:aaa/a1:server-groups" {
    container radius-server-groups {
      tailf:ncs-device-type "netconf";
      tailf:display-when "not(../../../../ncs:module) or ../../../../ncs:module[ncs:name='Cisco-IOS-XR-aaa-protocol-radius-cfg'] or (../../../../ncs:live-status-protocol[not(ncs:capability)]) or (../../../../ncs:live-status-protocol/ncs:capability/ncs:module[.='Cisco-IOS-XR-aaa-protocol-radius-cfg'])";
      description
        "RADIUS server group definition";
      list radius-server-group {
        key "server-group-name";
        description
          "RADIUS server group name";
        container accounting {
          description
            "List of filters in server group";
          uses live_ncs_REQUEST;
          uses live_ncs_REPLY;
        }
        container servers {
          description
            "List of RADIUS servers present in the group";
          list server {
            key "ordering-index ip-address auth-port-number acct-port-number";
            description
              "A server to include in the server group";
            leaf ordering-index {
              type uint32;
              description
                "This is used to sort the servers in the
                 order of precedence";
            }
            leaf ip-address {
              type inet:ip-address-no-zone;
              description
                "IP address of RADIUS server";
            }
            leaf auth-port-number {
              type inet:port-number;
              description
                "Authentication Port number (standard port
                 1645)";
            }
            leaf acct-port-number {
              type inet:port-number;
              description
                "Accounting Port number (standard port 1646)";
            }
          }
        }
        container private-servers {
          description
            "List of private RADIUS servers present in the
             group";
          list private-server {
            key "ordering-index ip-address auth-port-number acct-port-number";
            description
              "A private server to include in the server
               group";
            leaf private-timeout {
              type Aaa-radius-timeout;
              // NCS drop default statement
              description
                "Time to wait for a RADIUS server to reply";
            }
            leaf ignore-accounting-port {
              type boolean;
              description
                "Ignore Accounting port";
            }
            leaf private-retransmit {
              type Aaa-radius-retransmit;
              // NCS drop default statement
              description
                "Number of times to retransmit a request to
                 the RADIUS server";
            }
            leaf idle-time {
              type Aaa-radius-idle-time;
              // NCS drop default statement
              description
                "Idle time for the radius Server";
            }
            leaf private-key {
              type xr:Proprietary-password;
              description
                "RADIUS encryption key";
            }
            leaf username {
              type string;
              description
                "Username to be tested for automated testing";
            }
            leaf ignore-auth-port {
              type boolean;
              description
                "Ignore authentication Port";
            }
            leaf ordering-index {
              type uint32;
              description
                "This is used to sort the servers in the
                 order of precedence";
            }
            leaf ip-address {
              type inet:ip-address-no-zone;
              description
                "IP address of RADIUS server";
            }
            leaf auth-port-number {
              type inet:port-number;
              description
                "Authentication Port number (standard port
                 1645)";
            }
            leaf acct-port-number {
              type inet:port-number;
              description
                "Accounting Port number (standard port 1646)";
            }
          }
        }
        container server-group-throttle {
          description
            "Radius throttling options";
          leaf access {
            type Aaa-throttle-access;
            // NCS drop default statement
            description
              "To flow control the number of access requests
               sent to a radius server";
          }
          leaf accounting {
            type Aaa-throttle-accounting;
            // NCS drop default statement
            description
              "To flow control the number of accounting
               requests sent to a radius server";
          }
          leaf access-timeout {
            type Aaa-throttle-access-timeout;
            // NCS drop default statement
            description
              "Specify the number of timeouts exceeding
               which a throttled access request is dropped";
          }
        }
        container load-balance {
          description
            "Radius load-balancing options";
          container method {
            description
              "Method by which the next host will be picked";
            container name {
              description
                "Batch size for selection of the server";
              leaf least-outstanding {
                type uint32;
                // NCS drop default statement
                description
                  "Pick the server with the least transactions
                   outstanding";
              }
              leaf batch-size {
                type uint32 {
                  range "1..1500";
                }
                // NCS drop default statement
                description
                  "Batch size for selection of the server";
              }
              leaf ignore-preferred-server {
                type boolean;
                // NCS drop default statement
                description
                  "Disable preferred server for this Server
                   Group";
              }
            }
          }
        }
        container authorization {
          description
            "List of filters in server group";
          uses live_ncs_REQUEST;
          uses live_ncs_REPLY;
        }
        leaf dead-time {
          type Aaa-radius-dead-time;
          units "minute";
          description
            "This indicates the length of time (in minutes)
             for which RADIUS servers present in this group
             remain marked as dead";
        }
        leaf source-interface {
          type xr:Interface-name;
          description
            "Specify interface for source address in RADIUS
             packets";
        }
        leaf vrf {
          type string;
          description
            "Specify VRF name of RADIUS group";
        }
        leaf server-group-name {
          type xr:Cisco-ios-xr-string;
          description
            "RADIUS server group name";
        }
      }
    }
    description
      "This augment extends the configuration data of
       'Cisco-IOS-XR-aaa-locald-cfg'";
  }
  augment "/ncs:devices/ncs:device/ncs:config/a2:aaa/a1:server-groups" {
    container radius-server-groups {
      tailf:ncs-device-type "netconf";
      tailf:display-when "not(../../../../ncs:module) or ../../../../ncs:module[ncs:name='Cisco-IOS-XR-aaa-protocol-radius-cfg']";
      description
        "RADIUS server group definition";
      list radius-server-group {
        key "server-group-name";
        description
          "RADIUS server group name";
        container accounting {
          description
            "List of filters in server group";
          uses REQUEST;
          uses REPLY;
        }
        container servers {
          description
            "List of RADIUS servers present in the group";
          list server {
            key "ordering-index ip-address auth-port-number acct-port-number";
            description
              "A server to include in the server group";
            leaf ordering-index {
              type uint32;
              description
                "This is used to sort the servers in the
                 order of precedence";
            }
            leaf ip-address {
              type inet:ip-address-no-zone;
              description
                "IP address of RADIUS server";
            }
            leaf auth-port-number {
              type inet:port-number;
              description
                "Authentication Port number (standard port
                 1645)";
            }
            leaf acct-port-number {
              type inet:port-number;
              description
                "Accounting Port number (standard port 1646)";
            }
          }
        }
        container private-servers {
          description
            "List of private RADIUS servers present in the
             group";
          list private-server {
            key "ordering-index ip-address auth-port-number acct-port-number";
            description
              "A private server to include in the server
               group";
            leaf private-timeout {
              type Aaa-radius-timeout;
              default "5";
              description
                "Time to wait for a RADIUS server to reply";
            }
            leaf ignore-accounting-port {
              type boolean;
              description
                "Ignore Accounting port";
            }
            leaf private-retransmit {
              type Aaa-radius-retransmit;
              default "3";
              description
                "Number of times to retransmit a request to
                 the RADIUS server";
            }
            leaf idle-time {
              type Aaa-radius-idle-time;
              default "5";
              description
                "Idle time for the radius Server";
            }
            leaf private-key {
              type xr:Proprietary-password;
              description
                "RADIUS encryption key";
            }
            leaf username {
              type string;
              description
                "Username to be tested for automated testing";
            }
            leaf ignore-auth-port {
              type boolean;
              description
                "Ignore authentication Port";
            }
            leaf ordering-index {
              type uint32;
              description
                "This is used to sort the servers in the
                 order of precedence";
            }
            leaf ip-address {
              type inet:ip-address-no-zone;
              description
                "IP address of RADIUS server";
            }
            leaf auth-port-number {
              type inet:port-number;
              description
                "Authentication Port number (standard port
                 1645)";
            }
            leaf acct-port-number {
              type inet:port-number;
              description
                "Accounting Port number (standard port 1646)";
            }
          }
        }
        container server-group-throttle {
          description
            "Radius throttling options";
          leaf access {
            type Aaa-throttle-access;
            default "0";
            description
              "To flow control the number of access requests
               sent to a radius server";
          }
          leaf accounting {
            type Aaa-throttle-accounting;
            default "0";
            description
              "To flow control the number of accounting
               requests sent to a radius server";
          }
          leaf access-timeout {
            type Aaa-throttle-access-timeout;
            default "3";
            description
              "Specify the number of timeouts exceeding
               which a throttled access request is dropped";
          }
        }
        container load-balance {
          description
            "Radius load-balancing options";
          container method {
            description
              "Method by which the next host will be picked";
            container name {
              description
                "Batch size for selection of the server";
              leaf least-outstanding {
                type uint32;
                default "4";
                description
                  "Pick the server with the least transactions
                   outstanding";
              }
              leaf batch-size {
                type uint32 {
                  range "1..1500";
                }
                default "25";
                description
                  "Batch size for selection of the server";
              }
              leaf ignore-preferred-server {
                type boolean;
                default "true";
                description
                  "Disable preferred server for this Server
                   Group";
              }
            }
          }
        }
        container authorization {
          description
            "List of filters in server group";
          uses REQUEST;
          uses REPLY;
        }
        leaf dead-time {
          type Aaa-radius-dead-time;
          units "minute";
          description
            "This indicates the length of time (in minutes)
             for which RADIUS servers present in this group
             remain marked as dead";
        }
        leaf source-interface {
          type xr:Interface-name;
          description
            "Specify interface for source address in RADIUS
             packets";
        }
        leaf vrf {
          type string;
          description
            "Specify VRF name of RADIUS group";
        }
        leaf server-group-name {
          type xr:Cisco-ios-xr-string;
          description
            "RADIUS server group name";
        }
      }
    }
    description
      "This augment extends the configuration data of
       'Cisco-IOS-XR-aaa-locald-cfg'";
  }
}
