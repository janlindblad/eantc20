module Cisco-IOS-XR-sysadmin-tacacs-test-tacacs {
  // Generated by yanger -t ncs
  tailf:mount-id f5500-nc-1.0:f5500-nc-1.0;
  tailf:ncs-device-type "netconf";

  namespace "http://www.cisco.com/ns/yang/Cisco-IOS-XR-sysadmin-tacacs-test-tacacs";
  prefix Cisco-IOS-XR-sysadmin-tacacs-test-tacacs;

  import Cisco-IOS-XR-sysadmin-tacacs-tacacs-server {
    prefix tacacs-server;
  }
  import "f5500-nc-1.0" {
    prefix "f5500-nc-1.0";
  }
  import tailf-ncs {
    prefix ncs;
  }
  import tailf-common {
    prefix tailf;
  }

  organization
    "Cisco Systems Inc.";
  contact
    "aaa-ng-tacacs-dev@cisco.com";
  description
    "This module contains definitions
     for the Calvados model objects.

     This clie part is for test commands for tacacs

     Copyright (c) 2012-2018 by Cisco Systems, Inc.
     All rights reserved.";

  revision 2017-05-10 {
    description
      "Namespace changed from test_tacacs to Cisco-IOS-XR-sysadmin-tacacs-test-tacacs";
  }

  augment "/ncs:devices/ncs:template/ncs:ned-id/ncs:config/tacacs-server:tacacs-server" {
    // NCS drop config false container 'test-authentication'
    // NCS drop config false container 'test-authorization'
    // NCS drop config false container 'test-accounting'
  }
  augment "/ncs:devices/ncs:device/ncs:live-status/tacacs-server:tacacs-server" {
    container test-authentication {
      tailf:ncs-device-type "netconf";
      tailf:display-when "not(../../../ncs:module) or ../../../ncs:module[ncs:name='Cisco-IOS-XR-sysadmin-tacacs-test-tacacs'] or (../../../ncs:live-status-protocol[not(ncs:capability)]) or (../../../ncs:live-status-protocol/ncs:capability/ncs:module[.='Cisco-IOS-XR-sysadmin-tacacs-test-tacacs'])";
      presence "";
      leaf authentication {
        type string;
        // NCS drop mandatory statement
        description
          "Authentication";
      }
    }
    container test-authorization {
      tailf:ncs-device-type "netconf";
      tailf:display-when "not(../../../ncs:module) or ../../../ncs:module[ncs:name='Cisco-IOS-XR-sysadmin-tacacs-test-tacacs'] or (../../../ncs:live-status-protocol[not(ncs:capability)]) or (../../../ncs:live-status-protocol/ncs:capability/ncs:module[.='Cisco-IOS-XR-sysadmin-tacacs-test-tacacs'])";
      presence "";
      leaf authorization {
        type string;
        // NCS drop mandatory statement
        description
          "Authorization";
      }
    }
    container test-accounting {
      tailf:ncs-device-type "netconf";
      tailf:display-when "not(../../../ncs:module) or ../../../ncs:module[ncs:name='Cisco-IOS-XR-sysadmin-tacacs-test-tacacs'] or (../../../ncs:live-status-protocol[not(ncs:capability)]) or (../../../ncs:live-status-protocol/ncs:capability/ncs:module[.='Cisco-IOS-XR-sysadmin-tacacs-test-tacacs'])";
      presence "";
      leaf accounting {
        type string;
        // NCS drop mandatory statement
        description
          "Accounting";
      }
    }
  }
  augment "/ncs:devices/ncs:device/ncs:config/tacacs-server:tacacs-server" {
    // NCS drop config false container 'test-authentication'
    // NCS drop config false container 'test-authorization'
    // NCS drop config false container 'test-accounting'
  }
}
