module Cisco-IOS-XR-ipv4-arp-act {
  // Generated by yanger -t ncs
  tailf:mount-id f5500-nc-1.0:f5500-nc-1.0;
  tailf:ncs-device-type "netconf";

  namespace "http://cisco.com/ns/yang/Cisco-IOS-XR-ipv4-arp-act";
  prefix Cisco-IOS-XR-ipv4-arp-act;

  import Cisco-IOS-XR-types {
    prefix csc;
  }
  import ietf-inet-types {
    prefix inet;
  }
  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains a collection of YANG definitions
     for Cisco IOS-XR action package configuration.

     Copyright (c) 2018 by Cisco Systems, Inc.
     All rights reserved.";

  revision 2018-10-08 {
    description
      "IOS XR 6.1.1 revision.";
  }

  augment "/ncs:devices/ncs:device/ncs:rpc" {
    container rpc-clear-arp-api-stats-location {
      tailf:ncs-device-type "netconf";
      tailf:display-when "not(../../ncs:module) or ../../ncs:module[ncs:name='Cisco-IOS-XR-ipv4-arp-act']";
      tailf:action clear-arp-api-stats-location {
        tailf:actionpoint ncsproxy {
          tailf:internal;
        }
        csc:xr-task "arp";
        csc:cli-command "clear arp api-stats location <node-location>";
        input {
          leaf node-location {
            csc:cli-name "*";
            mandatory true;
            type string;
          }
        }
      }
    }
  }
  augment "/ncs:devices/ncs:device-group/ncs:ned-id/ncs:rpc" {
    container rpc-clear-arp-api-stats-location {
      tailf:ncs-device-type "netconf";
      tailf:display-when "/ncs:devices/ncs:device[ncs:name=current()/../../../ncs:member]/ncs:module[ncs:name='Cisco-IOS-XR-ipv4-arp-act']";
      tailf:action clear-arp-api-stats-location {
        tailf:actionpoint ncsproxy {
          tailf:internal;
        }
        csc:xr-task "arp";
        csc:cli-command "clear arp api-stats location <node-location>";
        input {
          leaf node-location {
            csc:cli-name "*";
            mandatory true;
            type string;
          }
        }
      }
    }
  }
  augment "/ncs:devices/ncs:device/ncs:rpc" {
    container rpc-clear-arp-api-stats-api {
      tailf:ncs-device-type "netconf";
      tailf:display-when "not(../../ncs:module) or ../../ncs:module[ncs:name='Cisco-IOS-XR-ipv4-arp-act']";
      tailf:action clear-arp-api-stats-api {
        tailf:actionpoint ncsproxy {
          tailf:internal;
        }
        csc:xr-task "arp";
        csc:cli-command "clear arp api-stats api <name>";
        input {
          leaf name {
            mandatory true;
            type string;
          }
        }
      }
    }
  }
  augment "/ncs:devices/ncs:device-group/ncs:ned-id/ncs:rpc" {
    container rpc-clear-arp-api-stats-api {
      tailf:ncs-device-type "netconf";
      tailf:display-when "/ncs:devices/ncs:device[ncs:name=current()/../../../ncs:member]/ncs:module[ncs:name='Cisco-IOS-XR-ipv4-arp-act']";
      tailf:action clear-arp-api-stats-api {
        tailf:actionpoint ncsproxy {
          tailf:internal;
        }
        csc:xr-task "arp";
        csc:cli-command "clear arp api-stats api <name>";
        input {
          leaf name {
            mandatory true;
            type string;
          }
        }
      }
    }
  }
}
