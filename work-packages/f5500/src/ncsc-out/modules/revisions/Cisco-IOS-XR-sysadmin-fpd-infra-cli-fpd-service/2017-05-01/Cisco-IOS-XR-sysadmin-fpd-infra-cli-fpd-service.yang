module Cisco-IOS-XR-sysadmin-fpd-infra-cli-fpd-service {
  // Generated by yanger -t ncs
  tailf:mount-id f5500-nc-1.0:f5500-nc-1.0;
  tailf:ncs-device-type "netconf";

  namespace "http://www.cisco.com/ns/yang/Cisco-IOS-XR-sysadmin-fpd-infra-cli-fpd-service";
  prefix Cisco-IOS-XR-sysadmin-fpd-infra-cli-fpd-service;

  import "f5500-nc-1.0" {
    prefix "f5500-nc-1.0";
  }
  import tailf-ncs {
    prefix ncs;
  }
  import tailf-common {
    prefix tailf;
  }

  organization
    "Cisco Systems, Inc.";
  contact
    "Cisco Systems, Inc.
     Customer Service

     Postal: 170 West Tasman Drive
     San Jose, CA 95134

     Tel: +1 800 553-NETS

     E-mail: cs-yang@cisco.com";
  description
    "This module contains definitions
     for the Calvados model objects.

     Copyright (c) 2012-2018 by Cisco Systems, Inc.
     All rights reserved.";

  revision 2017-05-01 {
    description
      "Namespace change to comply with Cisco guidelines on namespace";
  }

  augment "/ncs:devices/ncs:device/ncs:config" {
    // NCS drop config false list location
  }
  augment "/ncs:devices/ncs:device/ncs:live-status" {
    list location {
      tailf:ncs-device-type "netconf";
      tailf:display-when "not(../ncs:module) or ../ncs:module[ncs:name='Cisco-IOS-XR-sysadmin-fpd-infra-cli-fpd-service'] or (../ncs:live-status-protocol[not(ncs:capability)]) or (../ncs:live-status-protocol/ncs:capability/ncs:module[.='Cisco-IOS-XR-sysadmin-fpd-infra-cli-fpd-service'])";
      key "loc";
      leaf loc {
        type string;
      }
      list fpd2 {
        key "name";
        leaf name {
          type string;
        }
      }
    }
  }
  augment "/ncs:devices/ncs:template/ncs:ned-id/ncs:config" {
    // NCS drop config false list location
  }
}
