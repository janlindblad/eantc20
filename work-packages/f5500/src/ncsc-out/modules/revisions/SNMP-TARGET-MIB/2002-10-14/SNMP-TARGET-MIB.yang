module SNMP-TARGET-MIB {
  // Generated by yanger -t ncs
  tailf:mount-id f5500-nc-1.0:f5500-nc-1.0;
  tailf:ncs-device-type "netconf";

  namespace "http://tail-f.com/ns/mibs/SNMP-TARGET-MIB/200210140000Z";
  prefix SNMP-TARGET-MIB;
  // NCS drop tailf:id
  tailf:snmp-mib-module-name SNMP-TARGET-MIB;

  import ietf-yang-types {
    prefix yang;
  }
  import tailf-common {
    prefix tailf;
  }
  import SNMPv2-TC {
    prefix SNMPv2_TC;
  }
  import SNMP-FRAMEWORK-MIB {
    prefix SNMP_FRAMEWORK_MIB;
  }
  import "f5500-nc-1.0" {
    prefix "f5500-nc-1.0";
  }
  import tailf-ncs {
    prefix ncs;
  }

  revision 2002-10-14 {
    description
      "";
  }

  typedef snmpTargetParamsSecurityModelType {
    type int32 {
      range "1 .. 2147483647";
    }
  }

  typedef snmpTargetParamsNameType {
    type string {
      length "1 .. 32";
    }
  }

  typedef snmpTargetAddrParamsType {
    type string {
      length "1 .. 32";
    }
  }

  typedef snmpTargetAddrRetryCountType {
    type int32 {
      range "0 .. 255";
    }
  }

  typedef snmpTargetAddrNameType {
    type string {
      length "1 .. 32";
    }
  }

  typedef SnmpTagList {
    type string {
      length "min .. 255";
    }
  }

  typedef SnmpTagValue {
    type string {
      length "min .. 255";
    }
  }

  typedef snmpTargetAddrMMSType {
    type int32 {
      range "0 | 484 .. 2147483647";
    }
  }

  typedef snmpTargetAddrEngineIDType {
    type tailf:hex-list {
      pattern '(((([0-9A-Fa-f]{2}):){4,31})([0-9A-Fa-f]{2}))?';
      tailf:value-length "min .. 32";
    }
  }

  typedef UDPTMask {
    tailf:info
      "octectList, 0, 6 or 18 octets long";
    type union {
      type UDPTAddress;
      type EmptyOctetList;
    }
  }

  typedef EmptyOctetList {
    type tailf:octet-list {
      tailf:value-length "0";
    }
  }

  typedef UDPTAddress {
    type union {
      type UDPIPv4TAddress;
      type UDPIPv6TAddress;
    }
  }

  typedef UDPIPv6TAddress {
    tailf:info
      "ipv6+port (18 dot-separated octets)";
    type tailf:octet-list {
      tailf:value-length "18";
    }
  }

  typedef UDPIPv4TAddress {
    tailf:info
      "ipv4+port (6 dot-separated octets)";
    type tailf:octet-list {
      tailf:value-length "6";
    }
  }

  augment "/ncs:devices/ncs:device/ncs:config" {
    container SNMP-TARGET-MIB {
      tailf:ncs-device-type "netconf";
      tailf:display-when "not(../../ncs:module) or ../../ncs:module[ncs:name='SNMP-TARGET-MIB']";
      // NCS drop config false container snmpTargetObjects
      container snmpTargetAddrTable {
        list snmpTargetAddrEntry {
          key "snmpTargetAddrName";
          tailf:sort-order snmp-implied;
          tailf:snmp-oid "1.3.6.1.6.3.12.1.2";
          // NCS drop tailf:snmp-name
          // NCS drop tailf:snmp-name
          leaf snmpTargetAddrName {
            type snmpTargetAddrNameType;
            tailf:snmp-oid "1.3.6.1.6.3.12.1.2.1.1";
          }
          leaf snmpTargetAddrTDomain {
            type SNMPv2_TC:TDomain;
            mandatory true;
            tailf:snmp-oid "1.3.6.1.6.3.12.1.2.1.2";
          }
          leaf snmpTargetAddrTAddress {
            type UDPTAddress;
            mandatory true;
            tailf:snmp-oid "1.3.6.1.6.3.12.1.2.1.3";
          }
          leaf snmpTargetAddrTimeout {
            type SNMPv2_TC:TimeInterval;
            tailf:snmp-oid "1.3.6.1.6.3.12.1.2.1.4";
            default "1500";
          }
          leaf snmpTargetAddrRetryCount {
            type snmpTargetAddrRetryCountType;
            tailf:snmp-oid "1.3.6.1.6.3.12.1.2.1.5";
            default "3";
          }
          leaf snmpTargetAddrTagList {
            type SnmpTagList;
            tailf:snmp-oid "1.3.6.1.6.3.12.1.2.1.6";
            default "";
          }
          leaf snmpTargetAddrParams {
            type snmpTargetAddrParamsType;
            mandatory true;
            tailf:snmp-oid "1.3.6.1.6.3.12.1.2.1.7";
          }
          leaf snmpTargetAddrStorageType {
            type SNMPv2_TC:StorageType;
            tailf:snmp-oid "1.3.6.1.6.3.12.1.2.1.8";
            default "nonVolatile";
          }
          leaf snmpTargetAddrEngineID {
            type snmpTargetAddrEngineIDType;
            default "";
          }
          leaf snmpTargetAddrTMask {
            type UDPTMask;
            // NCS drop tailf:snmp-name
            default "";
          }
          leaf snmpTargetAddrMMS {
            type snmpTargetAddrMMSType;
            // NCS drop tailf:snmp-name
            default "2048";
          }
          leaf enabled {
            type boolean;
            default "true";
          }
        }
      }
      container snmpTargetParamsTable {
        list snmpTargetParamsEntry {
          key "snmpTargetParamsName";
          tailf:sort-order snmp-implied;
          tailf:snmp-oid "1.3.6.1.6.3.12.1.3";
          leaf snmpTargetParamsName {
            type snmpTargetParamsNameType;
            tailf:snmp-oid "1.3.6.1.6.3.12.1.3.1.1";
          }
          leaf snmpTargetParamsMPModel {
            type SNMP_FRAMEWORK_MIB:SnmpMessageProcessingModel;
            mandatory true;
            tailf:snmp-oid "1.3.6.1.6.3.12.1.3.1.2";
          }
          leaf snmpTargetParamsSecurityModel {
            type snmpTargetParamsSecurityModelType;
            mandatory true;
            tailf:snmp-oid "1.3.6.1.6.3.12.1.3.1.3";
          }
          leaf snmpTargetParamsSecurityName {
            type SNMP_FRAMEWORK_MIB:SnmpAdminString;
            mandatory true;
            tailf:snmp-oid "1.3.6.1.6.3.12.1.3.1.4";
          }
          leaf snmpTargetParamsSecurityLevel {
            type SNMP_FRAMEWORK_MIB:SnmpSecurityLevel;
            mandatory true;
            tailf:snmp-oid "1.3.6.1.6.3.12.1.3.1.5";
          }
          leaf snmpTargetParamsStorageType {
            type SNMPv2_TC:StorageType;
            tailf:snmp-oid "1.3.6.1.6.3.12.1.3.1.6";
            default "nonVolatile";
          }
        }
      }
    }
  }
  augment "/ncs:devices/ncs:device/ncs:live-status" {
    container SNMP-TARGET-MIB {
      tailf:ncs-device-type "netconf";
      tailf:display-when "not(../../ncs:module) or ../../ncs:module[ncs:name='SNMP-TARGET-MIB'] or (../../ncs:live-status-protocol[not(ncs:capability)]) or (../../ncs:live-status-protocol/ncs:capability/ncs:module[.='SNMP-TARGET-MIB'])";
      container snmpTargetObjects {
        tailf:snmp-oid "1.3.6.1.6.3.12.1";
        leaf snmpUnavailableContexts {
          type yang:counter32;
          tailf:snmp-oid "1.3.6.1.6.3.12.1.4";
        }
        leaf snmpUnknownContexts {
          type yang:counter32;
          tailf:snmp-oid "1.3.6.1.6.3.12.1.5";
        }
      }
      container snmpTargetAddrTable {
        list snmpTargetAddrEntry {
          key "snmpTargetAddrName";
          tailf:sort-order snmp-implied;
          tailf:snmp-oid "1.3.6.1.6.3.12.1.2";
          // NCS drop tailf:snmp-name
          // NCS drop tailf:snmp-name
          leaf snmpTargetAddrName {
            type snmpTargetAddrNameType;
            tailf:snmp-oid "1.3.6.1.6.3.12.1.2.1.1";
          }
          leaf snmpTargetAddrTDomain {
            type SNMPv2_TC:TDomain;
            // NCS drop mandatory statement
            tailf:snmp-oid "1.3.6.1.6.3.12.1.2.1.2";
          }
          leaf snmpTargetAddrTAddress {
            type UDPTAddress;
            // NCS drop mandatory statement
            tailf:snmp-oid "1.3.6.1.6.3.12.1.2.1.3";
          }
          leaf snmpTargetAddrTimeout {
            type SNMPv2_TC:TimeInterval;
            tailf:snmp-oid "1.3.6.1.6.3.12.1.2.1.4";
            // NCS drop default statement
          }
          leaf snmpTargetAddrRetryCount {
            type snmpTargetAddrRetryCountType;
            tailf:snmp-oid "1.3.6.1.6.3.12.1.2.1.5";
            // NCS drop default statement
          }
          leaf snmpTargetAddrTagList {
            type SnmpTagList;
            tailf:snmp-oid "1.3.6.1.6.3.12.1.2.1.6";
            // NCS drop default statement
          }
          leaf snmpTargetAddrParams {
            type snmpTargetAddrParamsType;
            // NCS drop mandatory statement
            tailf:snmp-oid "1.3.6.1.6.3.12.1.2.1.7";
          }
          leaf snmpTargetAddrStorageType {
            type SNMPv2_TC:StorageType;
            tailf:snmp-oid "1.3.6.1.6.3.12.1.2.1.8";
            // NCS drop default statement
          }
          leaf snmpTargetAddrEngineID {
            type snmpTargetAddrEngineIDType;
            // NCS drop default statement
          }
          leaf snmpTargetAddrTMask {
            type UDPTMask;
            // NCS drop tailf:snmp-name
            // NCS drop default statement
          }
          leaf snmpTargetAddrMMS {
            type snmpTargetAddrMMSType;
            // NCS drop tailf:snmp-name
            // NCS drop default statement
          }
          leaf enabled {
            type boolean;
            // NCS drop default statement
          }
        }
      }
      container snmpTargetParamsTable {
        list snmpTargetParamsEntry {
          key "snmpTargetParamsName";
          tailf:sort-order snmp-implied;
          tailf:snmp-oid "1.3.6.1.6.3.12.1.3";
          leaf snmpTargetParamsName {
            type snmpTargetParamsNameType;
            tailf:snmp-oid "1.3.6.1.6.3.12.1.3.1.1";
          }
          leaf snmpTargetParamsMPModel {
            type SNMP_FRAMEWORK_MIB:SnmpMessageProcessingModel;
            // NCS drop mandatory statement
            tailf:snmp-oid "1.3.6.1.6.3.12.1.3.1.2";
          }
          leaf snmpTargetParamsSecurityModel {
            type snmpTargetParamsSecurityModelType;
            // NCS drop mandatory statement
            tailf:snmp-oid "1.3.6.1.6.3.12.1.3.1.3";
          }
          leaf snmpTargetParamsSecurityName {
            type SNMP_FRAMEWORK_MIB:SnmpAdminString;
            // NCS drop mandatory statement
            tailf:snmp-oid "1.3.6.1.6.3.12.1.3.1.4";
          }
          leaf snmpTargetParamsSecurityLevel {
            type SNMP_FRAMEWORK_MIB:SnmpSecurityLevel;
            // NCS drop mandatory statement
            tailf:snmp-oid "1.3.6.1.6.3.12.1.3.1.5";
          }
          leaf snmpTargetParamsStorageType {
            type SNMPv2_TC:StorageType;
            tailf:snmp-oid "1.3.6.1.6.3.12.1.3.1.6";
            // NCS drop default statement
          }
        }
      }
    }
  }
  augment "/ncs:devices/ncs:template/ncs:ned-id/ncs:config" {
    container SNMP-TARGET-MIB {
      // NCS drop config false container snmpTargetObjects
      container snmpTargetAddrTable {
        list snmpTargetAddrEntry {
          // NCS patched for predictable order
          ordered-by user;
          key "snmpTargetAddrName";
          leaf snmpTargetAddrName {
            type string;
          }
          leaf snmpTargetAddrTDomain {
            type string;
            // NCS drop mandatory statement
          }
          leaf snmpTargetAddrTAddress {
            type string;
            // NCS drop mandatory statement
          }
          leaf snmpTargetAddrTimeout {
            type string;
            // NCS drop default statement
          }
          leaf snmpTargetAddrRetryCount {
            type string;
            // NCS drop default statement
          }
          leaf snmpTargetAddrTagList {
            type string;
            // NCS drop default statement
          }
          leaf snmpTargetAddrParams {
            type string;
            // NCS drop mandatory statement
          }
          leaf snmpTargetAddrStorageType {
            type string;
            // NCS drop default statement
          }
          leaf snmpTargetAddrEngineID {
            type string;
            // NCS drop default statement
          }
          leaf snmpTargetAddrTMask {
            type string;
            // NCS drop default statement
          }
          leaf snmpTargetAddrMMS {
            type string;
            // NCS drop default statement
          }
          leaf enabled {
            type string;
            // NCS drop default statement
          }
        }
      }
      container snmpTargetParamsTable {
        list snmpTargetParamsEntry {
          // NCS patched for predictable order
          ordered-by user;
          key "snmpTargetParamsName";
          leaf snmpTargetParamsName {
            type string;
          }
          leaf snmpTargetParamsMPModel {
            type string;
            // NCS drop mandatory statement
          }
          leaf snmpTargetParamsSecurityModel {
            type string;
            // NCS drop mandatory statement
          }
          leaf snmpTargetParamsSecurityName {
            type string;
            // NCS drop mandatory statement
          }
          leaf snmpTargetParamsSecurityLevel {
            type string;
            // NCS drop mandatory statement
          }
          leaf snmpTargetParamsStorageType {
            type string;
            // NCS drop default statement
          }
        }
      }
    }
  }
}
