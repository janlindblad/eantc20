module Cisco-IOS-XR-infra-statsd-act {

  namespace "http://cisco.com/ns/yang/Cisco-IOS-XR-infra-statsd-act";

  prefix "Cisco-IOS-XR-infra-statsd-act";

  import Cisco-IOS-XR-types { prefix "csc"; }

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR action package configuration.

     Copyright (c) 2018 by Cisco Systems, Inc.
     All rights reserved.";

  revision "2018-01-10" {
    description
      "IOS XR 6.4.1 revision.";
  }

  rpc clear-counters-controller {
    csc:xr-task "interface";
    csc:cli-command "clear counters <controller-name>";
    description
      "Controller name.
      ";
    input {
      leaf controller-name {
        mandatory true;
        type csc:Interface-name;
        description "Controller name";
      }
    }
  }

  rpc clear-counters-all {
    csc:xr-task "interface";
    csc:cli-command "clear counters all";
    description
      "Clear counters on all interfaces.
      ";
  }

  rpc clear-counters-interface {
    csc:xr-task "interface";
    csc:cli-command "clear counters interface <interface-name>";
    description
      "Clear counters for interface.
      ";
    input {
      leaf interface-name {
        mandatory true;
        type csc:Interface-name;
        description "Interface name";
      }
    }
  }

}
