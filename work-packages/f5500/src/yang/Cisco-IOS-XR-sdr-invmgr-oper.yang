module Cisco-IOS-XR-sdr-invmgr-oper {

  /*** NAMESPACE / PREFIX DEFINITION ***/

  namespace "http://cisco.com/ns/yang/Cisco-IOS-XR-sdr-invmgr-oper";


  prefix "Cisco-IOS-XR-sdr-invmgr-oper";

  /*** LINKAGE (IMPORTS / INCLUDES) ***/

  import Cisco-IOS-XR-types { prefix "xr"; }

  include Cisco-IOS-XR-sdr-invmgr-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR sdr-invmgr package operational data.

     This module contains definitions
     for the following management objects:
       sdr-inventory: SDR information

     Copyright (c) 2013-2018 by Cisco Systems, Inc.
     All rights reserved.";

  revision "2015-11-09" {
    description
      "IOS XR 6.0 revision.";
  }


  container sdr-inventory {
    config false;
    description "SDR information";

    container racks {
      description "RackTable";

      list rack {
        key "name";
        description "Rack name";
        leaf name {
          type xr:Cisco-ios-xr-string;
          description "Rack name";
        }

        list slot {
          key "name";
          description "Slot name";
          leaf name {
            type xr:Cisco-ios-xr-string;
            description "Slot name";
          }

          list card {
            key "name";
            description "Card";

            container attributes {
              description "Attributes";
              leaf config-state-string {
                type string;
                description "Config State String";
              }
              leaf power {
                type uint32 {
                  range "0..4294967295";
                }
                default "0";
                description "Power";
              }
              leaf config-state {
                type uint32 {
                  range "0..4294967295";
                }
                default "0";
                description "ConfigState";
              }
              leaf card-state {
                type uint32 {
                  range "0..4294967295";
                }
                default "0";
                description "CardState";
              }
              leaf vm-state {
                type uint32 {
                  range "0..4294967295";
                }
                default "0";
                description "VM State information";
              }
              leaf card-admin-state {
                type uint32 {
                  range "0..4294967295";
                }
                default "0";
                description "Card Admin State";
              }
              leaf card-type {
                type uint32 {
                  range "0..4294967295";
                }
                default "0";
                description "CardType";
              }
              leaf card-type-string {
                type string;
                description "Card Type String";
              }
              leaf node-name-string {
                type string;
                description "Node Name String";
              }
              leaf card-valid {
                type uint32 {
                  range "0..4294967295";
                }
                default "0";
                description "Card Valid";
              }
              leaf pi-slot-number {
                type uint32 {
                  range "0..4294967295";
                }
                default "0";
                description "Pi Slot Number";
              }
              leaf shutdown {
                type uint32 {
                  range "0..4294967295";
                }
                default "0";
                description "Shutdown";
              }
              leaf ctype {
                type uint32 {
                  range "0..4294967295";
                }
                default "0";
                description "CType";
              }
              leaf card-state-string {
                type string;
                description "Card State String";
              }
              leaf monitor {
                type uint32 {
                  range "0..4294967295";
                }
                default "0";
                description "Monitor";
              }
            }
            leaf name {
              type xr:Cisco-ios-xr-string;
              description "Card";
            }
          }
        }
      }
    }

    container memory {
      description "Memory";

      container racks {
        description "RackTable";

        list rack {
          key "name";
          description "Rack name";

          container node-ids {
            description "NodeIDTable";

            list node-id {
              key "name";
              description "Inventory Admin Mempool Data  Bag";
              leaf name {
                type xr:Cisco-ios-xr-string;
                description "nodeid";
              }
              uses INV-ADMIN-MEMPOOL-DATA;
            }
          }
          leaf name {
            type xr:Cisco-ios-xr-string;
            description "Rack name";
          }
        }
      }
    }
  }
}
