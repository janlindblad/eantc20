module Cisco-IOS-XR-freqsync-oper {

  /*** NAMESPACE / PREFIX DEFINITION ***/

  namespace "http://cisco.com/ns/yang/Cisco-IOS-XR-freqsync-oper";


  prefix "Cisco-IOS-XR-freqsync-oper";

  /*** LINKAGE (IMPORTS / INCLUDES) ***/

  import Cisco-IOS-XR-types { prefix "xr"; }

  import Cisco-IOS-XR-freqsync-datatypes { prefix "dt1"; }

  include Cisco-IOS-XR-freqsync-oper-sub1 {
    revision-date 2017-10-20;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR freqsync package operational data.

     This module contains definitions
     for the following management objects:
       frequency-synchronization: Frequency Synchronization
         operational data

     Copyright (c) 2013-2018 by Cisco Systems, Inc.
     All rights reserved.";

  revision "2017-10-20" {
    description
      "Combined selection point info from FSYNC-SP-INFO in FSYNC-SP-INFO-V2";
  }

  revision "2015-11-09" {
    description
      "IOS XR 6.0 revision.";
  }

  typedef Fsync-stream {
    type enumeration {
      enum local {
        value 1;
        description "Stream input from a local source";
      }
      enum selection-point {
        value 2;
        description
          "Stream input from a selection point on a remote
          node";
      }
    }
    description "Fsync stream";
  }
  typedef Fsync-source {
    type enumeration {
      enum ethernet {
        value 1;
        description "An ethernet interface";
      }
      enum sonet {
        value 2;
        description "A SONET interface";
      }
      enum clock {
        value 3;
        description "A clock interface";
      }
      enum internal {
        value 4;
        description "An internal clock";
      }
      enum ptp {
        value 5;
        description "A PTP clock";
      }
      enum satellite-access {
        value 6;
        description "A satellite access interface clock";
      }
      enum ntp {
        value 7;
        description "An NTP clock";
      }
    }
    description "Fsync source";
  }

  container frequency-synchronization {
    config false;
    description "Frequency Synchronization operational data";

    container global-nodes {
      description "Table for global node-specific operational data";

      list global-node {
        key "node";
        description
          "Global node-specific data for a particular node";

        container clock-interface-selection-back-traces {
          description
            "Selection backtrace operational data for
            clock-interfaces";

          list clock-interface-selection-back-trace {
            key "clock-type id";
            description
              "Selection backtrace operational data for a
              particular clock-interface or GNSS receiver";
            leaf clock-type {
              type dt1:Fsync-clock;
              description "Clock type";
            }
            leaf id {
              type uint32;
              description
                "Clock ID (port number for clock interfaces,
                receiver number for GNSS receivers";
            }
            uses FSYNC-SELECTION-BACKTRACE-INFO;
          }
        }

        container clock-interface-selection-forward-traces {
          description
            "Selection forwardtrace operational data for
            clock-interfaces";

          list clock-interface-selection-forward-trace {
            key "clock-type port";
            description
              "Selection forwardtrace operational data for a
              particular clock-interface";
            leaf clock-type {
              type dt1:Fsync-clock;
              description "Clock type";
            }
            leaf port {
              type uint32;
              description "Clock port";
            }
            uses FSYNC-SELECTION-FORWARDTRACE-INFO;
          }
        }

        container time-of-day-back-trace {
          description
            "Selection backtrace operational data for
            time-of-day on a particular node";
          uses FSYNC-SELECTION-BACKTRACE-INFO;
        }

        container ntp-selection-forward-trace {
          description
            "Selection forwardtrace operational data for a
            NTP clock";
          uses FSYNC-SELECTION-FORWARDTRACE-INFO;
        }

        container ptp-selection-forward-trace {
          description
            "Selection forwardtrace operational data for a
            PTP clock";
          uses FSYNC-SELECTION-FORWARDTRACE-INFO;
        }
        leaf node {
          type xr:Node-id;
          description "Node";
        }
      }
    }

    container global-interfaces {
      description "Table for global interface operational data";

      list global-interface {
        key "interface-name";
        description
          "Global interface information for a particular
          interface";

        container interface-selection-forward-trace {
          description
            "Selection forwardtrace operational data for a
            particular interface";
          uses FSYNC-SELECTION-FORWARDTRACE-INFO;
        }

        container interface-selection-back-trace {
          description
            "Selection backtrace operational data for a
            particular interface";
          uses FSYNC-SELECTION-BACKTRACE-INFO;
        }
        leaf interface-name {
          type xr:Interface-name;
          description "Interface name";
        }
      }
    }

    container summary {
      description "Summary operational data";
      uses FSYNC-SUMMARY-INFO;
    }

    container interface-datas {
      description "Table for interface operational data";

      list interface-data {
        key "interface-name";
        description "Operational data for a particular interface";
        leaf interface-name {
          type xr:Interface-name;
          description "Interface name";
        }
        uses FSYNC-IF-INFO-V2;
      }
    }

    container nodes {
      description "Table for node-specific operational data";

      list node {
        key "node";
        description "Node-specific data for a particular node";

        container ntp-data {
          description "NTP operational data";
          uses FSYNC-NTP-INFO-V2;
        }

        container selection-point-datas {
          description "Selection point data table";

          list selection-point-data {
            key "selection-point";
            description
              "Operational data for a given selection point";
            leaf selection-point {
              type uint32;
              description "Selection point ID";
            }
            uses FSYNC-SP-INFO-V2;
          }
        }

        container configuration-errors {
          description "Configuration error operational data";
          uses FSYNC-CONFIG-ERRORS-INFO;
        }

        container ptp-data {
          description "PTP operational data";
          uses FSYNC-PTP-INFO-V2;
        }

        container ssm-summary {
          description "SSM operational data";
          uses FSYNC-SSM-INFO;
        }

        container detailed-clock-datas {
          description "Table for detailed clock operational data";

          list detailed-clock-data {
            key "clock-type id";
            description
              "Detailed operational data for a particular
              clock";
            leaf clock-type {
              type dt1:Fsync-clock;
              description "Clock type";
            }
            leaf id {
              type uint32;
              description
                "Clock ID (port number for clock interfaces,
                receiver number for GNSS receivers";
            }
            uses FSYNC-CLOCK-INFO-V2;
          }
        }

        container clock-datas {
          description "Table for clock operational data";

          list clock-data {
            key "clock-type id";
            description "Operational data for a particular clock";
            leaf clock-type {
              type dt1:Fsync-clock;
              description "Clock type";
            }
            leaf id {
              type uint32;
              description
                "Clock ID (port number for clock interfaces,
                receiver number for GNSS receivers";
            }
            uses FSYNC-CLOCK-INFO-V2;
          }
        }

        container selection-point-inputs {
          description
            "Table for selection point input operational
            data";

          list selection-point-input {
            description
              "Operational data for a particular selection
              point input";
            leaf selection-point {
              type uint32;
              description "Selection point ID";
            }
            leaf stream-type {
              type Fsync-stream;
              description "Type of stream";
            }
            leaf source-type {
              type Fsync-source;
              description "Type of source";
            }
            leaf interface {
              type xr:Interface-name;
              description "Interface";
            }
            leaf clock-port {
              type uint32;
              description "Clock port";
            }
            leaf last-node {
              type xr:Node-id;
              description "Last node for a selection point stream";
            }
            leaf last-selection-point {
              type uint32;
              description
                "Last selection point for a selection point
                stream";
            }
            leaf output-id {
              type uint32;
              description "Output ID for a selection point stream";
            }
            uses FSYNC-SP-INPUT-INFO;
          }
        }
        leaf node {
          type xr:Node-id;
          description "Node";
        }
      }
    }
  }
}
