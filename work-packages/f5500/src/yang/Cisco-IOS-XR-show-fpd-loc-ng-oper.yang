module Cisco-IOS-XR-show-fpd-loc-ng-oper {

  /*** NAMESPACE / PREFIX DEFINITION ***/

  namespace "http://cisco.com/ns/yang"+
    "/Cisco-IOS-XR-show-fpd-loc-ng-oper";


  prefix "Cisco-IOS-XR-show-fpd-loc-ng-oper";

  /*** LINKAGE (IMPORTS / INCLUDES) ***/

  import Cisco-IOS-XR-types { prefix "xr"; }

  include Cisco-IOS-XR-show-fpd-loc-ng-oper-sub1 {
    revision-date 2017-05-01;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR show-fpd-loc-ng package operational data.

     This module contains definitions
     for the following management objects:
       show-fpd: Show hw-module fpd

     Copyright (c) 2013-2018 by Cisco Systems, Inc.
     All rights reserved.";

  revision "2017-05-01" {
    description
      "Fixing backward compatibility error in module.";
  }

  revision "2015-11-09" {
    description
      "IOS XR 6.0 revision.";
  }


  container show-fpd {
    config false;
    description "Show hw-module fpd";

    container locations {
      description "location table";

      list location {
        key "location-name";
        description "location";

        container fpds {
          description "Display fpds on given locations";

          list fpd {
            key "fpd-name";
            description "Display fpds detail";
            leaf fpd-name {
              type xr:Cisco-ios-xr-string {
                length "1..32";
              }
              description "Fpd Name";
            }
            uses FPD-INFO-LIST;
          }
        }
        leaf location-name {
          type xr:Cisco-ios-xr-string {
            length "1..32";
          }
          description "Fpd location";
        }
      }
    }

    container hw-module-fpd {
      description
        "Display fpds on all locations -show hw-module
        fpd";
      uses FPD-INFO-LIST;
    }

    container help-locations {
      description "help location table";

      list help-location {
        key "location-name";
        description "location";

        container help-fpd {
          description "Display fpds on given locations";
          uses FPD-LOC-INFO-LIST;
        }
        leaf location-name {
          type xr:Cisco-ios-xr-string {
            length "1..32";
          }
          description "Fpd location";
        }
      }
    }

    container hw-module-fpd-help-fpd {
      description "Display help-fpd -show hw-module fpd help-fpd";
      uses FPD-LOC-INFO-LIST;
    }

    container package {
      description "gets fpd package info";
      uses FPD-PKG-INFO-LIST;
    }

    container location-help {
      description "fpd upgradable locations";
      uses FPD-SHOW-LOCATION-NAME-LIST;
    }
  }
}
