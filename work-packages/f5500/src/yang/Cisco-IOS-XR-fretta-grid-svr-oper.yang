module Cisco-IOS-XR-fretta-grid-svr-oper {

  /*** NAMESPACE / PREFIX DEFINITION ***/

  namespace "http://cisco.com/ns/yang"+
    "/Cisco-IOS-XR-fretta-grid-svr-oper";


  prefix "Cisco-IOS-XR-fretta-grid-svr-oper";

  /*** LINKAGE (IMPORTS / INCLUDES) ***/

  import Cisco-IOS-XR-types { prefix "xr"; }

  include Cisco-IOS-XR-fretta-grid-svr-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR fretta-grid-svr package operational data.

     This module contains definitions
     for the following management objects:
       grid: GRID operational data

     Copyright (c) 2013-2018 by Cisco Systems, Inc.
     All rights reserved.";

  revision "2015-11-09" {
    description
      "IOS XR 6.0 revision.";
  }


  container grid {
    config false;
    description "GRID operational data";

    container nodes {
      description "Table of nodes";

      list node {
        key "node-name";
        description "Operational data for a particular node";

        container client-xr {
          description "GRID Client Table";

          list client {
            key "client-name";
            description "GRID Client Database";
            leaf client-name {
              type xr:Cisco-ios-xr-string;
              description "Client name";
            }
            uses GRID-SVR-SHOW-CLIENT;
          }
        }

        container clients {
          description "GRID Client Consistency Check";

          list client {
            key "client-name";
            description "GRID Client Consistency Check";
            leaf client-name {
              type xr:Cisco-ios-xr-string;
              description "Client name";
            }
            uses GRID-SVR-SHOW-CLIENT;
          }
        }
        leaf node-name {
          type xr:Node-id;
          description "Node ID";
        }
      }
    }
  }
}
