module Cisco-IOS-XR-ikev2-oper {

  /*** NAMESPACE / PREFIX DEFINITION ***/

  namespace "http://cisco.com/ns/yang/Cisco-IOS-XR-ikev2-oper";


  prefix "Cisco-IOS-XR-ikev2-oper";

  /*** LINKAGE (IMPORTS / INCLUDES) ***/

  import ietf-inet-types { prefix "inet"; }

  import Cisco-IOS-XR-types { prefix "xr"; }

  include Cisco-IOS-XR-ikev2-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ikev2 package operational data.

     This module contains definitions
     for the following management objects:
       ik-ev2: IKEv2 operational data

     Copyright (c) 2013-2018 by Cisco Systems, Inc.
     All rights reserved.";

  revision "2015-11-09" {
    description
      "IOS XR 6.0 revision.";
  }


  grouping IP {
    description "Common node of local-v4, remote-v4";

    list ip {
      key "address";
      description "IKEv2 SA data based on address";
      leaf address {
        type inet:ipv4-address-no-zone;
        description "Address";
      }
      uses IKEV2-EDM-SA-DB;
    }
  }

  container ik-ev2 {
    config false;
    description "IKEv2 operational data";

    container nodes {
      description "Per node IKEv2 operational data";

      list node {
        key "node-name";
        description "IKEv2 operational data for a particular node";

        container session {
          description "IKEv2 Session data";
          uses IKEV2-EDM-SESSION-DB;
        }

        container sa {
          description "IKEv2 SA data";

          container local-v4 {
            description "IKEv2 SA lookup on local IP";
            uses IP;
          }

          container remote-v4 {
            description "IKEv2 SA lookup on remote IP";
            uses IP;
          }

          container all {
            description "IKEv2 SA all data";
            uses IKEV2-EDM-SA-DB;
          }
        }

        container policies {
          description "IKEv2 policies on this node";

          list policy {
            key "name";
            description "IKEv2 policy data";
            leaf name {
              type xr:Cisco-ios-xr-string {
                length "1..32";
              }
              description "Name of the IKEv2 policy";
            }
            uses IKEV2-EDM-POLICY;
          }
        }

        container proposals {
          description "IKEv2 proposals on this node";

          list proposal {
            key "name";
            description "IKEv2 proposal data";
            leaf name {
              type xr:Cisco-ios-xr-string {
                length "1..32";
              }
              description "Name of the IKEv2 proposal";
            }
            uses IKEV2-EDM-PROPOSAL;
          }
        }

        container profiles {
          description "IKEv2 profiles on this node";

          list profile {
            key "name";
            description "IKEv2 profile data";
            leaf name {
              type xr:Cisco-ios-xr-string {
                length "1..32";
              }
              description "Name of the IKEv2 profile";
            }
            uses IKEV2-EDM-PROFILE;
          }
        }

        container keyrings {
          description "IKEv2 keyrings on this node";

          list keyring {
            key "name";
            description "IKEv2 keyring data";
            leaf name {
              type xr:Cisco-ios-xr-string {
                length "1..32";
              }
              description "Name of the IKEv2 keyring";
            }
            uses IKEV2-EDM-KEYRING;
          }
        }
        leaf node-name {
          type xr:Node-id;
          description "The identifier for the node";
        }
      }
    }
  }
}
