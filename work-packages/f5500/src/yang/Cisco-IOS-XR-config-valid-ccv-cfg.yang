module Cisco-IOS-XR-config-valid-ccv-cfg {

  /*** NAMESPACE / PREFIX DEFINITION ***/

  namespace "http://cisco.com/ns/yang"+
    "/Cisco-IOS-XR-config-valid-ccv-cfg";


  prefix "Cisco-IOS-XR-config-valid-ccv-cfg";

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR config-valid-ccv package configuration.

     This module contains definitions
     for the following management objects:
       configurationvalidation: Configuration for the Configuration
         Validation feature

     Copyright (c) 2013-2018 by Cisco Systems, Inc.
     All rights reserved.";

  revision "2015-11-09" {
    description
      "IOS XR 6.0 revision.";
  }

  typedef Failure-action {
    type enumeration {
      enum report {
        value 1;
        description "Report this failure type";
      }
    }
    description "Failure action";
  }
  typedef Failure {
    type enumeration {
      enum unsupported {
        value 0;
        description "Unsupported failure type";
      }
    }
    description "Failure";
  }

  container configurationvalidation {
    description
      "Configuration for the Configuration Validation
      feature";

    container failure-type-actions {
      description "Table for failure type actions";

      list failure-type-action {
        key "failure";
        description "Failure type action configuration";
        leaf action {
          type Failure-action;
          description "Action configuration for this failure type";
        }
        leaf failure {
          type Failure;
          description "Failure type";
        }
      }
    }
    leaf enable {
      type empty;
      description "Enable configuration validation";
    }
  }
}
