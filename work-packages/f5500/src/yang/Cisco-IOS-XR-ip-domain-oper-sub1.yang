submodule Cisco-IOS-XR-ip-domain-oper-sub1 {

  belongs-to Cisco-IOS-XR-ip-domain-oper {
    prefix Cisco-IOS-XR-ip-domain-oper-sub1;
  }

  /*** LINKAGE (IMPORTS / INCLUDES) ***/

  import ietf-inet-types { prefix "inet"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ip-domain package operational data.

     Copyright (c) 2013-2018 by Cisco Systems, Inc.
     All rights reserved.";

  revision "2017-05-01" {
    description
      "Fixing backward compatibility error in module.";
  }

  revision "2015-09-29" {
    description
      "IOS XR 6.0.0 revision.";
  }

  revision "2015-01-07" {
    description
      "IOS XR 5.3.1 revision.";
  }

  typedef String1 {
    type string {
      length "0..256";
    }
    description "String1";
  }
  typedef Domain-ipv6-address {
    type inet:ipv6-address;
    description "Domain ipv6 address";
  }
  identity Host-address-base {
    description "Base identity for Host-address";
  }
  identity ipv4 {
    base Host-address-base;
    description "IPv4 family address";
  }
  identity ipv6 {
    base Host-address-base;
    description "IPv6 family address";
  }
  typedef Host-address {
    type identityref {
      base Host-address-base;
    }
    description "Host Address Type";
  }
  typedef Server-domain-lkup {
    type enumeration {
      enum static-mapping {
        value 0;
        description "Static mapping";
      }
      enum domain-service {
        value 1;
        description "Domain service";
      }
    }
    description "Domain look up";
  }

  grouping DOMAIN-HOST-ALIAS-BAG {
    description "Domain host alias";
    leaf-list host-alias {
      type String1;
      description "Host alias list";
    }
  }

  grouping DOMAIN-SH-HOSTS-BAG {
    description "Domain hosts";

    container host-alias-list {
      description "Host alias";
      uses DOMAIN-HOST-ALIAS-BAG;
    }
    leaf af-name {
      type Host-address;
      description "Address type";
    }
    leaf age {
      type uint16;
      units "hour";
      description "Age in hours";
    }

    list host-address {
      description "Host address list";
      uses DOMAIN-IPADDRESS;
    }
  }

  grouping DOMAIN-IPADDRESS {
    description "IP Address";
    leaf af-name {
      type Host-address;
      description "AFName";
    }
    leaf ipv4-address {
      when "../af-name = 'ipv4'" {
        description "../AFName = 'IPv4'";
      }
      type inet:ipv4-address;
      description "IPv4 address";
    }
    leaf ipv6-address {
      when "../af-name = 'ipv6'" {
        description "../AFName = 'IPv6'";
      }
      type Domain-ipv6-address;
      description "IPv6 address";
    }
  }

  grouping DOMAIN-SH-SERVER-BAG {
    description "Domain servers";
    leaf domain-lookup {
      type Server-domain-lkup;
      description "Domain lookup";
    }
    leaf domain-name {
      type string {
        length "0..256";
      }
      description "Domain name";
    }
    leaf-list domain {
      type String1;
      description "Domain list";
    }

    list server-address {
      description "Server address list";
      uses DOMAIN-IPADDRESS;
    }
  }
}
