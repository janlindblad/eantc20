module Cisco-IOS-XR-procfind-oper {

  /*** NAMESPACE / PREFIX DEFINITION ***/

  namespace "http://cisco.com/ns/yang/Cisco-IOS-XR-procfind-oper";


  prefix "Cisco-IOS-XR-procfind-oper";

  /*** LINKAGE (IMPORTS / INCLUDES) ***/

  import Cisco-IOS-XR-types { prefix "xr"; }

  include Cisco-IOS-XR-procfind-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR procfind package operational data.

     This module contains definitions
     for the following management objects:
       proc-distribution: Process distribution information

     Copyright (c) 2013-2018 by Cisco Systems, Inc.
     All rights reserved.";

  revision "2015-11-09" {
    description
      "IOS XR 6.0 revision.";
  }


  container proc-distribution {
    config false;
    description "Process distribution information";

    container nodes {
      description "List of nodes";

      list node {
        key "node-name";
        description "Process distribution information per node";
        leaf node-name {
          type xr:Node-id;
          description "The node name";
        }

        list process {
          key "proc-name";
          description "Process distribution information";
          leaf proc-name {
            type string;
            description "Process Name";
          }

          list filter-type {
            key "filter-type";
            description "Process distribution information";
            leaf filter-type {
              type string;
              description "Filter Type";
            }
            uses PROCFIND-PROC;
          }
        }
      }
    }
  }
}
