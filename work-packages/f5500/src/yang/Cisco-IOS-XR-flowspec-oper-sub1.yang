submodule Cisco-IOS-XR-flowspec-oper-sub1 {

  belongs-to Cisco-IOS-XR-flowspec-oper {
    prefix Cisco-IOS-XR-flowspec-oper-sub1;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR flowspec package operational data.

     Copyright (c) 2013-2018 by Cisco Systems, Inc.
     All rights reserved.";

  revision "2015-11-09" {
    description
      "IOS XR 6.0 revision.";
  }

  typedef Fs-mgr-client-state {
    type enumeration {
      enum dormant {
        description "Dormant";
      }
      enum connected {
        description "Connected";
      }
      enum replay {
        description "Replay";
      }
      enum unconfigured {
        description "Unconfigured";
      }
    }
    description "FlowSpec manager client state";
  }

  grouping FS-MGR-FLOW-STATS-CTRS {
    description "Flowspec class stats counters.";
    leaf packets {
      type uint64;
      description "Number of packets";
    }
    leaf bytes {
      type uint64;
      units "byte";
      description "Number of bytes";
    }
  }

  grouping FS-MGR-FLOW-STATS {
    description "Flowspec class classified and drop stats.";

    container classified {
      description "Classified statistics";
      uses FS-MGR-FLOW-STATS-CTRS;
    }

    container dropped {
      description "Drop statistics";
      uses FS-MGR-FLOW-STATS-CTRS;
    }
  }

  grouping FS-MGR-NLRI {
    description "FlowSpec manager NLRI information";

    container flow-statistics {
      description "Flow statistics";
      uses FS-MGR-FLOW-STATS;
    }
  }

  grouping FS-MGR-TBL-SUMMARY {
    description "FlowSpec manager table summary information";
    leaf total-flows {
      type uint32;
      description "Total number of flows";
    }
    leaf service-policies {
      type uint32;
      description "Total number of attached service policies";
    }
    leaf local-install-enabled {
      type boolean;
      description "Local installation of flowspec rules";
    }
  }

  grouping FS-MGR-SUMMARY {
    description "FlowSpec manager summary information";
    leaf vrfafi-tables {
      type uint32;
      description "Total VRF+AFI tables";
    }
    leaf flows {
      type uint32;
      description "Total flows";
    }
  }

  grouping FS-MGR-CLIENT {
    description "FlowSpec manager client information";
    leaf client-state {
      type Fs-mgr-client-state;
      description "State of FS client";
    }
    leaf client-flows {
      type uint32;
      description "Number of client flows";
    }
  }
}
