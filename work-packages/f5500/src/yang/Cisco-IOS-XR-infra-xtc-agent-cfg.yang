module Cisco-IOS-XR-infra-xtc-agent-cfg {

  /*** NAMESPACE / PREFIX DEFINITION ***/

  namespace "http://cisco.com/ns/yang"+
    "/Cisco-IOS-XR-infra-xtc-agent-cfg";


  prefix "Cisco-IOS-XR-infra-xtc-agent-cfg";

  /*** LINKAGE (IMPORTS / INCLUDES) ***/

  import Cisco-IOS-XR-types { prefix "xr"; }

  import Cisco-IOS-XR-segment-routing-ms-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-xtc-agent package configuration.

     Copyright (c) 2013-2018 by Cisco Systems, Inc.
     All rights reserved.";

  revision "2018-11-28" {
    description
      "Added new SR-TE timers configuration.";
  }

  revision "2018-07-25" {
    description
      "Removed incorrect mandatory specifications.";
  }

  revision "2018-07-07" {
    description
      "Modified the allowed range for policy path weight.";
  }

  revision "2018-07-03" {
    description
      "Added TE-latency algorithm configuration.";
  }

  revision "2018-01-31" {
    description
      "Added BW configuration option for On Demand Color policy.";
  }

  revision "2017-12-21" {
    description
      "Added BW configuration option for SR policy.";
  }

  revision "2017-09-30" {
    description
      "Ensure propagation of MDA mandatory state to YANG model.";
  }

  revision "2017-09-11" {
    description
      "Initial version";
  }

  revision "2015-11-09" {
    description
      "IOS XR 6.0 revision.";
  }

  typedef Xtc-metric-value {
    type enumeration {
      enum relative {
        value 1;
        description "Relative metric value";
      }
      enum absolute {
        value 2;
        description "Absolute metric value";
      }
    }
    description "Xtc metric value";
  }
  typedef Xtc-affinity-rule {
    type enumeration {
      enum affinity-include-all {
        value 0;
        description "Include-all affinity rule";
      }
      enum affinity-exclude-any {
        value 1;
        description "Exclude-any affinity rule";
      }
      enum affinity-include-any {
        value 2;
        description "Include-any affinity rule";
      }
    }
    description "Xtc affinity rule";
  }

  grouping METRIC-MARGIN {
    description
      "Common node of metric,
      on-demand-color-dyn-mpls-metric";

    container metric-margin {
      description "Metric Margin";
      leaf value-type {
        type Xtc-metric-value;
        description "Metric margin type";
      }
      leaf absolute-value {
        when "../value-type = 'absolute'" {
          description "../ValueType = Absolute";
        }
        type uint32 {
          range "0..2147483647";
        }
        description "Absolute metric value";
      }
      leaf relative-value {
        when "../value-type = 'relative'" {
          description "../ValueType = Relative";
        }
        type uint32 {
          range "0..2147483647";
        }
        description "Relative metric value";
      }
    }
  }

  grouping ENABLE {
    description
      "Common node of traffic-engineering, policy,
      segment-list, candidate-paths, preference,
      path-info, metric, srte-interface, auto-route,
      on-demand-color, pcep";
    leaf enable {
      type empty;
      description "True only";
    }
  }

  grouping AFFINITY-RULE-TABLE {
    description
      "Common node of constraints,
      on-demand-color-dyn-mpls";

    container affinity-rules {
      description
        "SR path computation and verification affinity
        rules";

      list affinity-rule {
        key "rule";
        description
          "SR path computation and verification affinity
          rule";
        leaf rule {
          type Xtc-affinity-rule;
          description "Affinity rule type";
        }

        list affinity-name {
          key "affinity-name";
          description "Affinity rule name";
          leaf affinity-name {
            type xr:Cisco-ios-xr-string {
              length "1..32";
            }
            description "Affinity name";
          }
        }
      }
    }
  }

  grouping MAXIMUM-SID-DEPTH {
    description
      "Common node of traffic-engineering,
      on-demand-color";
    leaf maximum-sid-depth {
      type uint32 {
        range "1..255";
      }
      description "Maximum SID Depth Configuration";
    }
  }
}
