module Cisco-IOS-XR-sysadmin-tacacs-show-tacacs {
  namespace "http://www.cisco.com/ns/yang/Cisco-IOS-XR-sysadmin-tacacs-show-tacacs";
  prefix Cisco-IOS-XR-sysadmin-tacacs-show-tacacs;
  import tailf-common {
    prefix tailf;
  }
  import ietf-inet-types {
    prefix inet;
  }
  import Cisco-IOS-XR-sysadmin-tacacs-tacacs-server {
    prefix tacacs-server;
  }
  organization "Cisco Systems Inc.";
  contact
    "aaa-ng-tacacs-dev@cisco.com";

  description 
    "This module contains definitions
     for the Calvados model objects.

    This module defines yang model
for displaying tacacs+ server host info

    Copyright (c) 2012-2018 by Cisco Systems, Inc.
     All rights reserved.";
  revision 2017-05-10 {
    description
      "Namespace changed from show_tacacs to Cisco-IOS-XR-sysadmin-tacacs-show-tacacs";
  }


  typedef passwdStr {
    type tailf:md5-digest-string;
  }
  augment "/tacacs-server:tacacs-server" {
    container requests {
      config false;
      list ipv4 {
        key "addr port";
        leaf addr {
          description
            "Server IPv4 address";
          type inet:ip-address;
        }
        leaf port {
          description
            "Server Port";
          type inet:port-number;
        }
        leaf opens {
          description
            "Socket open count";
          type uint32;
        }
        leaf closes {
          description
            "Socket close count";
          type uint32;
        }
        leaf aborts {
          description
            "Socket abort count";
          type uint32;
        }
        leaf errors {
          description
            "Socket error count";
          type uint32;
        }
        leaf packets_in {
          description
            "Packets received count";
          type uint32;
        }
        leaf packets_out {
          description
            "Packets transmitted count";
          type uint32;
        }
      }
    }
  }
}
