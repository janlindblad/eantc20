module Cisco-IOS-XR-ip-iep-cfg {

  /*** NAMESPACE / PREFIX DEFINITION ***/

  namespace "http://cisco.com/ns/yang/Cisco-IOS-XR-ip-iep-cfg";


  prefix "Cisco-IOS-XR-ip-iep-cfg";

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-iep package configuration.

     This module contains definitions
     for the following management objects:
       ip-explicit-paths: IP Explicit Path config data

     Copyright (c) 2013-2018 by Cisco Systems, Inc.
     All rights reserved.";

  revision "2017-09-07" {
    description
      "Fixed type translation error.";
  }

  revision "2015-11-09" {
    description
      "IOS XR 6.0 revision.";
  }

  typedef Ip-iep-num {
    type enumeration {
      enum unnumbered {
        value 1;
        description "Unnumbered";
      }
      enum numbered {
        value 2;
        description "Numbered";
      }
    }
    description "Ip iep num";
  }
  typedef Ip-iep-hop {
    type enumeration {
      enum next-strict {
        value 2;
        description "NextStrict";
      }
      enum next-loose {
        value 3;
        description "NextLoose";
      }
      enum exclude {
        value 4;
        description "Exclude";
      }
      enum exclude-srlg {
        value 5;
        description "Exclude Shared Risk Link Group";
      }
      enum next-label {
        value 6;
        description "NextLabel";
      }
    }
    description "Ip iep hop";
  }
  typedef Ip-iep-path {
    type enumeration {
      enum identifier {
        value 1;
        description "Identifier";
      }
      enum name {
        value 2;
        description "Name";
      }
    }
    description "Ip iep path";
  }

  container ip-explicit-paths {
    description "IP Explicit Path config data";

    container paths {
      description "A list of explicit paths";

      list path {
        must "name or identifier" {
          description "Name or Identifier must be present.";
        }
        key "type";
        description "Config data for a specific explicit path";

        grouping PATH-CONTENT {
          description "PATH CONTENT";

          container hops {
            description "List of Hops";

            list hop {
              key "index-number";
              description "Hop Information";
              leaf index-number {
                type uint32 {
                  range "1..65535";
                }
                description "Index number";
              }
              leaf ip-address {
                when "../hop-type != 'next-label'" {
                  description "../HopType != NextLabel";
                }
                type inet:ipv4-address-no-zone;
                default "0.0.0.0";
                description "IP address of the hop";
              }
              leaf hop-type {
                type Ip-iep-hop;
                default "next-strict";
                description
                  "Include or exclude this hop in the path";
              }
              leaf if-index {
                when "../hop-type != 'next-label'" {
                  description "../HopType != NextLabel";
                }
                type uint32;
                default "0";
                description "Ifindex value";
              }
              leaf num-type {
                when "../hop-type != 'next-label'" {
                  description "../HopType != NextLabel";
                }
                type Ip-iep-num;
                default "numbered";
                description "Number type Numbered or Unnumbered";
              }
              leaf mpls-label {
                when "../hop-type = 'next-label'" {
                  description "../HopType = NextLabel";
                }
                type uint32 {
                  range "0..1048575";
                }
                description "MPLS Label";
              }
            }
          }
          leaf disable {
            type empty;
            description "Disable the explicit path";
          }
        }
        leaf type {
          type Ip-iep-path;
          description "Path type";
        }

        list name {
          when "../type = 'name'" {
            description "../Type = Name";
          }
          key "name";
          description "name";
          leaf name {
            type xr:Cisco-ios-xr-string;
            description "Path name";
          }
          uses PATH-CONTENT;
        }

        list identifier {
          when "../type = 'identifier'" {
            description "../Type = Identifier";
          }
          key "id";
          description "identifier";
          leaf id {
            type uint32 {
              range "1..65535";
            }
            description "Path identifier";
          }
          uses PATH-CONTENT;
        }
      }
    }
  }
}
