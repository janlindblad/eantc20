module Cisco-IOS-XR-infra-statsd-oper {

  /*** NAMESPACE / PREFIX DEFINITION ***/

  namespace "http://cisco.com/ns"+
    "/yang/Cisco-IOS-XR-infra-statsd-oper";


  prefix "Cisco-IOS-XR-infra-statsd-oper";

  /*** LINKAGE (IMPORTS / INCLUDES) ***/

  import Cisco-IOS-XR-types { prefix "xr"; }

  include Cisco-IOS-XR-infra-statsd-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-statsd package operational data.

     This module contains definitions
     for the following management objects:
       infra-statistics: Statistics Infrastructure

     Copyright (c) 2013-2018 by Cisco Systems, Inc.
     All rights reserved.";

  revision "2015-11-09" {
    description
      "IOS XR 6.0 revision.";
  }


  grouping DATA-RATE {
    description "Common node of latest, cache, total, interface";

    container data-rate {
      description "Datarate information";
      uses STATSDBAG-DATARATE;
    }
  }

  grouping PROTOCOL-TABLE {
    description "Common node of latest, cache, total, interface";

    container protocols {
      description "List of protocols";

      list protocol {
        key "protocol-name";
        description "Interface counters per protocol";
        leaf protocol-name {
          type xr:Cisco-ios-xr-string;
          description "Name of the protocol";
        }
        uses IFSTATSBAG-PROTO;
      }
    }
  }

  grouping INTERFACES-MIB-COUNTERS {
    description "Common node of latest, cache, total, interface";

    container interfaces-mib-counters {
      description
        "Set of interface counters as displayed by the
        InterfacesMIB";
      uses IFSTATSBAG-GENERIC;
    }
  }

  grouping GENERIC-COUNTERS {
    description "Common node of latest, cache, total, interface";

    container generic-counters {
      description "Generic set of interface counters";
      uses IFSTATSBAG-GENERIC;
    }
  }

  container infra-statistics {
    config false;
    description "Statistics Infrastructure";

    container interfaces {
      description "List of interfaces";

      list interface {
        key "interface-name";
        description "Statistics of an interface";

        container cache {
          description "Cached stats data of interfaces";
          uses PROTOCOL-TABLE;
          uses INTERFACES-MIB-COUNTERS;
          uses DATA-RATE;
          uses GENERIC-COUNTERS;
        }

        container latest {
          description "Latest stats data of interfaces";
          uses PROTOCOL-TABLE;
          uses INTERFACES-MIB-COUNTERS;
          uses DATA-RATE;
          uses GENERIC-COUNTERS;
        }

        container total {
          description "Total stats data of interfaces";
          uses PROTOCOL-TABLE;
          uses INTERFACES-MIB-COUNTERS;
          uses DATA-RATE;
          uses GENERIC-COUNTERS;
        }
        leaf interface-name {
          type xr:Interface-name;
          description "Name of the interface";
        }
        uses PROTOCOL-TABLE;
        uses INTERFACES-MIB-COUNTERS;
        uses DATA-RATE;
        uses GENERIC-COUNTERS;
      }
    }
  }
}
