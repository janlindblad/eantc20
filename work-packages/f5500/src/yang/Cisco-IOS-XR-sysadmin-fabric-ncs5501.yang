module Cisco-IOS-XR-sysadmin-fabric-ncs5501 {
  namespace "http://www.cisco.com/ns/yang/Cisco-IOS-XR-sysadmin-fabric-ncs5501";
  prefix Cisco-IOS-XR-sysadmin-fabric-ncs5501;
  import Cisco-IOS-XR-sysadmin-fabric-mgr-fgid {
    prefix fabric-fgid;
  }

  organization "Cisco Systems, Inc.";

  contact
    "Cisco Systems, Inc.
     Customer Service

     Postal: 170 West Tasman Drive
     San Jose, CA 95134

     Tel: +1 800 553-NETS

     E-mail: cs-yang@cisco.com";

  description 
    "This module contains definitions
     for the Calvados model objects.

    Copyright (c) 2012-2018 by Cisco Systems, Inc.
     All rights reserved.";
  revision 2017-05-01 {
    description
      "Namespace change to comply with Cisco guidelines on namespace";
  }


  grouping fabric {
    container fabric {
      description
        "Fabric resource commands";
      container oper {
        config false;
        uses fabric-fgid:fgid;
      }
    }
  }
}
