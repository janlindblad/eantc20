module Cisco-IOS-XR-man-ipsla-oper {

  /*** NAMESPACE / PREFIX DEFINITION ***/

  namespace "http://cisco.com/ns/yang/Cisco-IOS-XR-man-ipsla-oper";


  prefix "Cisco-IOS-XR-man-ipsla-oper";

  /*** LINKAGE (IMPORTS / INCLUDES) ***/

  import ietf-inet-types { prefix "inet"; }

  import Cisco-IOS-XR-types { prefix "xr"; }

  include Cisco-IOS-XR-man-ipsla-oper-sub3 {
    revision-date 2015-11-09;
  }

  include Cisco-IOS-XR-man-ipsla-oper-sub2 {
    revision-date 2015-11-09;
  }

  include Cisco-IOS-XR-man-ipsla-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR man-ipsla package operational data.

     This module contains definitions
     for the following management objects:
       ipsla: IPSLA operational data

     Copyright (c) 2013-2018 by Cisco Systems, Inc.
     All rights reserved.";

  revision "2015-11-09" {
    description
      "IOS XR 6.0 revision.";
  }

  typedef Ipsla-hour-index {
    type uint32;
    description "Ipsla hour index";
  }
  typedef Ipsla-operation-id {
    type uint32;
    description "Ipsla operation id";
  }
  typedef Ipsla-distribution-index {
    type uint32;
    description "Ipsla distribution index";
  }
  typedef Ipsla-bucket-index {
    type uint32;
    description "Ipsla bucket index";
  }
  typedef Ipsla-lsp-monitor-id {
    type uint32;
    description "Ipsla lsp monitor id";
  }
  typedef Ipsla-lpd-path-index {
    type uint32;
    description "Ipsla lpd path index";
  }
  typedef Ipsla-hop-index {
    type uint32;
    description "Ipsla hop index";
  }
  typedef Ipsla-life-index {
    type uint32;
    description "Ipsla life index";
  }
  typedef Ipsla-path-index {
    type uint32;
    description "Ipsla path index";
  }
  typedef Ipsla-sample-index {
    type uint32;
    description "Ipsla sample index";
  }
  typedef Ipsla-enhanced-interval {
    type uint32;
    description "Ipsla enhanced interval";
  }

  grouping DISTRIBUTION-INTERVAL-TABLE {
    description "Common node of target, hop";

    container distribution-intervals {
      description
        "Table of distribution intervals for a particular
        hop";

      list distribution-interval {
        key "distribution-index";
        description
          "1-hour aggregated statistics for a hop in a
          path-enabled operation";
        leaf distribution-index {
          type Ipsla-distribution-index;
          description "Distribution Interval";
        }
        uses IPSLA-GLOBAL-STATS-BAG;
      }
    }
  }

  container ipsla {
    config false;
    description "IPSLA operational data";

    container mpls-data {
      description "MPLS operational data";

      container lsp-monitors {
        description "List of MPLS LSP Monitor instances";

        list lsp-monitor {
          key "monitor-id";
          description "Operational data for MPLS LSP Monitor";

          container state {
            description "Operational state of MPLS LSP Monitor";
            uses IPSLA-MPLSLM-STATE-BAG;
          }

          container operations {
            description "List of operations in MPLS LSP Monitor";

            list operation {
              key "operation-id";
              description "Operation created in MPLS LSP Monitor";

              container state {
                description
                  "Operational state of the created operation";
                uses IPSLA-MPLSLM-OP-STATE-BAG;
              }

              container lpd-paths {
                description
                  "List of LPD paths in MPLS LPD group
                  operation";

                list lpd-path {
                  key "path-index";
                  description
                    "Operational state of LPD path in MPLS LSP
                    Group operation";
                  leaf path-index {
                    type Ipsla-lpd-path-index;
                    description "LPD path index";
                  }
                  uses IPSLA-MPLSLM-OP-PATH-STATE-BAG;
                }
              }
              leaf operation-id {
                type Ipsla-operation-id;
                description "Operation ID";
              }
            }
          }

          container scan-queues {
            description
              "List of Scan Queue entries in MPLS LSP
              Monitor";

            list scan-queue {
              key "address";
              description
                "Provider Edge(PE) addition or deletion
                requests in Scan Queue";
              leaf address {
                type inet:ipv4-address-no-zone;
                description "Nexthop Address";
              }
              uses IPSLA-MPLSLM-SCAN-QUEUE-BAG;
            }
          }
          leaf monitor-id {
            type Ipsla-lsp-monitor-id;
            description "Monitor ID";
          }
        }
      }

      container discovery {
        description "Provider Edge(PE) discovery operational data";

        container vpn {
          description "L3 VPN PE discovery operational data";

          container state {
            description "Operational state of PE discovery";
            uses IPSLA-DISCOVERY-STATE-BAG;
          }

          container nexthops {
            description
              "List of nexthop addresses for remote PE
              routers";

            list nexthop {
              key "address";
              description "Nexthop address for remote PE router";

              container vrfs {
                description "List of VRFs for the nexthop address";

                list vrf {
                  key "vrf-name";
                  description
                    "VRF information of the nexthop address";
                  leaf vrf-name {
                    type xr:Cisco-ios-xr-string {
                      length "1..32";
                    }
                    description "VRF Name";
                  }
                  uses IPSLA-DISCOVERY-VRF-BAG;
                }
              }

              container prefix {
                description "Prefix of the nexthop address";
                uses IPSLA-DISCOVERY-PREFIX-BAG;
              }
              leaf address {
                type inet:ipv4-address-no-zone;
                description "Nexthop Address";
              }
            }
          }
        }
      }
    }

    container responder {
      description "Data from responder probe handling";

      container ports {
        description "Statistics maintained by responder";

        list port {
          key "port";
          description "Port data";
          leaf port {
            type inet:port-number;
            description "Port";
          }
          uses IPSLA-RESP-PORT-INFO-BAG;
        }
      }
    }

    container operation-data {
      description "Operations data";

      container operations {
        description "Configured operations";

        list operation {
          key "operation-id";
          description "Operational data for an operation";

          container common {
            description "Common data for all operation types";

            container operational-state {
              description "Operational state for an operation";
              uses IPSLA-OPER-STATE-BAG;
            }
          }

          container lpd {
            description
              "LPD operational data of MPLS LSP group
              operation";

            container statistics {
              description "Statistics collected for LPD group";

              container latest {
                description
                  "LPD statistics collected during the last
                  sampling cycle";

                container target {
                  description "Latest statistics of LPD group";
                  uses IPSLA-LPD-STATS-BAG;
                }
              }

              container aggregated {
                description
                  "Statistics aggregated for LPD group
                  collected over time intervals";

                container hours {
                  description
                    "Table of LPD statistics aggregated over
                    1-hour intervals";

                  list hour {
                    key "hour-index";
                    description
                      "LPD statistics aggregated for a 1-hour
                      interval";
                    leaf hour-index {
                      type Ipsla-hour-index;
                      description "Hour Index";
                    }
                    uses IPSLA-LPD-STATS-BAG;
                  }
                }
              }
            }

            container status {
              description "Operational status of LPD group";

              container lpd-paths {
                description "Operational path state in LPD group";

                list lpd-path {
                  key "path-index";
                  description
                    "Current operational path state in LPD
                    group";
                  leaf path-index {
                    type Ipsla-lpd-path-index;
                    description "LPD path index";
                  }
                  uses IPSLA-LPD-PATH-STATE-BAG;
                }
              }

              container state {
                description "Operational status of LPD group";
                uses IPSLA-LPD-STATE-BAG;
              }
            }
          }

          container history {
            description "Historical data for an operation";

            container path {
              description
                "Historical data with multiple hops along the
                path";

              container lifes {
                description "Tables of lives for an operation";

                list life {
                  key "life-index";
                  description
                    "History data for a particular life of the
                    operation";

                  container buckets {
                    description
                      "Table of history buckets (samples) for a
                      particular operation";

                    list bucket {
                      key "bucket-index";
                      description "History bucket for an operation";

                      container samples {
                        description
                          "Table of samples for a particular cycle";

                        list sample {
                          key "sample-index";
                          description
                            "Data sample for particular cycle";
                          leaf sample-index {
                            type Ipsla-sample-index;
                            description "Sample Index";
                          }
                          uses IPSLA-HISTORY-BAG;
                        }
                      }
                      leaf bucket-index {
                        type Ipsla-bucket-index;
                        description "Bucket Index";
                      }
                    }
                  }
                  leaf life-index {
                    type Ipsla-life-index;
                    description "Life Index";
                  }
                }
              }
            }

            container target {
              description
                "Historical data for the destination node";

              container lifes {
                description "Tables of lives for an operation";

                list life {
                  key "life-index";
                  description
                    "Operational data for a particular life of
                    the operation";

                  container buckets {
                    description
                      "Table of history buckets (samples) for a
                      particular operation";

                    list bucket {
                      key "bucket-index";
                      description "History bucket for an operation";
                      leaf bucket-index {
                        type Ipsla-bucket-index;
                        description "Bucket Index";
                      }
                      uses IPSLA-HISTORY-BAG;
                    }
                  }
                  leaf life-index {
                    type Ipsla-life-index;
                    description "Life Index";
                  }
                }
              }
            }
          }

          container statistics {
            description "Statistics collected for an operation";

            container latest {
              description
                "Statistics collected during the last
                sampling cycle of the operation";

              container target {
                description "Latest statistics for the target node";
                uses IPSLA-GLOBAL-STATS-BAG;
              }

              container hops {
                description
                  "Latest statistics for hops in a
                  path-enabled operation";

                list hop {
                  key "hop-index";
                  description
                    "Latest stats for a hop in a path-enabled
                    operation";
                  leaf hop-index {
                    type Ipsla-hop-index;
                    description "Hop Index";
                  }
                  uses IPSLA-GLOBAL-STATS-BAG;
                }
              }

              container lpd-paths {
                description "List of latest LPD paths";

                list lpd-path {
                  key "path-index";
                  description
                    "Latest path statistics of MPLS LSP group
                    operation";
                  leaf path-index {
                    type Ipsla-lpd-path-index;
                    description "LPD path index";
                  }
                  uses IPSLA-LPD-PATH-STATS-BAG;
                }
              }
            }

            container aggregated {
              description
                "Statistics aggregated for data collected
                over time intervals";

              container enhanced-intervals {
                description
                  "Table of statistics aggregated over
                  enhanced intervals";

                list enhanced-interval {
                  key "enhanced-interval";
                  description
                    "Statistics aggregated over an interval
                    specified in seconds. Specified interval
                    must be a multiple of the operation
                    frequency";

                  container start-times {
                    description
                      "Table of start times for the intervals";

                    list start-time {
                      key "interval-start-time";
                      description
                        "Statistics aggregated over an enhanced
                        interval which starts at a specific time";
                      leaf interval-start-time {
                        type xr:Cisco-ios-xr-string;
                        description "Interval Start Time";
                      }
                      uses IPSLA-GLOBAL-STATS-BAG;
                    }
                  }
                  leaf enhanced-interval {
                    type Ipsla-enhanced-interval;
                    units "second";
                    description "Enhanced Interval in seconds";
                  }
                }
              }

              container hours {
                description
                  "Table of statistics aggregated over 1-hour
                  intervals";

                list hour {
                  key "hour-index";
                  description
                    "Statistics aggregated for a 1-hour
                    interval";

                  container distributed {
                    description
                      "Statistics aggregated on distribution
                      value intervals for in 1-hour intervals";

                    container paths {
                      description
                        "Table of paths identified in the 1-hour
                        interval";

                      list path {
                        key "path-index";
                        description
                          "Paths identified in a 1-hour interval";

                        container hops {
                          description
                            "Table of hops for a particular path";

                          list hop {
                            key "hop-index";
                            description
                              "1-hour aggregated statistics for a
                              hop in a path-enabled operation";
                            leaf hop-index {
                              type Ipsla-hop-index;
                              description "Hop Index";
                            }
                            uses DISTRIBUTION-INTERVAL-TABLE;
                          }
                        }
                        leaf path-index {
                          type Ipsla-path-index;
                          description "Path Index";
                        }
                      }
                    }

                    container target {
                      description
                        "Distribution statistics for the target
                        node";
                      uses DISTRIBUTION-INTERVAL-TABLE;
                    }
                  }

                  container non-distributed {
                    description
                      "Statistics aggregated for the total range
                      of values in 1-hour intervals";

                    container target {
                      description
                        "Total 1-hour aggregated statistics for
                        the target node";
                      uses IPSLA-GLOBAL-STATS-BAG;
                    }

                    container paths {
                      description
                        "Table of paths identified in the 1-hour
                        interval";

                      list path {
                        key "path-index";
                        description
                          "Paths identified in a 1-hour interval";

                        container hops {
                          description
                            "Table of hops for a particular path";

                          list hop {
                            key "hop-index";
                            description
                              "Total 1-hour aggregated statistics
                              for a hop in a path-enabled operation";
                            leaf hop-index {
                              type Ipsla-hop-index;
                              description "Hop Index";
                            }
                            uses IPSLA-GLOBAL-STATS-BAG;
                          }
                        }
                        leaf path-index {
                          type Ipsla-path-index;
                          description "Path Index";
                        }
                      }
                    }

                    container lpd-paths {
                      description "List of latest LPD paths";

                      list lpd-path {
                        key "path-index";
                        description
                          "Latest path statistics of MPLS LSP
                          group operation";
                        leaf path-index {
                          type Ipsla-lpd-path-index;
                          description "LPD path index";
                        }
                        uses IPSLA-LPD-PATH-STATS-BAG;
                      }
                    }
                  }
                  leaf hour-index {
                    type Ipsla-hour-index;
                    description "Hour Index";
                  }
                }
              }
            }
          }
          leaf operation-id {
            type Ipsla-operation-id;
            description "Operation ID";
          }
        }
      }
    }

    container application-info {
      description "IPSLA application information";
      uses IPSLA-APPLICATION-BAG;
    }
  }
}
