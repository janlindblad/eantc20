module Cisco-IOS-XR-ip-rip-oper {

  /*** NAMESPACE / PREFIX DEFINITION ***/

  namespace "http://cisco.com/ns/yang/Cisco-IOS-XR-ip-rip-oper";


  prefix "Cisco-IOS-XR-ip-rip-oper";

  /*** LINKAGE (IMPORTS / INCLUDES) ***/

  import ietf-inet-types { prefix "inet"; }

  import Cisco-IOS-XR-types { prefix "xr"; }

  include Cisco-IOS-XR-ip-rip-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-rip package operational data.

     This module contains definitions
     for the following management objects:
       rip: RIP operational data

     Copyright (c) 2013-2018 by Cisco Systems, Inc.
     All rights reserved.";

  revision "2015-11-09" {
    description
      "IOS XR 6.0 revision.";
  }


  grouping ROUTE-TABLE {
    description "Common node of default-vrf, vrf";

    container routes {
      description "RIP route database";

      list route {
        description "A route in the RIP database";
        leaf prefix {
          type inet:ipv4-address-no-zone;
          description "Network prefix";
        }
        leaf prefix-length {
          type uint32 {
            range "0..32";
          }
          description "Prefix length";
        }
        uses RIP-SHOW-ROUTE-BD;
      }
    }
  }

  grouping STATISTICS {
    description "Common node of default-vrf, vrf";

    container statistics {
      description "RIP statistics information";
      uses RIP-SHOW-STATISTICS-BD;
    }
  }

  grouping DEFAULT-VRF {
    description "Common node of rip, protocol";

    container default-vrf {
      description "RIP operational data for Default VRF";
      uses ROUTE-TABLE;
      uses CONFIGURATION;
      uses STATISTICS;
      uses INTERFACE-TABLE;
      uses GLOBAL;
    }
  }

  grouping CONFIGURATION {
    description "Common node of default-vrf, vrf";

    container configuration {
      description "RIP global configuration";
      uses RIP-SHOW-GLOBAL-CONFIG-BD;
    }
  }

  grouping INTERFACE-TABLE {
    description "Common node of default-vrf, vrf";

    container interfaces {
      description "RIP interfaces";

      list interface {
        key "interface-name";
        description "Information about a particular RIP interface";
        leaf interface-name {
          type xr:Interface-name;
          description "Interface name";
        }
        uses RIP-SHOW-INTERFACE-BD;
      }
    }
  }

  grouping GLOBAL {
    description "Common node of default-vrf, vrf";

    container global {
      description "Global Information ";
      uses RIP-SHOW-PROTO-VRF-BD;
    }
  }

  container rip {
    config false;
    description "RIP operational data";

    container vrfs {
      description "VRF related operational data";

      list vrf {
        key "vrf-name";
        description "Operational data for a particular VRF";
        leaf vrf-name {
          type xr:Cisco-ios-xr-string;
          description "Name of the VRF";
        }
        uses ROUTE-TABLE;
        uses CONFIGURATION;
        uses STATISTICS;
        uses INTERFACE-TABLE;
        uses GLOBAL;
      }
    }

    container protocol {
      description "Protocol operational data";

      container process {
        description "RIP global process ";
        uses RIP-SHOW-PROTO-PROC-BD;
      }
      uses DEFAULT-VRF;
    }
    uses DEFAULT-VRF;
  }
}
