submodule Cisco-IOS-XR-ip-udp-oper-sub4 {

  belongs-to Cisco-IOS-XR-ip-udp-oper {
    prefix Cisco-IOS-XR-ip-udp-oper-sub4;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ip-udp package operational data.

     Copyright (c) 2013-2018 by Cisco Systems, Inc.
     All rights reserved.";

  revision "2018-08-09" {
    description
      "bind_local field is added to PCB_DETAIL output";
  }

  revision "2018-03-04" {
    description
      "PCB_ID argument is passed in string format.";
  }

  revision "2017-09-07" {
    description
      "Fixed type translation error.";
  }

  revision "2016-02-26" {
    description
      "Descriptions updated.";
  }

  revision "2015-11-09" {
    description
      "IOS XR 6.0 revision.";
  }


  grouping IP-UDP {
    description "UDP Traffic Information";
    leaf udp-input-packets {
      type uint32;
      description "UDP Received";
    }
    leaf udp-checksum-error-packets {
      type uint32;
      description "UDP Checksum Errors";
    }
    leaf udp-no-port-packets {
      type uint32;
      description "UDP No Port";
    }
    leaf udp-bad-length-packets {
      type uint32;
      description "UDP bad length";
    }
    leaf udp-output-packets {
      type uint32;
      description "UDP Transmitted";
    }
    leaf udp-dropped-packets {
      type uint32;
      description "UDP drop for other reason";
    }
  }
}
