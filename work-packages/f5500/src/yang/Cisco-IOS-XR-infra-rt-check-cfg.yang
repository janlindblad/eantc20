module Cisco-IOS-XR-infra-rt-check-cfg {

  /*** NAMESPACE / PREFIX DEFINITION ***/

  namespace "http://cisco.com/ns"+
    "/yang/Cisco-IOS-XR-infra-rt-check-cfg";


  prefix "Cisco-IOS-XR-infra-rt-check-cfg";

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-rt-check package configuration.

     This module contains definitions
     for the following management objects:
       rcc: RCC (Route Consistency Checker) configuration

     Copyright (c) 2013-2018 by Cisco Systems, Inc.
     All rights reserved.";

  revision "2015-11-09" {
    description
      "IOS XR 6.0 revision.";
  }


  grouping UNICAST {
    description "Common node of ipv4, ipv6";

    container unicast {
      description "RCC configuration for unicast";
      uses PERIOD;
      uses ENABLE;
    }
  }

  grouping MULTICAST {
    description "Common node of ipv4, ipv6";

    container multicast {
      description "RCC configuration for multicast";
      uses PERIOD;
      uses ENABLE;
    }
  }

  grouping PERIOD {
    description "Common node of unicast, multicast, lcc";
    leaf period {
      type uint32 {
        range "100..600000";
      }
      units "millisecond";
      description "Period of check in milliseconds";
    }
  }

  grouping ENABLE {
    description "Common node of unicast, multicast, lcc";
    leaf enable {
      type empty;
      description "Enable RCC/LCC";
    }
  }

  grouping LCC {
    description "Common node of ipv4, ipv6";

    container lcc {
      description
        "IPv4/IPv6 LCC (Label Consistency Checker)
        configuration";
      uses PERIOD;
      uses ENABLE;
    }
  }

  container rcc {
    description "RCC (Route Consistency Checker) configuration";

    container ipv6 {
      description "RCC/LCC configuration for IPv6";
      uses LCC;
      uses UNICAST;
      uses MULTICAST;
    }

    container ipv4 {
      description "RCC/LCC configuration for IPv4";
      uses LCC;
      uses UNICAST;
      uses MULTICAST;
    }
  }
}
