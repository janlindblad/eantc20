module Cisco-IOS-XR-ipv6-acl-oper {

  /*** NAMESPACE / PREFIX DEFINITION ***/

  namespace "http://cisco.com/ns/yang/Cisco-IOS-XR-ipv6-acl-oper";


  prefix "Cisco-IOS-XR-ipv6-acl-oper";

  /*** LINKAGE (IMPORTS / INCLUDES) ***/

  import Cisco-IOS-XR-types { prefix "xr"; }

  import Cisco-IOS-XR-common-acl-datatypes { prefix "dt1"; }

  import Cisco-IOS-XR-ipv6-acl-datatypes { prefix "dt2"; }

  include Cisco-IOS-XR-ipv6-acl-oper-sub1 {
    revision-date 2017-05-01;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv6-acl package operational data.

     This module contains definitions
     for the following management objects:
       ipv6-acl-and-prefix-list: Root class of IPv6 Oper schema tree

     Copyright (c) 2013-2018 by Cisco Systems, Inc.
     All rights reserved.";

  revision "2017-05-01" {
    description
      "Fixing backward compatibility error in module.";
  }

  revision "2015-11-09" {
    description
      "IOS XR 6.0 revision.";
  }


  container ipv6-acl-and-prefix-list {
    config false;
    description "Root class of IPv6 Oper schema tree";

    container access-list-manager {
      description
        "AccessListManager containing ACLs and prefix
        lists";

      container prefixes {
        description "Table of prefix lists";

        list prefix {
          key "prefix-list-name";
          description "Name of the prefix list";

          container prefix-list-sequences {
            description
              "Table of all the SequenceNumbers per prefix
              list";

            list prefix-list-sequence {
              key "sequence-number";
              description "Sequence Number of a prefix list entry";
              leaf sequence-number {
                type dt1:Acl-sequence-number-range;
                description
                  "Sequence Number of the prefix list entry";
              }
              uses IPV6-PFX-EDM-ACE;
            }
          }
          leaf prefix-list-name {
            type dt2:Ipv6-acl-prefix-list-name;
            description "Name of the prefix list";
          }
        }
      }

      container usages {
        description
          "Table of Usage statistics of ACLs at different
          nodes";

        list usage {
          description "Usage statistics of an ACL at a node";
          leaf node-name {
            type xr:Node-id;
            description "Node where ACL is applied";
          }
          leaf application-id {
            type dt1:Acl-usage-app-id-enum;
            description "Application ID";
          }
          leaf access-list-name {
            type dt2:Ipv6-acl-prefix-list-name;
            description "Name of the ACL";
          }
          leaf usage-details {
            type string;
            mandatory true;
            description "Usage Statistics Details";
          }
        }
      }

      container accesses {
        description "ACL class displaying Usage and Entries";

        list access {
          key "access-list-name";
          description "Name of the Access List";

          container access-list-sequences {
            description "Table of all the sequence numbers per ACL";

            list access-list-sequence {
              key "sequence-number";
              description "Sequence number of an ACL entry";
              leaf sequence-number {
                type dt1:Acl-sequence-number-range;
                description "ACL entry sequence number";
              }
              uses IPV6-ACL-EDM-ACE;
            }
          }
          leaf access-list-name {
            type dt2:Ipv6-acl-prefix-list-name;
            description "Name of the Access List";
          }
        }
      }
    }

    container oor {
      description
        "Out Of Resources, Limits to the resources
        allocatable";

      container details {
        description "Details of the overall out of resource limit";
        uses IPV6-ACL-EDM-OOR-DETAIL;
      }

      container prefix-list-summary {
        description
          "Summary of the prefix Lists resource
          utilization";

        container details {
          description
            "Summary Detail of the prefix list Resource
            Utilisation";
          uses IPV6-ACL-EDM-OOR-DETAIL;
        }
      }

      container oor-accesses {
        description "Resource occupation details for ACLs";

        list oor-access {
          key "access-list-name";
          description
            "Resource occupation details for a particular
            ACL";
          leaf access-list-name {
            type dt2:Ipv6-acl-prefix-list-name;
            description "Name of the Access List";
          }
          uses IPV6-ACL-EDM-OOR-DETAIL;
        }
      }

      container oor-prefixes {
        description "Resource occupation details for prefix lists";

        list oor-prefix {
          key "prefix-list-name";
          description
            "Resource occupation details for a particular
            prefix list";
          leaf prefix-list-name {
            type dt2:Ipv6-acl-prefix-list-name;
            description "Name of a prefix list";
          }
          uses IPV6-ACL-EDM-OOR-DETAIL;
        }
      }

      container access-list-summary {
        description "Resource Limits pertaining to ACLs only";

        container details {
          description
            "Details containing the resource limits of the
            ACLs";
          uses IPV6-ACL-EDM-OOR-DETAIL;
        }
      }
    }
  }
}
