module Cisco-IOS-XR-sysmgr-oper {

  /*** NAMESPACE / PREFIX DEFINITION ***/

  namespace "http://cisco.com/ns/yang/Cisco-IOS-XR-sysmgr-oper";


  prefix "Cisco-IOS-XR-sysmgr-oper";

  /*** LINKAGE (IMPORTS / INCLUDES) ***/

  import Cisco-IOS-XR-types { prefix "xr"; }

  include Cisco-IOS-XR-sysmgr-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR sysmgr package operational data.

     This module contains definitions
     for the following management objects:
       system-process: Process information

     Copyright (c) 2013-2018 by Cisco Systems, Inc.
     All rights reserved.";

  revision "2015-11-09" {
    description
      "IOS XR 6.0 revision.";
  }


  grouping NODE {
    description "Common node of node-table, node-table";

    list node {
      key "node-name";
      description "Process information per node";

      container name {
        description "Process <WORD> information";

        container process-name-run-infos {
          description "Process <WORD> information";

          list process-name-run-info {
            key "proc-name";
            description "Process <WORD> run information";
            leaf proc-name {
              type xr:Cisco-ios-xr-string;
              description "Process Name";
            }
            uses PROC-BASIC-INFO;
          }
        }

        container process-name-infos {
          description "Process <WORD> information";

          list process-name-info {
            key "proc-name";
            description "Process <WORD> information";
            leaf proc-name {
              type xr:Cisco-ios-xr-string;
              description "Process Name";
            }
            uses PROC-BASIC-INFO;
          }
        }

        container process-name-run-details {
          description "Process <WORD> information";

          list process-name-run-detail {
            key "proc-name";
            description "Process <WORD> run detail information";
            leaf proc-name {
              type xr:Cisco-ios-xr-string;
              description "Process Name";
            }
            uses PROC-BASIC-DETAIL-INFO;
          }
        }

        container process-name-runverboses {
          description "Process <WORD> information";

          list process-name-runverbose {
            key "proc-name";
            description "Process <WORD> run verbose information";
            leaf proc-name {
              type xr:Cisco-ios-xr-string;
              description "Process Name";
            }
            uses PROC-BASIC-DETAIL-VERBOSE-INFO;
          }
        }

        container process-name-details {
          description "Process <WORD> information";

          list process-name-detail {
            key "proc-name";
            description "Process <WORD> detail information";
            leaf proc-name {
              type xr:Cisco-ios-xr-string;
              description "Process Name";
            }
            uses PROC-BASIC-DETAIL-INFO;
          }
        }

        container process-name-verboses {
          description "Process <WORD> information";

          list process-name-verbose {
            key "proc-name";
            description "Process <WORD> verbose information";
            leaf proc-name {
              type xr:Cisco-ios-xr-string;
              description "Process Name";
            }
            uses PROC-BASIC-DETAIL-VERBOSE-INFO;
          }
        }
      }

      container jids {
        description "Process job id information";

        list jid {
          key "job-id";
          description "Process <jid> information";
          leaf job-id {
            type uint32;
            description "Job ID";
          }
          uses PROC-BASIC-INFO;
        }
      }

      container dynamic {
        description "Process Dynamic information";
        uses PROCESSES-INFO;
      }

      container boot-stalled {
        description "Process Boot Stalled information";
        uses PROC-BOOT-STALLED-INFO;
      }

      container processes {
        description "Process all information";
        uses PROCESSES-INFO;
      }

      container startup {
        description "Process Startup information";
        uses PROCESSES-INFO;
      }

      container mandatory {
        description "Mandatory Process information";
        uses PROCESSES-INFO;
      }

      container abort {
        description "Process Abort information";
        uses PROC-ABORT-INFO;
      }

      container failover {
        description "Process Failover information";
        uses PROC-FAILOVER-INFO;
      }

      container boot {
        description "Process Boot information";
        uses PROC-BOOT-INFO;
      }

      container logs {
        description "Process Log information";
        uses LOG-INFO;
      }

      container searchpath {
        description "Process Searchpath information";
        uses PROC-SEARCHPATH-INFO;
      }
      leaf node-name {
        type xr:Node-id;
        description "The node name";
      }
    }
  }

  container system-process {
    config false;
    description "Process information";

    container node-table {
      description "List of nodes";
      uses NODE;
    }
  }
}
