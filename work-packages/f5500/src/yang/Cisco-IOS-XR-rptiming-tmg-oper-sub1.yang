submodule Cisco-IOS-XR-rptiming-tmg-oper-sub1 {

  belongs-to Cisco-IOS-XR-rptiming-tmg-oper {
    prefix Cisco-IOS-XR-rptiming-tmg-oper-sub1;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR rptiming-tmg package operational data.

     Copyright (c) 2013-2018 by Cisco Systems, Inc.
     All rights reserved.";

  revision "2015-11-09" {
    description
      "IOS XR 6.0 revision.";
  }


  grouping TMG-PLL-INFO {
    description "Timing PLL status";
    leaf t0-pll-state {
      type string {
        length "0..50";
      }
      description "T0 PLL state";
    }
    leaf t4-pll-state {
      type string {
        length "0..50";
      }
      description "T4 PLL state";
    }
    leaf ptp-pll-state {
      type string {
        length "0..50";
      }
      description "1588 PLL state";
    }
    leaf t0-pll-selected {
      type string {
        length "0..50";
      }
      description "T0 PLL selected";
    }
    leaf t4-pll-selected {
      type string {
        length "0..50";
      }
      description "T4 PLL selected";
    }
    leaf ptp-pll-selected {
      type string {
        length "0..50";
      }
      description "1588 PLL selected";
    }
    leaf t0-pll-mode {
      type string {
        length "0..50";
      }
      description "T0 PLL mode";
    }
    leaf t4-pll-mode {
      type string {
        length "0..50";
      }
      description "T4 PLL mode";
    }
    leaf ptp-pll-mode {
      type string {
        length "0..50";
      }
      description "1588 PLL mode";
    }
    leaf t0-pll-ic1-prio {
      type uint8;
      description "T0 PLL IC1 Priority";
    }
    leaf t0-pll-ic2-prio {
      type uint8;
      description "T0 PLL IC2 Priority";
    }
    leaf t0-pll-ic3-prio {
      type uint8;
      description "T0 PLL IC3 Priority";
    }
    leaf t0-pll-ic4-prio {
      type uint8;
      description "T0 PLL IC4 Priority";
    }
    leaf t0-pll-ic5-prio {
      type uint8;
      description "T0 PLL IC5 Priority";
    }
    leaf t0-pll-ic6-prio {
      type uint8;
      description "T0 PLL IC6 Priority";
    }
    leaf t0-pll-ic7-prio {
      type uint8;
      description "T0 PLL IC7 Priority";
    }
    leaf t0-pll-ic8-prio {
      type uint8;
      description "T0 PLL IC8 Priority";
    }
    leaf t0-pll-ic9-prio {
      type uint8;
      description "T0 PLL IC9 Priority";
    }
    leaf t0-pll-ic10-prio {
      type uint8;
      description "T0 PLL IC10 Priority";
    }
    leaf t0-pll-ic11-prio {
      type uint8;
      description "T0 PLL IC11 Priority";
    }
    leaf t4-pll-ic1-prio {
      type uint8;
      description "T4 PLL IC1 Priority";
    }
    leaf t4-pll-ic2-prio {
      type uint8;
      description "T4 PLL IC2 Priority";
    }
    leaf t4-pll-ic3-prio {
      type uint8;
      description "T4 PLL IC3 Priority";
    }
    leaf t4-pll-ic4-prio {
      type uint8;
      description "T4 PLL IC4 Priority";
    }
    leaf t4-pll-ic5-prio {
      type uint8;
      description "T4 PLL IC5 Priority";
    }
    leaf t4-pll-ic6-prio {
      type uint8;
      description "T4 PLL IC6 Priority";
    }
    leaf t4-pll-ic7-prio {
      type uint8;
      description "T4 PLL IC7 Priority";
    }
    leaf t4-pll-ic8-prio {
      type uint8;
      description "T4 PLL IC8 Priority";
    }
    leaf t4-pll-ic9-prio {
      type uint8;
      description "T4 PLL IC9 Priority";
    }
    leaf t4-pll-ic10-prio {
      type uint8;
      description "T4 PLL IC10 Priority";
    }
    leaf t4-pll-ic11-prio {
      type uint8;
      description "T4 PLL IC11 Priority";
    }
    leaf ptp-pll-ic1-prio {
      type uint8;
      description "PTP PLL IC1 Priority";
    }
    leaf ptp-pll-ic2-prio {
      type uint8;
      description "PTP PLL IC2 Priority";
    }
    leaf ptp-pll-ic3-prio {
      type uint8;
      description "PTP PLL IC3 Priority";
    }
    leaf ptp-pll-ic4-prio {
      type uint8;
      description "PTP PLL IC4 Priority";
    }
    leaf ptp-pll-ic5-prio {
      type uint8;
      description "PTP PLL IC5 Priority";
    }
    leaf ptp-pll-ic6-prio {
      type uint8;
      description "PTP PLL IC6 Priority";
    }
    leaf ptp-pll-ic7-prio {
      type uint8;
      description "PTP PLL IC7 Priority";
    }
    leaf ptp-pll-ic8-prio {
      type uint8;
      description "PTP PLL IC8 Priority";
    }
    leaf ptp-pll-ic9-prio {
      type uint8;
      description "PTP PLL IC9 Priority";
    }
    leaf ptp-pll-ic10-prio {
      type uint8;
      description "PTP PLL IC10 Priority";
    }
    leaf ptp-pll-ic11-prio {
      type uint8;
      description "PTP PLL IC11 Priority";
    }
    leaf ic1-valid {
      type boolean;
      description "IC Valid 1";
    }
    leaf ic2-valid {
      type boolean;
      description "IC Valid 2";
    }
    leaf ic3-valid {
      type boolean;
      description "IC Valid 3";
    }
    leaf ic4-valid {
      type boolean;
      description "IC Valid 4";
    }
    leaf ic5-valid {
      type boolean;
      description "IC Valid 5";
    }
    leaf ic6-valid {
      type boolean;
      description "IC Valid 6";
    }
    leaf ic7-valid {
      type boolean;
      description "IC Valid 7";
    }
    leaf ic8-valid {
      type boolean;
      description "IC Valid 8";
    }
    leaf ic9-valid {
      type boolean;
      description "IC Valid 9";
    }
    leaf ic10-valid {
      type boolean;
      description "IC Valid 10";
    }
    leaf ic11-valid {
      type boolean;
      description "IC Valid 11";
    }
    leaf t0-pll-freq-offset {
      type int32;
      description "T0 PLL Frequency Offset";
    }
    leaf t4-pll-freq-offset {
      type int32;
      description "T4 PLL Frequency Offset";
    }
    leaf ptp-pll-freq-offset {
      type int32;
      description "PTP PLL Frequency Offset";
    }
    leaf t0-pll-bandwidth {
      type string {
        length "0..50";
      }
      description "T0 PLL Bandwidth";
    }
    leaf t4-pll-bandwidth {
      type string {
        length "0..50";
      }
      description "T4 PLL Bandwidth";
    }
    leaf ptp-pll-bandwidth {
      type string {
        length "0..50";
      }
      description "PTP PLL Bandwidth";
    }
    leaf t0-pll-psl {
      type string {
        length "0..50";
      }
      description "T0 PLL PSL";
    }
    leaf t4-pll-psl {
      type string {
        length "0..50";
      }
      description "T4 PLL PSL";
    }
    leaf ptp-pll-psl {
      type string {
        length "0..50";
      }
      description "PTP PLL PSL";
    }
    leaf ic1-qual-min {
      type string {
        length "0..50";
      }
      description "IC1 Pull-in/Hold-in Min";
    }
    leaf ic1-qual-max {
      type string {
        length "0..50";
      }
      description "IC1 Pull-in/Hold-in Min";
    }
    leaf ic2-qual-min {
      type string {
        length "0..50";
      }
      description "IC2 Pull-in/Hold-in Min";
    }
    leaf ic2-qual-max {
      type string {
        length "0..50";
      }
      description "IC2 Pull-in/Hold-in Min";
    }
    leaf ic3-qual-min {
      type string {
        length "0..50";
      }
      description "IC3 Pull-in/Hold-in Min";
    }
    leaf ic3-qual-max {
      type string {
        length "0..50";
      }
      description "IC3 Pull-in/Hold-in Min";
    }
    leaf ic4-qual-min {
      type string {
        length "0..50";
      }
      description "IC4 Pull-in/Hold-in Min";
    }
    leaf ic4-qual-max {
      type string {
        length "0..50";
      }
      description "IC4 Pull-in/Hold-in Min";
    }
    leaf ic5-qual-min {
      type string {
        length "0..50";
      }
      description "IC5 Pull-in/Hold-in Min";
    }
    leaf ic5-qual-max {
      type string {
        length "0..50";
      }
      description "IC5 Pull-in/Hold-in Min";
    }
    leaf ic6-qual-min {
      type string {
        length "0..50";
      }
      description "IC6 Pull-in/Hold-in Min";
    }
    leaf ic6-qual-max {
      type string {
        length "0..50";
      }
      description "IC6 Pull-in/Hold-in Min";
    }
    leaf ic7-qual-min {
      type string {
        length "0..50";
      }
      description "IC7 Pull-in/Hold-in Min";
    }
    leaf ic7-qual-max {
      type string {
        length "0..50";
      }
      description "IC7 Pull-in/Hold-in Min";
    }
    leaf ic8-qual-min {
      type string {
        length "0..50";
      }
      description "IC8 Pull-in/Hold-in Min";
    }
    leaf ic8-qual-max {
      type string {
        length "0..50";
      }
      description "IC8 Pull-in/Hold-in Min";
    }
    leaf ic9-qual-min {
      type string {
        length "0..50";
      }
      description "IC9 Pull-in/Hold-in Min";
    }
    leaf ic9-qual-max {
      type string {
        length "0..50";
      }
      description "IC9 Pull-in/Hold-in Min";
    }
    leaf ic10-qual-min {
      type string {
        length "0..50";
      }
      description "IC10 Pull-in/Hold-in Min";
    }
    leaf ic10-qual-max {
      type string {
        length "0..50";
      }
      description "IC10 Pull-in/Hold-in Min";
    }
    leaf ic11-qual-min {
      type string {
        length "0..50";
      }
      description "IC11 Pull-in/Hold-in Min";
    }
    leaf ic11-qual-max {
      type string {
        length "0..50";
      }
      description "IC11 Pull-in/Hold-in Min";
    }
  }

  grouping TMG-CLKIN-INFO {
    description "Timing input clock status";
    leaf ic1-valid {
      type boolean;
      description "IC Valid 1";
    }
    leaf ic2-valid {
      type boolean;
      description "IC Valid 2";
    }
    leaf ic3-valid {
      type boolean;
      description "IC Valid 3";
    }
    leaf ic4-valid {
      type boolean;
      description "IC Valid 4";
    }
    leaf ic5-valid {
      type boolean;
      description "IC Valid 5";
    }
    leaf ic6-valid {
      type boolean;
      description "IC Valid 6";
    }
    leaf ic7-valid {
      type boolean;
      description "IC Valid 7";
    }
    leaf ic8-valid {
      type boolean;
      description "IC Valid 8";
    }
    leaf ic9-valid {
      type boolean;
      description "IC Valid 9";
    }
    leaf ic10-valid {
      type boolean;
      description "IC Valid 10";
    }
    leaf ic11-valid {
      type boolean;
      description "IC Valid 11";
    }
    leaf ic1-slot {
      type string {
        length "0..50";
      }
      description "IC Slot 1";
    }
    leaf ic2-slot {
      type string {
        length "0..50";
      }
      description "IC Slot 2";
    }
    leaf ic3-slot {
      type string {
        length "0..50";
      }
      description "IC Slot 3";
    }
    leaf ic4-slot {
      type string {
        length "0..50";
      }
      description "IC Slot 4";
    }
    leaf ic5-slot {
      type string {
        length "0..50";
      }
      description "IC Slot 5";
    }
    leaf ic6-slot {
      type string {
        length "0..50";
      }
      description "IC Slot 6";
    }
    leaf ic7-slot {
      type string {
        length "0..50";
      }
      description "IC Slot 7";
    }
    leaf ic8-slot {
      type string {
        length "0..50";
      }
      description "IC Slot 8";
    }
    leaf ic9-slot {
      type string {
        length "0..50";
      }
      description "IC Slot 9";
    }
    leaf ic10-slot {
      type string {
        length "0..50";
      }
      description "IC Slot 10";
    }
    leaf ic11-slot {
      type string {
        length "0..50";
      }
      description "IC Slot 11";
    }
    leaf ic1-split-xom {
      type string {
        length "0..50";
      }
      description "IC1 Split XO Mode Status";
    }
    leaf ic2-split-xom {
      type string {
        length "0..50";
      }
      description "IC2 Split XO Mode Status";
    }
    leaf ic3-split-xom {
      type string {
        length "0..50";
      }
      description "IC3 Split XO Mode Status";
    }
    leaf ic4-split-xom {
      type string {
        length "0..50";
      }
      description "IC4 Split XO Mode Status";
    }
    leaf ic5-split-xom {
      type string {
        length "0..50";
      }
      description "IC5 Split XO Mode Status";
    }
    leaf ic6-split-xom {
      type string {
        length "0..50";
      }
      description "IC6 Split XO Mode Status";
    }
    leaf ic7-split-xom {
      type string {
        length "0..50";
      }
      description "IC7 Split XO Mode Status";
    }
    leaf ic8-split-xom {
      type string {
        length "0..50";
      }
      description "IC8 Split XO Mode Status";
    }
    leaf ic9-split-xom {
      type string {
        length "0..50";
      }
      description "IC9 Split XO Mode Status";
    }
    leaf ic10-split-xom {
      type string {
        length "0..50";
      }
      description "IC10 Split XO Mode Status";
    }
    leaf ic11-split-xom {
      type string {
        length "0..50";
      }
      description "IC11 Split XO Mode Status";
    }
    leaf ic1-eppsm {
      type string {
        length "0..50";
      }
      description "IC1 ePPSM Status";
    }
    leaf ic2-eppsm {
      type string {
        length "0..50";
      }
      description "IC2 ePPSM Status";
    }
    leaf ic3-eppsm {
      type string {
        length "0..50";
      }
      description "IC3 ePPSM Status";
    }
    leaf ic4-eppsm {
      type string {
        length "0..50";
      }
      description "IC4 ePPSM Status";
    }
    leaf ic5-eppsm {
      type string {
        length "0..50";
      }
      description "IC5 ePPSM Status";
    }
    leaf ic6-eppsm {
      type string {
        length "0..50";
      }
      description "IC6 ePPSM Status";
    }
    leaf ic7-eppsm {
      type string {
        length "0..50";
      }
      description "IC7 ePPSM Status";
    }
    leaf ic8-eppsm {
      type string {
        length "0..50";
      }
      description "IC8 ePPSM Status";
    }
    leaf ic9-eppsm {
      type string {
        length "0..50";
      }
      description "IC9 ePPSM Status";
    }
    leaf ic10-eppsm {
      type string {
        length "0..50";
      }
      description "IC10 ePPSM Status";
    }
    leaf ic11-eppsm {
      type string {
        length "0..50";
      }
      description "IC11 ePPSM Status";
    }
    leaf ic1-pfm {
      type string {
        length "0..50";
      }
      description "IC1 PFM Status";
    }
    leaf ic2-pfm {
      type string {
        length "0..50";
      }
      description "IC2 PFM Status";
    }
    leaf ic3-pfm {
      type string {
        length "0..50";
      }
      description "IC3 PFM Status";
    }
    leaf ic4-pfm {
      type string {
        length "0..50";
      }
      description "IC4 PFM Status";
    }
    leaf ic5-pfm {
      type string {
        length "0..50";
      }
      description "IC5 PFM Status";
    }
    leaf ic6-pfm {
      type string {
        length "0..50";
      }
      description "IC6 PFM Status";
    }
    leaf ic7-pfm {
      type string {
        length "0..50";
      }
      description "IC7 PFM Status";
    }
    leaf ic8-pfm {
      type string {
        length "0..50";
      }
      description "IC8 PFM Status";
    }
    leaf ic9-pfm {
      type string {
        length "0..50";
      }
      description "IC9 PFM Status";
    }
    leaf ic10-pfm {
      type string {
        length "0..50";
      }
      description "IC10 PFM Status";
    }
    leaf ic11-pfm {
      type string {
        length "0..50";
      }
      description "IC11 PFM Status";
    }
    leaf ic1-gst {
      type string {
        length "0..50";
      }
      description "IC1 GST Status";
    }
    leaf ic2-gst {
      type string {
        length "0..50";
      }
      description "IC2 GST Status";
    }
    leaf ic3-gst {
      type string {
        length "0..50";
      }
      description "IC3 GST Status";
    }
    leaf ic4-gst {
      type string {
        length "0..50";
      }
      description "IC4 GST Status";
    }
    leaf ic5-gst {
      type string {
        length "0..50";
      }
      description "IC5 GST Status";
    }
    leaf ic6-gst {
      type string {
        length "0..50";
      }
      description "IC6 GST Status";
    }
    leaf ic7-gst {
      type string {
        length "0..50";
      }
      description "IC7 GST Status";
    }
    leaf ic8-gst {
      type string {
        length "0..50";
      }
      description "IC8 GST Status";
    }
    leaf ic9-gst {
      type string {
        length "0..50";
      }
      description "IC9 GST Status";
    }
    leaf ic10-gst {
      type string {
        length "0..50";
      }
      description "IC10 GST Status";
    }
    leaf ic11-gst {
      type string {
        length "0..50";
      }
      description "IC11 GST Status";
    }
    leaf ic1-cfm {
      type string {
        length "0..50";
      }
      description "IC1 CFM Status";
    }
    leaf ic2-cfm {
      type string {
        length "0..50";
      }
      description "IC2 CFM Status";
    }
    leaf ic3-cfm {
      type string {
        length "0..50";
      }
      description "IC3 CFM Status";
    }
    leaf ic4-cfm {
      type string {
        length "0..50";
      }
      description "IC4 CFM Status";
    }
    leaf ic5-cfm {
      type string {
        length "0..50";
      }
      description "IC5 CFM Status";
    }
    leaf ic6-cfm {
      type string {
        length "0..50";
      }
      description "IC6 CFM Status";
    }
    leaf ic7-cfm {
      type string {
        length "0..50";
      }
      description "IC7 CFM Status";
    }
    leaf ic8-cfm {
      type string {
        length "0..50";
      }
      description "IC8 CFM Status";
    }
    leaf ic9-cfm {
      type string {
        length "0..50";
      }
      description "IC9 CFM Status";
    }
    leaf ic10-cfm {
      type string {
        length "0..50";
      }
      description "IC10 CFM Status";
    }
    leaf ic11-cfm {
      type string {
        length "0..50";
      }
      description "IC11 CFM Status";
    }
    leaf ic1-scm {
      type string {
        length "0..50";
      }
      description "IC1 SCM Status";
    }
    leaf ic2-scm {
      type string {
        length "0..50";
      }
      description "IC2 SCM Status";
    }
    leaf ic3-scm {
      type string {
        length "0..50";
      }
      description "IC3 SCM Status";
    }
    leaf ic4-scm {
      type string {
        length "0..50";
      }
      description "IC4 SCM Status";
    }
    leaf ic5-scm {
      type string {
        length "0..50";
      }
      description "IC5 SCM Status";
    }
    leaf ic6-scm {
      type string {
        length "0..50";
      }
      description "IC6 SCM Status";
    }
    leaf ic7-scm {
      type string {
        length "0..50";
      }
      description "IC7 SCM Status";
    }
    leaf ic8-scm {
      type string {
        length "0..50";
      }
      description "IC8 SCM Status";
    }
    leaf ic9-scm {
      type string {
        length "0..50";
      }
      description "IC9 SCM Status";
    }
    leaf ic10-scm {
      type string {
        length "0..50";
      }
      description "IC10 SCM Status";
    }
    leaf ic11-scm {
      type string {
        length "0..50";
      }
      description "IC11 SCM Status";
    }
    leaf ic1-los {
      type string {
        length "0..50";
      }
      description "IC1 LOS Status";
    }
    leaf ic2-los {
      type string {
        length "0..50";
      }
      description "IC2 LOS Status";
    }
    leaf ic3-los {
      type string {
        length "0..50";
      }
      description "IC3 LOS Status";
    }
    leaf ic4-los {
      type string {
        length "0..50";
      }
      description "IC4 LOS Status";
    }
    leaf ic5-los {
      type string {
        length "0..50";
      }
      description "IC5 LOS Status";
    }
    leaf ic6-los {
      type string {
        length "0..50";
      }
      description "IC6 LOS Status";
    }
    leaf ic7-los {
      type string {
        length "0..50";
      }
      description "IC7 LOS Status";
    }
    leaf ic8-los {
      type string {
        length "0..50";
      }
      description "IC8 LOS Status";
    }
    leaf ic9-los {
      type string {
        length "0..50";
      }
      description "IC9 LOS Status";
    }
    leaf ic10-los {
      type string {
        length "0..50";
      }
      description "IC10 LOS Status";
    }
    leaf ic11-los {
      type string {
        length "0..50";
      }
      description "IC11 LOS Status";
    }
  }
}
