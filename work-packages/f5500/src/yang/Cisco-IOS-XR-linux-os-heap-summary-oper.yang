module Cisco-IOS-XR-linux-os-heap-summary-oper {

  /*** NAMESPACE / PREFIX DEFINITION ***/

  namespace "http://cisco.com/ns/yang"+
    "/Cisco-IOS-XR-linux-os-heap-summary-oper";


  prefix "Cisco-IOS-XR-linux-os-heap-summary-oper";

  /*** LINKAGE (IMPORTS / INCLUDES) ***/

  import Cisco-IOS-XR-types { prefix "xr"; }

  include Cisco-IOS-XR-linux-os-heap-summary-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR linux-os-heap-summary package operational data.

     This module contains definitions
     for the following management objects:
       heap-summary: Heap Summary

     Copyright (c) 2013-2018 by Cisco Systems, Inc.
     All rights reserved.";

  revision "2015-11-09" {
    description
      "IOS XR 6.0 revision.";
  }


  container heap-summary {
    config false;
    description "Heap Summary";

    container location-descriptions {
      description "Location";

      list location-description {
        key "node";
        description "Location specified in location";
        leaf node {
          type xr:Node-id;
          description "Node location";
        }
        uses SHOW-MEMORY-HEAP-SUMMARY-ALL-EDM-STRING;
      }
    }

    container all {
      description "All locations";
      uses SHOW-MEMORY-HEAP-SUMMARY-ALL-EDM-STRING;
    }
  }
}
