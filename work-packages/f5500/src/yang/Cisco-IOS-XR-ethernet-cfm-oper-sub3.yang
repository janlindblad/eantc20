submodule Cisco-IOS-XR-ethernet-cfm-oper-sub3 {

  belongs-to Cisco-IOS-XR-ethernet-cfm-oper {
    prefix Cisco-IOS-XR-ethernet-cfm-oper-sub3;
  }

  /*** LINKAGE (IMPORTS / INCLUDES) ***/

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ethernet-cfm package operational data.

     Copyright (c) 2013-2018 by Cisco Systems, Inc.
     All rights reserved.";

  revision "2017-10-06" {
    description
      "Traceroute transaction ID changed from int to uint.";
  }

  revision "2015-11-09" {
    description
      "IOS XR 6.0 revision.";
  }

  typedef Cfm-bag-sman-fmt {
    type enumeration {
      enum sman-vlan-id {
        value 1;
        description "Short MA Name is a 12-bit VLAN-ID";
      }
      enum sman-string {
        value 2;
        description "Short MA Name is a character string";
      }
      enum sman-uint16 {
        value 3;
        description "Short MA Name is a 16-bit unsigned integer";
      }
      enum sman-vpn-id {
        value 4;
        description "Short MA Name is a global VPN identifier";
      }
      enum sman-icc {
        value 32;
        description "Short MA Name uses the ICC-based format";
      }
      enum sman-unknown {
        value 33;
        description "Unknown Short MA Name format";
      }
    }
    description "Short MA Name format";
  }
  typedef Cfm-bag-mdid-fmt {
    type enumeration {
      enum mdid-null {
        value 1;
        description "MDID is explicity NULL";
      }
      enum mdid-dns-like {
        value 2;
        description "MDID is based on a DNS name";
      }
      enum mdid-mac-address {
        value 3;
        description "MDID is a (MAC address, integer) pair";
      }
      enum mdid-string {
        value 4;
        description "MDID is a character string";
      }
      enum mdid-unknown {
        value 5;
        description "Unknown MDID format";
      }
    }
    description "CFM MDID format";
  }
  typedef Cfm-bag-ccm-offload {
    type enumeration {
      enum offload-none {
        description "CCM processing has not been offloaded";
      }
      enum offload-software {
        description "CCM processing has been offloaded to software";
      }
      enum offload-hardware {
        description "CCM processing has been offloaded to hardware";
      }
    }
    description "Offload status of CCM processing";
  }
  typedef Cfm-bag-optional-hex-data {
    type yang:hex-string;
    description "Hex binary data which may be optionally present.";
  }
  typedef Cfm-bag-optional-string {
    type string;
    description "String which may be optionally present.";
  }
  typedef Cfm-bag-ccm-interval {
    type enumeration {
      enum interval-none {
        value 0;
        description "Invalid CCM interval";
      }
      enum interval3-3ms {
        value 1;
        description "Interval of 3.3ms";
      }
      enum interval10ms {
        value 2;
        description "Interval of 10ms";
      }
      enum interval100ms {
        value 3;
        description "Interval of 100ms";
      }
      enum interval1s {
        value 4;
        description "Interval of 1s";
      }
      enum interval10s {
        value 5;
        description "Interval of 10s";
      }
      enum interval1m {
        value 6;
        description "Interval of 1 min";
      }
      enum interval10m {
        value 7;
        description "Interval of 10 mins";
      }
    }
    description "CFM CCM intervals";
  }
  typedef Cfm-bag-bdid-fmt {
    type enumeration {
      enum invalid {
        value 0;
        description "Invalid BDID identifier format";
      }
      enum bd-id {
        value 1;
        description "Identifier is a bridge domain ID";
      }
      enum xc-p2p-id {
        value 2;
        description "Identifier is a P2P cross-connect ID";
      }
      enum xc-mp2mp-id {
        value 3;
        description "Identifier is a MP2MP cross-connect ID";
      }
      enum fxc-vlan-aware-id {
        value 4;
        description
          "Identifier is a VLAN-aware flexible
          cross-connect ID";
      }
      enum fxc-vlan-unaware-id {
        value 5;
        description
          "Identifier is a VLAN-unaware flexible
          cross-connect ID";
      }
      enum down-only {
        value 6;
        description "Identifier is a maintenance association name";
      }
    }
    description "Bridge domain identifier format";
  }
  typedef Cfm-ma-mp-variety {
    type enumeration {
      enum mip {
        description "MIP";
      }
      enum up-mep {
        description "Up MEP";
      }
      enum downmep {
        description "Down MEP";
      }
      enum unknown-mep {
        description "Unknown MEP";
      }
    }
    description "CFM MA Maintenance Point varieties";
  }
  typedef Mac-address {
    type yang:mac-address;
    description "MAC address type";
  }
  typedef Cfm-bag-issu-role {
    type enumeration {
      enum unknown {
        value 0;
        description "Unknown";
      }
      enum primary {
        value 1;
        description "Primary";
      }
      enum secondary {
        value 2;
        description "Secondary";
      }
    }
    description "CFM ISSU role";
  }
  typedef Cfm-bag-opcode {
    type enumeration {
      enum reserved {
        value 0;
        description "Reserved";
      }
      enum ccm {
        value 1;
        description "Continuity Check";
      }
      enum lbr {
        value 2;
        description "Loopback Reply";
      }
      enum lbm {
        value 3;
        description "Loopback Message";
      }
      enum ltr {
        value 4;
        description "Linktrace Reply";
      }
      enum ltm {
        value 5;
        description "Linktrace Message";
      }
    }
    description "CFM Opcode";
  }
  typedef Cfm-bag-ais-interval {
    type enumeration {
      enum ais-interval-none {
        value 0;
        description "Invalid AIS interval";
      }
      enum ais-interval1s {
        value 4;
        description "Interval of 1s";
      }
      enum ais-interval1m {
        value 6;
        description "Interval of 1 min";
      }
    }
    description "CFM AIS intervals";
  }
  typedef Cfm-bag-md-level {
    type enumeration {
      enum level0 {
        value 0;
        description "CFM level 0";
      }
      enum level1 {
        value 1;
        description "CFM level 1";
      }
      enum level2 {
        value 2;
        description "CFM level 2";
      }
      enum level3 {
        value 3;
        description "CFM level 3";
      }
      enum level4 {
        value 4;
        description "CFM level 4";
      }
      enum level5 {
        value 5;
        description "CFM level 5";
      }
      enum level6 {
        value 6;
        description "CFM level 6";
      }
      enum level7 {
        value 7;
        description "CFM level 7";
      }
      enum level-invalid {
        value 8;
        description "Invalid CFM level";
      }
    }
    description "CFM level";
  }
  typedef Cfm-bag-direction {
    type enumeration {
      enum direction-up {
        value 0;
        description "Up";
      }
      enum direction-down {
        value 1;
        description "Down";
      }
      enum direction-invalid {
        value 2;
        description "Invalid direction";
      }
    }
    description "MEP direction";
  }
  typedef Cfm-bag-stp-state {
    type enumeration {
      enum stp-up {
        description "Interface is UP";
      }
      enum stp-blocked {
        description "Interface is STP-blocked";
      }
      enum stp-unknown {
        description "Unknown Interface STP state";
      }
    }
    description "CFM STP state";
  }
  typedef Cfm-bag-iw-state {
    type enumeration {
      enum interworking-up {
        description "Interface is UP";
      }
      enum interworking-test {
        description "Interface is in TEST mode";
      }
    }
    description "CFM Interworking state";
  }

  grouping CFM-BAG-SMAN-VPNID-NAME {
    description "Short MA Name VPN ID name";
    leaf oui {
      type uint32;
      description "VPN authority organizationally-unique ID";
    }
    leaf index {
      type uint32;
      description "VPN index";
    }
  }

  grouping CFM-BAG-SMAN-V2 {
    description "Short MA Name types";

    container vpn-id-name {
      when "../short-ma-name-format-value = 'sman-vpn-id'" {
        description "../ShortMANameFormatValue = 'SMAN_VPN_ID'";
      }
      description "VPN ID name";
      uses CFM-BAG-SMAN-VPNID-NAME;
    }
    leaf short-ma-name-format-value {
      type Cfm-bag-sman-fmt;
      description "ShortMANameFormatValue";
    }
    leaf vlan-id-name {
      when "../short-ma-name-format-value = 'sman-vlan-id'" {
        description "../ShortMANameFormatValue = 'SMAN_VLAN_ID'";
      }
      type uint16;
      description "VLAN ID name";
    }
    leaf string-name {
      when "../short-ma-name-format-value = 'sman-string'" {
        description "../ShortMANameFormatValue = 'SMANString'";
      }
      type Cfm-bag-optional-string;
      description "String name";
    }
    leaf integer-name {
      when "../short-ma-name-format-value = 'sman-uint16'" {
        description "../ShortMANameFormatValue = 'SMAN_UINT16'";
      }
      type uint16;
      description "Unsigned integer name";
    }
    leaf icc-based {
      when "../short-ma-name-format-value = 'sman-icc'" {
        description "../ShortMANameFormatValue = 'SMAN_ICC'";
      }
      type Cfm-bag-optional-string;
      description "ICC-based format";
    }
    leaf short-ma-name-data {
      when "../short-ma-name-format-value = 'sman-unknown'" {
        description "../ShortMANameFormatValue = 'SMANUnknown'";
      }
      type Cfm-bag-optional-hex-data;
      description "Hex data";
    }
  }

  grouping CFM-BAG-MDID-MAC-NAME {
    description "MDID MAC name";
    leaf mac-address {
      type Mac-address;
      description "MAC address";
    }
    leaf integer {
      type uint16;
      description "Integer";
    }
  }

  grouping CFM-BAG-MDID-V2 {
    description "MDID types";

    container mac-name {
      when "../mdid-format-value = 'mdid-mac-address'" {
        description "../MDIDFormatValue = 'MDID_MACAddress'";
      }
      description "MAC address name";
      uses CFM-BAG-MDID-MAC-NAME;
    }
    leaf mdid-format-value {
      type Cfm-bag-mdid-fmt;
      description "MDIDFormatValue";
    }
    leaf dns-like-name {
      when "../mdid-format-value = 'mdid-dns-like'" {
        description "../MDIDFormatValue = 'MDID_DNSLike'";
      }
      type Cfm-bag-optional-string;
      description "DNS-like name";
    }
    leaf string-name {
      when "../mdid-format-value = 'mdid-string'" {
        description "../MDIDFormatValue = 'MDIDString'";
      }
      type Cfm-bag-optional-string;
      description "String name";
    }
    leaf mdid-data {
      when "../mdid-format-value = 'mdid-unknown'" {
        description "../MDIDFormatValue = 'MDIDUnknown'";
      }
      type Cfm-bag-optional-hex-data;
      description "Hex data";
    }
  }

  grouping CFM-BAG-SAT-PDU-CAPS {
    description "Satellite PDU Capabilities";
    leaf responder {
      type boolean;
      description "Responder";
    }
    leaf controller {
      type boolean;
      description "Controller";
    }
  }

  grouping CFM-BAG-SAT-ACCESS-PORT-CAPS {
    description "Satellite access port capabilities";

    container loopback {
      description "Loopback";
      uses CFM-BAG-SAT-PDU-CAPS;
    }

    container delay-measurement {
      description "Delay Measurement";
      uses CFM-BAG-SAT-PDU-CAPS;
    }

    container synthetic-loss-measurement {
      description "Synthetic Loss Measurement";
      uses CFM-BAG-SAT-PDU-CAPS;
    }
  }

  grouping CFM-MA-MEP-ERRORS {
    description "CFM MA MEP Errors";

    container mep {
      description "The MEP that has errors";
      uses CFM-MA-MP;
    }

    container service-bridge-domain {
      description
        "BD/XC ID for the MEP's Service, or Service name
        if the Service is 'down-only'";
      uses CFM-BAG-BDID;
    }

    container interface-bridge-domain {
      description
        "ID of the BD/XC that the MEP's EFP is in, if any";
      uses CFM-BAG-BDID;
    }

    container satellite-capabilities {
      description "Satellite Capabilities";
      uses CFM-BAG-SAT-ACCESS-PORT-CAPS;
    }
    leaf ccm-interval {
      type Cfm-bag-ccm-interval;
      description "Interval between CCMs sent on this MEP.";
    }
    leaf no-domain {
      type boolean;
      description "The MEP's Domain is not configured";
    }
    leaf no-service {
      type boolean;
      description "The MEP's Service is not configured";
    }
    leaf bridge-domain-mismatch {
      type boolean;
      description
        "The MEP's EFP is not in the Service's Bridge
        Domain";
    }
    leaf level-conflict {
      type boolean;
      description
        "Another MEP facing in the same direction is at
        the same Maintenance Level";
    }
    leaf ccm-interval-not-supported {
      type boolean;
      description
        "CCM Interval is less than minimum interval
        supported by hardware";
    }
    leaf offload-out-of-resources {
      type boolean;
      description "Offload resource limits have been exceeded";
    }
    leaf offload-multiple-local-mep {
      type boolean;
      description
        "Multiple offloaded MEPs on the same interface
        are not supported.";
    }
    leaf offload-no-cross-check {
      type boolean;
      description
        "The MEP should be offloaded but crosscheck has
        not been configured.";
    }
    leaf offload-multiple-peer-meps {
      type boolean;
      description
        "The MEP should be offloaded but multiple
        crosscheck MEPs have been configured, and this
        is not supported.";
    }
    leaf offload-mep-direction-not-supported {
      type boolean;
      description "The MEP direction does not support offload.";
    }
    leaf ais-configured {
      type boolean;
      description
        "AIS is configured on the same interface as the
        down MEP";
    }
    leaf bundle-level0 {
      type boolean;
      description
        "The MEP is configured in a domain at level 0, on
        a bundle interface or sub-interface.  This is
        not supported";
    }
    leaf bridge-domain-not-in-bd-infra {
      type boolean;
      description
        "A BD/XC specified in the MEG config, but it does
        not exist globally.";
    }
    leaf maid-format-not-supported {
      type boolean;
      description
        "The configured MAID format is not supported for
        hardware offload.";
    }
    leaf sman-format-not-supported {
      type boolean;
      description
        "The configured SMAN format is not supported for
        hardware offload.";
    }
    leaf mdid-format-not-supported {
      type boolean;
      description
        "The configured MDID format is not supported for
        hardware offload.";
    }
    leaf fatal-offload-error {
      type boolean;
      description
        "The platform returned a fatal error when passed
        the offload session.";
    }
    leaf satellite-limitation {
      type boolean;
      description
        "A satellite limitation is preventing MEP being
        offloaded to satellite.";
    }
    leaf sla-loopback-operations-disabled {
      type boolean;
      description
        "In-progress Ethernet SLA loopback operations are
        disabled due to satellite having loopback
        responder-only capabilities.";
    }
    leaf sla-synthetic-loss-operations-disabled {
      type boolean;
      description
        "In-progress Ethernet SLA synthetic loss
        measurement operations are disabled due to
        satellite having synthetic loss measurement
        responder-only capabilities.";
    }
    leaf sla-delay-measurement-operations-disabled {
      type boolean;
      description
        "In-progress Ethernet SLA delay measurement
        operations are disabled due to satellite having
        delay measurement responder-only capabilities.";
    }
    leaf no-valid-mac-address {
      type boolean;
      description
        "The EFP doesn't have a valid MAC address yet.
        This will also get set if the MAC address we
        have is a multicast address.";
    }
    leaf no-interface-type {
      type boolean;
      description
        "We haven't yet been able to look up the
        interface type to find whether the interface is
        a bundle.";
    }
    leaf not-in-im {
      type boolean;
      description "The EFP has been deleted from IM.";
    }
    leaf no-mlacp {
      type boolean;
      description
        "The EFP is a bundle and the mLACP mode is not
        yet known.";
    }
    leaf satellite-error-string {
      type string;
      description "Error string returned from satellite";
    }
    leaf satellite-id {
      type uint16;
      description "ID of the satellite";
    }
  }

  grouping CFM-BAG-BDID {
    description "Bridge domain identifier";
    leaf bridge-domain-id-format {
      type Cfm-bag-bdid-fmt;
      description "Bridge domain identifier format";
    }
    leaf group {
      type string;
      description "Name of the Bridge/XConnect Group";
    }
    leaf name {
      type string;
      description "Name of the Bridge Domain/XConnect";
    }
    leaf ce-id {
      type uint16;
      description "Local Customer Edge Identifier (CE-ID)";
    }
    leaf remote-ce-id {
      type uint16;
      description "Remote Customer Edge Identifier (CE-ID)";
    }
    leaf evi {
      type uint32;
      description "EVPN ID for VLAN-aware flexible cross-connects";
    }
  }

  grouping CFM-MA-MP {
    description "CFM MA Maintenance Point";
    leaf domain-name {
      type string;
      description "Domain name";
    }
    leaf level {
      type Cfm-bag-md-level;
      description "Domain level";
    }
    leaf service-name {
      type string;
      description "Service name";
    }
    leaf interface {
      type xr:Interface-name;
      description "Interface";
    }
    leaf maintenance-point-type {
      type Cfm-ma-mp-variety;
      description "Type of Maintenance Point";
    }
    leaf mep-id {
      type uint16;
      description "MEP ID";
    }
  }

  grouping CFM-MA-MP-BRIEF {
    description "CFM MA Maintenance Point Information";

    container maintenance-point {
      description "Maintenance Point";
      uses CFM-MA-MP;
    }
    leaf mep-has-error {
      type boolean;
      description "MEP error flag";
    }
    leaf mac-address {
      type Mac-address;
      description "MAC Address";
    }
  }

  grouping CFM-MA-SUMMARY {
    description "CFM MA Summary Information";
    leaf domains {
      type uint32;
      description "The number of domains in the CFM database.";
    }
    leaf services {
      type uint32;
      description "The number of services in the CFM database.";
    }
    leaf ccm-rate {
      type uint32;
      description "The combined rate of CCMs on this card.";
    }
    leaf local-meps {
      type uint32;
      description "The number of local MEPs in the CFM database.";
    }
    leaf operational-local-meps {
      type uint32;
      description "The number of operational local MEPs.";
    }
    leaf down-meps {
      type uint32;
      description "The number of down-MEPs.";
    }
    leaf up-meps {
      type uint32;
      description "The number of up-MEPs.";
    }
    leaf offloaded {
      type uint32;
      description
        "The number of MEPs for which CCM processing has
        been offloaded.";
    }
    leaf offloaded-at3-3ms {
      type uint32;
      description
        "The number of MEPs offloaded with CCMs at 3.3ms
        intervals.";
    }
    leaf offloaded-at10ms {
      type uint32;
      description
        "The number of MEPs offloaded with CCMs at 10ms
        intervals.";
    }
    leaf disabled-misconfigured {
      type uint32;
      description
        "The number of local MEPs disabled due to
        configuration errors.";
    }
    leaf disabled-out-of-resources {
      type uint32;
      description
        "The number of local MEPs disabled due to lack of
        resources.";
    }
    leaf disabled-operational-error {
      type uint32;
      description
        "The number of local MEPs disabled due to
        operational errors.";
    }
    leaf peer-meps {
      type uint32;
      description "The number of peer MEPs.";
    }
    leaf operational-peer-meps {
      type uint32;
      description
        "The number of operational peer MEPs recorded in
        the CFM database.";
    }
    leaf peer-meps-with-defects {
      type uint32;
      description "The number of peer MEPs with defects.";
    }
    leaf peer-meps-without-defects {
      type uint32;
      description "The number of peer MEPs without defects.";
    }
    leaf peer-meps-timed-out {
      type uint32;
      description "The number of peer MEPs that have timed out.";
    }
    leaf mips {
      type uint32;
      description "The number of MIPs";
    }
    leaf interfaces {
      type uint32;
      description "The number of interfaces running CFM.";
    }
    leaf bridge-domains-and-xconnects {
      type uint32;
      description "Number or bridge domains and crossconnects.";
    }
    leaf traceroute-cache-entries {
      type uint32;
      description "Number of traceroute cache entries.";
    }
    leaf traceroute-cache-replies {
      type uint32;
      description "Number of traceroute cache replies.";
    }
    leaf ccm-learning-db-entries {
      type uint32;
      description "Number of entries in the CCM learning database.";
    }
    leaf issu-role {
      type Cfm-bag-issu-role;
      description "ISSU Role of CFM-D, if any.";
    }
    leaf bnm-enabled-links {
      type uint32;
      description "Number of BNM Enabled Links";
    }
  }
}
