module Cisco-IOS-XR-spirit-install-act {

    namespace "http://cisco.com/ns/yang/Cisco-IOS-XR-spirit-install-act";

    prefix "Cisco-IOS-XR-spirit-install-act";

    import ietf-inet-types { prefix "inet"; }

    organization "Cisco Systems, Inc.";

    contact
    "Cisco Systems, Inc.
     Customer Service

     Postal: 170 West Tasman Drive
     San Jose, CA 95134

     Tel: +1 800 553-NETS

     E-mail: cs-yang@cisco.com";

    description
    "This module contains a collection of YANG definitions
     for Cisco IOS-XR action package configuration.

     Copyright (c) 2016-2018 by Cisco Systems, Inc.
     All rights reserved.";
  
    revision "2018-09-10" {
        description
            "Added output container with op-id and Error as leaf node";
    }

    revision "2017-10-23" {
        description
            "Yang support for all install action cli's";
    }

    revision "2017-07-27" {
        description
            "IOS XR 6.4.1 revision.";
    }

    rpc install-add {
        description "Cli-command install add source";
        input {
            leaf packagepath {
                type string;
            }

            leaf-list packagename {
                type string;
                max-elements 31;
            }
        }
        output {
            leaf op-id {
                description "operation id of the triggered action";
                type string; 
            }
            leaf Error {
                description "case when op-id is not triggered";
                type string;
            }
        }
    }

   rpc install-commit {
        description "Cli-command install commit";
        input {
            leaf sdr {
               description "commit packages in the system";
               type empty;
            }
        }
        output {
            leaf op-id {
                description "operation id of the triggered action";
                type string; 
            }
            leaf Error {
                description "case when op-id is not triggered";
                type string;
            }
        }
   }

    rpc install-remove {
        description "Cli-command remove";
        input {
           container packages {
               leaf-list packagename {
                 type string;
                 max-elements 32;
               }
           }
           container ids {
               leaf-list id-no {
                 type string;
                 max-elements 32;
               }
           }
           leaf inactive {
               description "Remove inactive packages from XR repo";
               type empty;
           }

           leaf inactiveall {
               description "Remove inactive packages from Host,Sysadmin and XR repo";
               type empty;
           }

        }
        output {
            leaf op-id {
                description "operation id of the triggered action";
                type string; 
            }
            leaf Error {
                description "case when op-id is not triggered";
                type string;
            }
        }
   }

   rpc install-prepare {
        description "Cli-command prepare";
        input {
           container packages {
               leaf-list packagename {
                 type string;
                 max-elements 32;
               }
           }
           container ids {
               leaf-list id-no {
                 type string;
                 max-elements 32;
               }
           }
           leaf clean {
               description "Clean the prepared packages";
               type empty;
           }
           container prepare-force{
               leaf-list packagename {
                 type string;
                 max-elements 32;
               }
               leaf-list ids {
                 type string;
                 max-elements 32;
               }
           }
        }
        output {
            leaf op-id {
                description "operation id of the triggered action";
                type string; 
            }
            leaf Error {
                description "case when op-id is not triggered";
                type string;
            }
        }
   }

   rpc install-activate {
        description "Cli-command activate";
        input {

           container warm {
               leaf-list packagename {
                 type string;
                 max-elements 32;
               }
               leaf-list ids {
                 type string;
                 max-elements 32;
               }
           }

           container warm-force {
               leaf-list packagename {
                 type string;
                 max-elements 32;
               }
               leaf-list ids {
                 type string;
                 max-elements 32;
               }
           }
           container warm-replace {
               leaf-list packagename {
                 type string;
                 max-elements 32;
               }
               leaf-list ids {
                 type string;
                 max-elements 32;
               }
           }

           container warm-replace-force {
               leaf-list packagename {
                 type string;
                 max-elements 32;
               }
               leaf-list ids {
                 type string;
                 max-elements 32;
               }
           }

           container reload {
               leaf-list packagename {
                 type string;
                 max-elements 32;
               }
               leaf-list ids {
                 type string;
                 max-elements 32;
               }
           }

           container reload-force {
               leaf-list packagename {
                 type string;
                 max-elements 32;
               }
               leaf-list ids {
                 type string;
                 max-elements 32;
               }
           }

           container replace {
               leaf-list packagename {
                 type string;
                 max-elements 32;
               }
               leaf-list ids {
                 type string;
                 max-elements 32;
               }
           }

           container replace-force {
               leaf-list packagename {
                 type string;
                 max-elements 32;
               }
               leaf-list ids {
                 type string;
                 max-elements 32;
               }
           }

           container activate-force {
               leaf-list packagename {
                 type string;
                 max-elements 32;
               }
               leaf-list ids {
                 type string;
                 max-elements 32;
               }
           }

           container packages {
               leaf-list packagename {
                 type string;
                 max-elements 32;
               }
           }
           container ids {
               leaf-list id-no {
                 type string;
                 max-elements 32;
                }
           }
           leaf activate_prepared_pkg {
               description "Activate the prepared package";
               type empty;
           }
          leaf force {
               description "Activate the prepared package with force option";
               type empty;
           }
           leaf activate-reload {
               description "Activate the prepared package with reload option";
               type empty;
           }
           leaf activate-reload-force {
               description "Activate the prepared package with reload force option";
               type empty;
           }
           leaf activate_warm_prepared_pkg {
               description "Activate the prepared package with warm option";
               type empty;
           }
           leaf activate_warm_force_prepared_pkg {
               description "Activate the prepared package with warm force option";
               type empty;
           }
           leaf activate_warm_replace_prepared_pkg {
               description "Activate the prepared package with warm replace option";
               type empty;
           }
           leaf activate_warm_force_replace_prepared_pkg {
               description "Activate the prepared package with warm force replace option";
               type empty;
           }
        }
        output {
            leaf op-id {
                description "operation id of the triggered action";
                type string; 
            }
            leaf Error {
                description "case when op-id is not triggered";
                type string;
            }
        }
   }

   rpc install-deactivate {
        description "Cli-command deactivate";
        input {

           container reload {
               leaf-list packagename {
                 type string;
                 max-elements 32;
               }
               leaf-list ids {
                 type string;
                 max-elements 32;
               }
           }
           container packages {
               leaf-list packagename {
                 type string;
                 max-elements 32;
               }
           }
           container ids {
               leaf-list id-no {
                 type string;
                 max-elements 32;
               }
           }
           leaf superseded {
               description "Deactivate all superseded packages";
               type empty;
           }
        }
        output {
            leaf op-id {
                description "operation id of the triggered action";
                type string; 
            }
            leaf Error {
                description "case when op-id is not triggered";
                type string;
            }
        }
   }

   rpc install-extract {
        description "Cli-command extract";
        input {
           container packages {
               leaf-list packagename {
                 type string;
                 max-elements 1;
               }
           }
        }
        output {
            leaf op-id {
                description "operation id of the triggered action";
                type string; 
            }
            leaf Error {
                description "case when op-id is not triggered";
                type string;
            }
        }
   }

   rpc install-verify {
        description "Cli-command install verify packages";
        input {
            leaf-list location {
               type string;
               max-elements 32;
            }
        }
        output {
            leaf op-id {
                description "operation id of the triggered action";
                type string; 
            }
            leaf Error {
                description "case when op-id is not triggered";
                type string;
            }
        }
   }
   
   rpc install-update {
       description "Cli-command install update";
       input {
           leaf packagepath {
               type string;
           }

           leaf-list packagename {
               type string;
               max-elements 31;
           }

           container warm {
               leaf packagepath {
                   type string;
               }

               leaf-list packagename {
                   type string;
                   max-elements 31; 
               }
           }

           container warm-force {
               leaf packagepath {
                   type string;
               }

               leaf-list packagename {
                   type string;
                   max-elements 31; 
               }
           }

           container warm-replace {
               leaf packagepath {
                   type string;
               }

               leaf-list packagename {
                   type string;
                   max-elements 31; 
               }
           }

           container warm-replace-force {
               leaf packagepath {
                   type string;
               }

               leaf-list packagename {
                   type string;
                   max-elements 31; 
               }
           }

           container force {
               leaf packagepath {
                   type string;
               }

               leaf-list packagename {
                   type string;
                   max-elements 31; 
               }
           }

           container replace {
               leaf packagepath {
                   type string;
               }

               leaf-list packagename {
                   type string;
                   max-elements 31; 
               }
           }

           container replace-force {
               leaf packagepath {
                   type string;
               }

               leaf-list packagename {
                   type string;
                   max-elements 31; 
               }
           }

           container replace-commit {
               leaf packagepath {
                   type string;
               }

               leaf-list packagename {
                   type string;
                   max-elements 31; 
               }
           }

           container replace-commit-force {
               leaf packagepath {
                   type string;
               }

               leaf-list packagename {
                   type string;
                   max-elements 31; 
               }
           }
           
       }
       output {
            leaf op-id {
                description "operation id of the triggered action";
                type string; 
            }
            leaf Error {
                description "case when op-id is not triggered";
                type string;
            }
       }
   }
}
