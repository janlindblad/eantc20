module Cisco-IOS-XR-man-ems-cfg {

  /*** NAMESPACE / PREFIX DEFINITION ***/

  namespace "http://cisco.com/ns/yang/Cisco-IOS-XR-man-ems-cfg";


  prefix "Cisco-IOS-XR-man-ems-cfg";

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR man-ems package configuration.

     This module contains definitions
     for the following management objects:
       grpc: GRPC configruation

     Copyright (c) 2013-2018 by Cisco Systems, Inc.
     All rights reserved.";

  revision "2018-04-16" {
    description
      "Added max-streams, max-streams-per-user, tls-cipher, and dscp.";
  }

  revision "2015-11-09" {
    description
      "IOS XR 6.0 revision.";
  }

  typedef Dscp {
    type union {
      type enumeration {
        enum default {
          value 0;
          description "Default (DSCP 000000)";
        }
        enum af11 {
          value 10;
          description "AF11 (DSCP 001010)";
        }
        enum af12 {
          value 12;
          description "AF12 (DSCP 001100)";
        }
        enum af13 {
          value 14;
          description "AF13 (DSCP 001110)";
        }
        enum af21 {
          value 18;
          description "AF21 (DSCP 010010)";
        }
        enum af22 {
          value 20;
          description "AF22 (DSCP 010100)";
        }
        enum af23 {
          value 22;
          description "AF23 (DSCP 010110)";
        }
        enum af31 {
          value 26;
          description "AF31 (DSCP 011010)";
        }
        enum af32 {
          value 28;
          description "AF32 (DSCP 011100)";
        }
        enum af33 {
          value 30;
          description "AF33 (DSCP 011110)";
        }
        enum af41 {
          value 34;
          description "AF41 (DSCP 100010)";
        }
        enum af42 {
          value 36;
          description "AF42 (DSCP 100100)";
        }
        enum af43 {
          value 38;
          description "AF43 (DSCP 100110)";
        }
        enum cs1 {
          value 8;
          description "CS1 (Precedence 1) (DSCP 001000)";
        }
        enum cs2 {
          value 16;
          description "CS2 (Precedence 2) (DSCP 010000)";
        }
        enum cs3 {
          value 24;
          description "CS3 (Precedence 3) (DSCP 011000)";
        }
        enum cs4 {
          value 32;
          description "CS4 (Precedence 4) (DSCP 100000)";
        }
        enum cs5 {
          value 40;
          description "CS5 (Precedence 5) (DSCP 101000)";
        }
        enum cs6 {
          value 48;
          description "CS6 (Precedence 6) (DSCP 110000)";
        }
        enum cs7 {
          value 56;
          description "CS7 (Precedence 7) (DSCP 111000)";
        }
        enum ef {
          value 46;
          description "EF (DSCP 101110)";
        }
      }
      type uint32 {
        range "0..63";
      }
    }
    description "Dscp";
  }
  typedef Grp-c-tls-cipher-default {
    type enumeration {
      enum disable {
        value 1;
        description "Default disable all ciphers";
      }
      enum enable {
        value 2;
        description "Default enable all ciphers";
      }
    }
    description "Grp c tls cipher default";
  }

  container grpc {
    description "GRPC configruation";

    container service-layer {
      description "Service Layer";
      leaf enable {
        type empty;
        description "Enable ServiceLayer";
      }
    }

    container tls-cipher {
      description "TLS ciphers";
      leaf default {
        type Grp-c-tls-cipher-default;
        description "Default of all ciphers.";
      }
      leaf enable {
        type string;
        description "Enable ciphers if default is disabled.";
      }
      leaf disable {
        type string;
        description "Disable ciphers if default is enabled.";
      }
    }

    container tls {
      description "Transport Layer Security (TLS)";
      leaf enable {
        status deprecated;
        type empty;
        description "Enable TLS";
      }
    }
    leaf port {
      type uint32 {
        range "10000..57999";
      }
      description "Server listening port";
    }
    leaf vrf {
      type string;
      description "Server vrf name";
    }
    leaf max-streams {
      type uint32 {
        range "1..128";
      }
      default "32";
      description "Maximum number of streaming gRPCs";
    }
    leaf enable {
        status deprecated;
      type empty;
      description "Enable GRPC";
    }
    leaf max-streams-per-user {
      type uint32 {
        range "1..128";
      }
      default "32";
      description "Maximum number of streaming gRPCs per user";
    }
    leaf max-request-per-user {
      type uint32 {
        range "1..32";
      }
      description "Maximum concurrent requests per user";
    }
    leaf no-tls {
      type empty;
      description "No TLS";
    }
    leaf tls-trustpoint {
      type string;
      description "Trustpoint Name";
    }
    leaf dscp {
      type Dscp;
      description "QoS marking DSCP to be set on transmitted gRPC";
    }
    leaf address-family {
      type string;
      description "Address family identifier type";
    }
    leaf tls-mutual {
      type empty;
      description "TLS mutual authentication";
    }
    leaf max-request-total {
      type uint32 {
        range "1..256";
      }
      description "Maximum concurrent requests in total";
    }
  }
}
