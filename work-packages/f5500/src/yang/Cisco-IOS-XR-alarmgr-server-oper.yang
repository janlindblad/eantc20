module Cisco-IOS-XR-alarmgr-server-oper {

  /*** NAMESPACE / PREFIX DEFINITION ***/

  namespace "http://cisco.com/ns/yang"+
    "/Cisco-IOS-XR-alarmgr-server-oper";


  prefix "Cisco-IOS-XR-alarmgr-server-oper";

  /*** LINKAGE (IMPORTS / INCLUDES) ***/

  import Cisco-IOS-XR-types { prefix "xr"; }

  include Cisco-IOS-XR-alarmgr-server-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR alarmgr-server package operational data.

     This module contains definitions
     for the following management objects:
       alarms: Show Alarms associated with XR

     Copyright (c) 2013-2018 by Cisco Systems, Inc.
     All rights reserved.";

  revision "2015-11-09" {
    description
      "IOS XR 6.0 revision.";
  }


  container alarms {
    config false;
    description "Show Alarms associated with XR";

    container detail {
      description "A set of detail alarm commands.";

      container detail-system {
        description "show detail system scope alarm related data.";

        container conditions {
          description "Show the Conditions present at this scope.";
          uses ALARM-MGR-SHOW-ALARM-INFO-CLI;
        }

        container active {
          description "Show the active alarms at this scope.";
          uses ALARM-MGR-SHOW-ALARM-INFO-CLI;
        }

        container history {
          description "Show the history alarms at this scope.";
          uses ALARM-MGR-SHOW-ALARM-INFO-CLI;
        }

        container suppressed {
          description "Show the suppressed alarms at this scope.";
          uses ALARM-MGR-SHOW-ALARM-INFO-SUPPR-CLI;
        }

        container stats {
          description "Show the service statistics.";
          uses ALARM-MGR-SHOW-ALARM-STATS;
        }

        container clients {
          description
            "Show the clients associated with this service.";
          uses ALARM-MGR-SHOW-CLIENT-INFO;
        }
      }

      container detail-card {
        description "Show detail card scope alarm related data.";

        container detail-locations {
          description "Table of DetailLocation";

          list detail-location {
            key "node-id";
            description "Specify a card location for alarms.";

            container conditions {
              description
                "Show the conditions present at this scope.";
              uses ALARM-MGR-SHOW-ALARM-INFO-CLI;
            }

            container active {
              description "Show the active alarms at this scope.";
              uses ALARM-MGR-SHOW-ALARM-INFO-CLI;
            }

            container history {
              description "Show the history alarms at this scope.";
              uses ALARM-MGR-SHOW-ALARM-INFO-CLI;
            }

            container suppressed {
              description
                "Show the suppressed alarms at this scope.";
              uses ALARM-MGR-SHOW-ALARM-INFO-SUPPR-CLI;
            }

            container stats {
              description "Show the service statistics.";
              uses ALARM-MGR-SHOW-ALARM-STATS;
            }

            container clients {
              description
                "Show the clients associated with this
                service.";
              uses ALARM-MGR-SHOW-CLIENT-INFO;
            }
            leaf node-id {
              type xr:Node-id;
              description "NodeID of the Location";
            }
          }
        }
      }
    }

    container brief {
      description "A set of brief alarm commands.";

      container brief-card {
        description "Show brief card scope alarm related data.";

        container brief-locations {
          description "Table of BriefLocation";

          list brief-location {
            key "node-id";
            description "Specify a card location for alarms.";

            container conditions {
              description
                "Show the conditions present at this scope.";
              uses ALARM-MGR-SHOW-ALARM-BRIEF-INFO;
            }

            container active {
              description "Show the active alarms at this scope.";
              uses ALARM-MGR-SHOW-ALARM-BRIEF-INFO;
            }

            container history {
              description "Show the history alarms at this scope.";
              uses ALARM-MGR-SHOW-ALARM-BRIEF-INFO;
            }

            container suppressed {
              description
                "Show the suppressed alarms at this scope.";
              uses ALARM-MGR-SHOW-ALARM-BRIEF-SUPPR-INFO;
            }
            leaf node-id {
              type xr:Node-id;
              description "NodeID of the Location";
            }
          }
        }
      }

      container brief-system {
        description "Show brief system scope alarm related data.";

        container conditions {
          description "Show the conditions present at this scope.";
          uses ALARM-MGR-SHOW-ALARM-BRIEF-INFO;
        }

        container active {
          description "Show the active alarms at this scope.";
          uses ALARM-MGR-SHOW-ALARM-BRIEF-INFO;
        }

        container history {
          description "Show the history alarms at this scope.";
          uses ALARM-MGR-SHOW-ALARM-BRIEF-INFO;
        }

        container suppressed {
          description "Show the suppressed alarms at this scope.";
          uses ALARM-MGR-SHOW-ALARM-BRIEF-SUPPR-INFO;
        }
      }
    }
  }
}
