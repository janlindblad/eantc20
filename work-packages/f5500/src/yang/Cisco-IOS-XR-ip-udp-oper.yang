module Cisco-IOS-XR-ip-udp-oper {

  /*** NAMESPACE / PREFIX DEFINITION ***/

  namespace "http://cisco.com/ns/yang/Cisco-IOS-XR-ip-udp-oper";


  prefix "Cisco-IOS-XR-ip-udp-oper";

  /*** LINKAGE (IMPORTS / INCLUDES) ***/

  import Cisco-IOS-XR-types { prefix "xr"; }

  include Cisco-IOS-XR-ip-udp-oper-sub4 {
    revision-date 2018-08-09;
  }

  include Cisco-IOS-XR-ip-udp-oper-sub3 {
    revision-date 2018-08-09;
  }

  include Cisco-IOS-XR-ip-udp-oper-sub2 {
    revision-date 2018-08-09;
  }

  include Cisco-IOS-XR-ip-udp-oper-sub1 {
    revision-date 2018-08-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-udp package operational data.

     This module contains definitions
     for the following management objects:
       udp: IP UDP Operational Data
       udp-connection: udp connection

     Copyright (c) 2013-2018 by Cisco Systems, Inc.
     All rights reserved.";

  revision "2018-08-09" {
    description
      "bind_local field is added to PCB_DETAIL output";
  }

  revision "2018-03-04" {
    description
      "PCB_ID argument is passed in string format.";
  }

  revision "2017-09-07" {
    description
      "Fixed type translation error.";
  }

  revision "2016-02-26" {
    description
      "Descriptions updated.";
  }

  revision "2015-11-09" {
    description
      "IOS XR 6.0 revision.";
  }

  typedef Lpts-pcb-query {
    type enumeration {
      enum all {
        value 0;
        description "No filter";
      }
      enum static-policy {
        value 1;
        description "Static policy filter";
      }
      enum interface {
        value 2;
        description "Interface filter";
      }
      enum packet {
        value 3;
        description "Packet type filter";
      }
    }
    description "Lpts pcb query";
  }

  container udp {
    config false;
    description "IP UDP Operational Data";

    container nodes {
      description "Node-specific UDP operational data";

      list node {
        key "node-name";
        description "UDP operational data for a particular node";

        container statistics {
          description "Statistical UDP operational data for a node";

          container ipv4-traffic {
            description "UDP Traffic statistics for IPv4";
            uses IP-UDP;
          }

          container ipv6-traffic {
            description "UDP Traffic statistics for IPv6";
            uses IP-UDP;
          }
        }
        leaf node-name {
          type xr:Node-id;
          description "Node name";
        }
      }
    }
  }

  container udp-connection {
    config false;
    description "udp connection";

    container nodes {
      description "List of UDP connections nodes";

      list node {
        key "node-name";
        description "Information about a particular node";

        container statistics {
          description "Statistics of UDP connections";

          container clients {
            description "Table listing clients";

            list client {
              key "client-id";
              description "Describing Client ID";
              leaf client-id {
                type uint32 {
                  range "0..4294967295";
                }
                description
                  "Displaying client's aggregated statistics";
              }
              uses TRANSP-CLIENT-STATS-BAG;
            }
          }

          container summary {
            description
              "Summary statistics across all UDP connections";
            uses UDP-SH-STATS-BAG;
          }

          container pcb-statistics {
            description
              "Table listing the UDP connections for which
              statistics are provided";

            list pcb-statistic {
              key "pcb-address";
              description
                "Satistics associated with a particular PCB";
              leaf pcb-address {
                type xr:Cisco-ios-xr-string;
                description "Protocol Control Block address";
              }
              uses UDP-SH-PCB-STATS-BAG;
            }
          }
        }

        container lpts {
          description "LPTS statistical data";

          container queries {
            description "List of query options";

            list query {
              key "query-name";
              description "Query option";

              container pcbs {
                description "List of PCBs";

                list pcb {
                  key "pcb-address";
                  description "A PCB information";
                  leaf pcb-address {
                    type xr:Cisco-ios-xr-string;
                    description "PCB address";
                  }
                  uses SHOW-PCB-INFO;
                }
              }
              leaf query-name {
                type Lpts-pcb-query;
                description "Query option";
              }
            }
          }
        }

        container pcb-details {
          description
            "Detail information for list of UDP connections
            .";

          list pcb-detail {
            key "pcb-address";
            description "Detail information about a UDP connection";
            leaf pcb-address {
              type xr:Cisco-ios-xr-string;
              description "Protocol Control Block address";
            }
            uses UDP-SH-TABLE-BAG;
          }
        }

        container pcb-briefs {
          description
            "Brief information for list of UDP connections.";

          list pcb-brief {
            key "pcb-address";
            description "Brief information about a UDP connection";
            leaf pcb-address {
              type xr:Cisco-ios-xr-string;
              description "Protocol Control Block address";
            }
            uses UDP-SH-BRIEF-BAG;
          }
        }
        leaf node-name {
          type xr:Node-id;
          description "Node name";
        }
      }
    }
  }
}
