submodule Cisco-IOS-XR-ofa-dpt-oper-sub1 {

  belongs-to Cisco-IOS-XR-ofa-dpt-oper {
    prefix Cisco-IOS-XR-ofa-dpt-oper-sub1;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ofa-dpt package operational data.

     Copyright (c) 2013-2018 by Cisco Systems, Inc.
     All rights reserved.";

  revision "2015-11-09" {
    description
      "IOS XR 6.0 revision.";
  }

  typedef Dpa-dpt-port-dir {
    type enumeration {
      enum transmit {
        value 0;
        description "Transmit Directtion";
      }
      enum receive {
        value 1;
        description "Receive Direction";
      }
    }
    description "Directtion of the Port";
  }
  typedef Dpa-dpt-histogram {
    type enumeration {
      enum sms-main-buffer-pool {
        value 0;
        description "sms main buffer pool";
      }
      enum ics-slice-active-contexts {
        value 1;
        description "Ingress Schd slice active contexts";
      }
      enum ics-slice-dram-active-contexts {
        value 2;
        description "DRAM active contexts";
      }
      enum sms-main-read-latency0 {
        value 3;
        description "Main SMS memory latency0";
      }
    }
    description "DPA DPT Histogram Type";
  }
  typedef Dpa-dpt-histogram-category {
    type enumeration {
      enum static {
        value 0;
        description "Time based histogram.";
      }
      enum rate {
        value 1;
        description "Rate based histogram";
      }
      enum event {
        value 2;
        description "Event based histogram";
      }
    }
    description "DPA DPT Histogram Category";
  }
  typedef Dpa-dpt-unit-of-measure {
    type enumeration {
      enum packets {
        value 0;
        description "Packets";
      }
      enum bytes {
        value 1;
        description "Bytes";
      }
      enum buffers {
        value 2;
        description "Buffers";
      }
      enum flows {
        value 3;
        description "Flows";
      }
      enum queues {
        value 4;
        description "queues";
      }
      enum flows-per-time-int {
        value 5;
        description "Flows Per Time Interval";
      }
      enum nano-seconds {
        value 6;
        description "Nano Seconds";
      }
      enum micro-seconds {
        value 7;
        description "Micro Seconds";
      }
      enum mili-seconds {
        value 8;
        description "Mili Seconds";
      }
      enum seconds {
        value 9;
        description "Seconds";
      }
      enum nanosec256 {
        value 10;
        description "256 Nano Seconds";
      }
      enum packet-rate-in-mbps {
        value 11;
        description "Packet Rate in Mbps";
      }
      enum packet-rate-in-gbps {
        value 12;
        description "Packet Rate in Gbps";
      }
    }
    description "DPA DPT Histogram unit of expression";
  }
  typedef Ofa-dpt-pkt-drop-sub {
    type enumeration {
      enum ofa-dpt-pd-invalid-drop-sub-type {
        value 0;
        description " Invalid drop type";
      }
      enum egq-cnm-cnt-drops {
        value 1;
        description " JERICHO EGQ BLOCK CnmCntDrops";
      }
      enum egq-crc-err-fabric-cnt {
        value 2;
        description " JERICHO EGQ BLOCK CrcErrFabricCnt ";
      }
      enum egq-crc-err-others-cnt {
        value 3;
        description " JERICHO EGQ BLOCK CrcErrOthersCnt";
      }
      enum egq-cup-err-fabric-cnt {
        value 4;
        description " JERICHO EGQ BLOCK CupErrFabricCnt";
      }
      enum egq-cup-err-others-cnt {
        value 5;
        description " JERICHO EGQ BLOCK";
      }
      enum egq-dbg-prp-sop-dscrd-mask-dis-cnt-err-in {
        value 6;
        description
          " JERICHO EGQ BLOCK
          DbgPrpSopDscrdMaskDisCntErrIn";
      }
      enum egq-dbg-prp-sop-dscrd-mask-dis-cnt-dif-nrdy {
        value 7;
        description
          " JERICHO EGQ BLOCK
          DbgPrpSopDscrdMaskDisCntDifNrdy";
      }
      enum egq-dbg-prp-sop-dscrd-mask-dis-cnt-cgm {
        value 8;
        description
          " JERICHO EGQ BLOCK DbgPrpSopDscrdMaskDisCntCgm";
      }
      enum egq-dbg-prp-sop-dscrd-mask-dis-cnt-fbc {
        value 9;
        description
          " JERICHO EGQ BLOCK DbgPrpSopDscrdMaskDisCntFbc";
      }
      enum egq-dbg-fabric0-dis-cnt {
        value 10;
        description " JERICHO EGQ BLOCK DbgFabric0DisCnt";
      }
      enum egq-dbg-fabric1is-cnt {
        value 11;
        description " JERICHO EGQ BLOCK DbgFabric1DisCnt";
      }
      enum egq-dbg-fabric2-dis-cnt {
        value 12;
        description " JERICHO EGQ BLOCK DbgFabric2DisCnt";
      }
      enum egq-dbg-ipt-mask-dis-cnt {
        value 13;
        description " JERICHO EGQ BLOCK DbgIptMaskDisCnt";
      }
      enum egq-dbg-mc-mesh-mask-dis-cnt {
        value 14;
        description " JERICHO EGQ BLOCK DbgMcMeshMaskDisCnt";
      }
      enum egq-dbg-tdm-dis-cnt {
        value 15;
        description " JERICHO EGQ BLOCK DbgTdmDisCnt";
      }
      enum egq-ehp-dscrd-pkt-cnt {
        value 16;
        description " JERICHO EGQ BLOCK EhpDscrdPktCnt";
      }
      enum egq-ehp-multicast-high-dscrds-cnt {
        value 17;
        description " JERICHO EGQ BLOCK EhpMulticastHighDscrdsCnt";
      }
      enum egq-ehp-multicast-low-dscrds-cnt {
        value 18;
        description " JERICHO EGQ BLOCKEhpMulticastLowDscrdsCnt ";
      }
      enum egq-erpp-lag-pruning-dscrds-cnt {
        value 19;
        description " JERICHO EGQ BLOCK ErppLagPruningDscrdsCnt";
      }
      enum egq-erpp-pmf-dscrds-cnt {
        value 20;
        description " JERICHO EGQ BLOCK ErppPmfDscrdsCnt";
      }
      enum egq-erpp-vlan-membership-dscrds-cnt {
        value 21;
        description
          " JERICHO EGQ BLOCK ErppVlanMembershipDscrdsCnt";
      }
      enum egq-pqp-dscrd-multicast-pkt-cnt {
        value 22;
        description " JERICHO EGQ BLOCK PqpDscrdMulticastPktCnt";
      }
      enum egq-pqp-dscrd-unicast-pkt-cnt {
        value 23;
        description " JERICHO EGQ BLOCK PqpDscrdUnicastPktCnt";
      }
      enum epni-epe-dscrd-pkts-cnt {
        value 30;
        description " JERICHO EPNI BLOCK EpeDscrdPktsCnt";
      }
      enum fcr-credit-drop-cnt {
        value 31;
        description " JERICHO FCR BLOCK CreditDropCnt";
      }
      enum fcr-fs-drop-cnt {
        value 32;
        description " JERICHO FCR BLOCK FsDropCnt";
      }
      enum fcr-reach-drop-cnt {
        value 33;
        description " JERICHO FCR BLOCK CellDropCnt1 ";
      }
      enum fda-egq-fab0-ovf-drop-cnt {
        value 40;
        description " JERICHO FDA BLOCK EgqFab0OvfDropCnt";
      }
      enum fda-egq-fab1-ovf-drop-cnt {
        value 41;
        description " JERICHO FDA BLOCK EgqFab1OvfDropCnt";
      }
      enum fda-egq-fab2-ovf-drop-cnt {
        value 42;
        description " JERICHO FDA BLOCK EgqFab2OvfDropCnt";
      }
      enum fda-egq-fab-drop-cnt {
        value 43;
        description " JERICHO FDA BLOCK EgqFabDropCnt";
      }
      enum fda-egq-fabfif0-prio0-drop-cnt {
        value 44;
        description " JERICHO FDA BLOCK EgqFabfif0Prio0DropCnt";
      }
      enum fda-egq-fabfif0-prio1-drop-cnt {
        value 45;
        description " JERICHO FDA BLOCK EgqFabfif0Prio1DropCnt";
      }
      enum fda-egq-fabfif0-prio2-drop-cnt {
        value 46;
        description " JERICHO FDA BLOCK EgqFabfif0Prio2DropCnt";
      }
      enum fda-egq-fabfif1-prio0-drop-cnt {
        value 47;
        description " JERICHO FDA BLOCK EgqFabfif1Prio0DropCnt";
      }
      enum fda-egq-fabfif1-prio1-drop-cnt {
        value 48;
        description " JERICHO FDA BLOCK EgqFabfif1Prio1DropCnt";
      }
      enum fda-egq-fabfif1-prio2-drop-cnt {
        value 49;
        description " JERICHO FDA BLOCK EgqFabfif1Prio2DropCnt";
      }
      enum fda-egq-fabfif2-prio0-drop-cnt {
        value 50;
        description " JERICHO FDA BLOCK EgqFabfif2Prio0DropCnt";
      }
      enum fda-egq-fabfif2-prio1-drop-cnt {
        value 51;
        description " JERICHO FDA BLOCK EgqFabfif2Prio1DropCnt";
      }
      enum fda-egq-fabfif2-prio2-drop-cnt {
        value 52;
        description " JERICHO FDA BLOCK EgqFabfif2Prio2DropCnt";
      }
      enum fda-egq-ipt-drop-cnt {
        value 53;
        description " JERICHO FDA BLOCK EgqIptDropCnt";
      }
      enum fda-egq-meshmc-drop-cnt {
        value 54;
        description " JERICHO FDA BLOCK EgqMeshmcDropCnt";
      }
      enum fda-egq-meshmc-ovf-drop-cnt {
        value 55;
        description " JERICHO FDA BLOCK EgqMeshmcOvfDropCnt";
      }
      enum fda-egq-meshmc-prio0-drop-cnt {
        value 56;
        description " JERICHO FDA BLOCK EgqMeshmcPrio0DropCnt";
      }
      enum fda-egq-meshmc-prio1-drop-cnt {
        value 57;
        description " JERICHO FDA BLOCK EgqMeshmcPrio1DropCnt";
      }
      enum fda-egq-meshmc-prio2-drop-cnt {
        value 58;
        description " JERICHO FDA BLOCK EgqMeshmcPrio2DropCnt";
      }
      enum fda-egq-tdm-drop-cnt {
        value 59;
        description " JERICHO FDA BLOCK EgqTdmDropCnt";
      }
      enum fda-fab-mct-drop-cnt {
        value 60;
        description " JERICHO FDA BLOCK FabMctDropCnt";
      }
      enum fdr-p1fdr-dscrd-cnt-a {
        value 61;
        description " JERICHO FDA BLOCK P1FDRDscrdCntA";
      }
      enum fdr-p1fdr-dscrd-cnt-b {
        value 62;
        description " JERICHO FDA BLOCK P1FDRDscrdCntB";
      }
      enum fdr-p1fdr-fifo-dscrd-cnt-a {
        value 63;
        description " JERICHO FDA BLOCK P1FDRFifoDscrdCntA";
      }
      enum fdr-p1fdr-fifo-dscrd-cnt-b {
        value 64;
        description " JERICHO FDA BLOCK P1FDRFifoDscrdCntB";
      }
      enum fdr-p2fdr-dscrd-cnt-a {
        value 65;
        description " JERICHO FDA BLOCK P2FDRDscrdCntA";
      }
      enum fdr-p2fdr-dscrd-cnt-b {
        value 66;
        description " JERICHO FDA BLOCK P2FDRDscrdCntB";
      }
      enum fdr-p2fdr-fifo-dscrd-cnt-a {
        value 67;
        description " JERICHO FDA BLOCK P2FDRFifoDscrdCntA";
      }
      enum fdr-p2fdr-fifo-dscrd-cnt-b {
        value 68;
        description " JERICHO FDA BLOCK P2FDRFifoDscrdCntB";
      }
      enum fdr-p3fdr-dscrd-cnt-a {
        value 69;
        description " JERICHO FDA BLOCK P3FDRDscrdCntA";
      }
      enum fdr-p3fdr-dscrd-cnt-b {
        value 70;
        description " JERICHO FDA BLOCK P3FDRDscrdCntB";
      }
      enum fdr-p3fdr-fifo-dscrd-cnt-a {
        value 71;
        description " JERICHO FDA BLOCK P3FDRFifoDscrdCntA";
      }
      enum fdr-p3fdr-fifo-dscrd-cnt-b {
        value 72;
        description " JERICHO FDA BLOCK P3FDRFifoDscrdntB";
      }
      enum fdt-unrch-dest-dscrd-cells-cnt {
        value 73;
        description " JERICHO FDA BLOCK UnrchDestDscrdCellsCnt";
      }
      enum idr-dscrd-bytes-cnt {
        value 80;
        description " JERICHO IDR BLOCK DscrdBytesCnt";
      }
      enum idr-dscrd-pkts-cnt {
        value 81;
        description " JERICHO IDR BLOCK DscrdPktsCnt";
      }
      enum ipt-deleted-cnm-pkts-cnt {
        value 90;
        description " JERICHO IPT BLOCK DeletedCnmPktsCnt";
      }
      enum ipt-deleted-lat-pkts-cnt {
        value 91;
        description " JERICHO IPT BLOCK DeletedLatPktsCnt";
      }
      enum iqm-dequeue-deleted-pkt-cnt {
        value 100;
        description " JERICHO IQM BLOCK DequeueDeletedPktCnt";
      }
      enum iqm-dyn-reject-pkt-cnts {
        value 101;
        description " JERICHO IQM BLOCK DynRejectPktCnts";
      }
      enum iqm-enqueue-dscrd-pkt-cnt {
        value 102;
        description " JERICHO IQM BLOCK EnqueueDscrdPktCnt";
      }
      enum iqm-queue-deleted-pkt-cnt {
        value 103;
        description " JERICHO IQM BLOCK QueueDeletedPktCnt";
      }
      enum iqm-queue-deq-delete-byte-cnt {
        value 104;
        description " JERICHO IQM BLOCK QueueDeqDeleteByteCnt";
      }
      enum iqm-queue-enq-dscrd-byte-cnt {
        value 105;
        description " JERICHO IQM BLOCK QueueEnqDscrdByteCnt";
      }
      enum iqm-queue-enq-dscrd-pkt-cnt {
        value 106;
        description " JERICHO IQM BLOCK QueueEnqDscrdPktCnt";
      }
      enum iqm-rjct-bdb-pkt-cnt {
        value 107;
        description " JERICHO IQM BLOCK IQM_RjctBdbPktCnt";
      }
      enum iqm-rjct-bdb-protct-pkt-cnt {
        value 108;
        description " JERICHO IQM BLOCK IQM_RjctBdbProtctPktCnt";
      }
      enum iqm-rjct-buff-type-err-pkt-cnt {
        value 109;
        description " JERICHO IQM BLOCK IQM_RjctBuffTypeErrPktCnt";
      }
      enum iqm-rjct-cnm-pkt-cnt {
        value 110;
        description " JERICHO IQM BLOCK IQM_RjctCnmPktCnt";
      }
      enum iqm-rjct-db-pkt-cnt {
        value 111;
        description " JERICHO IQM BLOCK IQM_RjctDbPktCnt";
      }
      enum iqm-rjct-dram-ineligible-pkt-cnt {
        value 112;
        description
          " JERICHO IQM BLOCK IQM_RjctDramIneligiblePktCnt";
      }
      enum iqm-rjct-isp-dup-pkt-cnt {
        value 113;
        description " JERICHO IQM BLOCK IQM_RjctIspDupPktCnt";
      }
      enum iqm-rjct-mc-err-pkt-cnt {
        value 114;
        description " JERICHO IQM BLOCK RjctMcErrPktCnt";
      }
      enum iqm-rjct-oc-bd-pkt-cnt {
        value 115;
        description " JERICHO IQM BLOCK IQM_RjctOcBdPktCnt";
      }
      enum iqm-rjct-qnum-ovf-pkt-cnt {
        value 116;
        description " JERICHO IQM BLOCK IQM_RjctQnumOvfPktCnt";
      }
      enum iqm-rjct-qnvalid-err-pkt-cnt {
        value 117;
        description " JERICHO IQM BLOCK IQM_RjctQnvalidErrPktCnt";
      }
      enum iqm-rjct-rsrc-err-pkt-cnt {
        value 118;
        description " JERICHO IQM BLOCK IQM_RjctRsrcErrPktCnt";
      }
      enum iqm-tot-delete-byte-cnt {
        value 119;
        description " JERICHO IQM BLOCK TotDeleteByteCnt";
      }
      enum iqm-tot-dscrd-byte-cnt {
        value 120;
        description " JERICHO IQM BLOCK TotDscrdByteCnt";
      }
      enum ire-pipe-bad-reassembly-context-pkt-cnt {
        value 130;
        description
          " JERICHO IRE BLOCK
          PipeBadReassemblyContextPktCnt";
      }
      enum nbih-num-dropped-bursts-cnt-rx-hrf {
        value 140;
        description " JERICHO NBIH BLOCK NumDroppedBurstsCntRxHrf";
      }
      enum nbih-pkt-drop-cnt-rx-hrf {
        value 141;
        description " JERICHO NBIH BLOCK PktDropCntRxHrf";
      }
      enum nbih-prd-pkt-drop-cnt-port {
        value 142;
        description " JERICHO NBIH BLOCK PrdPktDropCntPort";
      }
      enum nbih-rx-elk-burst-drop-cnt-elk {
        value 143;
        description " JERICHO NBIH BLOCK RxElkBurstDropCntElk";
      }
      enum nbih-rx-pkt-drop-cnt {
        value 144;
        description " JERICHO NBIH BLOCK RxPktDropCnt";
      }
      enum nbih-rx-pkt-fc-err-cnt {
        value 145;
        description " JERICHO NBIH BLOCK RxPktFcErrCnt";
      }
      enum ofa-dpt-drop-sub-type-max {
        value 171;
        description " Invlalid drop type, used for max count";
      }
    }
    description "DPT Packet Drop Counter Sub Type";
  }

  grouping OFA-DPT-EGRESS-MICROBURST-EVENT-INFO {
    description "VOQ Congestion Info Block";
    leaf time-stamp {
      type uint64;
      description "Timestamp";
    }
    leaf rack-number {
      type uint8;
      description "Rack number";
    }
    leaf slot-number {
      type uint8;
      description "Slot number";
    }
    leaf npu-number {
      type uint8;
      description "NPU number";
    }
    leaf npu-core-num {
      type uint8;
      description "NPU core";
    }

    list voq-info-array {
      description " VOQ Microburst Info Array";
      uses OFA-DPT-VOQ-INFO;
    }
  }

  grouping DPT-TELEMETRY-PORT-HISTOGRAM-BLOCK-INFO {
    description "PortHistogram Info Block";

    container loc-info {
      description "Location Info";
      uses DPA-DPT-LOC-INFO;
    }

    container gen-info {
      description "General Info";
      uses DPA-DPT-GEN-INFO;
    }
    leaf counter-id {
      type uint8;
      description "The selected Counter";
    }
    leaf direction {
      type Dpa-dpt-port-dir;
      description "Direction: Rx or Tx";
    }
    leaf inst-rate {
      type uint64;
      description "Instantaneuos Rate";
    }
    leaf avg-rate {
      type uint64;
      description "Average Rate";
    }
    leaf max-rate {
      type uint64;
      description "Max Rate";
    }
    leaf max-rate-upd-tmstamp {
      type uint64;
      description "Timestamp when max rate got updated";
    }

    list port-hist-values-array {
      description "Port Histogram SampleArray";
      uses DPT-TELEMETRY-HISTOGRAM-INFO;
    }
  }

  grouping DPT-TELEMETRY-HISTOGRAM-INFO {
    description "PortHistogram Per Sample Info";
    leaf time-stamp {
      type uint64;
      description "Timestamp when the sample was collected";
    }
    leaf-list density {
      type uint32;
      max-elements "8";
      description
        "Value which gets updated for the thresholds
        configured";
    }
  }

  grouping DPA-DPT-GEN-INFO {
    description "General Common Info";
    leaf time-stamp {
      type uint64;
      description "Timestamp";
    }
    leaf interface-name {
      type string;
      description "Interface name";
    }
    leaf measure-unit {
      type Dpa-dpt-unit-of-measure;
      description "Unit of Measurement along the x-axis";
    }
    leaf-list cfgthreshold {
      type uint32;
      max-elements "8";
      description "The bar values on the x-axis of histogram";
    }
  }

  grouping DPA-DPT-LOC-INFO {
    description "Location Info";
    leaf rack-number {
      type uint8;
      description "Rack number";
    }
    leaf slot-number {
      type uint8;
      description "Slot number";
    }
    leaf npu-number {
      type uint8;
      description "NPU number";
    }
    leaf slice-number {
      type uint8;
      description "Slice or core number";
    }
  }

  grouping DPT-TELEMETRY-HISTOGRAM-BLOCK-INFO {
    description "Histogram Info Block";

    container loc-info {
      description "Location Info";
      uses DPA-DPT-LOC-INFO;
    }

    container gen-info {
      description "General Info";
      uses DPA-DPT-GEN-INFO;
    }
    leaf histo-category {
      type Dpa-dpt-histogram-category;
      description "Category of the histogram";
    }
    leaf histo-type {
      type Dpa-dpt-histogram;
      description "Type of the histogram";
    }

    list histogram-value {
      description "Histogram Values";
      uses DPT-TELEMETRY-HISTOGRAM-INFO;
    }
  }

  grouping OFA-DPT-TOP8-VOQ-INFO {
    description "VOQ Congestion Info Block";
    leaf time-stamp {
      type uint64;
      description "Timestamp";
    }
    leaf rack-number {
      type uint8;
      description "Rack number";
    }
    leaf slot-number {
      type uint8;
      description "Slot number";
    }
    leaf npu-number {
      type uint8;
      description "NPU number";
    }

    list voq-top8-info-arraycore0 {
      description " Core 0 Top 8 congested VOQ Info Array";
      uses OFA-DPT-VOQ-INFO;
    }

    list voq-top8-info-array-core1 {
      description " Core 1 Top 8 congested VOQ Info Array";
      uses OFA-DPT-VOQ-INFO;
    }
  }

  grouping OFA-DPT-PKT-DROP-EVENT-INFO {
    description "Pkt Drop event Info";
    leaf drop-count {
      type uint32;
      description "NPU drop Count";
    }
    leaf pkt-drop-reason {
      type uint16;
      description "NPU Packet Drop Reason";
    }
    leaf pkt-drop-asic-code {
      type Ofa-dpt-pkt-drop-sub;
      description "NPU Packet Drop ASIC Specific reason";
    }
  }

  grouping OFA-DPT-PKT-DROP-INFO {
    description "NPU PACKET DROP Info";
    leaf time-stamp {
      type uint64;
      description "Timestamp";
    }
    leaf rack-number {
      type uint8;
      description "Rack number";
    }
    leaf slot-number {
      type uint8;
      description "Slot number";
    }
    leaf npu-number {
      type uint8;
      description "NPU number";
    }

    list pkt-drop-event-array {
      description "Pkt Drop Event Array ";
      uses OFA-DPT-PKT-DROP-EVENT-INFO;
    }
  }

  grouping OFA-DPT-VOQ-INFO {
    description "VOQ Info";
    leaf ifhandle {
      type xr:Interface-name;
      description "Interface handle";
    }
    leaf qos-queue {
      type uint32;
      description "Qos queue";
    }
    leaf voq-depth {
      type uint32;
      description "VOQ depth";
    }
  }

  grouping OFA-DPT-VOQ-BLOCK-INFO {
    description "VOQ Info Block";
    leaf time-stamp {
      type uint64;
      description "Timestamp";
    }
    leaf rack-number {
      type uint8;
      description "Rack number";
    }
    leaf slot-number {
      type uint8;
      description "Slot number";
    }
    leaf npu-number {
      type uint8;
      description "NPU number";
    }
    leaf npu-core-num {
      type uint8;
      description "NPU core";
    }

    list voq-info-array {
      description "VOQ Info Array";
      uses OFA-DPT-VOQ-INFO;
    }
  }

  grouping OFA-DPT-CFG-DB-MEM-BLOCK-INFO {
    description "CFG DB MEM Info Block";
    leaf time-stamp {
      type uint64;
      description "Timestamp";
    }
    leaf rack-number {
      type uint8;
      description "Rack number";
    }
    leaf slot-number {
      type uint8;
      description "Slot number";
    }
    leaf npu-number {
      type uint8;
      description "NPU number";
    }
    leaf lem-max-entries {
      type uint32;
      description "LEM MAX Entries";
    }
    leaf lem-inuse-entries {
      type uint32;
      description "LEM ALL INUSE Entries";
    }
    leaf lpm-max-entries {
      type uint32;
      description "LPM MAX Entries";
    }
    leaf lpm-inuse-entries {
      type uint32;
      description "LPM ALL INUSE Entries";
    }
    leaf lpm-ipv4-route-entries {
      type uint32;
      description "LPM IPV4 INUSE Entries";
    }
    leaf lpm-ipv6-route-entries {
      type uint32;
      description "LPM IPV6 INUSE Entries";
    }
    leaf lpm-mc-route-entries {
      type uint32;
      description "LPM MULTICAST INUSE Entries";
    }
    leaf etcam-max-entries {
      type uint32;
      description "ETCAM MAX Entries";
    }
    leaf etcam-inuse-entries {
      type uint32;
      description "ETCAM ALL INUSE Entries";
    }
    leaf etcam-ipv4-route-entries {
      type uint32;
      description "ETCAM IPV4 INUSE Entries";
    }
    leaf etcam-ipv6-route-entries {
      type uint32;
      description "ETCAM IPV6 INUSE Entries";
    }
    leaf etcam-mc-route-entries {
      type uint32;
      description "ETCAM MULTICAST INUSE Entries";
    }
  }

  grouping OFA-DPT-EGRESS-INTERFACE-BUFFER-INFO {
    description "Interface buffer Info ";
    leaf ifhandle {
      type xr:Interface-name;
      description "Interface handle";
    }
    leaf qnum {
      type uint32;
      description "Queue number (port+TC)";
    }
    leaf curr-uc-pd-per-interface {
      type uint32;
      description
        "EGQ UC Packet Descriptors Consumed per Interface";
    }
    leaf max-uc-pd-per-interface {
      type uint32;
      description
        "EGQ Maximum UC Consumed Packet Descriptors per
        Interface ";
    }
    leaf curr-uc-db-per-interface {
      type uint32;
      description "EGQ UC Data Buffers Consumed per Interface ";
    }
    leaf max-uc-db-per-interface {
      type uint32;
      description
        "EGQ Maximum UC Consumed Data Buffers per
        Interface ";
    }
    leaf curr-mc-pd-per-interface {
      type uint32;
      description
        "EGQ MC Packet Descriptors Consumed per Interface";
    }
    leaf max-mc-pd-per-interface {
      type uint32;
      description
        "EGQ Maximum MC Consumed Packet Descriptors per
        Interface ";
    }
    leaf curr-mc-db-per-interface {
      type uint32;
      description "EGQ MC Data Buffers Consumed per Interface ";
    }
    leaf max-mc-db-per-interface {
      type uint32;
      description
        "EGQ Maximum MC Consumed Data Buffers per
        Interface ";
    }
  }

  grouping OFA-DPT-INTERFACE-BUFFERS-INFO {
    description "NPU per Interface buffer information";
    leaf time-stamp {
      type uint64;
      description "Timestamp";
    }
    leaf rack-number {
      type uint8;
      description "Rack number";
    }
    leaf slot-number {
      type uint8;
      description "Slot number";
    }
    leaf npu-number {
      type uint8;
      description "NPU number";
    }

    list core0-egress-interface-buffer {
      description "NPU egress interface buffer";
      uses OFA-DPT-EGRESS-INTERFACE-BUFFER-INFO;
    }

    list core1-egress-interface-buffer {
      description "NPU egress interface buffer";
      uses OFA-DPT-EGRESS-INTERFACE-BUFFER-INFO;
    }
  }

  grouping OFA-DPT-NPU-EGRESS-BUF-INFO {
    description "NPU congestion Info";
    leaf total-pd-val {
      type uint32;
      description "Total Packet Descriptor value read";
    }
    leaf unicast-pd-val {
      type uint32;
      description "Unicast Packet Descriptor value read";
    }
    leaf multicast-pd-val {
      type uint32;
      description "Multicast Packet Descriptor value read";
    }
    leaf total-db-val {
      type uint32;
      description "Total Data Buffer value read";
    }
    leaf uc-db-val {
      type uint32;
      description "Unicast Data Buffer value read";
    }
    leaf mc-db-val {
      type uint32;
      description "Multicast Data Buffer value read";
    }
    leaf uc-pd-max-val {
      type uint32;
      description
        "Congestion Tracking Unicast PD MAX value since
        last read";
    }
    leaf uc-db-max-val {
      type uint32;
      description
        "Congestion Tracking Unicast PD MAX value since
        last read";
    }
    leaf mc-pd-max-val {
      type uint32;
      description
        "Congestion Tracking Multicast PD MAX value since
        last read";
    }
    leaf mc-db-max-val {
      type uint32;
      description
        "Congestion Tracking Multicast PD MAX value since
        last read";
    }
    leaf total-pd-max-val {
      type uint32;
      description
        "Congestion Tracking Total PD MAX value since
        last read";
    }
    leaf total-db-max-val {
      type uint32;
      description
        "Congestion Tracking Total PD MAX value since
        last read";
    }
  }

  grouping OFA-DPT-NPU-INGRESS-BUF-INFO {
    description "NPU congestion Info";
    leaf free-bdb-count {
      type uint32;
      description "Free Buffer Descriptor Block count";
    }
    leaf occupied-mnmc-db-count {
      type uint32;
      description "Occupied Mini Multi-cast Data Buffer count";
    }
    leaf occupied-bd-count {
      type uint32;
      description "Occupied Buffer Descriptor Count";
    }
    leaf free-bd-count {
      type uint32;
      description "Free Buffer Descriptor Count";
    }
    leaf occp-ocb-db-count {
      type uint32;
      description "Occupied OCB Buffer Count";
    }
    leaf free-full-mc-db-count {
      type uint32;
      description "Free Full Multicast Data Buffer Count";
    }
    leaf free-mmc-db-count {
      type uint32;
      description "Free Mini Multicast Data Buffer Count";
    }
    leaf min-occp-free-bdb-count {
      type uint32;
      description "Minimum Occupancy Free BDB";
    }
    leaf min-occp-ocb-db-count {
      type uint32;
      description "Minimum Occupancy Free OCB  Buffer Count";
    }
    leaf min-occp-free-full-mc-db-count {
      type uint32;
      description
        "Minimm Occupany Free Full Multicast Data Buffer
        Count";
    }
    leaf min-occp-free-mmc-db-count {
      type uint32;
      description
        "Minimum Occupancy Free Mini- Multicast Data
        Buffer Count";
    }
  }

  grouping OFA-DPT-NPU-BUFFER-INFO {
    description "NPU buffer congestion Info Block";

    container core0npu-ing-cng-info {
      description "NPU Congestion Info for core 0";
      uses OFA-DPT-NPU-INGRESS-BUF-INFO;
    }

    container core1npu-ing-cng-info {
      description "NPU Congestion Info for core 1";
      uses OFA-DPT-NPU-INGRESS-BUF-INFO;
    }

    container core0npu-egr-cng-info {
      description "NPU Congestion Info for core 0";
      uses OFA-DPT-NPU-EGRESS-BUF-INFO;
    }

    container core1npu-egr-cng-info {
      description "NPU Congestion Info for core 1";
      uses OFA-DPT-NPU-EGRESS-BUF-INFO;
    }
    leaf time-stamp {
      type uint64;
      description "Timestamp";
    }
    leaf rack-number {
      type uint8;
      description "Rack number";
    }
    leaf slot-number {
      type uint8;
      description "Slot number";
    }
    leaf npu-number {
      type uint8;
      description "NPU number";
    }
  }
}
