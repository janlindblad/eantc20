module Cisco-IOS-XR-ipv6-ospfv3-act {

    namespace "http://cisco.com/ns/yang/Cisco-IOS-XR-ipv6-ospfv3-act";
   
    prefix "Cisco-IOS-XR-ipv6-ospfv3-act";

    import Cisco-IOS-XR-types { prefix "xr"; }

    import ietf-inet-types { prefix "inet"; }
   
    organization "Cisco Systems, Inc.";
   
    contact
    "Cisco Systems, Inc.
     Customer Service

     Postal: 170 West Tasman Drive
     San Jose, CA 95134

     Tel: +1 800 553-NETS

     E-mail: cs-yang@cisco.com";
   
    description
    "This module contains a collection of YANG definitions
     for Cisco IOS-XR IPv6 OSPFv3 action package configuration.

     Copyright (c) 2016-2017 by Cisco Systems, Inc.
     All rights reserved.";
   
    revision "2016-09-14" {
        description
            "IOS XR 6.2.1 revision.";
    }

    rpc clear-ospfv3-routes {
        description "Clear OSPFv3 route table";
        input {
            container instance {
                description "Clear data from OSPFv3 instance";
                leaf instance-identifier {
                    description "OSPFv3 process instance identifier";
                    type string;
                }
            }
            leaf route {
                description "Clear OSPFv3 route table";
                mandatory true;
                type empty;
            }
        }
    }

    rpc clear-ospfv3-redistribution {
        description "Clear OSPFv3 route redistribution";
        input {
            container instance {
                description "Clear data from OSPFv3 instance";
                leaf instance-identifier {
                    description "OSPFv3 process instance identifier";
                    type string;
                }
            }
            leaf redistribution {
                description "Clear OSPFv3 route redistribution";
                mandatory true;
                type empty;
            }
        }
    }

    rpc clear-ospfv3-process {
        description "Clear (reset) OSPFv3 Process";
        input {
            container instance {
                description "Clear data from OSPFv3 instance";
                leaf instance-identifier {
                    description "OSPFv3 process instance identifier";
                    type string;
                }
            }
            leaf process {
                description "Reset OSPFv3 process";
                mandatory true;
                type empty;
            }
        }
    }

    rpc clear-ospfv3-statistics-neighbor {
        description "Clear OSPFv3 neighbor statistics per interface or neighbor id";
        input {
            container instance {
                description "Clear data from OSPFv3 instance";
                leaf instance-identifier {
                    description "OSPFv3 process instance identifier";
                    type string;
                }
            }
            container neighbor {
                leaf neighbor-id {
                    description "Neighbor ID";
                    type inet:ipv4-address;
                }
                leaf interface-name {
                    description "Interface";
                    type xr:Interface-name;
                }
            }
        }
    }

    rpc clear-ospfv3-statistics {
        description "Clear OSPFv3 counters and statistics";
        input {
            container instance {
                description "Clear data from OSPFv3 instance";
                leaf instance-identifier {
                    description "OSPFv3 process instance identifier";
                    type string;
                }
            }
            leaf prefix-priority {
                description "All OSPFv3 counters and statistics";
                type empty;
            }
            leaf spf {
                description "SPF statistics";
                type empty;
            }
            leaf neighbor {
                description "Neighbor statistics per neighbor id";
                type empty;
            }
        }
    }

    grouping OSPFv3-STAT-ATTRIBUTES {
        leaf process {
            description "Reset OSPFv3 process";
            type empty;
        }
        leaf redistribution {
            description "Clear OSPFv3 route redistrbution";
            type empty;
        }
        leaf route {
            description "Clear OSPFv3 route table";
            type empty;
        }
        container stats {
            description "OSPFv3 counters and statistics";
            leaf spf {
                description "SPF statistics";
                type empty; 
            } 
            leaf prefix-priority {
                description "SPF Prefix Priority statistics";
                type empty; 
            }
            container neighbor {
                description "Neighbor statistics per interface or neighbor id";
                leaf neighbor-id {
                    description "Neighbor ID";
                    type inet:ipv4-address;
                }
                container interface {
                    leaf interface-name {
                        description "OSPFv3 interface statistics";
                        type xr:Interface-name;
                    }
                }
            } 
        }
    }

    rpc clear-ospfv3-instance-vrf {
        description "Clear one or more non-default OSPFv3 VRFs in process";
        input {
            container instance {
                description "OSPFv3 instance name";
                leaf instance-identifier {
                    description "OSPFv3 process instance identifier";
                    mandatory true;
                    type string;
                }

                container vrf {
                    description "Clear one or more non-default OSPFv3 VRFs in process";
                    leaf vrf-name {
                        description "OSPFv3 VRF name";
                        mandatory true;
                        type string;
                    }
                    uses OSPFv3-STAT-ATTRIBUTES;
                }

                container all {
                    description "Clear all non-default OSPFv3 VRFs";
                    uses OSPFv3-STAT-ATTRIBUTES;
                }

                container all-inclusive {
                    description "Clear all non-default and default OSPFv3 VRFs";
                    uses OSPFv3-STAT-ATTRIBUTES;
                }
            }
        }
    }
}
