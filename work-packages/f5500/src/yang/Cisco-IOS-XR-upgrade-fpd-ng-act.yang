module Cisco-IOS-XR-upgrade-fpd-ng-act {

  /*** NAMESPACE / PREFIX DEFINITION ***/

  namespace "http://cisco.com/ns/yang/Cisco-IOS-XR-upgrade-fpd-ng-act";


  prefix "Cisco-IOS-XR-upgrade-fpd-ng-act";

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR upgrade-fpd package action data.

     This module contains definitions
     for the following management objects:
       fpd: Field programmable device (FPD) operational data

     Copyright (c) 2013-2017 by Cisco Systems, Inc.
     All rights reserved.";

  revision "2017-04-04" {
    description
      "IOS XR 6.3.1 revision.";
  }
  rpc upgrade-fpd {
      description "Execute FPD upgrade";
      input {
          leaf location {
              description "Location of the FPD to be upgraded";
              type string;
              mandatory true;
          }
          leaf fpd {
              description "name of the fpd to be upgraded";
              type string;
              mandatory true;
          }
          leaf force {
              description "Force the upgrade process";
              type empty;
              mandatory false;
          }
      }
  }
}
