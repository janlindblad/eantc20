module Cisco-IOS-XR-sysadmin-rvm-mgr {
  namespace "http://www.cisco.com/ns/yang/Cisco-IOS-XR-sysadmin-rvm-mgr";
  prefix Cisco-IOS-XR-sysadmin-rvm-mgr;
  organization "Cisco Systems Inc.";
  contact
    "Cisco Systems, Inc.
     Customer Service
     
     Postal: 170 West Tasman Drive
     San Jose, CA 95134
     
     Tel: +1 800 553-NETS
     
     E-mail: cs-yang@cisco.com";

  description 
    "This module contains definitions
     for the Calvados model objects.

    This module contains a collection of YANG
definitions for Cisco IOS-XR SysAdmin configuration.

Copyright(c) 2013-2017 by Cisco Systems, Inc.
All rights reserved.

    Copyright (c) 2012-2018 by Cisco Systems, Inc.
     All rights reserved.";
  revision 2017-04-12 {
    description
      "Changed the namespace and module name";
  }


  typedef nodetype_td {
    type enumeration {
      enum "sysadmin" {
        value 1;
      }
      enum "service" {
        value 2;
      }
    }
  }

  typedef flagtype_td {
    type enumeration {
      enum "clear" {
        value 0;
      }
      enum "set" {
        value 1;
      }
    }
  }
  container RVM {
    description
      "RVM Manager Info";
    config false;
    list all-locations {
      key "location";
      leaf location {
        type string;
      }
      container objects {
        description
          "RVM Manager Info";
        config false;
        list all-objs {
          key "index";
          leaf index {
            type uint32;
            description
              "Index into obj_db array";
          }
          leaf num_allocated {
            type uint32;
            description
              "Number of allocated nodes";
          }
          leaf num_freed {
            type uint32;
            description
              "Number of freed nodes";
          }
          leaf num_objects {
            type uint32;
            description
              "Number of current object nodes";
          }
        }
      }
      container node {
        description
          "RVM Manager Node Info";
        config false;
        list all-nodes {
          key "ipv4_addr";
          leaf ipv4_addr {
            type uint32;
            description
              "IP address of the node";
          }
          leaf ipv4_addr_str {
            type string;
            description
              "IP address of the node in string format";
          }
          leaf node_info {
            type string;
            description
              "Node type state and flag";
          }
          leaf node_hb_info {
            type string;
            description
              "Node heartbeat related info";
          }
          leaf node_card_info {
            type string;
            description
              "Card info the node belongs to";
          }
        }
      }
      container card {
        description
          "RVM Manager Card Info";
        config false;
        list all-cards {
          key "serial_num";
          leaf serial_num {
            type string;
            description
              "Serial number of the card";
          }
          leaf card_flag {
            type string;
            description
              "Card flags";
          }
          leaf card_info {
            type string;
            description
              "Card rack and slot num";
          }
          leaf sysadmin_nodes {
            type string;
            description
              "Sysadmin nodes on this card";
          }
          leaf xr_nodes {
            type string;
            description
              "XR nodes on this card";
          }
        }
      }
    }
  }
}
