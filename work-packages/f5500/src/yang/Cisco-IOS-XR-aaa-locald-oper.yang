module Cisco-IOS-XR-aaa-locald-oper {

  /*** NAMESPACE / PREFIX DEFINITION ***/

  namespace "http://cisco.com/ns/yang/Cisco-IOS-XR-aaa-locald-oper";


  prefix "Cisco-IOS-XR-aaa-locald-oper";

  /*** LINKAGE (IMPORTS / INCLUDES) ***/

  include Cisco-IOS-XR-aaa-locald-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR aaa-locald package operational data.

     This module contains definitions
     for the following management objects:
       aaa: AAA operational data

     Copyright (c) 2013-2018 by Cisco Systems, Inc.
     All rights reserved.";

  revision "2015-11-09" {
    description
      "IOS XR 6.0 revision.";
  }


  container aaa {
    config false;
    description "AAA operational data";

    container all-tasks {
      description "All tasks supported by system";
      uses SYSTEM-SUPPORTED-TASKS;
    }

    container currentuser-detail {
      description "Current user specific details";
      uses REMOTEUSR-DET;
    }

    container task-map {
      description "Task map of current user";
      uses REMOTEUSR-DET;
    }

    container taskgroups {
      description "Individual taskgroups container";

      list taskgroup {
        key "name";
        description "Specific Taskgroup Information";
        leaf name {
          type string;
          description "Taskgroup name";
        }
        uses TASKGROUP-DET;
      }
    }

    container users {
      description "Container for individual local user information";

      list user {
        key "name";
        description "Specific local user information";
        leaf name {
          type string;
          description "Username";
        }
        uses USER-DET;
      }
    }

    container password-policies {
      description
        "Container for individual password policy
        Information";

      list password-policy {
        key "name";
        description "Password policy details";
        leaf name {
          type string;
          description "Password policy name";
        }
        uses PP-DET;
      }
    }

    container usergroups {
      description "Container for individual usergroup Information";

      list usergroup {
        key "name";
        description "Specific Usergroup Information";
        leaf name {
          type string;
          description "Usergroup name";
        }
        uses USERGROUP-DET;
      }
    }

    container authen-method {
      description "Current users authentication method";
      uses REMOTEUSR-DET;
    }

    container current-usergroup {
      description "Specific Usergroup Information";
      uses REMOTEUSR-DET;
    }
  }
}
