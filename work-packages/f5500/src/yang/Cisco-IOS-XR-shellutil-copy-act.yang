module Cisco-IOS-XR-shellutil-copy-act {

    namespace "http://cisco.com/ns/yang/Cisco-IOS-XR-shellutil-copy-act";

    prefix "Cisco-IOS-XR-shellutil-copy-act";

    organization "Cisco Systems, Inc.";

    contact
    "Cisco Systems, Inc.
     Customer Service

     Postal: 170 West Tasman Drive
     San Jose, CA 95134

     Tel: +1 800 553-NETS

     E-mail: cs-yang@cisco.com";

    description
    "This module contains a collection of YANG definitions
     for Cisco IOS-XR action package configuration.

     Copyright (c) 2016, 2018 by Cisco Systems, Inc.
     All rights reserved.";

    revision "2018-05-20" {
        description
            "Updated the module name as per CISCO format";
    }

    revision "2018-01-20" {
        description
            "IOS XR 7.0.1 revision.";
    }

    rpc copy {
        input {
            leaf sourcename {
                type string;
                description "source file name to copy";
            }
            leaf destinationname {
                type string;
                description "destination file name";
                mandatory true;
            }
            leaf sourcefilesystem {
                type string;
                description "source file system e.g disk0: tftp";
                mandatory true;
            }
            leaf destinationfilesystem {
                type string;
                description "destination file system e.g disk0:, tftp:";
                mandatory true;
            }
            leaf sourcelocation {
                type string;
                description "source location";
            }
            leaf destinationlocation {
                type string;
                description "destination location";
            }
            leaf vrf {
                type string;
                description "vrf name";
            }
            leaf recurse {
                type boolean;
                description "recurse files to copy";
            }
        }
        output {
            leaf response {
                type string;
                description "Status of copy operation";
            }
        }
    }

}
