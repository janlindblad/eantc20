module Cisco-IOS-XR-mpls-ldp-cfg-datatypes {

  /*** NAMESPACE / PREFIX DEFINITION ***/

  namespace "http://cisco.com/ns/yang"+
    "/Cisco-IOS-XR-mpls-ldp-cfg-datatypes";


  prefix "Cisco-IOS-XR-mpls-ldp-cfg-datatypes";

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR mpls-ldp-cfg-datat package configuration.

     Copyright (c) 2013-2018 by Cisco Systems, Inc.
     All rights reserved.";

  revision "2015-11-09" {
    description
      "IOS XR 6.0 revision.";
  }

  typedef Mpls-ldp-nbr-password {
    type enumeration {
      enum disable {
        value 1;
        description
          "Disable the global default password for this
          neighbor";
      }
      enum specified {
        value 2;
        description "Specify a password for this neighbor";
      }
    }
    description "Mpls ldp nbr password";
  }
  typedef Mpls-ldp-downstream-on-demand {
    type enumeration {
      enum peer-acl {
        value 1;
        description "Downstream on Demand peers permitted by ACL";
      }
    }
    description "Mpls ldp downstream on demand";
  }
  typedef Mpls-ldp-router-id {
    type enumeration {
      enum address {
        value 1;
        description "Use given IP address as LDP Router ID";
      }
    }
    description "Mpls ldp router id";
  }
  typedef Mpls-ldp-interval-time {
    type uint32 {
      range "1..65535";
    }
    description "Mpls ldp interval time";
  }
  typedef Mpls-ldp-hold-time {
    type uint32 {
      range "1..65535";
    }
    description "Mpls ldp hold time";
  }
  typedef Mpls-ldpaf-name {
    type enumeration {
      enum ipv4 {
        value 4;
        description "IPv4";
      }
      enum ipv6 {
        value 6;
        description "IPv6";
      }
    }
    description "Mpls ldpaf name";
  }
  typedef Mpls-ldp-session-protection {
    type enumeration {
      enum all {
        value 1;
        description "Protect all peer sessions";
      }
      enum for {
        value 2;
        description "Protect peer session(s) permitted by peer ACL";
      }
      enum all-with-duration {
        value 3;
        description
          "Protect all peer sessions and holdup protection
          for given duration";
      }
      enum for-with-duration {
        value 4;
        description
          "Protect peer session(s) permitted by peer ACL
          and holdup protection for given duration";
      }
      enum all-with-forever {
        value 5;
        description
          "Protect all peer sessions and holdup protection
          forever";
      }
      enum for-with-forever {
        value 6;
        description
          "Protect peer session(s) permitted by peer ACL
          and holdup protection forever";
      }
    }
    description "Mpls ldp session protection";
  }
}
