submodule Cisco-IOS-XR-fib-common-oper-sub6 {

  belongs-to Cisco-IOS-XR-fib-common-oper {
    prefix Cisco-IOS-XR-fib-common-oper-sub6;
  }

  /*** LINKAGE (IMPORTS / INCLUDES) ***/

  import ietf-yang-types { prefix "yang"; }

  include Cisco-IOS-XR-fib-common-oper-sub4 {
    revision-date 2017-09-07;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR fib-common package operational data.

     Copyright (c) 2013-2018 by Cisco Systems, Inc.
     All rights reserved.";

  revision "2017-09-07" {
    description
      "Fixed type translation error.";
  }

  revision "2017-05-01" {
    description
      "Fixing backward compatibility error in module.";
  }

  revision "2017-01-20" {
    description
      "IOS XR 6.2.1 revision";
  }

  revision "2015-11-09" {
    description
      "IOS XR 6.0 revision.";
  }


  grouping FIB-SH-COFO-TBL-ID-PER-SDR {
    description "FIB SH COFO TBL ID PER SDR";
    leaf sdrid {
      type uint32;
      description "SDR ID";
    }
    leaf num-ofipv4-tables {
      type uint16;
      description "Number of Tables for IPv4";
    }
    leaf num-ofipv6-tables {
      type uint16;
      description "Number of Tables for IPv6";
    }
    leaf num-ofmpls-tables {
      type uint16;
      description "Number of Tables for MPLS";
    }
  }

  grouping FIB-SH-COFO-TBL-ID-DB-SUM {
    description "FIB cofo table id summary information";
    leaf number-of-tbl-id-allocated {
      type uint32;
      description "Number of Table Id Allocated";
    }
    leaf tbl-id-minimum {
      type uint32;
      description "Minimum Table Id in Range";
    }
    leaf tbl-id-maximum {
      type uint32;
      description "Maximum Table Id in Range";
    }
    leaf tbl-id-last-allocated {
      type uint32;
      description "Last Table Id Allocated";
    }
    leaf tbl-id-default-v4 {
      type uint32;
      description "COFO default V4 Table Id";
    }
    leaf tbl-id-default-v6 {
      type uint32;
      description "COFO default V6 Table Id";
    }
    leaf number-of-tbl-id-in-gc {
      type uint32;
      description "Number of Table Id in Garbage Collection List";
    }

    list per-sdr-stat {
      description "Per SDR statistics";
      uses FIB-SH-COFO-TBL-ID-PER-SDR;
    }
  }

  grouping FIB-SH-COFO-TBL-ID-ENTRY-INFO {
    description "FIB cofo table id information";

    container object-base {
      description "FIB Object Base information";
      uses FIB-SH-FIB-OBJ-BASE;
    }
    leaf sdrid {
      type uint32;
      description "SDR ID";
    }
    leaf protocol-type {
      type uint32;
      description "Protocol";
    }
    leaf route-distinguisher {
      type yang:hex-string;
      description "Route Distinguisher";
    }
    leaf table-id-xr {
      type uint32;
      description "Table ID";
    }
    leaf vrf-name {
      type string;
      description "VRF Name";
    }
    leaf table-pointer {
      type uint64;
      description "Table Pointer";
    }
  }

  grouping FIB-SH-COFO-IDB-BUNDLE-MEMBER-INFO {
    description "FIB SH COFO IDB BUNDLE MEMBER INFO";
    leaf intf-index {
      type uint32;
      description "Interface Index";
    }
    leaf unique-id {
      type uint8;
      description "Unique Identifier";
    }
    leaf order-num {
      type uint8;
      description "Link Order Number";
    }
    leaf weight {
      type uint8;
      description "Member Weight";
    }
    leaf pic {
      type uint64;
      description "Port Information Context";
    }
  }

  grouping FIB-SH-COFO-IDB-TBL-ENTRY-INFO {
    description "FIB cofo idb entry information";

    container object-base {
      description "FIB Object Base information";
      uses FIB-SH-FIB-OBJ-BASE;
    }
    leaf sdrid {
      type uint32;
      description "SDR ID";
    }
    leaf intf-type {
      type uint32;
      description "Interface Type";
    }
    leaf intf-index {
      type uint32;
      description "Interface Index";
    }
    leaf intf-state {
      type uint32;
      description "Interface State";
    }
    leaf parent-intf-index {
      type uint32;
      description "Parent Interface Index";
    }
    leaf parent-intf-type {
      type uint32;
      description "Parent Interface Type";
    }
    leaf bundle-member-total-weight {
      type uint16;
      description "Bundle Member Total Weight";
    }
    leaf main-pointer {
      type uint64;
      description "Main Interface Pointer";
    }
    leaf table-pointer {
      type uint64;
      description "Table Pointer";
    }
    leaf hardware-handle {
      type uint64;
      description "Hardware Handle";
    }
    leaf intf-name {
      type string;
      description "Interface Name";
    }
    leaf-list pic {
      type uint64;
      description "Port Information Context";
    }

    list bundle-member-info {
      description "Bundle Member Info";
      uses FIB-SH-COFO-IDB-BUNDLE-MEMBER-INFO;
    }
  }
}
