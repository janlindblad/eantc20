module xr-5500a-nc {
  yang-version 1.1;
  namespace "http://tail-f.com/ns/ned-id/xr-5500a-nc";
  prefix xr-5500a-nc;

  import tailf-common {
    prefix tailf;
  }

  import tailf-ncs-ned {
    prefix ned;
  }

  identity xr-5500a-nc {
    tailf:abstract;
    base ned:netconf-ned-id;
  }
}
