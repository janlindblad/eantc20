module xr-5500a-nc-1.0 {
  yang-version 1.1;
  namespace "http://tail-f.com/ns/ned-id/xr-5500a-nc-1.0";
  prefix xr-5500a-nc-1.0;

  import xr-5500a-nc {
    prefix family;
  }

  identity xr-5500a-nc-1.0 {
    base family:xr-5500a-nc;
  }
}
