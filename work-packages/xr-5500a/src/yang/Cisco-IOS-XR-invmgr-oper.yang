module Cisco-IOS-XR-invmgr-oper {

  /*** NAMESPACE / PREFIX DEFINITION ***/

  namespace "http://cisco.com/ns/yang/Cisco-IOS-XR-invmgr-oper";


  prefix "invmgr-oper";

  /*** LINKAGE (IMPORTS / INCLUDES) ***/

  import Cisco-IOS-XR-types { prefix "xr"; }

  include Cisco-IOS-XR-invmgr-oper-sub4 {
    revision-date 2018-04-19;
  }

  include Cisco-IOS-XR-invmgr-oper-sub3 {
    revision-date 2018-04-19;
  }

  include Cisco-IOS-XR-invmgr-oper-sub2 {
    revision-date 2018-04-19;
  }

  include Cisco-IOS-XR-invmgr-oper-sub1 {
    revision-date 2018-04-19;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR invmgr package operational data.

     This module contains definitions
     for the following management objects:
       inventory: Inventory information

     Copyright (c) 2013-2018 by Cisco Systems, Inc.
     All rights reserved.";

  revision "2018-04-19" {
    description
      "Added additional bags";
  }

  revision "2017-09-07" {
    description
      "Fixed type translation error.";
  }

  revision "2017-05-01" {
    description
      "Fixing backward compatibility error in module.";
  }

  revision "2015-11-09" {
    description
      "IOS XR 6.0 revision.";
  }


  grouping THRESH-BAG {
    description
      "Common node of minor-lo, minor-hi, major-lo,
      major-hi, critical-lo, critical-hi";

    container thresh-bag {
      description "Environment threshold info";
      uses ENVMON-THRESHOLD-INFO;
    }
  }

  grouping INVMGR-EXT1-OPER-THRESH-BAG {
    description
      "Common node of minor-lo, minor-hi, major-lo,
      major-hi, critical-lo, critical-hiCommon node of
      minor-lo, minor-hi, major-lo, major-hi,
      critical-lo, critical-hi";

    container thresh-bag {
      description "Environment threshold info";
      uses ENVMON-THRESHOLD-INFO;
    }
  }

  grouping ATTRIBUTES {
    description
      "Common node of rack, slot, tsi1, tsi2, tsi3, tsi4
      , tsi5, tsi6, tsi7, tsi8, tsi9, tsi10, tsi11";

    container attributes {
      description "Attributes";

      container inv-basic-bag {
        description "Inventory Basic Bag";
        uses INV-PHY-ENTITY-BASIC-INFO;
      }

      container env-sensor-info {
        description "Environment sensor info";
        uses ENVMON-SENSOR-INFO;
      }

      container pwg-info {
        description "Inventory EDM PWG info";
        uses INV-PWG-INFO;
      }

      container env-sensor-info-xml {
        description "Environment sensor info XML";
        uses ENVMON-SENSOR-INFO-XML;
      }

      container inv-asset-bag {
        description "Inventory Asset Bag";
        uses INV-PHY-ENTITY-ASSET-INFO;
      }

      container threshold {
        description "Threshold";

        container major-lo {
          description "Major Low";
          uses THRESH-BAG;
        }

        container critical-hi {
          description "Critical High";
          uses THRESH-BAG;
        }

        container minor-hi {
          description "Minor High";
          uses THRESH-BAG;
        }

        container major-hi {
          description "Major High";
          uses THRESH-BAG;
        }

        container critical-lo {
          description "Critical Low";
          uses THRESH-BAG;
        }

        container minor-lo {
          description "Minor Low";
          uses THRESH-BAG;
        }
      }

      container fru-info {
        description "Inventory EDM FRU info";
        uses INV-CARD-FRU-INFO;
      }

      container inv-eeprom-info {
        description "Inventory EDM EEPROM Information Bag";
        uses INVMGR-EEPROM-OPAQUE-DATA;
      }
    }
  }

  grouping SLOT {
    description "Common node of powershelf, fantray, entity";

    list slot {
      key "name";
      description "Slot number";

      container tsi1s {
        description "Entity Level 1";

        list tsi1 {
          key "name";
          description "TSI1";

          container tsi2s {
            description "Entity Level 2";

            list tsi2 {
              key "name";
              description "TSI2";

              container tsi3s {
                description "Entity Level 3";

                list tsi3 {
                  key "name";
                  description "TSI3";

                  container tsi4s {
                    description "Entity Level 4";

                    list tsi4 {
                      key "name";
                      description "TSI4";

                      container tsi5s {
                        description "Entity Level 5";

                        list tsi5 {
                          key "name";
                          description "TSI5";

                          container tsi6s {
                            description "Entity Level 6";

                            list tsi6 {
                              key "name";
                              description "TSI6";

                              container tsi7s {
                                description "Entity Level 7";

                                list tsi7 {
                                  key "name";
                                  description "TSI7";

                                  container tsi8s {
                                    description "Entity Level 8";

                                    list tsi8 {
                                      key "name";
                                      description "TSI8";

                                      container tsi9s {
                                        description
                                          "Entity Level 9";

                                        list tsi9 {
                                          key "name";
                                          description "TSI9";

                                          container tsi10s {
                                            description
                                              "Entity Level 10";

                                            list tsi10 {
                                              key "name";
                                              description "TSI10";

                                              container tsi11s {
                                                description
                                                  "Entity Level 11";

                                                list tsi11 {
                                                  key "name";
                                                  description
                                                    "TSI11";
                                                  leaf name {
                                                    type xr:Cisco-ios-xr-string;
                                                    description
                                                      "TSI11";
                                                  }
                                                  uses ATTRIBUTES;
                                                }
                                              }
                                              leaf name {
                                                type xr:Cisco-ios-xr-string;
                                                description "TSI10";
                                              }
                                              uses ATTRIBUTES;
                                            }
                                          }
                                          leaf name {
                                            type xr:Cisco-ios-xr-string;
                                            description "TSI9";
                                          }
                                          uses ATTRIBUTES;
                                        }
                                      }
                                      leaf name {
                                        type xr:Cisco-ios-xr-string;
                                        description "TSI8";
                                      }
                                      uses ATTRIBUTES;
                                    }
                                  }
                                  leaf name {
                                    type xr:Cisco-ios-xr-string;
                                    description "TSI7";
                                  }
                                  uses ATTRIBUTES;
                                }
                              }
                              leaf name {
                                type xr:Cisco-ios-xr-string;
                                description "TSI6";
                              }
                              uses ATTRIBUTES;
                            }
                          }
                          leaf name {
                            type xr:Cisco-ios-xr-string;
                            description "TSI5";
                          }
                          uses ATTRIBUTES;
                        }
                      }
                      leaf name {
                        type xr:Cisco-ios-xr-string;
                        description "TSI4";
                      }
                      uses ATTRIBUTES;
                    }
                  }
                  leaf name {
                    type xr:Cisco-ios-xr-string;
                    description "TSI3";
                  }
                  uses ATTRIBUTES;
                }
              }
              leaf name {
                type xr:Cisco-ios-xr-string;
                description "TSI2";
              }
              uses ATTRIBUTES;
            }
          }
          leaf name {
            type xr:Cisco-ios-xr-string;
            description "TSI1";
          }
          uses ATTRIBUTES;
        }
      }
      leaf name {
        type xr:Cisco-ios-xr-string;
        description "Slot name";
      }
      uses ATTRIBUTES;
    }
  }

  container inventory {
    config false;
    description "Inventory information";

    container entities {
      description "Entities Table";

      list entity {
        key "name";
        description "Entity name";

        container subentities {
          description "SubEntities Table";

          list subentity {
            key "name";
            description "Subentity Bag";
            leaf name {
              type string;
              description "Subentity name";
            }
            uses SUBENTITY-INFO;
          }
        }

        container attributes {
          description "Attributes";

          container inv-basic-bag {
            description "Inventory Basic Bag";
            uses INV-PHY-ENTITY-BASIC-INFO;
          }

          container vm-node-id {
            description "VM Node ID Tuple";
            uses VM-NODEID-INFO;
          }

          container threshold {
            description "Threshold";

            container minor-hi {
              description "Minor High";
              uses INVMGR-EXT1-OPER-THRESH-BAG;
            }

            container major-hi {
              description "Major High";
              uses INVMGR-EXT1-OPER-THRESH-BAG;
            }

            container minor-lo {
              description "Minor Low";
              uses INVMGR-EXT1-OPER-THRESH-BAG;
            }

            container major-lo {
              description "Major Low";
              uses INVMGR-EXT1-OPER-THRESH-BAG;
            }

            container critical-hi {
              description "Critical High";
              uses INVMGR-EXT1-OPER-THRESH-BAG;
            }

            container critical-lo {
              description "Critical Low";
              uses INVMGR-EXT1-OPER-THRESH-BAG;
            }
          }

          container vm-done {
            description "VM Done Tuple";
            uses VMDONE-INFO;
          }

          container fru-info {
            description "Inventory EDM FRU info";
            uses INV-CARD-FRU-INFO;
          }

          container env-sensor-info-xml {
            description "Environment sensor info XML";
            uses ENVMON-SENSOR-INFO-XML;
          }

          container inv-asset-bag {
            description "Inventory Asset Bag";
            uses INV-PHY-ENTITY-ASSET-INFO;
          }

          container env-sensor-info {
            description "Environment sensor info";
            uses ENVMON-SENSOR-INFO;
          }

          container node-id {
            description "Node ID Tuple";
            uses NODEID-INFO;
          }

          container inv-eeprom-info {
            description "Inventory EDM EEPROM Information Bag";
            uses INVMGR-EEPROM-OPAQUE-DATA;
          }
        }
        leaf name {
          type string;
          description "Entity name";
        }
      }
    }

    container racks {
      description "RackTable";

      list rack {
        key "name";
        description "Rack name";

        container entity {
          description "Entity information";
          uses SLOT;
        }

        container powershelf {
          description "Powershelf information";
          uses SLOT;
        }

        container fantray {
          description "Fantray information";
          uses SLOT;
        }
        leaf name {
          type xr:Cisco-ios-xr-string;
          description "Rack name";
        }
        uses ATTRIBUTES;
      }
    }
  }
}
