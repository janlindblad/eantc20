submodule Cisco-IOS-XR-fretta-grid-svr-oper-sub1 {

  belongs-to Cisco-IOS-XR-fretta-grid-svr-oper {
    prefix Cisco-IOS-XR-fretta-grid-svr-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR fretta-grid-svr package operational data.

     Copyright (c) 2013-2018 by Cisco Systems, Inc.
     All rights reserved.";

  revision "2015-11-09" {
    description
      "IOS XR 6.0 revision.";
  }


  grouping GRID-SVR-SHOW-CLIENT-DATA {
    description "Client information and resource ID database";
    leaf res-id {
      type uint32;
      description "Resource ID";
    }
  }

  grouping GRID-SVR-SHOW-CLIENT {
    description "Client information";

    list client-data {
      description "Client information";
      uses GRID-SVR-SHOW-CLIENT-DATA;
    }
  }
}
