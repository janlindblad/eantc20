module Cisco-IOS-XR-ofa-dpt-oper {

  /*** NAMESPACE / PREFIX DEFINITION ***/

  namespace "http://cisco.com/ns/yang/Cisco-IOS-XR-ofa-dpt-oper";


  prefix "ofa-dpt-oper";

  /*** LINKAGE (IMPORTS / INCLUDES) ***/

  include Cisco-IOS-XR-ofa-dpt-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ofa-dpt package operational data.

     This module contains definitions
     for the following management objects:
       data-path-telemetry: Data Path Telemetry

     Copyright (c) 2013-2018 by Cisco Systems, Inc.
     All rights reserved.";

  revision "2015-11-09" {
    description
      "IOS XR 6.0 revision.";
  }


  container data-path-telemetry {
    config false;
    description "Data Path Telemetry";

    container sensor {
      description "Data Path Telemetry Sensor Table";

      container npu-buffer-data {
        description
          "Data Path Telemetry sensor Node for NPU Packet
          Buffer utilization info";
        uses OFA-DPT-NPU-BUFFER-INFO;
      }

      container interface-buffer-data {
        description
          "Data Path Telemetry sensor data for Interface
          Buffer utilization info";
        uses OFA-DPT-INTERFACE-BUFFERS-INFO;
      }

      container npu-cfg-mem-util {
        description
          "Data Path Telemetry sensor data for NPU Config
          DB memory utilization info";
        uses OFA-DPT-CFG-DB-MEM-BLOCK-INFO;
      }

      container non-zero-voq-data {
        description
          "Data Path Telemetry sensor data for non-zero
          Voqs";
        uses OFA-DPT-VOQ-BLOCK-INFO;
      }

      container pkt-drop-data {
        description
          "Data Path Telemetry sensor data for NPU packet
          Drop events";
        uses OFA-DPT-PKT-DROP-INFO;
      }

      container top8-voq-data {
        description
          "Data Path Telemetry sensor data for top 8
          congested Voqs";
        uses OFA-DPT-TOP8-VOQ-INFO;
      }

      container histogram-data {
        description
          "Data Path Telemetry sensor data for Histograms
          in general";
        uses DPT-TELEMETRY-HISTOGRAM-BLOCK-INFO;
      }

      container rx-port-histogram {
        description
          "Data Path Telemetry sensor data for Rx Port
          Histograms";
        uses DPT-TELEMETRY-PORT-HISTOGRAM-BLOCK-INFO;
      }

      container egress-micro-burst-event {
        description
          "Data Path Telemetry sensor data for NPU Egress
          Microburst event info";
        uses OFA-DPT-EGRESS-MICROBURST-EVENT-INFO;
      }

      container tx-port-histogram {
        description
          "Data Path Telemetry sensor data for Tx Port
          Histograms";
        uses DPT-TELEMETRY-PORT-HISTOGRAM-BLOCK-INFO;
      }
    }
  }
}
