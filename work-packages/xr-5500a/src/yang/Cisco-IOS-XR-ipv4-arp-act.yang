module Cisco-IOS-XR-ipv4-arp-act {

    namespace "http://cisco.com/ns/yang/Cisco-IOS-XR-ipv4-arp-act";
    
    prefix "arp-act";
    
    import Cisco-IOS-XR-types { prefix "csc"; }
    import ietf-inet-types { prefix "inet"; }
    
    organization "Cisco Systems, Inc.";
    
    contact
    "Cisco Systems, Inc.
     Customer Service

     Postal: 170 West Tasman Drive
     San Jose, CA 95134

     Tel: +1 800 553-NETS

     E-mail: cs-yang@cisco.com";
    
    description 
    "This module contains a collection of YANG definitions
     for Cisco IOS-XR action package configuration.

     Copyright (c) 2018 by Cisco Systems, Inc.
     All rights reserved.";
    
    revision "2018-10-08" {
        description
            "IOS XR 6.1.1 revision.";
    }

    rpc clear-arp-api-stats-api {
        csc:xr-task "arp";
        csc:cli-command "clear arp api-stats api <name>";
        input {
            leaf name {
                mandatory true;
                type string;
            }
        }
    }
    rpc clear-arp-api-stats-location {
        csc:xr-task "arp";
        csc:cli-command "clear arp api-stats location <node-location>";
        input {
            leaf node-location {
                csc:cli-name "*";
                mandatory true;
                type string;
            }
        }
    }
}
