module Cisco-IOS-XR-rptiming-dti-oper {

  /*** NAMESPACE / PREFIX DEFINITION ***/

  namespace "http://cisco.com/ns"+
    "/yang/Cisco-IOS-XR-rptiming-dti-oper";


  prefix "rptiming-dti-oper";

  /*** LINKAGE (IMPORTS / INCLUDES) ***/

  import Cisco-IOS-XR-types { prefix "xr"; }

  include Cisco-IOS-XR-rptiming-dti-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR rptiming-dti package operational data.

     This module contains definitions
     for the following management objects:
       dti-controller: DTI interface controller status and
         configuration

     Copyright (c) 2013-2018 by Cisco Systems, Inc.
     All rights reserved.";

  revision "2015-11-09" {
    description
      "IOS XR 6.0 revision.";
  }


  container dti-controller {
    config false;
    description "DTI interface controller status and configuration";

    container nodes {
      description "List of nodes applicable to DTI controller";

      list node {
        key "node-name";
        description "DTI operational data for a single node";

        container client {
          description "Display DTI client status";
          uses DTI-CLIENT-INFO;
        }

        container port {
          description "Display DTI input port status";
          uses DTI-PORT-INFO;
        }

        container time-of-day {
          description "Display DTI time-of-day status";
          uses DTI-TOD-INFO;
        }
        leaf node-name {
          type xr:Node-id;
          description "Node Name";
        }
      }
    }
  }
}
