submodule Cisco-IOS-XR-perf-meas-oper-sub1 {

  belongs-to Cisco-IOS-XR-perf-meas-oper {
    prefix Cisco-IOS-XR-perf-meas-oper-sub1;
  }

  /*** LINKAGE (IMPORTS / INCLUDES) ***/

  import ietf-inet-types { prefix "inet"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR perf-meas package operational data.

     Copyright (c) 2013-2018 by Cisco Systems, Inc.
     All rights reserved.";

  revision "2017-10-17" {
    description
      "Revision Zero.";
  }

  revision "2015-11-09" {
    description
      "IOS XR 6.0 revision.";
  }


  grouping PM-RESP-INTF-BAG {
    description "PM Responder Interface bag";

    container interface-counters {
      description "Per interface responder counters";
      uses PM-COUNTER-RESP-BAG;
    }
    leaf interface-name-xr {
      type string;
      description "Interface name";
    }
    leaf interface-handle {
      type uint32;
      description "Interface handle";
    }
    leaf source-address {
      type inet:ipv4-address;
      description "Source Address";
    }
    leaf source-v6-address {
      type inet:ipv6-address;
      description "Source V6 Address";
    }
    leaf packet-rate {
      type uint32;
      description "Incoming packet rate";
    }
    leaf packet-rate-high-water-mark {
      type uint32;
      description "Incoming packet rate high water mark";
    }
    leaf cleanup-time-remaining {
      type uint32;
      units "second";
      description
        "Seconds until an inactive interface is cleaned
        up";
    }
  }

  grouping PM-COUNTER-RESP-BAG {
    description "PM Responder counters";
    leaf reply-packet-sent {
      type uint64;
      description "Response packets sent";
    }
    leaf reply-packet-sent-error {
      type uint64;
      description "Response packets sent error";
    }
    leaf query-packet-received {
      type uint64;
      description "Response packets received";
    }
    leaf received-packet-error-urotlv-not-present {
      type uint64;
      description "Received packet error, URO TLV not present";
    }
    leaf received-packet-error-invalid-source-port-number {
      type uint64;
      description
        "Received packet error, invalid source port
        number";
    }
    leaf received-packet-error-no-source-address {
      type uint64;
      description "Received packet error, no source address";
    }
    leaf received-packet-error-no-return-path {
      type uint64;
      description "Received packet error, no return path";
    }
    leaf received-packet-error-invalid-querier-control-code {
      type uint64;
      description
        "Received packet error, invalid querier control
        code";
    }
    leaf received-packet-error-unsupported-timestamp-format {
      type uint64;
      description
        "Received packet error, unsupported timestamp
        format";
    }
    leaf received-packet-error-timestamp-not-available {
      type uint64;
      description "Received packet error, timestamp not available";
    }
    leaf received-packet-error-unsupported-mandatory-tlv {
      type uint64;
      description
        "Received packet error, unsupported mandatory TLV";
    }
    leaf received-packet-error-invalid-packet {
      type uint64;
      description "Received packet error, invalid packet";
    }
  }

  grouping PM-RESP-SUMMARY-BAG {
    description "PM Responder summary bag";

    container responder-counters {
      description "Global responder counters";
      uses PM-COUNTER-RESP-BAG;
    }
    leaf total-interfaces {
      type uint32;
      description "Number of interfaces in the responder cache";
    }
    leaf packet-rate {
      type uint32;
      description "Global incoming packet rate";
    }
    leaf packet-rate-high-water-mark {
      type uint32;
      description "Global incoming packet rate high water mark";
    }
  }
}
