module Cisco-IOS-XR-pfi-im-cmd-ctrlr-oper {

  /*** NAMESPACE / PREFIX DEFINITION ***/

  namespace "http://cisco.com/ns/yang"+
    "/Cisco-IOS-XR-pfi-im-cmd-ctrlr-oper";


  prefix "Cisco-IOS-XR-pfi-im-cmd-ctrlr-oper";

  /*** LINKAGE (IMPORTS / INCLUDES) ***/

  import Cisco-IOS-XR-types { prefix "xr"; }

  include Cisco-IOS-XR-pfi-im-cmd-ctrlr-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR pfi-im-cmd-ctrlr package operational data.

     This module contains definitions
     for the following management objects:
       controllers: Controller operational data

     Copyright (c) 2013-2018 by Cisco Systems, Inc.
     All rights reserved.";

  revision "2015-11-09" {
    description
      "IOS XR 6.0 revision.";
  }


  container controllers {
    config false;
    description "Controller operational data";

    container controllers {
      description "Descriptions for controllers";

      list controller {
        key "interafce-name";
        description "Description for a particular controller";
        leaf interafce-name {
          type xr:Interface-name;
          description "The name of the controller";
        }
        uses IM-CTRLR-DESC-INFO;
      }
    }
  }
}
