submodule Cisco-IOS-XR-fretta-bcm-dpa-npu-stats-oper-sub1 {

  belongs-to Cisco-IOS-XR-fretta-bcm-dpa-npu-stats-oper {
    prefix Cisco-IOS-XR-fretta-bcm-dpa-npu-stats-oper-sub1;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR fretta-bcm-dpa-npu-stats package operational data.

     Copyright (c) 2013-2018 by Cisco Systems, Inc.
     All rights reserved.";

  revision "2015-11-09" {
    description
      "IOS XR 6.0 revision.";
  }


  grouping DPA-VOQ-INGRESS-PACKET-STATISTICS {
    description "DPA VOQ INGRESS PACKET STATISTICS";
    leaf received-bytes {
      type uint64;
      units "byte";
      description "Bytes Received on the port";
    }
    leaf received-packets {
      type uint64;
      description "Packets Received on the port";
    }
    leaf dropped-bytes {
      type uint64;
      units "byte";
      description "Bytes Dropped on the port";
    }
    leaf dropped-packets {
      type uint64;
      description "Packets Dropeed on the port";
    }
  }

  grouping DPA-VOQ-INTF-PORT {
    description "DPA VOQ INTF PORT";
    leaf in-use {
      type boolean;
      description "Flag to indicate if port is in use";
    }
    leaf rack-num {
      type uint8;
      description "Rack of port";
    }
    leaf slot-num {
      type uint8;
      description "Slot of port";
    }
    leaf npu-num {
      type uint8;
      description "NPU of port";
    }
    leaf npu-core {
      type uint8;
      description "NPU core of port";
    }
    leaf port-num {
      type uint8;
      description "Port Number of port";
    }
    leaf if-handle {
      type uint32;
      description "IfHandle of port";
    }
    leaf sys-port {
      type uint32;
      description "System port of port";
    }
    leaf pp-port {
      type uint32;
      description "PP Port number of port";
    }
    leaf port-speed {
      type uint32;
      description "Port speed of port";
    }
    leaf voq-base {
      type uint32;
      description "Voq Base number of port";
    }
    leaf connector-id {
      type uint32;
      description "Connector id of port";
    }
    leaf is-local-port {
      type boolean;
      description "Flag to indicate if port is local to the node";
    }

    list voq-stat {
      max-elements "8";
      description
        "Keeps a record of the received and dropped
        packets and bytes on the port";
      uses DPA-VOQ-INGRESS-PACKET-STATISTICS;
    }
  }

  grouping DPA-TRAP-STATS {
    description "DPA TRAP STATS";
    leaf trap-strength {
      type uint32;
      description "Trap Strength of the trap";
    }
    leaf priority {
      type uint32;
      description "Priority of the trap";
    }
    leaf trap-id-xr {
      type uint32;
      description "Id of the trap";
    }
    leaf gport {
      type uint32;
      description "Gport of the trap";
    }
    leaf fec-id {
      type uint32;
      description "Fec id of the trap";
    }
    leaf policer-id {
      type uint32;
      description "Id of the policer on the trap";
    }
    leaf stats-id {
      type uint32;
      description "Stats Id of the trap";
    }
    leaf encap-id {
      type uint32;
      description "Encap Id of the trap";
    }
    leaf mc-group {
      type uint32;
      description "McGroup of the trap";
    }
    leaf trap-string {
      type string;
      description "Name String of the trap";
    }
    leaf id {
      type uint32;
      description "Id for internal use";
    }
    leaf offset {
      type uint64;
      description "Offset for internal use";
    }
    leaf npu-id {
      type uint64;
      description "NpuId on which trap is enabled";
    }
    leaf packet-dropped {
      type uint64;
      description
        "Number of packets dropped after hitting the trap";
    }
    leaf packet-accepted {
      type uint64;
      description
        "Number of packets accepted after hitting the
        trap";
    }
  }

  grouping FIA-EDM-DEVICE-STATS-ASIC-BRIEF-INFO {
    description "ASIC statistics";
    leaf nbi-rx-total-byte-cnt {
      type uint64;
      units "byte";
      description "Total bytes sent from NIF to IRE";
    }
    leaf nbi-rx-total-pkt-cnt {
      type uint64;
      description "Total packets sent from NIF to IRE";
    }
    leaf ire-cpu-pkt-cnt {
      type uint64;
      description "CPU ingress received packet counter";
    }
    leaf ire-nif-pkt-cnt {
      type uint64;
      description "NIF received packet counter";
    }
    leaf ire-oamp-pkt-cnt {
      type uint64;
      description "OAMP ingress received packet counter";
    }
    leaf ire-olp-pkt-cnt {
      type uint64;
      description "OLP ingress received packet counter";
    }
    leaf ire-rcy-pkt-cnt {
      type uint64;
      description "Recycling ingress received packet counter";
    }
    leaf ire-fdt-if-cnt {
      type uint64;
      description "Performance counter of the FDT interface";
    }
    leaf idr-mmu-if-cnt {
      type uint64;
      description "Performance counter of the MMU interface";
    }
    leaf idr-ocb-if-cnt {
      type uint64;
      description "Performance counter of the OCB interface";
    }
    leaf iqm-enqueue-pkt-cnt {
      type uint64;
      description "Counts enqueued packets";
    }
    leaf iqm-dequeue-pkt-cnt {
      type uint64;
      description "Counts dequeued packets";
    }
    leaf iqm-deleted-pkt-cnt {
      type uint64;
      description
        "Counts matched packets discarded in the DEQ
        process";
    }
    leaf iqm-enq-discarded-pkt-cnt {
      type uint64;
      description "Counts all packets discarded at the ENQ pipe";
    }
    leaf ipt-egq-pkt-cnt {
      type uint64;
      description "EGQ packet counter";
    }
    leaf ipt-enq-pkt-cnt {
      type uint64;
      description "ENQ packet counter";
    }
    leaf ipt-fdt-pkt-cnt {
      type uint64;
      description "FDT packet counter";
    }
    leaf ipt-cfg-event-cnt {
      type uint64;
      description "Configurable event counter";
    }
    leaf ipt-cfg-byte-cnt {
      type uint64;
      units "byte";
      description "Configurable bytes counter";
    }
    leaf fdt-ipt-desc-cell-cnt {
      type uint64;
      description "Descriptor cell counter";
    }
    leaf fdt-ire-desc-cell-cnt {
      type uint64;
      description "IRE internal descriptor cell counter";
    }
    leaf fdt-transmitted-data-cells-cnt {
      type uint64;
      description "Counts all transmitted data cells";
    }
    leaf fdr-p1-cell-in-cnt {
      type uint64;
      description "FDR total incoming cell counter at pipe 1";
    }
    leaf fdr-p2-cell-in-cnt {
      type uint64;
      description "FDR total incoming cell counter at pipe 2";
    }
    leaf fdr-p3-cell-in-cnt {
      type uint64;
      description "FDR total incoming cell counter at pipe 3";
    }
    leaf fdr-cell-in-cnt-total {
      type uint64;
      description "FDR total incoming cell counter";
    }
    leaf fda-cells-in-cnt-p1 {
      type uint64;
      description "FDA input cell counter P1";
    }
    leaf fda-cells-in-cnt-p2 {
      type uint64;
      description "FDA input cell counter P2";
    }
    leaf fda-cells-in-cnt-p3 {
      type uint64;
      description "FDA input cell counter P3";
    }
    leaf fda-cells-in-tdm-cnt {
      type uint64;
      description "FDA input cell counter TDM";
    }
    leaf fda-cells-in-meshmc-cnt {
      type uint64;
      description "FDA input cell counter MESHMC";
    }
    leaf fda-cells-in-ipt-cnt {
      type uint64;
      description "FDA input cell counter IPT";
    }
    leaf fda-cells-out-cnt-p1 {
      type uint64;
      description "FDA output cell counter P1";
    }
    leaf fda-cells-out-cnt-p2 {
      type uint64;
      description "FDA output cell counter P2";
    }
    leaf fda-cells-out-cnt-p3 {
      type uint64;
      description "FDA output cell counter P3";
    }
    leaf fda-cells-out-tdm-cnt {
      type uint64;
      description "FDA output cell counter TDM";
    }
    leaf fda-cells-out-meshmc-cnt {
      type uint64;
      description "FDA output cell counter MESHMC";
    }
    leaf fda-cells-out-ipt-cnt {
      type uint64;
      description "FDA output cell counter IPT";
    }
    leaf fda-egq-drop-cnt {
      type uint64;
      description "FDA EGQ drop counter";
    }
    leaf fda-egq-meshmc-drop-cnt {
      type uint64;
      description "FDA EGQ MESHMC drop counter";
    }
    leaf egq-fqp-pkt-cnt {
      type uint64;
      description "FQP2EPE packet counter";
    }
    leaf egq-pqp-uc-pkt-cnt {
      type uint64;
      description "PQP2FQP unicast packet counter";
    }
    leaf egq-pqp-discard-uc-pkt-cnt {
      type uint64;
      description "PQP discarded unicast packet counter";
    }
    leaf egq-pqp-uc-bytes-cnt {
      type uint64;
      units "byte";
      description "PQP2FQP unicast bytes counter";
    }
    leaf egq-pqp-mc-pkt-cnt {
      type uint64;
      description "PQP2FQP multicast packet counter";
    }
    leaf egq-pqp-discard-mc-pkt-cnt {
      type uint64;
      description "PQP discarded multicast packet counter";
    }
    leaf egq-pqp-mc-bytes-cnt {
      type uint64;
      units "byte";
      description "PQP2FQP multicast bytes counter";
    }
    leaf egq-ehp-uc-pkt-cnt {
      type uint64;
      description "EHP2PQP unicast packet counter";
    }
    leaf egq-ehp-mc-high-pkt-cnt {
      type uint64;
      description "EHP2PQP multicast high packet counter";
    }
    leaf egq-ehp-mc-low-pkt-cnt {
      type uint64;
      description "EHP2PQP multicast low packet counter";
    }
    leaf egq-deleted-pkt-cnt {
      type uint64;
      description "EHP2PQP discarded packet counter";
    }
    leaf egq-ehp-mc-high-discard-cnt {
      type uint64;
      description
        "Number of multicast high packets discarded
        because multicast FIFO is full";
    }
    leaf egq-ehp-mc-low-discard-cnt {
      type uint64;
      description
        "Number of multicast low packets discarded
        because multicast FIFO is full";
    }
    leaf egq-erpp-lag-pruning-discard-cnt {
      type uint64;
      description
        "Number of packet descriptors discarded due to
        LAG multicast pruning";
    }
    leaf egq-erpp-pmf-discard-cnt {
      type uint64;
      description
        "Number of packet descriptors discarded due to
        ERPP PMF";
    }
    leaf egq-erpp-vlan-mbr-discard-cnt {
      type uint64;
      description
        "Number of packet descriptors discarded because
        of egress VLAN membership";
    }
    leaf epni-epe-byte-cnt {
      type uint64;
      units "byte";
      description "EPE2PNI bytes counter";
    }
    leaf epni-epe-pkt-cnt {
      type uint64;
      description "EPE2PNI packet counter";
    }
    leaf epni-epe-discard-cnt {
      type uint64;
      description "EPE discarded packet counter";
    }
    leaf nbi-tx-total-byte-cnt {
      type uint64;
      units "byte";
      description "Total bytes sent from EGQ to NIF";
    }
    leaf nbi-tx-total-pkt-cnt {
      type uint64;
      description "Total packets sent from EGQ to NIF";
    }
  }

  grouping FIA-EDM-STATS-BRIEF-INFO {
    description "ASIC statistics information";

    container statistics {
      description "Statistics";
      uses FIA-EDM-DEVICE-STATS-ASIC-BRIEF-INFO;
    }
    leaf valid {
      type boolean;
      description "Flag to indicate if data is valid";
    }
    leaf rack-number {
      type uint32;
      description "Rack number";
    }
    leaf slot-number {
      type uint32;
      description "Slot number";
    }
    leaf asic-instance {
      type uint32;
      description "ASIC instance";
    }
    leaf chip-version {
      type uint16;
      description "Chip version";
    }
  }

  grouping FIA-EDM-DEVICE-STATS-FIELD-INFO {
    description "Detailed ASIC statistics field information";
    leaf field-name {
      type string {
        length "0..80";
      }
      description "Field name";
    }
    leaf field-value {
      type uint64;
      description "Field value";
    }
    leaf is-overflow {
      type boolean;
      description "Flag to indicate overflow";
    }
  }

  grouping FIA-EDM-DEVICE-STATS-BLK-INFO {
    description "Detailed ASIC statistics block information";
    leaf block-name {
      type string {
        length "0..10";
      }
      description "Block name";
    }
    leaf num-fields {
      type uint8;
      description "Number of fields";
    }

    list field-info {
      description "Field information";
      uses FIA-EDM-DEVICE-STATS-FIELD-INFO;
    }
  }

  grouping FIA-EDM-DEVICE-STATS-ASIC-INFO {
    description "Detailed ASIC statistics information";
    leaf num-blocks {
      type uint8;
      description "Number of blocks";
    }

    list block-info {
      description "Block information";
      uses FIA-EDM-DEVICE-STATS-BLK-INFO;
    }
  }

  grouping FIA-EDM-STATS-INFO {
    description "Detailed ASIC statistics";

    container statistics {
      description "Statistics";
      uses FIA-EDM-DEVICE-STATS-ASIC-INFO;
    }
    leaf valid {
      type boolean;
      description "Flag to indicate if data is valid";
    }
    leaf rack-number {
      type uint32;
      description "Rack number";
    }
    leaf slot-number {
      type uint32;
      description "Slot number";
    }
    leaf asic-instance {
      type uint32;
      description "ASIC instance";
    }
    leaf chip-version {
      type uint16;
      description "Chip version";
    }
  }
}
