module CISCO-ENTITY-FRU-CONTROL-MIB {
  namespace "http://tail-f.com/ns/mibs/CISCO-ENTITY-FRU-CONTROL-MIB/200311240000Z";
  prefix CISCO-ENTITY-FRU-CONTROL-MIB;
  import ietf-yang-types {
    prefix yang;
  }
  import SNMPv2-TC {
    prefix SNMPv2-TC;
  }
  import INET-ADDRESS-MIB {
    prefix INET-ADDRESS-MIB;
  }
  import Cisco-IOS-XR-sysadmin-entity-mib {
    prefix ENTITY-MIB;
  }

  organization "Cisco Systems, Inc.";

  contact
    "Cisco Systems, Inc.
     Customer Service

     Postal: 170 West Tasman Drive
     San Jose, CA 95134

     Tel: +1 800 553-NETS

     E-mail: cs-yang@cisco.com";

  description 
    "This module contains definitions
     for the Calvados model objects.

    Copyright (c) 2012-2018 by Cisco Systems, Inc.
     All rights reserved.";
  revision 2003-11-24 {
    description
      "";
  }

  container CISCO-ENTITY-FRU-CONTROL-MIB {
    container cefcFRUPower {
      config false;
      leaf cefcMaxDefaultInLinePower {
        type cefcMaxDefaultInLinePowerType;
        default "12500";
      }
      leaf cefcMaxDefaultHighInLinePower {
        type uint32;
      }
    }
    container cefcMIBNotificationEnables {
      config false;
      leaf cefcMIBEnableStatusNotification {
        type SNMPv2-TC:TruthValue;
        default "false";
      }
    }
    container cefcFRUPowerSupplyGroupTable {
      config false;
      list cefcFRUPowerSupplyGroupEntry {
        key "entPhysicalIndex";
        leaf entPhysicalIndex {
          type ENTITY-MIB:PhysicalIndex;
        }
        leaf cefcPowerRedundancyMode {
          type PowerRedundancyType;
        }
        leaf cefcPowerUnits {
          type string {
            length "0 .. 255";
          }
          config false;
        }
        leaf cefcTotalAvailableCurrent {
          type FRUCurrentType;
          config false;
        }
        leaf cefcTotalDrawnCurrent {
          type FRUCurrentType;
          config false;
        }
        leaf cefcPowerRedundancyOperMode {
          type PowerRedundancyType;
          config false;
        }
      }
    }
    container cefcFRUPowerStatusTable {
      config false;
      list cefcFRUPowerStatusEntry {
        key "entPhysicalIndex";
        leaf entPhysicalIndex {
          type ENTITY-MIB:PhysicalIndex;
        }
        leaf cefcFRUPowerAdminStatus {
          type PowerAdminType;
          config false;
        }
        leaf cefcFRUPowerOperStatus {
          type PowerOperType;
          config false;
        }
        leaf cefcFRUCurrent {
          type FRUCurrentType;
          config false;
        }
      }
    }
    container cefcFRUPowerSupplyValueTable {
      config false;
      list cefcFRUPowerSupplyValueEntry {
        key "entPhysicalIndex";
        leaf entPhysicalIndex {
          type ENTITY-MIB:PhysicalIndex;
        }
        leaf cefcFRUTotalSystemCurrent {
          type FRUCurrentType;
        }
        leaf cefcFRUDrawnSystemCurrent {
          type FRUCurrentType;
        }
        leaf cefcFRUTotalInlineCurrent {
          type FRUCurrentType;
        }
        leaf cefcFRUDrawnInlineCurrent {
          type FRUCurrentType;
        }
      }
    }
    container cefcModuleTable {
      config false;
      list cefcModuleEntry {
        key "entPhysicalIndex";
        leaf entPhysicalIndex {
          type ENTITY-MIB:PhysicalIndex;
        }
        leaf cefcModuleAdminStatus {
          type ModuleAdminType;
          config false;
        }
        leaf cefcModuleOperStatus {
          type ModuleOperType;
          config false;
        }
        leaf cefcModuleResetReason {
          type ModuleResetReasonType;
          config false;
        }
        leaf cefcModuleStatusLastChangeTime {
          type yang:timestamp;
          config false;
        }
        leaf cefcModuleLastClearConfigTime {
          type yang:timestamp;
          config false;
        }
        leaf cefcModuleResetReasonDescription {
          type string {
            length "0 .. 255";
          }
          config false;
        }
        leaf cefcModuleStateChangeReasonDescr {
          type string {
            length "0 .. 255";
          }
          config false;
        }
        leaf cefcModuleUpTime {
          type FRUTimeSeconds;
          config false;
        }
      }
    }
    container cefcIntelliModuleTable {
      config false;
      list cefcIntelliModuleEntry {
        key "entPhysicalIndex";
        config false;
        leaf entPhysicalIndex {
          type ENTITY-MIB:PhysicalIndex;
        }
        leaf cefcIntelliModuleIPAddrType {
          type INET-ADDRESS-MIB:InetAddressType;
          config false;
        }
        leaf cefcIntelliModuleIPAddr {
          type INET-ADDRESS-MIB:InetAddress;
          config false;
        }
      }
    }
    container cefcFanTrayStatusTable {
      config false;
      list cefcFanTrayStatusEntry {
        key "entPhysicalIndex";
        config false;
        leaf entPhysicalIndex {
          type ENTITY-MIB:PhysicalIndex;
        }
        leaf cefcFanTrayOperStatus {
          type cefcFanTrayOperStatusType;
          config false;
        }
      }
    }
    container cefcPhysicalTable {
      config false;
      list cefcPhysicalEntry {
        key "entPhysicalIndex";
        config false;
        leaf entPhysicalIndex {
          type ENTITY-MIB:PhysicalIndex;
        }
        leaf cefcPhysicalStatus {
          type cefcPhysicalStatusType;
          config false;
        }
      }
    }
  }

  typedef PowerRedundancyType {
    type enumeration {
      enum "notsupported" {
        value 1;
      }
      enum "redundant" {
        value 2;
      }
      enum "combined" {
        value 3;
      }
    }
  }

  typedef PowerAdminType {
    type enumeration {
      enum "on" {
        value 1;
      }
      enum "off" {
        value 2;
      }
      enum "inlineAuto" {
        value 3;
      }
      enum "inlineOn" {
        value 4;
      }
    }
  }

  typedef PowerOperType {
    type enumeration {
      enum "offEnvOther" {
        value 1;
      }
      enum "on" {
        value 2;
      }
      enum "offAdmin" {
        value 3;
      }
      enum "offDenied" {
        value 4;
      }
      enum "offEnvPower" {
        value 5;
      }
      enum "offEnvTemp" {
        value 6;
      }
      enum "offEnvFan" {
        value 7;
      }
      enum "failed" {
        value 8;
      }
      enum "onButFanFail" {
        value 9;
      }
    }
  }

  typedef FRUCurrentType {
    type int32 {
      range "-1000000000 .. 1000000000";
    }
  }

  typedef ModuleAdminType {
    type enumeration {
      enum "enabled" {
        value 1;
      }
      enum "disabled" {
        value 2;
      }
      enum "reset" {
        value 3;
      }
      enum "outOfServiceAdmin" {
        value 4;
      }
    }
  }

  typedef ModuleOperType {
    type enumeration {
      enum "unknown" {
        value 1;
      }
      enum "ok" {
        value 2;
      }
      enum "disabled" {
        value 3;
      }
      enum "okButDiagFailed" {
        value 4;
      }
      enum "boot" {
        value 5;
      }
      enum "selfTest" {
        value 6;
      }
      enum "failed" {
        value 7;
      }
      enum "missing" {
        value 8;
      }
      enum "mismatchWithParent" {
        value 9;
      }
      enum "mismatchConfig" {
        value 10;
      }
      enum "diagFailed" {
        value 11;
      }
      enum "dormant" {
        value 12;
      }
      enum "outOfServiceAdmin" {
        value 13;
      }
      enum "outOfServiceEnvTemp" {
        value 14;
      }
      enum "poweredDown" {
        value 15;
      }
      enum "poweredUp" {
        value 16;
      }
      enum "powerDenied" {
        value 17;
      }
      enum "powerCycled" {
        value 18;
      }
      enum "okButPowerOverWarning" {
        value 19;
      }
      enum "okButPowerOverCritical" {
        value 20;
      }
      enum "updatingFPD" {
        value 21;
      }
    }
  }

  typedef ModuleResetReasonType {
    type enumeration {
      enum "unknown" {
        value 1;
      }
      enum "powerUp" {
        value 2;
      }
      enum "parityError" {
        value 3;
      }
      enum "clearConfigReset" {
        value 4;
      }
      enum "manualReset" {
        value 5;
      }
      enum "watchDogTimeoutReset" {
        value 6;
      }
      enum "resourceOverflowReset" {
        value 7;
      }
      enum "missingTaskReset" {
        value 8;
      }
      enum "lowVoltageReset" {
        value 9;
      }
      enum "controllerReset" {
        value 10;
      }
      enum "systemReset" {
        value 11;
      }
      enum "switchoverReset" {
        value 12;
      }
      enum "upgradeReset" {
        value 13;
      }
      enum "downgradeReset" {
        value 14;
      }
      enum "cacheErrorReset" {
        value 15;
      }
      enum "deviceDriverReset" {
        value 16;
      }
      enum "softwareExceptionReset" {
        value 17;
      }
      enum "restoreConfigReset" {
        value 18;
      }
      enum "abortRevReset" {
        value 19;
      }
      enum "burnBootReset" {
        value 20;
      }
      enum "standbyCdHealthierReset" {
        value 21;
      }
      enum "nonNativeConfigClearReset" {
        value 22;
      }
      enum "memoryProtectionErrorReset" {
        value 23;
      }
    }
  }

  typedef FRUTimeSeconds {
    type uint32 {
      range "0 .. 4294967295";
    }
  }

  typedef cefcMaxDefaultInLinePowerType {
    type int32 {
      range "0 .. 12500";
    }
  }

  typedef cefcFanTrayOperStatusType {
    type enumeration {
      enum "unknown" {
        value 1;
      }
      enum "up" {
        value 2;
      }
      enum "down" {
        value 3;
      }
      enum "warning" {
        value 4;
      }
    }
  }

  typedef cefcPhysicalStatusType {
    type enumeration {
      enum "other" {
        value 1;
      }
      enum "supported" {
        value 2;
      }
      enum "unsupported" {
        value 3;
      }
      enum "incompatible" {
        value 4;
      }
    }
  }
}
