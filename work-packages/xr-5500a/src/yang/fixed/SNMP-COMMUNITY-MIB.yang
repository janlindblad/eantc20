module SNMP-COMMUNITY-MIB {
  namespace "http://tail-f.com/ns/mibs/SNMP-COMMUNITY-MIB/200308060000Z";
  prefix SNMP-COMMUNITY-MIB;
  tailf:id "";
  tailf:snmp-mib-module-name "SNMP-COMMUNITY-MIB";
  import tailf-common {
    prefix tailf;
  }
  import SNMPv2-TC {
    prefix SNMPv2_TC;
  }
  import SNMP-TARGET-MIB {
    prefix SNMP_TARGET_MIB;
  }
  import SNMP-FRAMEWORK-MIB {
    prefix SNMP_FRAMEWORK_MIB;
  }

  revision 2003-08-06 {
    description
      "";
  }

  container SNMP-COMMUNITY-MIB {
    container snmpCommunityTable {
      list snmpCommunityEntry {
        key "snmpCommunityIndex";
        tailf:sort-order "snmp-implied";
        tailf:snmp-oid "1.3.6.1.6.3.18.1.1";
        tailf:callpoint "snmp" {
          tailf:internal;
          tailf:set-hook "node";
        }
        leaf snmpCommunityIndex {
          type snmpCommunityIndexType;
          tailf:snmp-oid "1.3.6.1.6.3.18.1.1.1.1";
        }
        leaf snmpCommunityName {
          type snmpCommunityNameType;
          mandatory true;
          tailf:snmp-oid "1.3.6.1.6.3.18.1.1.1.2";
        }
        leaf snmpCommunitySecurityName {
          type snmpCommunitySecurityNameType;
          mandatory true;
          tailf:snmp-oid "1.3.6.1.6.3.18.1.1.1.3";
        }
        leaf snmpCommunityContextEngineID {
          type SNMP_FRAMEWORK_MIB:SnmpEngineID;
          mandatory true;
          tailf:snmp-oid "1.3.6.1.6.3.18.1.1.1.4";
        }
        leaf snmpCommunityContextName {
          type snmpCommunityContextNameType;
          tailf:snmp-oid "1.3.6.1.6.3.18.1.1.1.5";
          default "";
        }
        leaf snmpCommunityTransportTag {
          type SNMP_TARGET_MIB:SnmpTagValue;
          tailf:snmp-oid "1.3.6.1.6.3.18.1.1.1.6";
          default "";
        }
        leaf snmpCommunityStorageType {
          type SNMPv2_TC:StorageType;
          tailf:snmp-oid "1.3.6.1.6.3.18.1.1.1.7";
          default "permanent";
        }
      }
    }
  }

  typedef snmpCommunityIndexType {
    type string {
      length "1 .. 32";
    }
  }

  typedef snmpCommunityNameType {
    type string;
  }

  typedef snmpCommunitySecurityNameType {
    type string {
      length "1 .. 32";
    }
  }

  typedef snmpCommunityContextNameType {
    type string {
      length "min .. 32";
    }
  }

  typedef snmpTargetAddrNameType {
    type string {
      length "1 .. 32";
    }
  }

  typedef snmpTargetAddrTMaskType {
    type tailf:hex-list {
      pattern "(((([0-9A-Fa-f]{2}):){0,254}([0-9A-Fa-f]{2}))){0,1}";
      tailf:value-length "min .. 255";
    }
  }

  typedef snmpTargetAddrMMSType {
    type int32 {
      range "0 .. 2147483647";
    }
  }
}
