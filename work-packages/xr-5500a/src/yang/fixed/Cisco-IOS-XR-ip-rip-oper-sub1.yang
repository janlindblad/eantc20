submodule Cisco-IOS-XR-ip-rip-oper-sub1 {

  belongs-to Cisco-IOS-XR-ip-rip-oper {
    prefix Cisco-IOS-XR-ip-rip-oper-sub1;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ip-rip package operational data.

     Copyright (c) 2013-2018 by Cisco Systems, Inc.
     All rights reserved.";

  revision "2015-11-09" {
    description
      "IOS XR 6.0 revision.";
  }

  typedef Interface-state {
    type enumeration {
      enum interface-none {
        value 0;
        description "Interface does not exist";
      }
      enum interface-down {
        value 1;
        description "Interface exists but IP is down";
      }
      enum interface-up {
        value 2;
        description "Interface exists and IP is up";
      }
      enum interface-unknown {
        value 3;
        description "Unknown state";
      }
    }
    description "Interface state";
  }
  typedef Rip-route-origin {
    type enumeration {
      enum rip-rt-org-runover {
        value 0;
        description "configured 'network'";
      }
      enum rip-rt-org-redist {
        value 1;
        description "redistributed";
      }
      enum rip-rt-org-auto-summary {
        value 2;
        description "auto summary";
      }
      enum rip-rt-org-rip {
        value 3;
        description "learned via RIP";
      }
      enum rip-rt-org-intsummary {
        value 4;
        description "interface summary-address";
      }
      enum rip-rt-org-unused {
        value 5;
        description "route stay in for triggered rip";
      }
    }
    description "Rip route origin";
  }

  grouping RIP-SHOW-PROTO-PROC-BD {
    description "RIP protocol process data";
    leaf vrf-config-count {
      type uint32;
      description "Number of VRFs configured";
    }
    leaf vrf-active-count {
      type uint32;
      description "Number of active VRFs";
    }
    leaf socket-descriptor {
      type int32;
      description "Socket descriptior";
    }
    leaf current-oom-state {
      type int32;
      description "Current OOM state";
    }
    leaf route-count {
      type uint32;
      description "Number of routes allocated";
    }
    leaf path-count {
      type uint32;
      description "Number of paths allocated";
    }

    list vrf-summary {
      description "List of VRFs configured";
      uses RIP-SHOW-VRF-SUMM-BD;
    }
  }

  grouping RIP-SHOW-IF-SUMM-BD {
    description "RIP Interface summary data";
    leaf interface-name {
      type string;
      description "Interface name";
    }
    leaf enabled {
      type boolean;
      description "RIP enabled indicator";
    }
    leaf state {
      type Interface-state;
      description "Interface state";
    }
    leaf destination-address {
      type inet:ipv4-address;
      description "IP address";
    }
    leaf prefix-length {
      type uint32;
      description "Prefix length of IP address";
    }
    leaf oom-flags {
      type uint32;
      description "Current OOM flags";
    }
    leaf send-version {
      type uint32;
      description "RIP versions this interface sends out";
    }
    leaf receive-version {
      type uint32;
      description "RIP versions this interface will receive";
    }
    leaf neighbor-count {
      type uint32;
      description "Number of neighbors seen";
    }
  }

  grouping RIP-SHOW-VRF-SUMM-BD {
    description "RIP VRF summary data";
    leaf vrf-name {
      type string;
      description "VRF Name";
    }
    leaf active {
      type boolean;
      description "VRF Active indicator";
    }
    leaf oom-flags {
      type uint32;
      description "Current OOM flags";
    }
    leaf route-count {
      type uint32;
      description "Number of routes allocated";
    }
    leaf path-count {
      type uint32;
      description "Number of paths allocated";
    }
    leaf update-timer {
      type uint32;
      description "Update timer";
    }
    leaf next-update-time {
      type uint32;
      description "Time left for next update";
    }
    leaf invalid-timer {
      type uint32;
      description "Invalid timer";
    }
    leaf hold-down-timer {
      type uint32;
      description "Holddown timer";
    }
    leaf flush-timer {
      type uint32;
      description "Flush timer";
    }
    leaf interface-configured-count {
      type uint32;
      description "Number of interfaces configured";
    }
    leaf active-interface-count {
      type uint32;
      description "Number of active interfaces";
    }
  }

  grouping RIP-SHOW-PROTO-VRF-BD {
    description "RIP protocol VRF data";

    container vrf-summary {
      description "VRF summary data";
      uses RIP-SHOW-VRF-SUMM-BD;
    }

    list interface-summary {
      description "List of Interfaces configured";
      uses RIP-SHOW-IF-SUMM-BD;
    }
  }

  grouping RIP-PEER-BD {
    description "A RIP peer";
    leaf peer-uptime {
      type uint32;
      description "Uptime of this peer";
    }
    leaf peer-address {
      type inet:ipv4-address;
      description "IP Address of this peer";
    }
    leaf peer-version {
      type uint8;
      description "RIP version for this peer";
    }
    leaf discarded-peer-packets {
      type uint32;
      description "Discarded packets from this peer";
    }
    leaf discarded-peer-routes {
      type uint32;
      description "Discarded routes from this peer";
    }
  }

  grouping RIP-SUMMARY-BD {
    description "A RIP summary route";
    leaf prefix {
      type inet:ipv4-address;
      description "Summary address prefix";
    }
    leaf prefix-length {
      type uint32;
      description "Summary address prefix length";
    }
    leaf next-hop-address {
      type inet:ipv4-address;
      description "Summary address next hop";
    }
    leaf metric {
      type int32;
      description "Summary metric";
    }
  }

  grouping RIP-SHOW-INTERFACE-BD {
    description "A RIP-enabled interface";
    leaf interface {
      type string;
      description "Interface name";
    }
    leaf if-handle {
      type xr:Interface-name;
      description "Interface handle";
    }
    leaf rip-enabled {
      type boolean;
      description "Whether RIP is enabled on this interface";
    }
    leaf is-passive-interface {
      type boolean;
      description "Passive interface indicator";
    }
    leaf multicast-address {
      type boolean;
      description "Use broadcast address for v2 packets";
    }
    leaf accept-metric {
      type boolean;
      description "Accept routes of metric 0 indicator";
    }
    leaf send-version {
      type uint32;
      description "Versions that the interface is sending";
    }
    leaf receive-version {
      type uint32;
      description "Versions that the interface will recieve";
    }
    leaf state {
      type Interface-state;
      description "Current state of the interface";
    }
    leaf destination-address {
      type inet:ipv4-address;
      description "IP Address of this interface";
    }
    leaf prefix-length {
      type uint32;
      description "Prefix length of the IP address";
    }
    leaf metric-cost {
      type uint32;
      description "Cost added to routes through this interface";
    }
    leaf split-horizon {
      type boolean;
      description "Split horizon enabled indicator";
    }
    leaf poison-horizon {
      type boolean;
      description "Poisoned reverse enabled indicator";
    }
    leaf triggered-rip {
      type boolean;
      description "Triggered RIP enabled indicator";
    }
    leaf neighbor-address {
      type inet:ipv4-address;
      description "Interface's triggered RIP neighbor";
    }
    leaf oom-flags {
      type uint32;
      description "Out-of-memory status flags";
    }
    leaf join-status {
      type boolean;
      description "Multicast group join status";
    }
    leaf lpts-state {
      type boolean;
      description "LPTSState";
    }
    leaf auth-mode {
      type uint32;
      description "Authentication Mode";
    }
    leaf auth-keychain {
      type string;
      description "Authentication Keychain Name";
    }
    leaf send-auth-key-exists {
      type boolean;
      description "Authentication send key exists";
    }
    leaf auth-key-md5 {
      type boolean;
      description
        "Authentication key programmed with MD5 algorithm";
    }
    leaf auth-key-send-id {
      type uint64;
      description "Current active Send Authentication Key Id";
    }
    leaf total-pkt-recvd {
      type uint32;
      description "Total packets received";
    }
    leaf pkt-drop-wrong-kc {
      type uint32;
      description
        "Packets dropped due to wrong keychain configured";
    }
    leaf pkt-drop-no-auth {
      type uint32;
      description
        "Packets dropped due to missing authentication
        data";
    }
    leaf pkt-drop-invalid-auth {
      type uint32;
      description
        "Packets dropped due to invalid authentication
        data";
    }
    leaf pkt-accepted-valid-auth {
      type uint32;
      description "Packets accepted with valid authentication data";
    }

    list rip-summary {
      description "User defined summary addresses";
      uses RIP-SUMMARY-BD;
    }

    list rip-peer {
      description "Neighbors on this interface";
      uses RIP-PEER-BD;
    }
  }

  grouping RIP-SHOW-STATISTICS-BD {
    description "RIP statistics";
    leaf received-packets {
      type uint32;
      description "Total packets received";
    }
    leaf discarded-packets {
      type uint32;
      description "Total discarded packets";
    }
    leaf discarded-routes {
      type uint32;
      description "Total discarded routes";
    }
    leaf standby-packets-received {
      type uint32;
      description "Packets rx in SRP";
    }
    leaf sent-messages {
      type uint32;
      description "Number of messages sent";
    }
    leaf sent-message-failures {
      type uint32;
      description "Number of message send failures";
    }
    leaf query-responses {
      type uint32;
      description "Number of RIP queries responded to";
    }
    leaf periodic-updates {
      type uint32;
      description "Number of periodic RIP updates";
    }
    leaf route-count {
      type uint32;
      description "Number of routes allocated";
    }
    leaf path-count {
      type uint32;
      description "Number of paths allocated";
    }
    leaf route-malloc-failures {
      type uint32;
      description
        "Number of failures to allocate memory for a
        route";
    }
    leaf path-malloc-failures {
      type uint32;
      description
        "Number of failures to allocate memory for a path";
    }
    leaf rib-updates {
      type uint32;
      description "Number of route updates to RIB made by RIP";
    }
  }

  grouping RIP-SHOW-GLOBAL-CONFIG-BD {
    description "RIP's configuration settings";
    leaf active {
      type boolean;
      description "VRF active indicator";
    }
    leaf vr-fised-socket {
      type boolean;
      description "VRF added to socket indicator";
    }
    leaf rip-version {
      type int32;
      description "Version of RIP configured";
    }
    leaf default-metric {
      type uint8;
      description "Default metric for RIP routes";
    }
    leaf maximum-paths {
      type uint8;
      description "Maximum number of paths a route can have";
    }
    leaf auto-summarize {
      type boolean;
      description "Auto-summarization indicator";
    }
    leaf multicast-address {
      type boolean;
      description "Use broadcast/multicast address indicator";
    }
    leaf flash-threshold {
      type uint8;
      description "Flash update threshold";
    }
    leaf input-q-length {
      type uint16;
      description "Length of the input queue";
    }
    leaf triggered-rip {
      type boolean;
      description "Triggered RIP enabled indicator";
    }
    leaf validation-indicator {
      type boolean;
      description "Incoming packet source validation indicator";
    }
    leaf update-timer {
      type uint32;
      description "Update timer";
    }
    leaf next-update-time {
      type uint32;
      description "Time left for next update";
    }
    leaf invalid-timer {
      type uint32;
      description "Invalid timer";
    }
    leaf hold-down-timer {
      type uint32;
      description "Holddown timer";
    }
    leaf flush-timer {
      type uint32;
      description "Flush timer";
    }
    leaf oom-flags {
      type uint32;
      description "Out-of-memory status flags";
    }
    leaf nsf-status {
      type boolean;
      description "NSF Enable status";
    }
    leaf nsf-life-time {
      type uint32;
      description "NSF life time";
    }
  }

  grouping RIP-PATH-BD {
    description "A RIP route path";
    leaf source-address {
      type inet:ipv4-address;
      description "Source address";
    }
    leaf next-hop-address {
      type inet:ipv4-address;
      description "Next hop address";
    }
    leaf metric {
      type uint16;
      description "Metric";
    }
    leaf tag {
      type uint16;
      description "Tag";
    }
    leaf interface {
      type xr:Interface-name;
      description "Interface";
    }
    leaf uptime {
      type uint32;
      description "Up time";
    }
    leaf is-permanent {
      type boolean;
      description "Permanent indicator";
    }
  }

  grouping RIP-SHOW-ROUTE-BD {
    description "A route in RIP's local routing table";
    leaf destination-address {
      type inet:ipv4-address;
      description "Destination IP Address for this route";
    }
    leaf prefix-length-xr {
      type uint32;
      description "Prefix length of IP address";
    }
    leaf distance {
      type uint16;
      description "Route administrative distance";
    }
    leaf bgp-count {
      type uint16;
      description "Hop count for this route";
    }
    leaf route-type {
      type uint16;
      description "Type of this route";
    }
    leaf route-summary {
      type boolean;
      description "Summary route placeholder indicator";
    }
    leaf route-tag {
      type uint16;
      description "Generic route information";
    }
    leaf version {
      type uint8;
      description "RIB supplied version number";
    }
    leaf attributes {
      type uint32;
      description "RIB supplied route attributes";
    }
    leaf active {
      type boolean;
      description "Active route indicator";
    }
    leaf path-origin {
      type Rip-route-origin;
      description "Where this route was learnt";
    }
    leaf hold-down {
      type boolean;
      description "Indicates whether route is in holddown";
    }

    list paths {
      description "The paths for this route";
      uses RIP-PATH-BD;
    }
  }
}
