module Cisco-IOS-XR-snmp-agent-oper {

  /*** NAMESPACE / PREFIX DEFINITION ***/

  namespace "http://cisco.com/ns/yang/Cisco-IOS-XR-snmp-agent-oper";


  prefix "Cisco-IOS-XR-snmp-agent-oper";

  /*** LINKAGE (IMPORTS / INCLUDES) ***/

  import ietf-inet-types { prefix "inet"; }

  import Cisco-IOS-XR-types { prefix "xr"; }

  include Cisco-IOS-XR-snmp-agent-oper-sub7 {
    revision-date 2018-07-20;
  }

  include Cisco-IOS-XR-snmp-agent-oper-sub6 {
    revision-date 2018-07-20;
  }

  include Cisco-IOS-XR-snmp-agent-oper-sub5 {
    revision-date 2018-07-20;
  }

  include Cisco-IOS-XR-snmp-agent-oper-sub4 {
    revision-date 2018-07-20;
  }

  include Cisco-IOS-XR-snmp-agent-oper-sub3 {
    revision-date 2018-07-20;
  }

  include Cisco-IOS-XR-snmp-agent-oper-sub2 {
    revision-date 2018-07-20;
  }

  include Cisco-IOS-XR-snmp-agent-oper-sub1 {
    revision-date 2018-07-20;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR snmp-agent package operational data.

     This module contains definitions
     for the following management objects:
       snmp: SNMP operational data

     Copyright (c) 2013-2018 by Cisco Systems, Inc.
     All rights reserved.";

  revision "2018-07-20" {
    description
      "Fixed English plural name transformation error.";
  }

  revision "2017-09-07" {
    description
      "Fixed type translation error.";
  }

  revision "2017-05-01" {
    description
      "Fixing backward compatibility error in module.";
  }

  revision "2016-06-01" {
    description
      "IOS XR 6.0.1 revision.";
  }

  revision "2015-01-07" {
    description
      "IOS XR 5.3.1 revision.";
  }


  container snmp {
    config false;
    description "SNMP operational data";

    container trap-servers {
      description "List of trap hosts";

      list trap-server {
        description
          "Trap server and port to which the trap is to be
          sent and statistics";
        leaf trap-host {
          type string;
          description "Trap Host";
        }
        leaf port {
          type inet:port-number;
          description "Trap port";
        }
        uses SNMP-TRAP-STATS;
      }
    }

    container information {
      description "SNMP operational information";

      container hosts {
        description "SNMP host information";

        list host {
          key "name";
          description "SNMP target host name";
          leaf name {
            type xr:Cisco-ios-xr-string;
            description "Group name";
          }

          list host-information {
            key "user";
            description
              "Host name ,udp-port , user, security model
              and level";
            leaf user {
              type xr:Cisco-ios-xr-string;
              description "SNMP host user";
            }
            uses SNMP-SNMP-HOST-XML;
          }
        }
      }

      container system-up-time {
        description "System up time";
        uses SNMP-SYSUPTIME-EDM;
      }

      container nms-addresses {
        description "SNMP request type summary ";

        list nms-address {
          key "nms-addr";
          description "NMS address";
          leaf nms-addr {
            type xr:Cisco-ios-xr-string;
            description "NMS address";
          }
          uses SNMP-REQ-NMS-SUM;
        }
      }

      container engine-id {
        description "SNMP engine ID";
        uses SNMP-ENGINEID;
      }

      container rx-queue {
        description "SNMP rx queue statistics";
        uses SNMP-RXQUE;
      }

      container system-name {
        description "System name";
        uses SNMP-SYSNAME;
      }

      container request-type-detail {
        description "SNMP request type details ";

        container nms-addresses {
          description "snmp request type details ";

          list nms-address {
            key "nms-addr";
            description "NMS address";
            leaf nms-addr {
              type xr:Cisco-ios-xr-string;
              description "NMS address";
            }
            uses SNMP-Q-STATS-B;
          }
        }
      }

      container duplicate-drop {
        description "Duplicate request status, count, time ";
        uses SNMP-STATISTICS;
      }

      container bulk-stats-transfers {
        description "List of bulkstats transfer on the system";

        list bulk-stats-transfer {
          key "transfer-name";
          description "SNMP bulkstats transfer name";
          leaf transfer-name {
            type xr:Cisco-ios-xr-string;
            description "Transfer name";
          }
          uses SNMP-BULKSTATS-B;
        }
      }

      container trap-infos {
        description "SNMP trap OID";

        list trap-info {
          description
            "SNMP Trap infomation like server , port and
            trapOID";
          leaf trap-host {
            type string;
            description "Trap Host";
          }
          leaf port {
            type inet:port-number;
            description "Trap port";
          }
          uses SNMP-TRAPS-INFO;
        }
      }

      container poll-oids {
        description "OID list for poll PDU";

        list poll-oid {
          key "object-id";
          description "PDU drop info for OID";
          leaf object-id {
            type xr:Cisco-ios-xr-string;
            description "Object ID";
          }
          uses SNMP-OID-STATS-B;
        }
      }

      container infom-details {
        description "SNMP trap OID";

        list infom-detail {
          description
            "SNMP Trap infomation like server , port and
            trapOID";
          leaf trap-host {
            type string;
            description "Trap Host";
          }
          leaf port {
            type inet:port-number;
            description "Trap port";
          }
          uses SNMP-TRAPS-INFO;
        }
      }

      container statistics {
        description "SNMP statistics";
        uses SNMP-STATS;
      }

      container incoming-queue {
        description "Incoming queue details ";
        uses SNMP-INCOMING-Q-STATS-ENTRY;
      }

      container context-mapping {
        description
          "Context name, features name, topology name,
          instance";
        uses SNMP-CTX-MAPPING-XML;
      }

      container trap-oids {
        description "SNMP trap OID";

        list trap-oid {
          key "trap-oid";
          description "SNMP trap ";
          leaf trap-oid {
            type xr:Cisco-ios-xr-string;
            description "Trap object ID";
          }
          uses SNMP-TRAPS-COUNT;
        }
      }

      container nm-spackets {
        description "SNMP overload statistics ";

        list nm-spacket {
          key "packetcount";
          description "NMS packet drop count";
          leaf packetcount {
            type xr:Cisco-ios-xr-string;
            description "NMS packet drop count";
          }
          uses SNMP-OVERLOAD-STATS;
        }
      }

      container mibs {
        description "List of MIBS supported on the system";

        list mib {
          key "name";
          description "SNMP MIB Name";

          container oids {
            description "List of OIDs per MIB";

            list oid {
              key "oid";
              description "Object identifiers of a mib";
              leaf oid {
                type string;
                description "Object Identifier";
              }
              leaf oid-name {
                type string;
                mandatory true;
                description "MIB OID Name";
              }
            }
          }

          container mib-information {
            description "MIB state and information";
            uses SNMP-MIB-INFO;
          }
          leaf name {
            type xr:Cisco-ios-xr-string;
            description "MIB Name";
          }
        }
      }

      container serial-numbers {
        description "SNMP statistics pdu ";

        list serial-number {
          description "Serial number";
          leaf number {
            type xr:Cisco-ios-xr-string;
            description "Serial number";
          }
          leaf req-id {
            type uint32;
            description "Request ID";
          }
          leaf port {
            type inet:port-number;
            description "Port";
          }
          uses SNMP-PDU-STATS;
        }
      }

      container drop-nms-addresses {
        description "NMS list for drop PDU";

        list drop-nms-address {
          key "nms-addr";
          description "PDU drop info for NMS";
          leaf nms-addr {
            type xr:Cisco-ios-xr-string;
            description "NMS address";
          }
          uses SNMP-PDU-DROP-STATS;
        }
      }

      container views {
        description "SNMP view information";

        list view {
          key "name";
          description "SNMP target view name";
          leaf name {
            type xr:Cisco-ios-xr-string;
            description "View name";
          }

          list view-information {
            key "object-id";
            description
              "View name ,familytype, storagetype and status";
            leaf object-id {
              type xr:Cisco-ios-xr-string;
              description "SNMP view OID";
            }
            uses SNMP-SNMP-VIEW-XML-ENTRY;
          }
        }
      }

      container system-descr {
        description "System description";
        uses SNMP-SYSDESCR;
      }

      container tables {
        description "List of table";

        container groups {
          description "List of vacmAccessTable";

          list group {
            key "name";
            description "SNMP group name";

            container group-informations {
              description "Group Model";

              list group-information {
                description "Group name ,status  and information";
                leaf modelnumber {
                  type xr:Cisco-ios-xr-string;
                  description "Model number";
                }
                leaf level {
                  type xr:Cisco-ios-xr-string;
                  description "Level";
                }
                uses SNMP-VACM-ACCESS-ENTRY;
              }
            }
            leaf name {
              type xr:Cisco-ios-xr-string;
              description "Group Name";
            }
          }
        }

        container user-engine-ids {
          description "List of User";

          list user-engine-id {
            key "engine-id";
            description "SNMP engineId";
            leaf engine-id {
              type xr:Cisco-ios-xr-string;
              description "SNMP Engine ID";
            }

            list user-name {
              key "user-name";
              description "User name ,storage type ,status ";
              leaf user-name {
                type xr:Cisco-ios-xr-string;
                description "User name";
              }
              uses SNMP-USM-USER-ENTRY;
            }
          }
        }
      }

      container system-oid {
        description "System object ID";
        uses SNMP-SYSOBJID;
      }

      container trap-queue {
        description "SNMP trap queue statistics";
        uses SNMP-TRAPQUE;
      }
    }

    container interfaces {
      description "List of interfaces";

      list interface {
        key "name";
        description "Interface Name";
        leaf name {
          type xr:Interface-name;
          description "Interface Name";
        }
        leaf interface-index {
          type uint32;
          mandatory true;
          description "Interface Index as used by MIB tables";
        }
      }
    }

    container correlator {
      description "Trap Correlator operational data";

      container rule-details {
        description
          "Table that contains the database of correlation
          rule details";

        list rule-detail {
          key "rule-name";
          description "Details of one of the correlation rules";
          leaf rule-name {
            type string {
              length "1..32";
            }
            description "Correlation Rule Name";
          }
          uses SNMP-CORR-RULE-DETAIL-BAG;
        }
      }

      container buffer-status {
        description
          "Describes buffer utilization and parameters
          configured";
        uses SNMP-CORR-BUFFER-INFO-BAG;
      }

      container rule-set-details {
        description "Table that contains the ruleset detail info";

        list rule-set-detail {
          key "rule-set-name";
          description "Detail of one of the correlation rulesets";
          leaf rule-set-name {
            type string {
              length "1..32";
            }
            description "Ruleset Name";
          }
          uses SNMP-CORR-RULESET-DETAIL-BAG;
        }
      }

      container traps {
        description "Correlated traps Table";

        list trap {
          key "entry-id";
          description "One of the correlated traps";
          leaf entry-id {
            type uint32;
            description "Entry ID";
          }
          uses SNMP-CORR-TRAP-BUFFER-BAG;
        }
      }
    }

    container interface-indexes {
      description "List of index";

      list interface-index {
        key "interface-index";
        description "Interface Index";
        leaf interface-index {
          type uint32;
          description "Interface Index as used by MIB tables";
        }
        leaf interface-name {
          type string;
          mandatory true;
          description "Interface Name";
        }
      }
    }

    container if-indexes {
      description "List of ifnames";

      list if-index {
        key "interface-index";
        description "Interface Index";
        leaf interface-index {
          type uint32;
          description "Interface Index as used by MIB tables";
        }
        uses SNMP-IFINDEX-IFNAME;
      }
    }
  }
}
