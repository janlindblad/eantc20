submodule Cisco-IOS-XR-fib-common-oper-sub7 {

  belongs-to Cisco-IOS-XR-fib-common-oper {
    prefix Cisco-IOS-XR-fib-common-oper-sub7;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR fib-common package operational data.

     Copyright (c) 2013-2018 by Cisco Systems, Inc.
     All rights reserved.";

  revision "2017-09-07" {
    description
      "Fixed type translation error.";
  }

  revision "2017-05-01" {
    description
      "Fixing backward compatibility error in module.";
  }

  revision "2017-01-20" {
    description
      "IOS XR 6.2.1 revision";
  }

  revision "2015-11-09" {
    description
      "IOS XR 6.0 revision.";
  }


  grouping FIB-STATISTICS-BAG-DROPS {
    description "FIB drop statistics";
    leaf no-route-packets {
      type uint64;
      description "no route pkt";
    }
    leaf punt-unreachable-packets {
      type uint64;
      description "Punt generate unreach pkt";
    }
    leaf df-unreachable-packets {
      type uint64;
      description "DF unreachable pkt";
    }
    leaf encapsulation-failure-packets {
      type uint64;
      description "encapsulation failure pkt";
    }
    leaf incomplete-adjacency-packets {
      type uint64;
      description "incomplete adjacency pkt";
    }
    leaf unresolved-prefix-packets {
      type uint64;
      description "unresolved prefix pkt";
    }
    leaf unsupported-feature-packets {
      type uint64;
      description "unsupported feature pkt";
    }
    leaf discard-packets {
      type uint64;
      description "discard pkt";
    }
    leaf checksum-error-packets {
      type uint64;
      description "checksum error pkt";
    }
    leaf fragmenation-consumed-packets {
      type uint64;
      description "frag consumed packet pkt";
    }
    leaf fragmenation-failure-packets {
      type uint64;
      description "fragmenation failure pkt";
    }
    leaf null-packets {
      type uint64;
      description "null0 pkt";
    }
    leaf rpf-check-failure-packets {
      type uint64;
      description "RPF check failures pkt";
    }
    leaf acl-in-rpf-packets {
      type uint64;
      description "ACL in RPF pkt";
    }
    leaf rp-destination-drop-packets {
      type uint64;
      description "rp dest drop pkt";
    }
    leaf total-number-of-drop-packets {
      type uint64;
      description "the total number of drop pkt";
    }
    leaf mpls-disabled-interface {
      type uint64;
      description "mpls disabled in interface";
    }
    leaf gre-lookup-failed-drop {
      type uint64;
      description "GRE tunnel lookup failed drop pkt";
    }
    leaf gre-error-drop {
      type uint64;
      description "GRE processing errors";
    }
    leaf lisp-punt-drops {
      type uint64;
      description "LISP Punt drops";
    }
    leaf lisp-encap-error-drops {
      type uint64;
      description "Lisp encap error drops";
    }
    leaf lisp-decap-error-drops {
      type uint64;
      description "Lisp decap error drops";
    }
    leaf multi-label-drops {
      type uint64;
      description "Drops for the packets with multi[le labels";
    }
    leaf unreachable-sr-label-drops {
      type uint64;
      description "No route or unresolved route of MPLS SR labels";
    }
    leaf ttl-expired-sr-label-drops {
      type uint64;
      description "TTL expired drops of MPLS SR labels";
    }
  }
}
