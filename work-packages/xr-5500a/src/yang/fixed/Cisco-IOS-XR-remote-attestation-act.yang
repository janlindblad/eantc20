module Cisco-IOS-XR-remote-attestation-act {

 namespace "http://cisco.com/ns/yang/Cisco-IOS-XR-remote-attestation-act";

 prefix "Cisco-IOS-XR-remote-attestation-act";

organization "Cisco Systems, Inc.";

 contact
   "Cisco Systems, Inc.
    Customer Service
    Postal: 170 West Tasman Drive
    San Jose, CA 95134
    Tel: +1 800 553-NETS
    E-mail: cs-yang@cisco.com";


description
  "This module defines procedure for remote attestation
    of a network platform''s security posture.
    This is useful to assess trustworthiness of
    hardware and software of a network device.

   Copyright (c) 2017 IETF Trust and the persons identified
   as authors of the code. All rights reserved.

   Redistribution and use in source and binary forms, with
   or without modification, is permitted pursuant to, and
   subject to the license terms contained in, the Simplified
   BSD License set forth in Section 4.c of the IETF Trust''s
   Legal Provisions Relating to IETF Documents
   (http://trustee.ietf.org/license-info).

   This version of this YANG module is part of RFC VVVV; see
   the RFC itself for full legal notices.";

revision 2017-06-08 {
       description "Initial revision.";
       reference
    "RFC VVVV: NETCONF Server and RESTCONF Server Operational
         Models";
 }


 grouping PCR-DUMP {
    description
      "Defines TPM PCR register";
    leaf index {
       type uint16;
       description
   "PCR index";
    }
    leaf-list value {
       type uint8;
       min-elements 20;
       max-elements 64;
       description
   "PCR register content";
    }
 }

 grouping BOOT-EVENT-LOG {
   description
     "Defines an event log corresponding to the event that extended the PCR";
   leaf event-number {
       type uint32;
       description
   "Unique event number of this event";
   }
   leaf event-type {
       type uint32;
       description
   "log event type";
   }
   leaf pcr-index {
      type uint16;
      description
  "Defines the PCR index that this event extended";
   }
   list digest-list {
     key digest-hash-algorithm;
     description "Hash of event data";
     leaf digest-hash-algorithm {
       type enumeration {
   enum SHA1 {
     value 0;
   }
   enum SHA256 {
     value 1;
   }
   enum SHA384 {
     value 2;
   }
   enum SHA512 {
     value 3;
   }
       }
       description
   "Algorithm for this digest";
     }
     leaf digest {
   type binary;
   description
     "The hash of the event data";
     }
   }
    leaf event-size {
       type uint32;
       description
   "Size of the event data";
    }
    leaf event-data {
  type binary;
  description
    "the event data size determined by event-size";
    }
 }

 grouping IMA-EVENT {
   description
     "Defines an hash log extend event for IMA measurements";
   leaf event-number {
       type uint64;
       description
  "Unique number for this event for sequencing";
   }
   leaf ima-template {
       type string;
       description
            "Name of the template used for event
             for e.g. ima, ima-ng";
   }
   leaf filename-hint {
       type string;
       description
   "File that was measured";
   }
   leaf filedata-hash {
       type binary;
       description
    "Hash of filedata";
   }
   leaf template-hash-algorithm {
       type string;
       description
       "Algorithm used for template-hash";
   }
   leaf template-hash {
  type binary;
  description
   " hash(filedata-hash, filename-hint)";
   }
   leaf pcr-index {
      type uint16;
      description
  "Defines the PCR index that this event extended";
   }
   leaf signature {
       type binary;
       description
       "The file signature";
   }
 }

rpc get-certificate {
  description
  "Query certificate.
  Returns certificate chain
  associated with the queried certificate.
  An optional nonce can be provided, that is then used to
  return a signature over the certificate contents returned.";

  input {
    leaf nonce {
      type binary {
          length "0..64";
      }
      description
      "Nonce to be included in the attested output
      to prevent replay attacks";
    }
    leaf certificate-identifier {
      type string;
      description
      "Certificate identifier";
    }
    leaf location {
      type string;
      description
      "In a distributed system get the data from a specific node
      identified by the location. If this field is not specified
      data associated with each node forming the system will be
      returned.";
    }
  }
    output {
      container get-certificate-response {
      list system-certificates {
        key node-location;
        description
        "Certificate data of a node in a distributed system
        identified by the location";
        leaf node-location {
          type string;
          description
          "Location of the node in the distributed system";
        }
        leaf nonce {
          type binary {
              length "0..64";
          }
          description
          "Nonce used for this output";
        }
        container certificates {
          description
          "Certificates chain associated with the certificate
          being queried";
          list certificate {
            key name;
            description
            "A X.509 certificate";
            leaf name {
              type string;
              description
              "A node-unique certificate identifier";
            }
            leaf value {
              type binary;
              description
              "Certificate content in DER format.";
            }
          }
        }
        leaf signature_version {
          type uint32;
          description
          "Signature version designates
          the format of the signed data.";
        }
        leaf signature {
          type binary;
          description
          "The optional RSA or ECDSA signature across
          the certificates,the signature version and
          the input nonce.Signed data format is:
          Nonce || UINT32 signature version ||
          [Certificate included in the response in DER format].";
        }
      }

      }
      }
      }


      rpc attest-platform-config-registers {
        description
        "Attest Platform Configuration Register(PCRs)";
        input {
          leaf-list pcr-index {
             type uint16;
             min-elements 1;
             description
         "PCR register indices to be included in the attested output";
          }
          leaf nonce {
            type binary {
                length "0..64";
            }
            description
            "Nonce to be included in the attested output
            to prevent replay attacks";
          }
          leaf attestation-certificate-identifier {
            type string;
            description
            "Identifier of the certificate to be used for attestation";
          }
          leaf location {
            type string;
            description
            "In a distributed system get the data from a specific node
            identified by the location. If this field is not specified
            data associated with each node forming the system will be
            returned.";
          }
        }
        output {
          container platform-config-registers {
            description "Attested Platform Config Register values";
            leaf nonce {
              type binary {
                  length "0..64";
              }
              description
              "Nonce used for this output";
            }
            list node-data {
              key node-location;
              description
              "Certificate data of a node in a distributed system
              identified by the location";
              leaf node-location {
                type string;
                description
                "Location of the node in the distributed system";
              }
              leaf up-time {
                type uint32;
                description
                "Uptime in seconds of this node reporting its data";
              }
              list PCR {
                key index;
                description
                "List of requested PCR contents";
                uses PCR-DUMP;
              }
              leaf pcr-quote {
                type binary;
                description
                "TPM PCR Quote";
              }
              leaf pcr-quote-signature {
                  type binary;
                  description
                  "PCR Quote signature using TPM-held
                  ECC or RSA restricted key";
                }
            }
          }
        }
      }

          rpc get-platform-boot-integrity-event-logs {
            description
            "Get platform's boot integrity";
            input {
              leaf location {
                type string;
                description
                "In a distributed system get the data from a specific node
                identified by the location. If this field is not specified
                data associated with each node forming the system will be
                returned.";
              }
              leaf start-event-number {
                type uint64;
                description
                "To filter event logs to be retrieved.
                - If set only events with sequence number
                greater than that specified in this argument
                will be returned.";
              }
              leaf end-event-number {
                type uint64;
                must "current()  >= ../start-event-number" {
                  description
                     "end-event-number must be used with and be greater than or
                      equal to <start-event-number>";
                 }
                description
                "To control event logs to be retrieved.
                - If set only events with sequence number
                in the range of start-event-number to end-event-number
                will be returned.";
              }
            }
            output {
              container system-boot-integrity {
                description "Boot integrity event logs";
                list node-data {
                  key node-location;
                  description
                  "Boot integrity event logs of a node in a distributed system
                  identified by the location";
                  leaf node-location {
                    type string;
                    description
                    "Location of the node in the distributed system";
                  }
                  leaf up-time {
                    type uint32;
                    description
                    "Uptime in seconds of this node reporting its data";
                  }
                  list event_log {
                    key event-number;
                    description
                    "Ordered list of TCG described event log
                    that extended the PCRs in the order they
                    were logged";
                    uses BOOT-EVENT-LOG;
                  }
                }
              }
            }
          }

          rpc get-platform-ima-event-logs {
            description
            "Get platform IMA event logs";
            input {
              leaf location {
                type string;
                description
                "In a distributed system get the data from a specific node
                identified by the location. If this field is not specified
                data associated with each node forming the system will be
                returned.";
              }
              leaf start-event-number {
                type uint64;
                description
                "To filter event logs to be retrieved.
                - If set only events with sequence number
                greater than that specified in this argument
                will be returned.";
              }
              leaf end-event-number {
                type uint64;
                must "current()  >= ../start-event-number" {
                  description
                     "end-event-number must be used with and be greater than or
                      equal to <start-event-number>";
                 }
                description
                "To control event logs to be retrieved.
                - If set only events with sequence number
                in the range of start-event-number to end-event-number
                will be returned.";
              }
            }
            output {
              container system-ima {
                description "Runtime integrity measurement event logs";
                list node-data {
                  key node-location;
                  description
                  "IMA event logs of a node in a distributed system
                  identified by the location";
                  leaf node-location {
                    type string;
                    description
                    "Location of the node in the distributed system";
                  }
                  leaf up-time {
                    type uint32;
                    description
                    "Uptime in seconds of this node reporting its data";
                  }
                  list ima-event-log {
                    key event-number;
                    description
                    "Ordered list of ima event logs by event-number";
                    uses IMA-EVENT;
                  }
                }
              }
            }
            }
              notification hardware-intergrity-failure {
                description
                "Notifies failure of hardware integrity check";
                leaf system-identifier {
                  type string;
                  description
                  "System identifier";
                }
              }

              notification boot-integrity-failure {
                description
                "Notifies failure of boot integrity checks at
                any stage of boot";
                leaf system-identifier {
                  type string;
                  description
                  "System identifier";
                }
              }
              notification runtime-integrity-failure {
                description
                "Notifies failure of runtime integrity checks";
                leaf system-identifier {
                  type string;
                  description
                  "System identifier";
                }
                leaf filename-hint {
                  type string;
                  description
                  "File that was appraised and failed integrity checks";
                }
                leaf filedata-hash {
                  type binary;
                  description
                  "Hash of filedata that failed IMA appraisal";
                }
              }

}
