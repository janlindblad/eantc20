submodule Cisco-IOS-XR-fretta-bcm-dpa-hw-resources-oper-sub1 {

  belongs-to Cisco-IOS-XR-fretta-bcm-dpa-hw-resources-oper {
    prefix Cisco-IOS-XR-fretta-bcm-dpa-hw-resources-oper-sub1;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR fretta-bcm-dpa-hw-resources package operational data.

     Copyright (c) 2013-2018 by Cisco Systems, Inc.
     All rights reserved.";

  revision "2015-11-09" {
    description
      "IOS XR 6.0 revision.";
  }


  grouping OFA-SYSDB-LT-HW-RESOURCE {
    description "OFA SYSDB LT HW RESOURCE";
    leaf lt-id {
      type uint32;
      description "lt id";
    }
    leaf name {
      type string;
      description "name";
    }
    leaf hw-entries {
      type uint32;
      description "hw entries";
    }
    leaf sw-entries {
      type uint32;
      description "sw entries";
    }
  }

  grouping OFA-SYSDB-NPU-HW-RESOURCE {
    description "OFA SYSDB NPU HW RESOURCE";
    leaf max-allowed {
      type uint32;
      description "max allowed";
    }
    leaf npu-id {
      type uint32;
      description "npu id";
    }
    leaf max-entries {
      type uint32;
      description "max entries";
    }
    leaf red-oor-threshold {
      type uint32;
      description "red oor threshold";
    }
    leaf red-oor-threshold-percent {
      type uint32;
      description "red oor threshold percent";
    }
    leaf yellow-oor-threshold {
      type uint32;
      description "yellow oor threshold";
    }
    leaf yellow-oor-threshold-percent {
      type uint32;
      description "yellow oor threshold percent";
    }
    leaf inuse-objects {
      type uint32;
      description "inuse objects";
    }
    leaf num-lt {
      type uint32;
      description "num lt";
    }
    leaf oor-change-count {
      type uint32;
      description "oor change count";
    }
    leaf oor-state-change-time1 {
      type string;
      description "oor state change time1";
    }
    leaf oor-state-change-time2 {
      type string;
      description "oor state change time2";
    }
    leaf oor-state {
      type string;
      description "oor state";
    }

    list lt-hwr {
      description "lt hwr";
      uses OFA-SYSDB-LT-HW-RESOURCE;
    }
  }

  grouping OFA-SYSDB-HW-RESOURCE {
    description "OFA SYSDB HW RESOURCE";
    leaf resource-id {
      type uint32;
      description "resource id";
    }
    leaf name {
      type string;
      description "name";
    }
    leaf num-npus {
      type uint32;
      description "num npus";
    }
    leaf cmd-invalid {
      type boolean;
      description "cmd invalid";
    }

    list npu-hwr {
      description "npu hwr";
      uses OFA-SYSDB-NPU-HW-RESOURCE;
    }
  }

  grouping OFA-SYSDB-STATS-APP-USAGE {
    description "OFA SYSDB STATS APP USAGE";
    leaf app-type {
      type string;
      description "app type";
    }
    leaf num-cntrs-for-app {
      type uint32;
      description "num cntrs for app";
    }
    leaf num-cntrs-used {
      type uint32;
      description "num cntrs used";
    }
  }

  grouping OFA-SYSDB-STATS-CNTR-ENG {
    description "OFA SYSDB STATS CNTR ENG";
    leaf state {
      type string;
      description "state";
    }
    leaf core-id {
      type uint32;
      description "core id";
    }

    list apps-info {
      description "apps info";
      uses OFA-SYSDB-STATS-APP-USAGE;
    }
  }

  grouping OFA-SYSDB-STATS-HW-RESOURCE {
    description "OFA SYSDB STATS HW RESOURCE";
    leaf sys-cp-cnfg-prof {
      type uint32;
      description "sys cp cnfg prof";
    }
    leaf next-avail-cp-id {
      type uint32;
      description "next avail cp id";
    }
    leaf num-cntr-engines {
      type uint32;
      description "num cntr engines";
    }

    list cntr-engine {
      description "cntr engine";
      uses OFA-SYSDB-STATS-CNTR-ENG;
    }
  }
}
