submodule Cisco-IOS-XR-ipv4-autorp-oper-sub1 {

  belongs-to Cisco-IOS-XR-ipv4-autorp-oper {
    prefix Cisco-IOS-XR-ipv4-autorp-oper-sub1;
  }

  /*** LINKAGE (IMPORTS / INCLUDES) ***/

  import ietf-inet-types { prefix "inet"; }

  include Cisco-IOS-XR-ipv4-autorp-oper-sub2 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ipv4-autorp package operational data.

     Copyright (c) 2013-2018 by Cisco Systems, Inc.
     All rights reserved.";

  revision "2015-11-09" {
    description
      "IOS XR 6.0 revision.";
  }


  grouping AUTORP-MAP-SUMMARY-BAG {
    description "Auto-RP Mapping Agent summary";
    leaf is-maximum-disabled {
      type boolean;
      description "Is maximum enforcement disabled ?";
    }
    leaf cache-limit {
      type uint32;
      description "Maximum group to RP mapping entries allowed";
    }
    leaf cache-count {
      type uint32;
      description
        "Number of group to RP mapping entries in the
        cache";
    }
  }

  grouping AUTORP-MAP-RANGE-BAG {
    description "MRIB multicast-routing entry-interface";
    leaf prefix {
      type inet:ipv4-address;
      description "Prefix of the range";
    }
    leaf prefix-length {
      type uint8;
      description "Prefix length of the range";
    }
    leaf protocol-mode {
      type Autorp-protocol-mode;
      description "Protocol Mode";
    }
    leaf is-advertised {
      type boolean;
      description "Is this entry advertised ?";
    }
    leaf create-type {
      type uint8;
      description "Source of the entry";
    }
    leaf check-point-object-id {
      type uint32;
      description "Checkpoint object id";
    }
    leaf uptime {
      type uint64;
      units "second";
      description "Uptime in seconds";
    }
  }

  grouping AUTORP-MAP-RP-BAG {
    description "Auto-RP Mapping Agent entry";
    leaf rp-address-xr {
      type inet:ipv4-address;
      description "Candidate-RP address";
    }
    leaf expiry-time {
      type uint64;
      units "second";
      description "Time for expiration in seconds";
    }
    leaf pim-version {
      type uint8;
      description "PIM version of the CRP";
    }

    list range {
      description "Array of ranges";
      uses AUTORP-MAP-RANGE-BAG;
    }
  }

  grouping AUTORP-MAP-TRAFFIC-BAG {
    description "Auto-RP Mapping Agent Traffic Counters";
    leaf active-sent-packets {
      type uint32;
      description "Number of packets sent in active role";
    }
    leaf standby-sent-packets {
      type uint32;
      description
        "Number of packets dropped in send path in
        standby role";
    }
    leaf active-received-packets {
      type uint32;
      description "Number of packets received in active role";
    }
    leaf standby-received-packets {
      type uint32;
      description
        "Number of packets dropped in receive path in
        standby role";
    }
  }
}
