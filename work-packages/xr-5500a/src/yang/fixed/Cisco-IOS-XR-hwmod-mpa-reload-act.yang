module Cisco-IOS-XR-hwmod-mpa-reload-act {

    namespace "http://cisco.com/ns/yang/Cisco-IOS-XR-hwmod-mpa-reload-act";
    
    prefix "Cisco-IOS-XR-hwmod-mpa-reload-act";
    
    organization "Cisco Systems, Inc.";
    
    contact
    "Cisco Systems, Inc.
     Customer Service

     Postal: 170 West Tasman Drive
     San Jose, CA 95134

     Tel: +1 800 553-NETS

     E-mail: cs-yang@cisco.com";
    
    description 
    "This module contains a collection of YANG definitions
     for Cisco IOS-XR MPA reload action package configuration.

     Copyright (c) 2016-2017 by Cisco Systems, Inc.
     All rights reserved.";
    
    revision "2016-06-30" {
        description
            "IOS XR 6.2.1 revision.";
    } 
    
    rpc hw-module-subslot {
        description "Execute subslot h/w module operations";
        input {
            leaf subslot {
                description "Fully qualified location specification";
                type string;
            }
            leaf reload {
                description "Cycle subslot h/w reset";
                type empty;
            }
        }
    }
}
