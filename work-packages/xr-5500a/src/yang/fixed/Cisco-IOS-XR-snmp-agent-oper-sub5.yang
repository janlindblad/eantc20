submodule Cisco-IOS-XR-snmp-agent-oper-sub5 {

  belongs-to Cisco-IOS-XR-snmp-agent-oper {
    prefix Cisco-IOS-XR-snmp-agent-oper-sub5;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR snmp-agent package operational data.

     Copyright (c) 2013-2018 by Cisco Systems, Inc.
     All rights reserved.";

  revision "2018-07-20" {
    description
      "Fixed English plural name transformation error.";
  }

  revision "2017-09-07" {
    description
      "Fixed type translation error.";
  }

  revision "2017-05-01" {
    description
      "Fixing backward compatibility error in module.";
  }

  revision "2016-06-01" {
    description
      "IOS XR 6.0.1 revision.";
  }

  revision "2015-01-07" {
    description
      "IOS XR 5.3.1 revision.";
  }


  grouping SNMP-OVERLOAD-STATS {
    description "SNMP Overload statastics";
    leaf number-of-nmsq-pkts-dropped {
      type uint32;
      description
        "Number of packets which are currently enqueued
        within the NMS queues";
    }
    leaf number-of-pkts-dropped {
      type uint32;
      description "Number of packets dropped";
    }
    leaf overload-start-time {
      type string;
      description "Time of overload contol begin";
    }
    leaf overload-end-time {
      type string;
      description "Time of overload contol End";
    }
  }
}
