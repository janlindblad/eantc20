submodule Cisco-IOS-XR-man-ipsla-oper-sub3 {

  belongs-to Cisco-IOS-XR-man-ipsla-oper {
    prefix Cisco-IOS-XR-man-ipsla-oper-sub3;
  }

  /*** LINKAGE (IMPORTS / INCLUDES) ***/

  import ietf-inet-types { prefix "inet"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR man-ipsla package operational data.

     Copyright (c) 2013-2018 by Cisco Systems, Inc.
     All rights reserved.";

  revision "2015-11-09" {
    description
      "IOS XR 6.0 revision.";
  }


  grouping IPSLA-RESP-SENDER-BAG {
    description "IPSLA sender id";
    leaf ip-address {
      type inet:ipv4-address;
      description "IP address of Sender";
    }
    leaf port {
      type uint16;
      description "Port on which Sender is sending";
    }
    leaf last-recv-time {
      type uint64;
      description "Last received time";
    }
    leaf ipv6-address {
      type inet:ipv6-address;
      description "IPv6 address of Sender";
    }
  }

  grouping IPSLA-RESP-PORT-INFO-BAG {
    description "IPSLA Responder active ports information";
    leaf port-xr {
      type uint16;
      description "Port on which Responder is listening";
    }
    leaf local-address {
      type inet:ipv4-address;
      description "IP address of Responder";
    }
    leaf num-probes {
      type uint32;
      description "Number of probes received from remote end";
    }
    leaf ctrl-probes {
      type uint32;
      description
        "Number of control probes received from remote
        end";
    }
    leaf permanent {
      type boolean;
      description "Port type if this is permanent or dynamic port";
    }
    leaf discard-on {
      type boolean;
      description "Current discard socket option flag for the port";
    }
    leaf pd-time-stamp-failed {
      type boolean;
      description "PD Timestamp failure";
    }
    leaf is-ipsla {
      type boolean;
      description "IPSLA or TWAMP protocol";
    }
    leaf drop-counter {
      type uint32;
      description "Drop counter for the Responder port";
    }
    leaf socket {
      type int32;
      description "Socket";
    }
    leaf local-ipv6-address {
      type inet:ipv6-address;
      description "IPv6 address of Responder";
    }
    leaf family {
      type int32;
      description "Represent if v4 or v6";
    }

    list sender {
      description "List of senders";
      uses IPSLA-RESP-SENDER-BAG;
    }
  }
}
