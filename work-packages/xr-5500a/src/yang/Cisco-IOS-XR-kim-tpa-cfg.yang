module Cisco-IOS-XR-kim-tpa-cfg {

  /*** NAMESPACE / PREFIX DEFINITION ***/

  namespace "http://cisco.com/ns/yang/Cisco-IOS-XR-kim-tpa-cfg";


  prefix "kim-tpa-cfg";

  /*** LINKAGE (IMPORTS / INCLUDES) ***/

  import Cisco-IOS-XR-types { prefix "xr"; }

  import ietf-inet-types { prefix "inet"; }

  /*** META INFORMATION ***/
  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR kim-tpa package configuration.

     This module contains definitions
     for the following management objects:
       tpa: tpa configuration commands

     Copyright (c) 2013-2018 by Cisco Systems, Inc.
     All rights reserved.";

  revision "2018-07-27" {
    description
      "Added support for protection configuration";
  }

  revision "2017-09-07" {
    description
      "Fixed type translation error.";
  }

  revision "2015-11-09" {
    description
      "IOS XR 6.0 revision.";
  }

  typedef Ip-protocol {
    type enumeration {
      enum tcp {
        value 6;
        description "Transmission Control Protocol, RFC 793";
      }
      enum udp {
        value 17;
        description "User Datagram Protocol, RFC 768";
      }
    }
    description "Ip protocol";
  }

  grouping UPDATE-SOURCE {
    description "Common node of ipv4, ipv6";

    container update-source {
      description "Interface used for Source Address";
      leaf interface-name {
        type xr:Interface-name;
        must "not(../active-management)";
        description "Interface name for source address";
      }
      leaf active-management {
        type empty;
        must "not(../interface-name)";
        description "Use the management port on the Active RP";
      }
    }
  }

  grouping PROTECTION {
    description "Common node of ipv4, ipv6";

    container allow-entries {

      list allow-entry {
        key "protocol local-port";
        description "Allow traffic matching a filter";
        leaf protocol {
          type Ip-protocol;
          description "L4 protocol";
        }
        leaf local-port {
          type xr:Cisco-ios-xr-port-number;
          description "Local port";
        }
      }

      list allow-entry-local-address {
        key "local-address protocol local-port";
        description "Allow traffic matching a filter";
        leaf local-address {
          type inet:ip-prefix;
          description "local prefix/length";
        }
        leaf protocol {
          type Ip-protocol;
          description "L4 protocol";
        }
        leaf local-port {
          type xr:Cisco-ios-xr-port-number;
          description "Local port";
        }
      }

      list allow-entry-remote-address {
        key "remote-address protocol local-port";
        description "Allow traffic matching a filter";
        leaf remote-address {
          type inet:ip-prefix;
          description "remote prefix/length";
        }
        leaf protocol {
          type Ip-protocol;
          description "L4 protocol";
        }
        leaf local-port {
          type xr:Cisco-ios-xr-port-number;
          description "Local port";
        }
      }

      list allow-entry-local-address-remote-address {
        key "local-address remote-address protocol local-port";
        description "Allow traffic matching a filter";
        leaf local-address {
          type inet:ip-prefix;
          description "local prefix/length";
        }
        leaf remote-address {
          type inet:ip-prefix;
          description "remote prefix/length";
        }
        leaf protocol {
          type Ip-protocol;
          description "L4 protocol";
        }
        leaf local-port {
          type xr:Cisco-ios-xr-port-number;
          description "Local port";
        }
      }

      list allow-entry-interface-name {
        key "interface-name protocol local-port";
        description "Allow traffic matching a filter";
        leaf interface-name {
          type xr:Interface-name;
          description "Interface name";
        }
        leaf protocol {
          type Ip-protocol;
          description "L4 protocol";
        }
        leaf local-port {
          type xr:Cisco-ios-xr-port-number;
          description "Local port";
        }
      }

      list allow-entry-local-address-interface-name {
        key "local-address interface-name protocol local-port";
        description "Allow traffic matching a filter";
        leaf local-address {
          type inet:ip-prefix;
          description "local prefix/length";
        }
        leaf interface-name {
          type xr:Interface-name;
          description "Interface name";
        }
        leaf protocol {
          type Ip-protocol;
          description "L4 protocol";
        }
        leaf local-port {
          type xr:Cisco-ios-xr-port-number;
          description "Local port";
        }
      }

      list allow-entry-remote-address-interface-name {
        key "remote-address interface-name protocol local-port";
        description "Allow traffic matching a filter";
        leaf remote-address {
          type inet:ip-prefix;
          description "remote prefix/length";
        }
        leaf interface-name {
          type xr:Interface-name;
          description "Interface name";
        }
        leaf protocol {
          type Ip-protocol;
          description "L4 protocol";
        }
        leaf local-port {
          type xr:Cisco-ios-xr-port-number;
          description "Local port";
        }
      }

      list allow-entry-local-address-remote-address-interface-name {
        key "local-address remote-address interface-name protocol"+
          " local-port";
        description "Allow traffic matching a filter";
        leaf local-address {
          type inet:ip-prefix;
          description "local prefix/length";
        }
        leaf remote-address {
          type inet:ip-prefix;
          description "remote prefix/length";
        }
        leaf interface-name {
          type xr:Interface-name;
          description "Interface name";
        }
        leaf protocol {
          type Ip-protocol;
          description "L4 protocol";
        }
        leaf local-port {
          type xr:Cisco-ios-xr-port-number;
          description "Local port";
        }
      }
      description "Traffic protection configuration";
    }
  }

  grouping DEFAULT-ROUTE {
    description "Common node of ipv4, ipv6";
    leaf default-route {
      type string;
      description "Default interface used for routing";
    }
  }

  grouping EGRESS-UPDATE-SOURCE {
    description "Common node of ipv4, ipv6";

    container interface-names {
      description
        "Interface used for source address for egress
        interface";

      list interface-name {
        key "interface-name";
        description "Egress interface name";
        leaf egress-interface-source {
          type xr:Interface-name;
          description "Interface name for source address";
        }
        leaf interface-name {
          type xr:Cisco-ios-xr-string;
          description "Interface";
        }
      }
    }
  }

  container tpa {
    description "tpa configuration commands";

    container vrf-names {
      description "VRF container";

      list vrf-name {
        key "vrf-name";
        description "VRF name";

        container east-west-names {
          description "EastWest container";

          list east-west-name {
            key "east-west-name";
            description "East West interface";
            leaf east-west-name {
              type xr:Cisco-ios-xr-string;
              description "Interface";
            }
            leaf vrf {
              type string;
              description "VRF name";
            }
            leaf interface {
              type string;
              description "Interface";
            }
          }
        }

        container address-family {
          description "Address family";

          container ipv6 {
            description "IPv6 configuration";
            uses DEFAULT-ROUTE;
            uses EGRESS-UPDATE-SOURCE;
            uses PROTECTION;
            uses UPDATE-SOURCE;
          }

          container ipv4 {
            description "IPv4 configuration";
            uses DEFAULT-ROUTE;
            uses EGRESS-UPDATE-SOURCE;
            uses PROTECTION;
            uses UPDATE-SOURCE;
          }
        }
        leaf disable {
          type empty;
          description "Disable routes and interfaces";
        }
        leaf vrf-name {
          type xr:Cisco-ios-xr-string {
            length "1..32";
          }
          description "VRF name";
        }
      }
    }

    container logging {
      description "Third party app logging";

      container kim {
        description "KIM logging";
        leaf rotation-max {
          type uint32;
          description "How many log rotation files to keep";
        }
        leaf file-size-max-kb {
          type uint32;
          units "kilobyte";
          description "Size in Kilobytes of the log file";
        }
      }
    }

    container statistics {
      description "Statistics";
      leaf max-intf-events {
        type uint32;
        description "How many interface events to record";
      }
      leaf max-lpts-events {
        type uint32;
        description "How many LPTS events to record";
      }
      leaf statistics-update-frequency {
        type uint32;
        units "second";
        description "Statistics update frequency into Linux";
      }
    }
  }
}
