module Cisco-IOS-XR-controller-odu-oper {

  /*** NAMESPACE / PREFIX DEFINITION ***/

  namespace "http://cisco.com/ns/yang"+
    "/Cisco-IOS-XR-controller-odu-oper";


  prefix "controller-odu-oper";

  /*** LINKAGE (IMPORTS / INCLUDES) ***/

  import Cisco-IOS-XR-types { prefix "xr"; }

  include Cisco-IOS-XR-controller-odu-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR controller-odu package operational data.

     This module contains definitions
     for the following management objects:
       odu: ODU operational data

     Copyright (c) 2013-2018 by Cisco Systems, Inc.
     All rights reserved.";

  revision "2015-11-09" {
    description
      "IOS XR 6.0 revision.";
  }


  container odu {
    config false;
    description "ODU operational data";

    container controllers {
      description "All ODU Port operational data";

      list controller {
        key "controller-name";
        description "ODU Port operational data";

        container prbs {
          description "ODU port operational data";
          uses ODU-PRBS-INFO;
        }

        container info {
          description "ODU port operational data";
          uses ODU-PER-PORT-INFO;
        }
        leaf controller-name {
          type xr:Interface-name;
          description "Port name";
        }
      }
    }
  }
}
