submodule Cisco-IOS-XR-fib-common-oper-sub2 {

  belongs-to Cisco-IOS-XR-fib-common-oper {
    prefix Cisco-IOS-XR-fib-common-oper;
  }

  /*** LINKAGE (IMPORTS / INCLUDES) ***/

  import ietf-yang-types { prefix "yang"; }

  import Cisco-IOS-XR-types { prefix "xr"; }

  include Cisco-IOS-XR-fib-common-oper-sub1 {
    revision-date 2017-09-07;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR fib-common package operational data.

     Copyright (c) 2013-2018 by Cisco Systems, Inc.
     All rights reserved.";

  revision "2017-09-07" {
    description
      "Fixed type translation error.";
  }

  revision "2017-05-01" {
    description
      "Fixing backward compatibility error in module.";
  }

  revision "2017-01-20" {
    description
      "IOS XR 6.2.1 revision";
  }

  revision "2015-11-09" {
    description
      "IOS XR 6.0 revision.";
  }

  typedef Next-hop {
    type enumeration {
      enum tx {
        value 0;
        description "TX";
      }
      enum rx {
        value 1;
        description "RX";
      }
      enum special {
        value 2;
        description "Special";
      }
    }
    description "MPLS Forwarding Next Hop Type";
  }
  typedef Proto {
    type enumeration {
      enum ipv4 {
        value 0;
        description "IPv4";
      }
      enum ipv6 {
        value 1;
        description "IPv6";
      }
      enum mpls {
        value 2;
        description "MPLS";
      }
    }
    description "MPLS Forwarding Protocol Type";
  }

  grouping MPLS-FRR-DB-ENTRY {
    description "MPLS FRR DB ENTRY";

    container frr-db {
      description "FRR DB";
      uses FIB-MPLS-FRR-DB-ENTRY;
    }
    leaf outgoing-lable-string {
      type string;
      description "Output label in string format";
    }
    leaf frr-lable-string {
      type string;
      description "FRR label in string format";
    }
  }

  grouping MPLS-SH-TEHEAD {
    description "Information about TE tunnel head";

    container tunnel-info {
      description "Tunnel head information";
      uses FIB-MPLS-SH-TUN-INFO;
    }

    container fwdg {
      description "Tunnel forwarding information";
      uses MPLS-SH-LEAF;
    }
  }

  grouping MPLS-LABEL-SECURITY-SUMMARY {
    description "MPLS LABEL SECURITY SUMMARY";
    leaf rpf-drops {
      type uint64;
      description "RPF drops";
    }
    leaf multi-label-drops {
      type uint64;
      description "Multi-label drops";
    }
  }

  grouping MPLS-LABEL-SECURITY-INTF {
    description "MPLS LABEL SECURITY INTF";
    leaf rpf-enabled {
      type boolean;
      description "RPF is enabled on interface";
    }
    leaf rpf-supported {
      type boolean;
      description "RPF stats supported per interface";
    }
    leaf mld-enabled {
      type boolean;
      description "Multi-label drop is enabled on interface";
    }
    leaf mld-supported {
      type boolean;
      description
        "Multi-label drop counters are supported per
        interface";
    }
    leaf rpf-drops {
      type uint64;
      description "RPF drops";
    }
    leaf multi-label-drops {
      type uint64;
      description "Multi-label drops";
    }
    leaf rpfifh {
      type xr:Interface-name;
      description "RPF interface handle";
    }
  }

  grouping MPLS-MCAST-INFO {
    description "Information for mpls multicast entries";
    leaf multicast-mol-base-flags {
      type uint32;
      description "MOL base flags";
    }
    leaf multicast-mol-flags {
      type uint16;
      description "MOL flags";
    }
    leaf multicast-mol-referance-count {
      type uint16;
      description "MOL refcount";
    }
    leaf multicast-tunnel-interface-handler {
      type xr:Interface-name;
      description "multicast mpls tunnel";
    }
    leaf multicast-tunnel-id {
      type uint32;
      description
        "multicast mpls P2MP-TE tunnel id or MLDP Tunnel
        LSMID on all nodes";
    }
    leaf multicast-tunnel-next-hop-information {
      type uint32;
      description "multicast nhinfo for p2mp TE Head";
    }
    leaf multicast-tunnel-lspvif {
      type uint32;
      description "multicast LSPVIF for MLDP Tunnels";
    }
    leaf multicast-mpls-output-paths {
      type uint16;
      description "num multicast mpls output paths ";
    }
    leaf multicast-mpls-protocol-output-paths {
      type uint16;
      description "num multicast mpls prot output paths ";
    }
    leaf multicast-mpls-local-output-paths {
      type uint16;
      description "num multicast mpls local output paths";
    }
    leaf multicast-rpf-id {
      type uint32;
      description "The multicast RPF-ID ";
    }
    leaf multicast-encap-id {
      type uint32;
      description "The multicast ENCAP-ID ";
    }
    leaf multicast-platform-data-length {
      type uint8;
      description "The multicast platform data len";
    }
    leaf multicast-platform-data {
      type yang:hex-string;
      description "The multicast platform data";
    }
  }

  grouping MPLS-LDI-INFO {
    description
      "Detailed load sharing information for mpls table
      entries";
    leaf ldi-hardware-information {
      type yang:hex-string;
      description "Hardware info";
    }
  }

  grouping MPLS-ADJ-EXACT-ROUTE-HASH-INFO {
    description "MPLS Adj Exact-Route Hash info";
    leaf hash-index-is-valid {
      type boolean;
      description "Is Hash Index valid?";
    }
    leaf hash-index {
      type uint8;
      description "Hash Index value";
    }
  }

  grouping MPLS-FWD-INFO {
    description "MPLS FWD INFO";
    leaf l3-mtu {
      type uint32;
      description "L3 MTU";
    }
    leaf total-encapsulation-size {
      type uint32;
      description "Total encapsulation size: L2 + MPLS";
    }
    leaf mac-size {
      type uint32;
      description "Length of L2 encapsulation";
    }
    leaf transmit-number-of-packets-switched {
      type uint64;
      description "Number of packets switched";
    }
    leaf transmit-number-of-bytes-switched {
      type uint64;
      units "byte";
      description "Number of Bytes switched";
    }
    leaf status {
      type int32;
      description "Status";
    }
    leaf next-hop-interface {
      type xr:Interface-name;
      description "Next hop interface";
    }
    leaf next-hop-protocol {
      type Proto;
      description "The address family (V4/V6) ";
    }
    leaf next-hop-string {
      type string;
      description "Next hop address in string format";
    }
    list label-stack {
      description "Label stack";
        leaf entry {
                  type uint32;

                  description "Label stack";
        }
    }
  }

  grouping MPLS-ADJ-INFO {
    description "MPLS ADJ INFO";

    container label-information-detail {
      description "Detail label info";
      uses MPLS-FWD-INFO;
    }

    container exact-route-hash-info {
      description "Path's Hash info in case of exact-route command";
      uses MPLS-ADJ-EXACT-ROUTE-HASH-INFO;
    }
    leaf label-information-type {
      type uint32;
      description "Label-Info type";
    }
    leaf local-label {
      type uint32;
      description "Local label";
    }
    leaf outgoing-label {
      type uint32;
      description "Outgoing label";
    }
    leaf mpls-adjacency-flags {
      type uint32;
      description "MPLS Adjacency flags";
    }
    leaf tunnel-id-present {
      type boolean;
      description "Tunnel id present?";
    }
    leaf label-information-path-index {
      type uint32;
      description "LabelInformationPathIndex";
    }
    leaf label-information-next-hop-type {
      type Next-hop;
      description "NHinfo Type";
    }
    leaf label-information-next-hop-protocol {
      type Proto;
      description "The address family (v4/v6) ";
    }
    leaf tx-bytes {
      type uint64;
      units "byte";
      description "Bytes transmitted per LSP";
    }
    leaf tx-packets {
      type uint64;
      description "Packets transmitted per LSP";
    }
    leaf outgoing-interface {
      type string;
      description "Output Interface in string format";
    }
    leaf outgoing-physical-interface {
      type string;
      description "Output Physical Interface in string format";
    }
    leaf outgoing-parent-interface {
      type string;
      description "Output Parent Interface in string format";
    }
    leaf tunnel-interface {
      type string;
      description "Tunnel Interface in string format";
    }
    leaf outgoing-label-string {
      type string;
      description "Output Label in string format";
    }
    leaf prefix-or-id {
      type string;
      description "Prefix Or ID";
    }
    leaf label-information-next-hop-string {
      type string;
      description "Next hop address in string format";
    }
    leaf label-information-route-version {
      type uint64;
      description "The version of the route";
    }
    leaf label-information-time-in-milli-seconds {
      type uint64;
      description "The time of last update in msec";
    }
  }

  grouping MPLS-SH-LEAF {
    description "Information about label leaf";

    container ldi-information {
      description "LDI-info in FIB leaf";
      uses MPLS-LDI-INFO;
    }

    container multicast-information {
      description "The multicast info";
      uses MPLS-MCAST-INFO;
    }
    leaf leaf-local-label {
      type uint32;
      description "Local label";
    }
    leaf eos-bit {
      type uint32;
      description "EOS bit";
    }
    leaf hardware-information {
      type yang:hex-string;
      description "Hardware info";
    }
    leaf leaf-referance-count {
      type uint32;
      description "Number of references to the leaf";
    }
    leaf leaf-flags {
      type uint32;
      description "The leaf flags";
    }
    leaf path-list-referance-count {
      type uint32;
      description "Number of references to the pathlist";
    }
    leaf path-list-flags {
      type uint32;
      description "The pathlist flags";
    }
    leaf ldi-referance-count {
      type uint32;
      description "Number of references to the LDI";
    }
    leaf ldi-flags {
      type uint32;
      description "The LDI flags";
    }
    leaf ldi-type {
      type uint32;
      description "The LDI type";
    }
    leaf ldi-pointer {
      type uint32;
      description "The pointer to the LDI";
    }
    leaf lw-ldi-type {
      type uint32;
      description "The LW-LDI type";
    }
    leaf lw-ldi-pointer {
      type uint32;
      description "The pointer to the LW-LDI";
    }
    leaf lw-ldi-refernace-count {
      type uint32;
      description "The LW-LDI refcounter";
    }
    leaf lw-shared-ldi-pointer {
      type uint32;
      description "The pointer to the shared LDI in LW-LDI";
    }
    leaf lspa-flags {
      type uint32;
      description "The LSPA flags";
    }
    leaf afi-table-id {
      type uint32;
      description "The AFI table ID";
    }
    leaf multicast-label {
      type boolean;
      description "The unicast or multicast label";
    }
    leaf leaf-time-in-milli-seconds {
      type uint64;
      description "The time of last update in msec";
    }
    leaf total-number-of-packets-switched {
      type uint64;
      description
        "The total number of packets switched on all
        paths";
    }
    leaf total-number-of-bytes-switched {
      type uint64;
      units "byte";
      description "The total number of bytes switched on all paths";
    }

    list label-information {
      description "Label-infos in FIB leaf";
      uses MPLS-ADJ-INFO;
    }
  }

  grouping MPLS-FWDING-SUMMARY {
    description "MPLS FWDING SUMMARY";
    leaf ipv4-imposition-entries {
      type uint32;
      description "Number of IPv4 imposition entries";
    }
    leaf reserved-label-entries {
      type uint32;
      description "Number of reserved label entries";
    }
    leaf label-switched-entries {
      type uint32;
      description "Number of label swap/disposition entries";
    }
    leaf deleted-stale-entries {
      type uint32;
      description "Number of delete stale label entries";
    }
    leaf te-head-entries {
      type uint32;
      description "Number of TE tunnel head imposition entries";
    }
    leaf te-frr-head-entries {
      type uint32;
      description "Number of TE FRR tunnel head imposition entries";
    }
    leaf te-frr-interface-entries {
      type uint32;
      description "Number of TE FRR protected interface entries";
    }
    leaf te-frr-next-hop-entries {
      type uint32;
      description "Number of TE FRR protected next-hop entries";
    }
    leaf te-mid-points-entries {
      type uint32;
      description "Number of TE MidPoints forwarding entries";
    }
    leaf te-frr-mid-points-entries {
      type uint32;
      description "Number of TE FRR MidPoints forwarding entries";
    }
    leaf te-internal-entries {
      type uint32;
      description "Number of TE internal forwarding entries";
    }
    leaf te-frr-internal-entries {
      type uint32;
      description "Number of TE internal forwarding entries";
    }
    leaf total-forwarding-updates {
      type uint32;
      description "Total forwarding updates from LSD to LFDs";
    }
    leaf total-forwarding-update-messages {
      type uint32;
      description
        "Total forwarding update messages from LSD to
        LFDs";
    }
    leaf total-p2mp-forwarding-updates {
      type uint32;
      description "Total forwarding updates from MRIB to LFDs";
    }
    leaf total-p2mp-forwarding-added-or-modify-messages {
      type uint32;
      description
        "Total p2mp forwarding add/modify messages from
        MRIB to LFDs";
    }
    leaf total-p2mp-forwarding-delete-messages {
      type uint32;
      description
        "Total p2mp forwarding del messages from MRIB to
        LFDs";
    }
    leaf total-p2mp-forwarding-drop-messages {
      type uint32;
      description
        "Total p2mp forwarding messages dropped from MRIB
        to LFDs";
    }
    leaf total-p2mp-iir-forwarding-drop-messages {
      type uint32;
      description
        "Total IIR triggered p2mp forwarding MRIB
        messages dropped";
    }
    leaf lowest-label {
      type uint32;
      description "Lowest label in use";
    }
    leaf highest-label {
      type uint32;
      description "Highest Label in use";
    }
    leaf ignore-protect {
      type uint32;
      description "Number of TE tunnels treated as non-protected";
    }
    leaf mte-head-entries {
      type uint32;
      description "Number of MTE tunnel head entries";
    }
    leaf mte-ll-entries {
      type uint32;
      description "Number of MTE local entries";
    }
    leaf mte-midpoint-entries {
      type uint32;
      description "Number of MTE midpoint entries";
    }
    leaf global-dropped-packets {
      type uint64;
      description "Number of global FIB packets dropped";
    }
    leaf global-fragmented-packets {
      type uint64;
      description "Number of global FIB packets fragmented";
    }
    leaf global-failed-lookups {
      type uint64;
      description "Number of global failed lookups";
    }
    leaf lrpf-entries {
      type uint32;
      description "Number of labels with RPF";
    }
  }
}
