submodule Cisco-IOS-XR-mpls-te-oper-sub5 {

  belongs-to Cisco-IOS-XR-mpls-te-oper {
    prefix Cisco-IOS-XR-mpls-te-oper;
  }

  /*** LINKAGE (IMPORTS / INCLUDES) ***/

  import ietf-inet-types { prefix "inet"; }

  import Cisco-IOS-XR-types { prefix "xr"; }

  include Cisco-IOS-XR-mpls-te-oper-sub6 {
    revision-date 2018-08-01;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR mpls-te package operational data.

     Copyright (c) 2013-2018 by Cisco Systems, Inc.
     All rights reserved.";

  revision "2018-08-01" {
    description
      "Removed empty groupings.";
  }

  revision "2017-09-07" {
    description
      "Fixed type translation error.";
  }

  revision "2017-05-01" {
    description
      "Fixing backward compatibility error in module.";
  }

  revision "2015-11-09" {
    description
      "IOS XR 6.0 revision.";
  }

  typedef Tunnel-state-enum {
    type enumeration {
      enum tunnel-state-unknown {
        description "No known state";
      }
      enum new {
        description "Tunnel is new";
      }
      enum preempting {
        description "Tunnel is being preempted";
      }
      enum admitting {
        description "Path being admitted";
      }
      enum half-admitted {
        description
          "Path was admitted partially and was then
          rejected";
      }
      enum admitted {
        description "Path is already admitted successfully";
      }
      enum reservation-admitting {
        description "Reservation being admitted";
      }
      enum reservation-half-admitted {
        description
          "Reservation was admitted partially and was then
          rejected";
      }
      enum reservation-admitted {
        description "Reservation is already admitted successfully";
      }
    }
    description "Types of tunnel admission states";
  }
  typedef Bandwidth-state-enum {
    type enumeration {
      enum bandwidth-held {
        description
          "Bandwidth is held, is not guaranteed when it is
          time to reserve";
      }
      enum bandwidth-reserved {
        description
          "Bandwidth is reserved and can be used for
          forwarding";
      }
      enum bandwidth-unknown {
        description "Bandwidth is unknown";
      }
    }
    description "Types of bandwidth states";
  }
  typedef Bandwidth-accounting-collection {
    type enumeration {
      enum rsvp-te {
        description "RSVP TE";
      }
      enum segment-routing {
        description "Segment Routing";
      }
    }
    description "Types of bandwidth accounting collection";
  }
  typedef Bandwidth-type-enum {
    type enumeration {
      enum pool0 {
        description "Bandwidth from the pool0";
      }
      enum pool1 {
        description "Pool1 bandwidth";
      }
      enum unknown {
        description "Unknown Bandwidth";
      }
    }
    description "Types of bandwidth pools";
  }
  typedef Admission-policy {
    type enumeration {
      enum reject-all {
        description "Deprecated";
      }
      enum allow-all {
        description "Deprecated";
      }
      enum reject-huge {
        description "Deprecated";
      }
      enum allow-if-room {
        description "Deprecated";
      }
    }
    description "Deprecated";
  }
  typedef Signaling-agent-enum {
    type enumeration {
      enum no-signaling {
        description "Deprecated - No signaling protocol configured";
      }
      enum rsvp-signaling {
        description "Deprecated - RSVP is the signaling protocol";
      }
    }
    description "Deprecated - Signaling Agent";
  }
  typedef Resource-provider {
    type enumeration {
      enum resource-provider-none {
        description "Unknown";
      }
      enum packet-switch-capable {
        description "Packet Switch Capable";
      }
      enum time-division-multiplex {
        description "TDM - SONET/SDH";
      }
      enum lambda-switch-capable {
        description "Lambda Switch Capable";
      }
      enum fiber-switch-capable {
        description "Fiber Switch Capable";
      }
      enum g709odu-capable {
        description "Resource provider of type G709-ODU";
      }
    }
    description "The resource provider type";
  }
  typedef Link-direction-enum {
    type enumeration {
      enum link-direction-up-stream {
        description "Upstream direction, Tail to Head";
      }
      enum link-direction-down-stream {
        description "Upstream direction, Head to Tail";
      }
      enum link-direction-unknown {
        description "Unknown direction";
      }
    }
    description "Link direction types";
  }
  typedef Bandwidth-unit-enum {
    type enumeration {
      enum kilo-bits-per-second {
        description "kilobits per second";
      }
      enum kilo-bytes-per-second {
        description "kilobytes per second";
      }
    }
    description "Types of bandwidth units";
  }
  typedef Flooding-trigger {
    type enumeration {
      enum flooding-reason-unknown {
        description "Not known what caused flooding";
      }
      enum link-up {
        description "TE link came Up";
      }
      enum link-down {
        description "TE link went Down";
      }
      enum threshold-up {
        description "Up threshold crossed in pool0";
      }
      enum threshold-down {
        description "Down threshold crossed in pool0";
      }
      enum threshold-up-pool1 {
        description "Up threshold crossed in pool1";
      }
      enum threshold-down-pool1 {
        description "Down threshold crossed in pool1";
      }
      enum timer-expired {
        description "Periodic timer expired";
      }
      enum bandwidth-change {
        description "Link BW changed";
      }
      enum user {
        description "User triggered flooding";
      }
      enum rsvp-timeout {
        description "RSVP timed out";
      }
      enum rsvp-reconnect {
        description "RSVP reconnected";
      }
      enum te-exited {
        description "TE-control process exited";
      }
      enum srlg-change {
        description "Link SRLG changed";
      }
      enum hw-oor-green {
        description "HW resources are green";
      }
      enum hw-oor-yellow {
        description "HW resources are yellow";
      }
      enum hw-oor-red {
        description "HW resources are red";
      }
      enum hw-oor-recovery-duration-expired {
        description
          "HW Resources are back to normal and the
          transition period is over";
      }
      enum lsp-oor-green {
        description "LSP resources are green";
      }
      enum lsp-oor-yellow {
        description "LSP resources are yellow";
      }
      enum lsp-oor-red {
        description "LSP resources are red";
      }
      enum lsp-oor-recovery-duration-expired {
        description
          "LSP resources are back to normal and the
          transition period is over";
      }
      enum max-res-bandwidth-threshold-up {
        description "Max reservable bandwidth up threshold crossed";
      }
      enum max-res-bandwidth-threshold-down {
        description
          "Max reservable bandwidth down threshold crossed";
      }
    }
    description "Types of flooding triggers";
  }
  typedef Te-auto-tun-exp-path-hop {
    type enumeration {
      enum ipv4-address-type {
        description "IPv4 Address Type";
      }
      enum mpls-label-type {
        description "MPLS Label Type";
      }
      enum ipv4-and-label-type {
        description "IPv4 Address and MPLS Label Type";
      }
    }
    description "Auto tunnel hop type";
  }
  typedef In-addr-ipv6 {
    type inet:ipv6-address;
    description "In addr ipv6";
  }
  typedef Lsp-oor-state {
    type enumeration {
      enum lsp-oor-green {
        description "LSP numbers are in normal state";
      }
      enum lsp-oor-yellow {
        description "LSP numbers exceed the minor threshold";
      }
      enum lsp-oor-red {
        description "LSP numbers exceed the major threshold";
      }
    }
    description "LSP OOR states";
  }
  typedef Te-s2l-output-rw-explicit-null {
    type enumeration {
      enum tes2l-output-rw-exp-null {
        value 0;
        description "No explicit null imposed";
      }
      enum tes2l-output-rw-exp-null-v4 {
        value 1;
        description "IPv4 explicit null imposed";
      }
      enum tes2l-output-rw-exp-null-v6 {
        value 2;
        description "IPv6 explicit null imposed";
      }
    }
    description "Explicit-null type";
  }
  typedef Mpls-te-tunnels-process-status {
    type enumeration {
      enum not-running {
        description "MPLS TE process is not running";
      }
      enum running {
        description "MPLS TE process is running";
      }
      enum not-registered-with-rsvp {
        description "MPLS TE process has not registered with RSVP";
      }
    }
    description "Mpls te tunnels process status";
  }
  typedef Mpls-te-frr-sharing {
    type enumeration {
      enum sharing-none {
        description "No Fate Sharing";
      }
      enum sharing-pri-oi-backup-oi-parent {
        description
          "Primary Sharing outgoing interface with the
          Parent of the backup outgoing interface";
      }
      enum sharing-pri-oi-parent-backup-oi {
        description
          "Primary Sharing Parent of the outgoing
          interface with the backup outgoing interface";
      }
      enum sharing-pri-oi-parent-backup-oi-parent {
        description
          "Primary Sharing Parent of the outgoing
          interface with the Parent of the backup
          outgoing interface";
      }
    }
    description "FRR sharing type";
  }
  typedef Mpls-te-bw-limit {
    type enumeration {
      enum bandwidth-limited {
        description "Bandwidth is limited";
      }
      enum bandwidth-unlimited {
        description "Bandwidth is unlimited";
      }
      enum bandwidth-none {
        description "Bandwidth is None";
      }
    }
    description "Bandwidth limit type";
  }
  typedef Mpls-te-backup-usage {
    type enumeration {
      enum backup-not-protecting {
        description "Backup is not protecting any LSP";
      }
      enum backup-protecting {
        description "Backup is protecting at least one LSP";
      }
    }
    description "FRR backup tunnel usage status";
  }
  typedef Mpls-te-backup {
    type enumeration {
      enum backup-static {
        description "Backup type is static";
      }
      enum backup-auto {
        description "Backup type is auto-tunnel";
      }
    }
    description "FRR backup tunnel type";
  }
  typedef Mpls-te-backup-status {
    type enumeration {
      enum backup-none {
        description "Backup not found";
      }
      enum backup-unused {
        description "Backup status undefined";
      }
      enum backup-next-next-hop {
        description
          "Backup is next next hop safe (node protection)";
      }
      enum backup-next-hop {
        description "Backup is next hop safe (link protection)";
      }
      enum backup-next-next-hop-srlg {
        description
          "Backup is next next hop and SRLG safe (node
          protection)";
      }
      enum backup-next-hop-srlg {
        description
          "Backup is next hop and SRLG safe (link
          protection)";
      }
    }
    description "FRR backup status";
  }
  typedef Te-sync-pending-reason {
    type enumeration {
      enum current-lspoos {
        description "Current LSP OOS";
      }
      enum reopt-lspoos {
        description "Reopt LSP OOS";
      }
      enum standby-lspoos {
        description "Standby LSP OOS";
      }
      enum standby-reopt-lspoos {
        description "Standby Reopt LSP OOS";
      }
      enum restore-lspoos {
        description "Restore LSP OOS";
      }
      enum invalid-sync-id {
        description "Invalid internal ID";
      }
      enum null-pointer {
        description "Null pointer";
      }
      enum pending-flag {
        description "Pending flag set";
      }
      enum del-from-act-flag {
        description "Deleted by Active set";
      }
      enum oos-from-act-flag {
        description "OOS with Active set";
      }
      enum unknown {
        description "Unknown";
      }
    }
    description "Te sync pending reason";
  }
  typedef Te-sync-not-ready-reason {
    type enumeration {
      enum idt-in-progress {
        description "IDT in progress";
      }
      enum standby-not-connected {
        description "Standby not connected";
      }
      enum collaborator-disconnected {
        description "Collaborator disconnected";
      }
      enum collaborator-timeout {
        description "Collaborator timeout";
      }
      enum unknown {
        description "Unknown";
      }
    }
    description "Te sync not ready reason";
  }
  typedef Te-sync-status-show {
    type enumeration {
      enum master-sync-status-show {
        description "Master sync status information";
      }
      enum slave-sync-status-show {
        description "Slave sync status information";
      }
    }
    description "Te sync status show";
  }
  typedef Mpls-te-dste-class-status {
    type enumeration {
      enum configured {
        description "The TE class is explicitely configured";
      }
      enum default {
        description "The TE class is a default";
      }
      enum unused {
        description
          "The TE class is unused due to a configuration
          conflict";
      }
    }
    description "DSTE class status";
  }
  typedef Te-proc-role {
    type enumeration {
      enum unknown {
        description "Unknown";
      }
      enum v1-active {
        description "V1 Active";
      }
      enum v2-active {
        description "V2 Active";
      }
      enum v1-standby {
        description "V1 Standby";
      }
      enum v2-standby {
        description "V2 Standby";
      }
      enum v1-active-post-big-bang {
        description "V1 Active post big bang";
      }
      enum v1-standby-post-big-bang {
        description "V1 Standby post big bang";
      }
      enum number-of-role {
        description "Number of role";
      }
    }
    description "TE Process Role";
  }
  typedef Te-acl {
    type enumeration {
      enum acl-type-unknown {
        value 0;
        description "Unknown type of ACL";
      }
      enum acl-type-access-list {
        value 1;
        description "Access-list type of ACL";
      }
      enum acl-type-prefix-list {
        value 2;
        description "Prefix-list type of ACL";
      }
      enum acl-type-unregistered {
        value 3;
        description "ACL failed to register to ACL infra";
      }
    }
    description "Te acl";
  }
  typedef Mpls-te-p2mp-timer {
    type enumeration {
      enum lmrib-restart {
        value 0;
        description "P2MP Local Multicast RIB restart";
      }
      enum lmrib-recovery {
        value 1;
        description "P2MP LMRIB recovery";
      }
      enum rsvp-restart {
        value 2;
        description "P2MP RSVP restart";
      }
      enum lsd-restart {
        value 3;
        description "LSD restart";
      }
      enum lsd-recovery {
        value 4;
        description "LSD recovery";
      }
      enum clear-in-progress-bandwidth {
        value 5;
        description
          "Timer to clear the inprogress bandwidth for all
          the nodes in the topology";
      }
      enum rsi-restart {
        value 6;
        description "RSI restart";
      }
      enum rsi-recovery {
        value 7;
        description "RSI recovery";
      }
      enum ipv4-caps-replay {
        value 8;
        description
          "Timer to timeout the replay of IPv4 Caps after
          a TE or IM restart";
      }
      enum retry-acl-registration-timer {
        value 9;
        description "Timer to retry ACL registration";
      }
      enum mpls-te-exit {
        value 10;
        description "MPLS TE Exit";
      }
      enum mpls-te-nsr-peer-restart {
        value 11;
        description "MPLS TE NSR Peer Restart";
      }
      enum mpls-te-issu-peer-restart {
        value 12;
        description "MPLS TE ISSU Peer Restart";
      }
      enum bfd-restart {
        value 13;
        description "BFD restart";
      }
      enum bfd-recovery {
        value 14;
        description "BFD recovery";
      }
      enum im-oc-restart {
        value 15;
        description "IM Optical Connection restart";
      }
      enum im-oc-recovery {
        value 16;
        description "IM Optical Connection recovery";
      }
      enum rib-restart {
        value 17;
        description "RIB restart";
      }
      enum rib-recovery {
        value 18;
        description "RIB recovery";
      }
      enum rib-next-hop-route-cleanup {
        value 19;
        description "RIB next-hop route cleanup";
      }
      enum rsi-srlg-producer-retry {
        value 20;
        description "RSI SRLG-producer connection retry";
      }
      enum eoc-reg-retry {
        value 21;
        description "End-of-Config registration retry";
      }
      enum fib-restart {
        value 22;
        description "FIB restart";
      }
      enum fib-recovery {
        value 23;
        description "FIB recovery";
      }
      enum fib-next-hop-route-cleanup {
        value 24;
        description "FIB next-hop route cleanup";
      }
      enum fib-next-hop-register-retry {
        value 25;
        description "FIB next-hop register retry";
      }
      enum tun-backend-scan-retry {
        value 26;
        description "Tunnel Backend Scan Retry";
      }
      enum tunnel-checkpoint-list-service {
        value 27;
        description "Tunnel Checkpoint list service";
      }
      enum tunnel-service-binding-sid-allocation-retry {
        value 28;
        description "Tunnel Service Binding SID Allocation Retry";
      }
      enum im-sync-delay {
        value 29;
        description "IM sync delay";
      }
      enum timer-not-used {
        value 30;
        description "Do not use";
      }
    }
    description "P2MP timer types";
  }
  typedef Mpls-te-afi {
    type enumeration {
      enum ipv4-unicast {
        description "MPLS TE IPv4 unicast";
      }
      enum ipv4-multicast {
        description "MPLS TE IPv4 multicast";
      }
      enum ipv6-unicast {
        description "MPLS TE IPv6 unicast";
      }
      enum ipv6-multicast {
        description "MPLS TE IPv6 multicast";
      }
    }
    description "Mpls te afi";
  }
  typedef Mpls-te-tunnel-announce {
    type enumeration {
      enum announce-type-not-set {
        description "Tunnel announcement type not set";
      }
      enum autoroute {
        description "Autoroute-announced tunnel";
      }
      enum forward-adjacency {
        description "Forwarding-adjacency tunnel";
      }
    }
    description "Type of TE tunnel announcement to IGP";
  }
  typedef Te-target-addr {
    type enumeration {
      enum invalid-te-target-type {
        description "Invalid TE Target Type";
      }
      enum te-target-type-ipv4 {
        description "TE Target IPv4 Type";
      }
      enum te-target-type-label {
        description "TE Target Label Type";
      }
    }
    description "TE Target Address Type";
  }
  typedef Flex-lsp-lockout-origination {
    type enumeration {
      enum lockout-origination-none {
        description "Flex LSP Lockout Origination None";
      }
      enum lockout-origination-local {
        description "Flex LSP Lockout Originated From Local";
      }
      enum lockout-origination-remote {
        description "Flex LSP Lockout Originated From Remote";
      }
    }
    description "TE Flex LSP Lockout Origination";
  }
  typedef Te-rev-ero-reject-reasons {
    type enumeration {
      enum none {
        description "None";
      }
      enum bad-reverse-ero {
        description "Bad Reverse ERO";
      }
      enum tie-rejected {
        description "Tie Rejected";
      }
      enum standby-not-required {
        description "Standby Not Required";
      }
      enum admin-state {
        description "Admin State";
      }
      enum priority {
        description "Priority";
      }
      enum class-type {
        description "Class Type";
      }
      enum bad-association {
        description "Bad Associated Tunnel";
      }
    }
    description "TE Reverse ERO Reject Reasons";
  }
  typedef Mte-path-option {
    type enumeration {
      enum none {
        description "No Path Option type";
      }
      enum dynamic {
        description "Dynamic Path Option type";
      }
      enum explicit {
        description "Explicit Path Option type";
      }
      enum no-ero {
        description "No ERO Path Option type";
      }
      enum segment-routing {
        description "One SID SegmentRouting Path Option type";
      }
      enum po-count {
        description "Number of Path option types";
      }
    }
    description "Path Option Type";
  }
  typedef Mpls-te-mgmt-gmpls-label-origin {
    type enumeration {
      enum not-set {
        description "Not set";
      }
      enum uni-c {
        description "UNI C";
      }
      enum uni-n {
        description "UNI N";
      }
    }
    description "GMPLS label source";
  }
  typedef Mpls-te-tunnel-state {
    type enumeration {
      enum state-down {
        description "Tunnel state is down";
      }
      enum state-up {
        description "Tunnel state is up";
      }
      enum state-down-policy {
        description
          "Tunnel state is down as it has been deactivated
          administratively";
      }
      enum state-lockout {
        description "Tunnel state is lockout";
      }
    }
    description "Tunnel state";
  }
  typedef Mpls-te-soft-preemption-resolution {
    type enumeration {
      enum soft-preemption-resolution-none {
        value 0;
        description "No Soft Preemption Resolution";
      }
      enum soft-preemption-resolution-pending {
        value 1;
        description
          "Soft Preemption has no resolution since it is
          still pending";
      }
      enum soft-preemption-resolution-reopt-completed {
        value 2;
        description "The soft preempted LSP has been reoptimized";
      }
      enum soft-preemption-resolution-teardown {
        value 3;
        description "The soft preempted LSP has been torn";
      }
      enum soft-preemption-resolution-frr-triggered {
        value 4;
        description "The soft preempted LSP has been fast rerouted";
      }
      enum soft-preemption-resolution-path-protetion-switchover {
        value 5;
        description
          "The soft preempted LSP was switched with the
          protection LSP";
      }
    }
    description "The possible ways for soft preemption to end";
  }
  typedef Mpls-te-iep-hop {
    type enumeration {
      enum iep-hop-type-unknown {
        description "Unknown IEP hop type";
      }
      enum iep-hop-type-strict-next {
        description "Strict next IEP hop type";
      }
      enum iep-hop-type-exclude {
        description "Exclude IEP hop type";
      }
      enum iep-hop-type-exclude-node {
        description "Exclude Node IEP hop type";
      }
      enum iep-hop-type-exclude-srlg {
        description "Exclude SRLG IEP hop type";
      }
      enum iep-hop-type-loose-next {
        description "Loose next IEP hop type";
      }
      enum iep-hop-type-next {
        description "Next IEP hop type";
      }
      enum iep-hop-type-share-srlg {
        description "Weighted SRLG IEP hop type";
      }
    }
    description "Explicit path hop type";
  }
  typedef Mpls-te-pce-fail-reasons {
    type enumeration {
      enum te-pce-fail-no-reason {
        description "No reason";
      }
      enum te-pce-fail-no-pce {
        description "No PCE to send request";
      }
      enum te-pce-fail-sub-pool {
        description "Sub pool bandwidth tunnel";
      }
      enum te-pce-fail-intra-area {
        description "Intra Area Tunnel";
      }
      enum te-pce-fail-gmpls {
        description "GMPLS Tunnel";
      }
      enum te-pce-fail-pending {
        description "Pending request";
      }
      enum te-pce-fail-oor {
        description "OOR condition";
      }
      enum te-pce-fail-bidirectional {
        description "Bi directional";
      }
      enum te-pce-fail-no-path {
        description "No Path received from PCE";
      }
      enum te-pce-fail-request-timeout {
        description "Request Timeout";
      }
    }
    description "PCE failure reasons";
  }
  typedef Te-autobw-app-rej {
    type enumeration {
      enum application-allowed {
        description "Application allowed";
      }
      enum auto-bw-disabled {
        description "Auto-bw disabled";
      }
      enum tunnel-is-down {
        description "TunnelIsDown";
      }
      enum tunnel-is-frr {
        description "TunnelIsFRRActive";
      }
      enum tunnel-is-backup {
        description "TunnelIsBackup";
      }
      enum tunnel-is-lock-down {
        description "TunnelIsLockdown";
      }
    }
    description "Reason for auto-bandwidth application rejection";
  }
  typedef Te-autobw-app-trigger {
    type enumeration {
      enum application-none {
        description "No BW Application";
      }
      enum application-periodic {
        description "BW Application Periodic";
      }
      enum application-manual {
        description "BW Application Manual";
      }
      enum application-overflow {
        description "BW Application Overflow";
      }
      enum application-underflow {
        description "BW Application Underflow";
      }
    }
    description "Auto-bandwidth application trigger";
  }
  typedef Te-hop-limit-ignore {
    type enumeration {
      enum ignore-unknown {
        description "Ignore for an unknown reason";
      }
      enum ignore-explicit {
        description "Ignore due to explicit path option";
      }
      enum ignore-pce {
        description "Ignore due to PCE path option";
      }
    }
    description "Te hop limit ignore";
  }
  typedef Mpls-te-metric-qualifier {
    type enumeration {
      enum metric-default {
        description "Default metric";
      }
      enum metric-global {
        description "This metric was specified globally";
      }
      enum metric-interface {
        description
          "This metric was specified on this particular
          tunnel";
      }
    }
    description "Metric qualifier";
  }
  typedef Te-path-selection-tiebreaker {
    type enumeration {
      enum min-fill {
        value 1;
        description "Min Fill";
      }
      enum max-fill {
        value 2;
        description "Max Fill";
      }
      enum random {
        value 3;
        description "Random";
      }
    }
    description "Path selection tiebreaker type";
  }
  typedef Mpls-te-loadshare {
    type enumeration {
      enum loadshare-equal {
        description "Equal load-sharing on this tunnel";
      }
      enum loadshare-bandwidth-based {
        description
          "Loadshare inferred from bandwidth configuration";
      }
      enum loadshare-configured {
        description
          "Loadshare determined from explicit
          configuration";
      }
    }
    description "load-share type";
  }
  typedef Te-destination-state {
    type enumeration {
      enum destination-disabled {
        description "The destination is disabled in configuration";
      }
      enum destination-down {
        description "The destination is down";
      }
      enum destination-up {
        description "The destination is up";
      }
    }
    description "P2MP destination state";
  }
  typedef Mpls-mte-tunnel-fail-reason {
    type enumeration {
      enum mtunnel-fail-reason-unapplicable {
        description "None of the reasons below is valid";
      }
      enum mtunnel-fail-reason-shutdown {
        description "Tunnel interface is shutdown";
      }
      enum mtunnel-fail-reason-no-destination {
        description "No destination is configured";
      }
      enum mtunnel-fail-reason-no-path-option {
        description "No path option is configured";
      }
      enum mtunnel-fail-reason-no-source {
        description "No ip source address is configured";
      }
      enum mtunnel-fail-reason-collaborator-disc {
        description "Collaborator not connected";
      }
      enum mtunnel-fail-reason-unmatched-class-type-priority {
        description
          "The class type and priority do not match any of
          the TE-classes";
      }
      enum mtunnel-fail-reason-invalid-bidir-cfg {
        description
          "Configured bidirectional, incomplete switching
          capability config";
      }
      enum mtunnel-fail-reason-po-switchover {
        description
          "Manual path-option switchover failed due to
          destination(s) down";
      }
      enum mtunnel-fail-reason-no-tunnel-id {
        description "No tunnel-id is configured";
      }
      enum mtunnel-fail-reason-no-link {
        description "Tunnel's egress link doesn't exist";
      }
      enum mtunnel-fail-reason-link-shutdown {
        description "Tunnel's egress link is shut down";
      }
      enum mtunnel-fail-reason-link-lmp-down {
        description "LMP is down on the tunnel's egress link";
      }
      enum mtunnel-fail-reason-source-destination-same {
        description
          "Tunnel source and destination addresses are the
          same";
      }
      enum mtunnel-fail-reason-otn-no-odu-level {
        description "OTN tunnel does not have odu-level set";
      }
      enum mtunnel-fail-reason-bidir-assoc-id-missing {
        description
          "Bidirectional is configured without Association
          ID";
      }
      enum mtunnel-fail-reason-bfdgal-on-unidirectional {
        description
          "BFD GAL mode is supported on bidirectional
          tunnels only";
      }
      enum mtunnel-fail-reason-destination-invalid {
        description
          "Termination is supported with unnumbered
          destination only";
      }
      enum mtunnel-fail-reason-termination-bandwidth-mismatch {
        description
          "Termination bandwidth should match signalled
          bandwidth";
      }
      enum mtunnel-fail-reason-termination-has-protection {
        description "Termination supports only working path-option";
      }
      enum "mtunnel-fail-reason-termination-has-invalid-src-dest"+
        "-ifindex" {
        description
          "Termination case must have source and
          destination valid ifindex";
      }
      enum "mtunnel-fail-reason-termination-has-invalid-payload"+
        "-type" {
        description
          "Termination payload type has to be valid for
          configured bandwidth";
      }
    }
    description "Reason for tunnel being down";
  }
  typedef Mte-tunnel-oper-state {
    type enumeration {
      enum tunnel-state-oper-unknown {
        description "Tunnel is in unknown state";
      }
      enum operational-down {
        description "Tunnel is in operational down state";
      }
      enum operational-up {
        description "Tunnel is in operational up state";
      }
    }
    description "Tunnel operational state";
  }
  typedef Mte-tunnel-admin-state {
    type enumeration {
      enum tunnel-state-admin-unknown {
        description "Tunnel is in unknown state";
      }
      enum admin-shutdown {
        description "Tunnel is in admin shutdown state";
      }
      enum admin-up {
        description "Tunnel is in admin up state";
      }
    }
    description "Tunnel admin state";
  }
  typedef Te-vif-bfd-encap-mode {
    type enumeration {
      enum ip {
        description "BFD Encap Mode IP";
      }
      enum gal {
        description "BFD Encap Mode GAL";
      }
    }
    description "BFD Encap Mode";
  }
  typedef Mpls-te-bfd-session-down-action1 {
    type enumeration {
      enum reopt {
        value 0;
        description "BFD session down action reoptimization";
      }
      enum re-setup {
        value 1;
        description "BFD session down action tear down and resetup";
      }
    }
    description "BFD session down action";
  }
  typedef Te-lsp-path-protection-role {
    type enumeration {
      enum protection-role-not-set {
        description "Protection role not set";
      }
      enum protection-role-working {
        description "Working";
      }
      enum protection-role-protecting {
        description "Protecting";
      }
      enum protection-role-pending {
        description "Pending";
      }
    }
    description "Protection Role";
  }
  typedef Mte-reopt-trigger {
    type enumeration {
      enum no-trigger {
        description "No trigger";
      }
      enum timer-trigger {
        description "Timer Trigger";
      }
      enum bandwidth-change-trigger {
        description "Bandwidth Change Trigger";
      }
      enum auto-bandwidth-overflow-trigger {
        description "Auto Bandwidth Overflow Trigger";
      }
      enum auto-bandwidth-underflow-trigger {
        description "Auto Bandwidth Underflow Trigger";
      }
      enum auto-bandwidth-adjustment-trigger {
        description "Auto Bandwidth Adjustment Trigger";
      }
      enum metric-type-change-trigger {
        description "Metric Type Change Trigger";
      }
      enum user-trigger {
        description "User Trigger";
      }
      enum frr-trigger {
        description "FRR Trigger";
      }
      enum remerge-error-trigger {
        description "Remerge Error Trigger";
      }
      enum preferred-path-trigger {
        description
          "Reception of the preferred path exists path
          error";
      }
      enum preferred-tree-trigger {
        description
          "Reception of the preferred tree exists path
          error";
      }
      enum due-to-maximum-metric {
        description
          "Reoptimization triggered due to receiving an
          LSA with MAX metric";
      }
      enum path-option-switchover-trigger {
        description "Path option switchover";
      }
      enum path-protection-switchover-trigger {
        description "Path Protection Switchover Trigger";
      }
      enum reroute-sticky-path-trigger {
        description "Reroute Sticky Path trigger";
      }
      enum iep-enable-reoptimization-trigger {
        description "IEP Enable Reoptimization Trigger";
      }
      enum affinity-path-verification-fail-trigger {
        description "Affinity path verification failure trigger";
      }
      enum cost-limit-path-verification-fail-trigger {
        description "Cost limit path verification failure trigger";
      }
      enum delay-limit-path-verification-fail-trigger {
        description "Delay limit path verification failure trigger";
      }
      enum soft-preemption-trigger {
        description "Soft preemption trigger";
      }
      enum iep-changed {
        description "Explicit path has changed";
      }
      enum po-changed {
        description "Path-option has changed";
      }
      enum dest-changed {
        description "Destination has changed";
      }
      enum reopt-try-to-force-it {
        description "Reoptimization with try-to-force-it option";
      }
      enum topology-change-trigger {
        description "Topology change trigger";
      }
      enum reopt-link-up-event {
        description "Topology link-up event trigger";
      }
      enum bfd-session-down-trigger {
        description "FRR enabled and BFD session down trigger";
      }
      enum reverse-assoc-s2l-received-trigger {
        description "Reverse associated S2L received trigger";
      }
      enum gmpls-uni-multilayer-trigger {
        description "Multilayer recovery for GMPLS-UNI";
      }
      enum gmpls-uni-user-trigger {
        description "User-triggered GMPLS-UNI reopt request";
      }
      enum path-selection-tiebreaker-change-trigger {
        description "Path Selection Tiebreaker Change Trigger";
      }
      enum sr-egress-path-change-trigger {
        description "Segment-Routing Egress Path Change Trigger";
      }
      enum overload-bit-trigger {
        description "Overload-bit set on current path";
      }
      enum pce-trigger {
        description "PCE Trigger";
      }
      enum lockout-metric-trigger {
        description
          "Reoptimization triggered due to receiving an
          LSA with Lockout metric";
      }
      enum bfd-session-config-change-trigger {
        description "BFD session configuration change";
      }
      enum higher-priority-po-change-trigger {
        description "Higher priority path option changed";
      }
      enum sr-area-spf-support-change-trigger {
        description
          "Segment-Routing IGP Area SPF Support Change
          Trigger";
      }
      enum trigger-not-used {
        description "Not used";
      }
    }
    description "Reoptimization trigger";
  }
  typedef Mpls-te-reopt-decision-reason {
    type enumeration {
      enum decision-reason-none {
        value 0;
        description "No reason";
      }
      enum not-superset {
        value 1;
        description
          "Reopt LSP not signalled because it is not a
          superset of the current LSP";
      }
      enum superset {
        value 2;
        description
          "Reopt LSP is signalled because it is a superset
          of the current LSP";
      }
      enum lsp-frr-active {
        value 3;
        description
          "Reopt LSP is signalled because the current LSP
          is in FRR";
      }
      enum bandwidth-change {
        value 4;
        description
          "Reopt LSP is signalled  because there is a
          bandwidth change";
      }
      enum metric-type-change {
        value 5;
        description
          "Reopt LSP is signalled because there is a
          metric type change";
      }
      enum better-path-option-indexes {
        value 6;
        description
          "Reopt LSP is signalled because it has better
          path option indexes than the current LSP";
      }
      enum inter-area-preferred-path-exists {
        value 7;
        description
          "Reopt LSP is signalled because an inter-area
          preferred path exists";
      }
      enum inter-area-preferred-tree-exists {
        value 8;
        description
          "Reopt LSP is signalled because an inter-area
          preferred tree exists";
      }
      enum worse-path-option-indexes {
        value 9;
        description
          "Reopt LSP is not signalled because it has worse
          path option indexes than the current LSP";
      }
      enum better-cumulative-metric {
        value 10;
        description
          "Reopt LSP is signalled because it has better
          path option indexes than the current LSP";
      }
      enum worse-cumulative-metric {
        value 11;
        description
          "Reopt LSP is not signalled because it has worse
          cumulative metric than the current LSP";
      }
      enum identical {
        value 12;
        description
          "Reopt LSP is not signalled because it is
          identical to the current LSP";
      }
      enum no-s2-ls {
        value 13;
        description
          "Reopt LSP is not signalled because it has no
          S2Ls";
      }
      enum no-current-lsp {
        value 14;
        description "Reopt LSP not signalled, no current LSP";
      }
      enum user-path-option-switchover {
        value 15;
        description
          "Reopt LSP signalled due to user requested
          path-option switchover";
      }
      enum better-hops {
        value 16;
        description
          "Reopt LSP is signalled because it has more S2Ls
          with less hops than the current LSP";
      }
      enum worse-hops {
        value 17;
        description
          "Reopt LSP is not signalled because it has less
          S2Ls with less hops than the current LSP";
      }
      enum pce-force {
        value 18;
        description
          "PCE based reoptimization triggered by CLI with
          force option than the current LSP";
      }
      enum affinity-changed {
        value 19;
        description
          "Reopt LSP is signalled  because there is an
          affinity change";
      }
      enum cost-limit {
        value 20;
        description
          "Reopt LSP is signalled  because the path cost
          limit is crossed";
      }
      enum sig-timeout {
        value 21;
        description
          "Re-opt LSP could not be signalled within
          signalling timeout";
      }
      enum not-superset-inst-timer-expired {
        value 22;
        description
          "Re-opt LSP is not a superset when the install
          timer expired";
      }
      enum path-verifiction-failed {
        value 23;
        description "Re-opt LSP path verification failed";
      }
      enum soft-preemption-recovery {
        value 24;
        description
          "Re-opt LSP is signalled because of soft
          preemption recovery";
      }
      enum iep-changed {
        value 25;
        description
          "Re-opt LSP is signalled because the inuse
          explicit-path has changed";
      }
      enum po-changed {
        value 26;
        description
          "Re-opt LSP is signalled because the inuse
          path-option has changed";
      }
      enum dest-changed {
        value 27;
        description
          "Re-opt LSP is signalled because the destination
          has changed";
      }
      enum better-igp-area {
        value 28;
        description
          "Reopt LSP is signalled because its path was
          calculated in a preferred IGP-area to the
          current LSP";
      }
      enum worse-igp-area {
        value 29;
        description
          "Reopt LSP is not signalled because its path was
          calculated in a worse IGP-area than the current
          LSP";
      }
      enum better-bandwidth-load-balancing {
        value 30;
        description
          "Reopt LSP is signalled because it gives better
          bandwidth load balancing than the current LSP";
      }
      enum worse-bandwidth-load-balancing {
        value 31;
        description
          "Reopt LSP is not signalled because it gives
          worse bandwidth load balancing than the current
          LSP";
      }
      enum bfd-session-down {
        value 32;
        description
          "Reopt LSP is signaled because BFD sesssion went
          down";
      }
      enum auto-pcc-reopt {
        value 33;
        description
          "Re-opt LSP is signalled because it was
          triggered by a PCE";
      }
      enum sr-egress-path-changed {
        value 34;
        description
          "Reopt LSP is signaled because the egress
          path(s) changed";
      }
      enum overload-bit-set {
        value 35;
        description
          "Reopt LSP is signalled because the current LSP
          uses an OL node";
      }
      enum better-diversity {
        value 36;
        description
          "Reopt LSP is signalled because it has better
          diversity than the current LSP";
      }
      enum worse-diversity {
        value 37;
        description
          "Reopt LSP is not signalled because it has worse
          diversity than the current lsp";
      }
      enum bfd-session-type-changed {
        value 38;
        description
          "Reopt LSP is signalled because BFD sesssion
          tyep is changed";
      }
      enum lsp-drop-mode {
        value 39;
        description
          "Reopt LSP is signalled because current LSP is
          in drop mode";
      }
      enum strict-spf {
        value 40;
        description
          "Reopt LSP is signalled because it uses strict
          SPF while current doesn't";
      }
      enum delay-limit {
        value 41;
        description
          "Reopt LSP is signalled  because the path delay
          limit is crossed";
      }
      enum lockout-metric {
        value 42;
        description
          "Reopt LSP is signalled  because one of the
          links is locked out";
      }
      enum intra-area {
        value 43;
        description
          "Reopt LSP is signalled because it has better
          intra-areaness";
      }
      enum clear-sticky {
        value 44;
        description
          "Reopt LSP is signalled because clear sticky
          command";
      }
      enum not-used {
        value 45;
        description "Not used, must be last entry";
      }
    }
    description "Reoptimization decision";
  }
  typedef Mpls-te-lsp-wrap-state {
    type enumeration {
      enum lsp-wrap-not-ready {
        description "LSP Wrap state is not ready";
      }
      enum lsp-wrap-active {
        description "LSP Wrap state is active";
      }
      enum lsp-wrap-ready {
        description "LSP Wrap state is ready";
      }
    }
    description "LSP Wrap state";
  }
  typedef Te-sr-sid {
    type enumeration {
      enum srsid-not-set {
        description "Type not set";
      }
      enum srsid-node {
        description "Segment-Routing Node";
      }
      enum srsid-adj {
        description "Segment-Routing Link";
      }
      enum srsid-unknown {
        description "Segment-Routing Unknown";
      }
    }
    description "Segment-Routing SID types";
  }
  typedef Te-association-tie-role {
    type enumeration {
      enum none {
        description "Association Role None";
      }
      enum master {
        description "Association Role Master";
      }
      enum slave {
        description "Association Role Slave";
      }
    }
    description "TE Association Tie Breaker Role";
  }
  typedef Te-vif-bfd {
    type enumeration {
      enum bfd-disabled {
        value 0;
        description "BFD Fast Detect Not Enabled";
      }
      enum bfd-enabled {
        value 1;
        description "Regular BFD Enabled";
      }
      enum sbfd-enabled {
        value 2;
        description "SBFD Enabled";
      }
    }
    description "BFD Type";
  }
  typedef Te-bfd-lsp-session-state {
    type enumeration {
      enum bfd-over-lsp-session-state-none {
        value 0;
        description "BFDOverLSP session state none";
      }
      enum bfd-over-lsp-session-state-created {
        value 1;
        description "BFDOverLSP session state created";
      }
      enum bfd-over-lsp-session-state-up {
        value 2;
        description "BFDOverLSP session state up";
      }
      enum bfd-over-lsp-session-state-down {
        value 3;
        description "BFDOverLSP session state down";
      }
      enum bfd-over-lsp-session-state-admin-down {
        value 4;
        description "BFDOverLSP session state admin down";
      }
      enum bfd-over-lsp-session-state-deleted {
        value 5;
        description "BFDOverLSP sesssion state deleted";
      }
      enum bfd-over-lsp-session-state-create-failed {
        value 6;
        description "BFDOverLSP session state create failed";
      }
    }
    description "TE BFDOverLSP Session State";
  }
  typedef Gmpls-uni-mgmt-dwdm-cs {
    type enumeration {
      enum not-set {
        description "Not Set";
      }
      enum dwdm100g-hz {
        description "100GHz";
      }
      enum dwdm50g-hz {
        description "50GHz";
      }
      enum dwdm25g-hz {
        description "25GHz";
      }
      enum dwdm12g-hz {
        description "12.5GHz";
      }
      enum dwdm6g-hz {
        description "6.25GHz";
      }
    }
    description "GMPLS-UNI DWDM channel spacings";
  }
  typedef Gmpls-uni-mgmt-wdm-grid {
    type enumeration {
      enum not-set {
        description "Not Set";
      }
      enum dwdm {
        description "DWDM";
      }
      enum cwdm {
        description "CWDM";
      }
    }
    description "GMPLS-UNI WDM grid";
  }
  typedef Mpls-te-mgmt-gmpls-label {
    type enumeration {
      enum not-set {
        description "Not Set";
      }
      enum fixed-wdm {
        description "Fixed-grid WDM";
      }
      enum fixed-g709otn {
        description "Fixed-size G709 OTN";
      }
    }
    description "GMPLS label type";
  }
  typedef Mpls-te-soft-preemption-state {
    type enumeration {
      enum soft-preemption-not-pending {
        description
          "Soft Preemption has not been triggered and is
          not pending";
      }
      enum soft-preemption-pending {
        description
          "Soft Preemption has been triggered and is
          pending";
      }
    }
    description "The possible states for soft preemption";
  }
  typedef Mpls-te-tunnels-signaling-status {
    type enumeration {
      enum down {
        description "The tunnel is down";
      }
      enum recovering {
        description "The tunnel is recovering";
      }
      enum recovered {
        description "The tunnel is recovered";
      }
      enum connected {
        description "The tunnel is connected";
      }
      enum disabled {
        description "The tunnel signalling is disabled";
      }
      enum proceeding {
        description "The tunnel signalling is proceeding";
      }
      enum wait-bfd-session-up {
        description "The tunnel is waiting for BFD session up";
      }
      enum wait-sr-segment-path-up {
        description "The tunnel is waiting for SR segment path";
      }
      enum wait-local-label {
        description "The tunnel is waiting for a local label";
      }
      enum wait-local-label-rewrite {
        description
          "The tunnel is waiting for a local label rewrite";
      }
    }
    description "Tunnel signalling status";
  }
  typedef Mpls-te-frr-state {
    type enumeration {
      enum frr-inactive {
        description "FRR state is inactive";
      }
      enum frr-active {
        description "FRR state is active";
      }
      enum frr-ready {
        description "FRR state is ready";
      }
    }
    description "FRR state";
  }
  typedef Te-controller-state {
    type enumeration {
      enum notready {
        description "Controller not ready";
      }
      enum admin-down {
        description "Controller is admin down";
      }
      enum down {
        description "Controller is operationally down";
      }
      enum shutdown {
        description "Controller is shutdown";
      }
      enum error-disabled {
        description "Controller is disabled due to error";
      }
      enum up {
        description "Controller is operationally up";
      }
      enum unknown {
        description "Controller state unknown";
      }
    }
    description "Controller States";
  }
  typedef Te-mgmt-generic-fspec {
    type enumeration {
      enum te-generic-fspec-type-g709otn {
        description "TE G709 OTN FSpec type";
      }
    }
    description "TE generic FSpec types";
  }
  typedef Te-mgmt-generic-tspec {
    type enumeration {
      enum te-generic-tspec-type-g709otn {
        description "TE G709 OTN TSpec type";
      }
    }
    description "TE generic TSpec types";
  }
  typedef Rsvp-mgmt-rro-subobj {
    type enumeration {
      enum ipv4rro-type {
        value 1;
        description "IPv4 RRO Type";
      }
      enum label-rro-type {
        value 3;
        description "Label RRO Type";
      }
      enum unnumbered-rro-type {
        value 4;
        description "Unnumbered RRO Type";
      }
      enum srlg-rro-type {
        value 34;
        description "SRLG RRO Type";
      }
    }
    description "RSVP RRO Types";
  }
  typedef Rsvp-mgmt-ero-subobj-status {
    type enumeration {
      enum rsvp-mgmt-ero-status-not-available {
        value 0;
        description "ERO is not available in topology";
      }
      enum rsvp-mgmt-ero-status-available {
        value 1;
        description "ERO is available in topology";
      }
      enum rsvp-mgmt-ero-status-bw-not-available {
        value 2;
        description "ERO doesn't have bw available in topology";
      }
    }
    description "RSVP ERO Status";
  }
  typedef Rsvp-mgmt-ero-subobj {
    type enumeration {
      enum rsvp-mgmt-ero-type-ipv4 {
        value 1;
        description "IPv4 ERO Type";
      }
      enum rsvp-mgmt-ero-type-un-num {
        value 4;
        description "Unnumbered ERO Type";
      }
    }
    description "RSVP ERO Types";
  }
  typedef Mpls-te-metric {
    type enumeration {
      enum metric-not-set {
        description "Metric type not set";
      }
      enum metric-igp {
        description "Metric for IGP routes";
      }
      enum metric-te {
        description "Metric for MPLS traffic engineering tunnels";
      }
      enum metric-delay {
        description "Delay Metric";
      }
    }
    description "Metric type";
  }
  typedef Te-path-inval-action {
    type enumeration {
      enum none {
        value 0;
        description "TE path selection invalidation action none";
      }
      enum tear {
        value 1;
        description "TE path selection invalidation action tear";
      }
      enum drop {
        value 2;
        description "TE path selection invalidation action drop";
      }
    }
    description "Path selection invalidation action type";
  }
  typedef Te-s2l-sr-path-selection {
    type enumeration {
      enum te-s2l-sr-path-selection-any {
        value 0;
        description
          "TE S2L Segment-Routing Path Selection type Any";
      }
      enum te-s2l-sr-path-selection-adj-unprotected {
        value 1;
        description
          "TE S2L Segment-Routing Path Selection type
          Adjacency Unprotected";
      }
      enum te-s2l-sr-path-selection-adj-protected {
        value 2;
        description
          "TE S2L Segment-Routing Path Selection type
          Adjacency Protected";
      }
    }
    description "Segment-routing path selection type";
  }
  typedef Te-bfd-reverse-path {
    type enumeration {
      enum bfd-reverse-path-none {
        value 0;
        description "BFD reverse path not enabled";
      }
      enum bfd-reverse-path-binding-label {
        value 1;
        description "BFD reverse path binding label";
      }
    }
    description "BFD Reverse Path Type";
  }
  typedef Te-pce-disjoint {
    type enumeration {
      enum none {
        value 0;
        description "PCE Disjoint Type none";
      }
      enum link {
        value 1;
        description "PCE Disjoint Type link";
      }
      enum node {
        value 2;
        description "PCE Disjoint Type node";
      }
      enum srlg {
        value 3;
        description "PCE Disjoint Type srlg";
      }
    }
    description "PCE Disjoint Path type";
  }
  typedef Tunnel-attribute-set {
    type enumeration {
      enum tunnel-attribute-set-none {
        value 0;
        description "No Tunnel AttributeSet configured";
      }
      enum tunnel-attribute-set-static {
        value 1;
        description "Tunnel AttributeSet Type is Static";
      }
      enum tunnel-attribute-set-path-option {
        value 2;
        description "Tunnel AttributeSet Type is Path Option";
      }
      enum tunnel-attribute-set-not-used {
        value 3;
        description "None";
      }
      enum tunnel-attribute-set-auto-backup {
        value 4;
        description "Tunnel AttributeSet Type is AutoBackup";
      }
      enum tunnel-attribute-set-auto-mesh {
        value 5;
        description "Tunnel AttributeSet Type is AutoMesh";
      }
      enum tunnel-attribute-set-xro {
        value 6;
        description "Tunnel AttributeSet Type is XRO";
      }
      enum tunnel-attribute-set-p2mpte {
        value 7;
        description "Tunnel AttributeSet Type is P2MP TE";
      }
      enum tunnel-attribute-aps-pp {
        value 8;
        description
          "Tunnel AttributeSet Type is APS Path Protection";
      }
      enum tunnel-attribute-set-p2p-te {
        value 9;
        description "Tunnel AttributeSet Type is P2P TE";
      }
    }
    description "Tunnel attribute set";
  }
  typedef Mpls-te-pathoption {
    type enumeration {
      enum path-option-unknown {
        description "Unknown Path Option";
      }
      enum path-option-dynamic {
        description "Dynamic Path Option";
      }
      enum path-option-explicit-name {
        description "Explicit name Path Option";
      }
      enum path-option-explicit-id {
        description "Explicit Identifier Path Option";
      }
      enum path-option-pce {
        description "PCE Path Option";
      }
      enum path-option-no-ero {
        description "No-ERO Path Option";
      }
      enum path-option-segment-routing {
        description "Segment-Routing Path Option";
      }
    }
    description "Path-option type";
  }
  typedef Mpls-te-bw-pool {
    type enumeration {
      enum te-bandwidth-pool0 {
        description "Bandwidth pool type is pool0";
      }
      enum te-bandwidth-pool1 {
        description "Bandwidth pool type is pool1";
      }
      enum te-bandwidth-any-pool {
        description "Bandwidth pool type is any pool";
      }
    }
    description "Bandwidth pool type";
  }
  typedef Hw-oor-state {
    type enumeration {
      enum oor-green {
        description "NPU resources are in normal state";
      }
      enum oor-yellow {
        description "NPU resources are in minor state";
      }
      enum oor-red {
        description "NPU resources are in Major state";
      }
    }
    description "NPU resources states";
  }

  grouping MPLS-LM-SOFT-PREEMPTION-LINK-INFO {
    description "Soft Preemption Info per Link";
    leaf link-address {
      type inet:ipv4-address;
      description "The link's IPv4 address";
    }
    leaf total-soft-preempted-bandwidth-bc0 {
      type uint64;
      description
        "The total BC0 BW that is softly preempted: this
        is the sum of bandwidth for all the LSPs that
        were soft preempted";
    }
    leaf total-soft-preempted-bandwidth-bc1 {
      type uint64;
      description
        "The total BC1 BW that is softly preempted: this
        is the sum of bandwidth for all the LSPs that
        were soft preempted";
    }
    leaf current-soft-preempted-bandwidth-bc0 {
      type uint64;
      description
        "The current BC0 BW that is softly preempted:
        this is the sum of bandwidth for the LSPs that
        are soft preempted and have not been torn down
        yet";
    }
    leaf current-soft-preempted-bandwidth-bc1 {
      type uint64;
      description
        "The current BC1 BW that is softly preempted:
        this is the sum of bandwidth for the LSPs that
        are soft preempted and have not been torn down
        yet";
    }
    leaf release-soft-preempted-bandwidth-bc0 {
      type uint64;
      description
        "The total released BC0 BW that is softly
        preempted: this is the sum of bandwidth for the
        LSPs that are soft preempted and are torn down";
    }
    leaf release-soft-preempted-bandwidth-bc1 {
      type uint64;
      description
        "The total released BC1 BW that is softly
        preempted: this is the sum of bandwidth for the
        LSPs that are soft preempted and are torn down";
    }
    leaf current-over-subscribed-bandwidth-bc0 {
      type uint64;
      description
        "The BC0 bandwidth that is over subscribed on
        this link: this is the difference between the
        maximum available BC0 BW on the link and the sum
        of the currently reserved BC0 bandwidth and the
        currently soft preempted BC0 BW";
    }
    leaf current-over-subscribed-bandwidth-bc1 {
      type uint64;
      description
        "The BC1 bandwidth that is over subscribed on
        this link: this is the difference between the
        maximum available BC1 BW on the link and the sum
        of the currently reserved BC1 bandwidth and the
        currently soft preempted BC1 BW";
    }

    list current-soft-preemption-lsp {
      description
        "List of the soft preempted LSPs that are not yet
        cleaned up";
      uses MPLS-LM-PREEMPTED-LSP;
    }
  }

  grouping MPLS-TE-SOFT-PREEMPTION-GLOBAL-INFO {
    description "Global Soft Preemption Info";
    leaf is-configured {
      type boolean;
      description "Is global soft-preemption configured";
    }
    leaf is-timeout-interval-configured {
      type boolean;
      description
        "Is global soft-preemption timeout interval
        configured";
    }
    leaf timeout-interval {
      type uint32;
      description "Global soft-preemption timeout interval";
    }
  }

  grouping MPLS-LM-ADMISSION-CONTROL-TUNNEL-INFO {
    description "Information about a given admitted tunnel";
    leaf tunnel-name {
      type string;
      description "The admitted tunnel's name";
    }
    leaf bandwidth-state {
      type Bandwidth-state-enum;
      description "The bandwidth state";
    }
    leaf bandwidth-pool {
      type Bandwidth-type-enum;
      description "The bandwidth pool";
    }
    leaf setup-priority {
      type uint8;
      description "The tunnel's setup priority";
    }
    leaf hold-priority {
      type uint8;
      description "The tunnel's hold priority";
    }
    leaf up-link-name {
      type string;
      description "The uplink's name for this tunnel";
    }
    leaf down-link-name {
      type string;
      description "The downlink's name for this tunnel";
    }
    leaf tunnel-state {
      type Tunnel-state-enum;
      description "The tunnel's state";
    }
    leaf bandwidth {
      type uint64;
      description "The bandwidth used by this tunnel";
    }
    leaf local-label {
      type uint32;
      description "The local label";
    }
    leaf outgoing-label {
      type uint32;
      description "The outgoing label";
    }
    leaf backup-interface {
      type string;
      description "The backup Interface";
    }
    leaf is-rerouted {
      type boolean;
      description "TRUE if the tunnel is currently rerouted";
    }
  }

  grouping MPLS-LM-ADMISSION-CONTROL-COMMON-INFO {
    description "Global information about admitted tunnels";
    leaf is-role-standby {
      type boolean;
      description "TRUE if Role is Standby, Active otherwise";
    }
    leaf total-tunnels {
      type uint32;
      description "Total p2p tunnels admitted";
    }
    leaf total-p2mp-tunnels {
      type uint32;
      description "Total p2mp tunnels admitted";
    }
    leaf selected-tunnels {
      type uint32;
      description "Number of tunnels selected";
    }
    leaf bandwidth-units {
      type Bandwidth-unit-enum;
      description "Bandwidth units";
    }
  }

  grouping MPLS-LM-INTERFACE-HW-OOR-INFO {
    description
      "Information about NPU Resources state for the
      link";
    leaf hw-oor-state {
      type Hw-oor-state;
      description
        "The NPU (Network Processor Unit) HW resource
        state";
    }
    leaf hw-oor-timestamp {
      type uint32;
      description "Timestamp when the OOR state last changed";
    }
    leaf hw-o-or-green-recovery-time {
      type uint32;
      units "second";
      description
        "Time Remaining in Green Recovery State (seconds)";
    }

    list hw-o-or-link-statistic {
      max-elements "3";
      description "HW OOR statistics for the link";
      uses TE-HW-OOR-STATS;
    }
  }

  grouping MPLS-LM-INTERFACE-LOCKOUT-INFO {
    description
      "Information about flex LSP lockout info for the
      link";
    leaf is-lockout {
      type boolean;
      description "True if link is locked out";
    }
    leaf lockout-on-timestamp {
      type uint32;
      description "Timestamp when the lockout is set";
    }
    leaf lockout-off-timestamp {
      type uint32;
      description "Timestamp when the lockout is cleared";
    }
  }

  grouping MPLS-LM-INTERFACE-LINK-AREA-INFO {
    description
      "Information about an area to which the link
      belongs";
    leaf area-id {
      type string;
      description "Area id";
    }
    leaf neighbor-id {
      type string;
      description "The interface neighbor id";
    }
    leaf neighbor-address {
      type inet:ipv4-address;
      description "The interface's neighbor's ip address";
    }
    leaf is-neighbor-up {
      type boolean;
      description "TRUE if the neighbor is up";
    }
    leaf igp-metric {
      type uint32;
      description "The link's IGP metric";
    }
  }

  grouping MPLS-TE-DARKBW-SAMPLE-SR {
    description
      "Information about a single Segment Routing
      bandwidth accounting sample";
    leaf timestamp {
      type uint32;
      units "second";
      description "Timestamp in seconds of this sample";
    }
    leaf sr-rate {
      type uint64;
      units "kbit/s";
      description
        "Segment Routing traffic rate measured in
        Kilobits per second in this sample";
    }
  }

  grouping MPLS-TE-DARKBW-HISTORY-SR {
    description "Segment Routing Bandwidth accounting history";

    list sr-active-interval-sample {
      description
        "Segment Routing samples in the current
        application interval";
      uses MPLS-TE-DARKBW-SAMPLE-SR;
    }

    list sr-previous-interval-sample {
      description
        "Segment Routing samples in the previous
        application interval";
      uses MPLS-TE-DARKBW-SAMPLE-SR;
    }
  }

  grouping MPLS-TE-DARKBW-SAMPLE-RSVP {
    description
      "Information about a single RSVP-TE bandwidth
      accounting sample";
    leaf timestamp {
      type uint32;
      units "second";
      description "Timestamp in seconds of this sample";
    }
    leaf total-rate {
      type uint64;
      units "kbit/s";
      description
        "Total traffic rate measured in Kilobits per
        second in this sample";
    }
    leaf rsvp-te-rate {
      type uint64;
      units "kbit/s";
      description
        "RSVP-TE traffic rate measured in Kilobits per
        second in this sample";
    }
    leaf non-rsvp-te-rate {
      type uint64;
      units "kbit/s";
      description
        "Non-RSVP-TE traffic rate measured in Kilobits
        per second in this sample";
    }
  }

  grouping MPLS-TE-DARKBW-HISTORY-RSVP {
    description "RSVP-TE Bandwidth accounting history";

    list rsvp-te-active-interval-sample {
      description
        "RSVP-TE samples in the current application
        interval";
      uses MPLS-TE-DARKBW-SAMPLE-RSVP;
    }

    list rsvp-te-previous-interval-sample {
      description
        "RSVP-TE samples in the previous application
        interval";
      uses MPLS-TE-DARKBW-SAMPLE-RSVP;
    }
  }

  grouping MPLS-TE-DARKBW-BW-UTIL-SR {
    description
      "Information about Segment Routing bandwidth
      utilization in bandwidth accounting";
    leaf sr-bandwidth-utilization {
      type uint64;
      units "kbit/s";
      description
        "Segment Routing bandwidth utilization measured
        in kilobits per second";
    }
    leaf sr-adjusted-bandwidth-utilization {
      type uint64;
      units "kbit/s";
      description
        "Adjusted Segment Routing bandwidth utilization
        measured in kilobits per second";
    }
    leaf sr-enforced-bandwidth-utilization {
      type uint64;
      units "kbit/s";
      description
        "Enforced Segment Routing bandwidth utilization
        measured in kilobits per second";
    }
  }

  grouping MPLS-TE-DARKBW-BW-UTIL-RSVP {
    description
      "Information about RSVP-TE bandwidth utilization
      in bandwidth accounting";
    leaf total-link-bandwidth-utilization {
      type uint64;
      units "kbit/s";
      description
        "Total bandwidth utilization measured in kilobits
        per second";
    }
    leaf rsvp-te-bandwidth-utilization {
      type uint64;
      units "kbit/s";
      description
        "RSVP-TE bandwidth utilization measured in
        kilobits per second";
    }
    leaf non-rsvp-te-bandwidth-utilization {
      type uint64;
      units "kbit/s";
      description
        "Non-RSVP-TE bandwidth utilization measured in
        kilobits per second";
    }
    leaf rsvp-te-adjusted-bandwidth-utilization {
      type uint64;
      units "kbit/s";
      description
        "Adjusted RSVP-TE bandwidth utilization measured
        in kilobits per second";
    }
    leaf rsvp-te-enforced-bandwidth-utilization {
      type uint64;
      units "kbit/s";
      description
        "Enforced RSVP-TE bandwidth utilization measured
        in kilobits per second";
    }
  }

  grouping MPLS-LM-DARKBW-LINK-COMMON-INFO {
    description "Information for bandwidth accounting per link";

    container rsvp-te-bandwidth-utilization {
      description "RSVP-TE Bandwidth utilization information";
      uses MPLS-TE-DARKBW-BW-UTIL-RSVP;
    }

    container sr-bandwidth-utilization {
      description
        "Segment Routing Bandwidth utilization
        information";
      uses MPLS-TE-DARKBW-BW-UTIL-SR;
    }
    leaf is-bandwidth-account-enabled {
      type boolean;
      description "TRUE if bandwidth accounting is enabled";
    }
    leaf application-enforced {
      type boolean;
      description
        "TRUE if bandwidth accounting application is
        enforced";
    }
    leaf collection-type {
      type Bandwidth-accounting-collection;
      description
        "The type of traffic collected for bandwidth
        accounting";
    }
    leaf sample-interval {
      type uint32;
      units "second";
      description
        "Sampling interval in seconds for bandwidth
        accounting stats";
    }
    leaf sample-time-remaining {
      type uint32;
      units "second";
      description
        "This value indicates the number of seconds until
        the next sampling";
    }
    leaf last-sample-collection-timestamp {
      type uint32;
      description "Timestamp for the last sample collection";
    }
    leaf next-sample-collection {
      type uint32;
      description "Timestamp for the next sample collection";
    }
    leaf application-interval {
      type uint32;
      units "second";
      description
        "Application interval in seconds for bandwidth
        accounting stats";
    }
    leaf application-time-remaining {
      type uint32;
      units "second";
      description
        "This value indicates the number of seconds until
        the next application";
    }
    leaf last-application-timestamp {
      type uint32;
      description "Timestamp for the last application";
    }
    leaf next-application {
      type uint32;
      description "Timestamp for the next application";
    }
    leaf adjustment-factor {
      type uint32;
      description
        "This value indicates the adjustment factor
        applied to measured non RSVP-TE bandwidth";
    }
    leaf max-reservable-bandwidth-threshold-are-default {
      type boolean;
      description
        "TRUE if the maximum reservable bandwidth
        flooding thresholds are default";
    }
    leaf up-threshold-max-reservable-bandwidth {
      type uint8;
      description
        "The up threshold for flooding the maximum
        reservable bandwidth";
    }
    leaf down-threshold-max-reservable-bandwidth {
      type uint8;
      description
        "The down threshold for flooding the maximum
        reservable bandwidth";
    }
  }

  grouping MPLS-LM-DARKBW-LINK-INFO {
    description
      "Detail information for bandwidth accounting per
      link";

    container bandwidth-account-common-info {
      description "Common info for bandwidth accounting";
      uses MPLS-LM-DARKBW-LINK-COMMON-INFO;
    }

    container rsvp-te-bandwidth-sample-history {
      description "RSVP-TE Bandwidth samples history";
      uses MPLS-TE-DARKBW-HISTORY-RSVP;
    }

    container sr-bandwidth-sample-history {
      description "Segment Routing Bandwidth samples history";
      uses MPLS-TE-DARKBW-HISTORY-SR;
    }
  }

  grouping MPLS-LM-INTERFACE-LINK-INFO {
    description "IGP and area information of a link";

    container link-common {
      description "The link's common info";
      uses MPLS-LM-COMMON-LINK-INFO;
    }

    container bandwidth-account {
      description "Bandwidth Account info";
      uses MPLS-LM-DARKBW-LINK-INFO;
    }

    container hw-oor {
      description
        "The link's NPU OOR info. This field is NULL for
        platforms that do not support HW-OOR
        notifications";
      uses MPLS-LM-INTERFACE-HW-OOR-INFO;
    }
    leaf reason-not-flooded {
      type string;
      description
        "Reason why link is not flooded
        (area-independent)";
    }
    leaf maximum-reservation-bandwidth-rdm {
      type uint64;
      description "The link's maximum reservable BW in RDM";
    }
    leaf reservable-pool0-bandwidth-rdm {
      type uint64;
      description "The link's reservable pool0 BW in RDM";
    }
    leaf reservable-pool1-bandwidth-rdm {
      type uint64;
      description "The link's reservable pool1 BW in RDM";
    }
    leaf maximum-reservation-bandwidth-mam {
      type uint64;
      description "The link's maximum reservable BW in MAM";
    }
    leaf reservable-pool0-bandwidth-mam {
      type uint64;
      description "The link's reservable pool0 BW in MAM";
    }
    leaf reservable-pool1-bandwidth-mam {
      type uint64;
      description "The link's reservable pool1 BW in MAM";
    }
    leaf link-attributes {
      type uint32;
      description "Deprecated";
    }
    leaf is-attribute-incomplete {
      type boolean;
      description
        "TRUE if one or more affinity definition(s)
        is/are unknown";
    }
    leaf is-name-based-attribute {
      type boolean;
      description
        "TRUE, if name based attribute style is in effect";
    }
    leaf te-metric {
      type uint32;
      description "The link's TE metric";
    }
    leaf is-te-metric-valid {
      type boolean;
      description
        "Flag to indicate whether the link's TE metric is
        a valid value";
    }
    list link-extended-attribute {
      description "The link's extended attribute bit map";
        leaf entry {
                  type uint32;

                  description "The link's extended attribute bit map";
        }
    }
    list link-forwad-ref-value {
      description "Reference bits for undefined affinity names";
        leaf entry {
                  type uint32;

                  description "Reference bits for undefined affinity names";
        }
    }

    list affinity-map {
      description "Affinity map array";
      uses MPLS-TE-AFFINITY-MAP-INFO;
    }

    list areas {
      description "Per-area data";
      uses MPLS-LM-INTERFACE-LINK-AREA-INFO;
    }

    list lockout {
      description "Flex LSP Lockout info";
      uses MPLS-LM-INTERFACE-LOCKOUT-INFO;
    }
  }

  grouping MPLS-LM-INTERFACE-COMMON-INFO {
    description "Global info about links";
    leaf is-role-standby {
      type boolean;
      description "TRUE if Role is Standby, Active otherwise";
    }
    leaf links {
      type uint16;
      description "The number of links";
    }
    leaf maximum-links {
      type uint16;
      description "Maximum number of links supported";
    }
  }

  grouping MPLS-LM-SUMMARY-DARKBW {
    description "Summary information for bandwidth accounting";
    leaf is-bandwidth-account-enabled {
      type boolean;
      description "TRUE if bandwidth accounting is enabled";
    }
    leaf sample-interval {
      type uint32;
      description "Sample interval for bandwidth accounting stats";
    }
    leaf sample-time-remaining {
      type uint32;
      units "second";
      description
        "This value indicates the number of seconds until
        the next sample collection";
    }
    leaf application-interval {
      type uint32;
      description
        "Application interval for bandwidth accounting
        stats";
    }
    leaf application-time-remaining {
      type uint32;
      units "second";
      description
        "This value indicates the number of seconds until
        the next application";
    }
    leaf links-count {
      type uint32;
      description "Total number of links";
    }
    leaf maximum-links {
      type uint32;
      description "Maximum number of links supported";
    }
  }

  grouping MPLS-LM-SUMMARY-AREA-INFO {
    description "Summary information of an area";
    leaf area-id {
      type string;
      description "Area id";
    }
    leaf protocol {
      type Igp-protocol;
      description "Protocol running over the area";
    }
    leaf is-flooded {
      type boolean;
      description "TRUE if flooding occurred in this area";
    }
    leaf is-periodic-flooding-on {
      type boolean;
      description "TRUE if periodic flooding is on";
    }
    leaf periodic-flooding-interval {
      type uint16;
      units "second";
      description "Flooding period in seconds";
    }
    leaf links-flooded {
      type uint16;
      description "Number of flooded links";
    }
    leaf system-id {
      type string;
      description "IGP id of local node";
    }
    leaf local-node-router-id {
      type inet:ipv4-address;
      description "Local router id";
    }
    leaf igp-neighbors {
      type uint16;
      description "Number of IGP neighbors";
    }
  }

  grouping MPLS-LM-SUMMARY-COMMON-INFO {
    description "Summary information for all the areas";

    container bandwidth-account-summary {
      description "Bandwidth account summary";
      uses MPLS-LM-SUMMARY-DARKBW;
    }
    leaf is-role-standby {
      type boolean;
      description "TRUE if Role is Standby, Active otherwise";
    }
    leaf links {
      type uint16;
      description "Total number of links";
    }
    leaf maximum-links {
      type uint16;
      description "Maximum number of links supported";
    }
    leaf is-flooding-enabled {
      type boolean;
      description "TRUE if flooding is enabled";
    }

    list areas-summary {
      description "Summary info for the areas";
      uses MPLS-LM-SUMMARY-AREA-INFO;
    }
  }

  grouping MPLS-TE-BANDWIDTH-ACCOUNT-SAMPLE-SR {
    description
      "Information about a single Segment Routing
      bandwidth accounting sample";
    leaf timestamp-nanosec {
      type uint64;
      units "nanosecond";
      description "Timestamp in nano-seconds of this sample";
    }
    leaf sr-rate {
      type uint64;
      units "kbit/s";
      description
        "Segment Routing traffic rate measured in
        Kilobits per second in this sample";
    }
    leaf sr-packet-rate {
      type uint64;
      units "packet/s";
      description
        "Segment Routing traffic rate measured in packets
        per second in this sample";
    }
  }

  grouping MPLS-TE-BANDWIDTH-ACCOUNT-HISTORY-SR {
    description "Segment Routing bandwidth account history";

    list sr-active-interval-sample {
      description
        "Segment Routing samples in the current
        application interval";
      uses MPLS-TE-BANDWIDTH-ACCOUNT-SAMPLE-SR;
    }

    list sr-previous-interval-sample {
      description
        "Segment Routing samples in the previous
        application interval";
      uses MPLS-TE-BANDWIDTH-ACCOUNT-SAMPLE-SR;
    }
  }

  grouping MPLS-TE-BANDWIDTH-ACCOUNT-SAMPLE-RSVP {
    description
      "Information about a single RSVP-TE bandwidth
      accounting sample";
    leaf timestamp-nanosec {
      type uint64;
      units "nanosecond";
      description "Timestamp in nano-seconds of this sample";
    }
    leaf total-rate {
      type uint64;
      units "kbit/s";
      description
        "Total traffic rate measured in Kilobits per
        second in this sample";
    }
    leaf total-packet-rate {
      type uint64;
      units "packet/s";
      description
        "Total traffic rate measured in packets per
        second in this sample";
    }
    leaf rsvp-te-rate {
      type uint64;
      units "kbit/s";
      description
        "RSVP-TE traffic rate measured in Kilobits per
        second in this sample";
    }
    leaf rsvp-te-packet-rate {
      type uint64;
      units "packet/s";
      description
        "RSVP-TE traffic rate measured in packets per
        second in this sample";
    }
    leaf non-rsvp-te-rate {
      type uint64;
      units "kbit/s";
      description
        "Non-RSVP-TE traffic rate measured in Kilobits
        per second in this sample";
    }
    leaf non-rsvp-te-packet-rate {
      type uint64;
      units "packet/s";
      description
        "Non-RSVP-TE traffic rate measured in packets per
        second in this sample";
    }
  }

  grouping MPLS-TE-BANDWIDTH-ACCOUNT-HISTORY-RSVP {
    description "RSVP-TE bandwidth account history";

    list rsvp-te-active-interval-sample {
      description
        "RSVP-TE samples in the current application
        interval";
      uses MPLS-TE-BANDWIDTH-ACCOUNT-SAMPLE-RSVP;
    }

    list rsvp-te-previous-interval-sample {
      description
        "RSVP-TE samples in the previous application
        interval";
      uses MPLS-TE-BANDWIDTH-ACCOUNT-SAMPLE-RSVP;
    }
  }

  grouping MPLS-TE-BANDWIDTH-ACCOUNT-BW-UTIL-SR {
    description
      "Information about Segment Routing bandwidth
      utilization in bandwidth accounting";
    leaf sr-bandwidth-utilization {
      type uint64;
      units "kbit/s";
      description
        "Segment Routing bandwidth utilization measured
        in kilobits per second";
    }
    leaf sr-adjusted-bandwidth-utilization {
      type uint64;
      units "kbit/s";
      description
        "Adjusted Segment Routing bandwidth utilization
        measured in kilobits per second";
    }
    leaf sr-enforced-bandwidth-utilization {
      type uint64;
      units "kbit/s";
      description
        "Enforced Segment Routing bandwidth utilization
        measured in kilobits per second";
    }
  }

  grouping MPLS-TE-BANDWIDTH-ACCOUNT-BW-UTIL-RSVP {
    description
      "Information about RSVP-TE bandwidth utilization
      in bandwidth accounting";
    leaf total-link-bandwidth-utilization {
      type uint64;
      units "kbit/s";
      description
        "Total bandwidth utilization measured in kilobits
        per second";
    }
    leaf rsvp-te-bandwidth-utilization {
      type uint64;
      units "kbit/s";
      description
        "RSVP-TE bandwidth utilization measured in
        kilobits per second";
    }
    leaf non-rsvp-te-bandwidth-utilization {
      type uint64;
      units "kbit/s";
      description
        "Non-RSVP-TE bandwidth utilization measured in
        kilobits per second";
    }
    leaf rsvp-te-adjusted-bandwidth-utilization {
      type uint64;
      units "kbit/s";
      description
        "Adjusted RSVP-TE bandwidth utilization measured
        in kilobits per second";
    }
    leaf rsvp-te-enforced-bandwidth-utilization {
      type uint64;
      units "kbit/s";
      description
        "Enforced RSVP-TE bandwidth utilization measured
        in kilobits per second";
    }
  }

  grouping MPLS-LM-BANDWIDTH-ACCOUNT-LINK-TELEMETRY-INFO {
    description
      "Telemetry information for bandwidth accounting
      per link";

    container rsvp-te-bandwidth-utilization {
      description "RSVP-TE bandwidth utilization information";
      uses MPLS-TE-BANDWIDTH-ACCOUNT-BW-UTIL-RSVP;
    }

    container sr-bandwidth-utilization {
      description
        "Segment Routing bandwidth utilization
        information";
      uses MPLS-TE-BANDWIDTH-ACCOUNT-BW-UTIL-SR;
    }
    leaf is-bandwidth-account-enabled {
      type boolean;
      description "TRUE if bandwidth accounting is enabled";
    }
    leaf application-enforced {
      type boolean;
      description "TRUE if application is enforced";
    }
    leaf collection-type {
      type Bandwidth-accounting-collection;
      description
        "The type of traffic collected for bandwidth
        accounting";
    }
    leaf sample-time-remaining-timestamp-nanosec {
      type uint64;
      units "nanosecond";
      description
        "This value indicates the number of nano-seconds
        until the next sampling";
    }
    leaf last-sample-collection-timestamp-nanosec {
      type uint64;
      units "nanosecond";
      description
        "Timestamp for the last sample collection in
        nano-seconds";
    }
    leaf next-sample-collection-nanosec {
      type uint64;
      units "nanosecond";
      description
        "Timestamp for the next sample collection in
        nano-seconds";
    }
    leaf application-time-remaining-nanosec {
      type uint64;
      units "nanosecond";
      description
        "This value indicates the number of nano-seconds
        until the next application";
    }
    leaf last-application-timestamp-nanosec {
      type uint64;
      units "nanosecond";
      description
        "Timestamp for the last application in
        nano-seconds";
    }
    leaf next-application-timestamp-nanosec {
      type uint64;
      units "nanosecond";
      description
        "Timestamp for the next application in
        nano-seconds";
    }
    leaf effective-maximum-reservable-bandwidth {
      type uint64;
      description "Maximum reservable bandwidth effective";
    }
  }

  grouping MPLS-LM-BANDWIDTH-ACCOUNT-LINK-TEL-DET-INFO {
    description
      "Detail telemetry bandwidth accounting information
      per link";

    container common-info {
      description "Information for bandwidth accounting telemetry";
      uses MPLS-LM-BANDWIDTH-ACCOUNT-LINK-TELEMETRY-INFO;
    }

    container rsvp-te-sample-history {
      description "History of bandwidth accounting RSVP-TE samples";
      uses MPLS-TE-BANDWIDTH-ACCOUNT-HISTORY-RSVP;
    }

    container sr-sample-history {
      description
        "History of bandwidth accounting Segment Routing
        samples";
      uses MPLS-TE-BANDWIDTH-ACCOUNT-HISTORY-SR;
    }
    leaf link-id {
      type string;
      description "The link's ID";
    }
  }

  grouping MPLS-LM-BW-LINK-BW-POOL-INFO {
    description
      "Information about the bandwidth of a given pool
      and priority";
    leaf hold-priority {
      type uint8;
      description "The BW priority";
    }
    leaf held-amount {
      type uint32;
      description "The held bandwidth";
    }
    leaf total-held-amount {
      type uint32;
      description "The total held bandwidth";
    }
    leaf locked-amount {
      type uint32;
      description "The locked bandwidth";
    }
    leaf total-locked-amount {
      type uint32;
      description "The total locked bandwidth";
    }
  }

  grouping MPLS-LM-BW-LINK-DIR-BW-INFO {
    description "Information about the bandwidth of a given  link.";
    leaf bandwidth-direction {
      type Link-direction-enum;
      description "BW Direction";
    }
    leaf is-admission-method-allocated-bandwidth {
      type boolean;
      description
        "True if the link's admit method is based on
        Allocated BW";
    }
    leaf bandwidth-units {
      type Bandwidth-unit-enum;
      description "Bandwidth units";
    }

    list bandwidth-pool0 {
      max-elements "8";
      description "Pool0 BW info for the different priority levels";
      uses MPLS-LM-BW-LINK-BW-POOL-INFO;
    }

    list bandwidth-pool1 {
      max-elements "8";
      description "Pool1 BW info for the different priority levels";
      uses MPLS-LM-BW-LINK-BW-POOL-INFO;
    }
  }

  grouping MPLS-LM-FLOODED-AREA {
    description "Information for the flooded area";
    leaf flooded-area {
      type string;
      description "The flooded area information";
    }
  }

  grouping MPLS-LM-LINK-FLAGS {
    description "Link properties";
    leaf is-mpls-te-on {
      type boolean;
      description "Deprecated - TRUE if the link is a TE-Link";
    }
    leaf signaling-agent {
      type Signaling-agent-enum;
      description "Deprecated - Signaling agent";
    }
    leaf is-admin-up {
      type boolean;
      description "TRUE if the link is admin up";
    }
  }

  grouping MPLS-LM-INTF-SWITCHING-CAP-INFO {
    description
      "Information about the Interface Switching
      Capability Descriptor (IXCD)";
    leaf key {
      type uint8;
      description "The switching capability descriptor key";
    }
    leaf switching-capability {
      type uint8;
      description "The switching capability";
    }
    leaf encoding {
      type uint8;
      description "The link encoding type";
    }
  }

  grouping MPLS-LM-COMMON-LINK-INFO {
    description "Link information";

    container link-flags {
      description "The link's flags";
      uses MPLS-LM-LINK-FLAGS;
    }
    leaf link-id {
      type string;
      description "The link's id";
    }
    leaf link-address {
      type inet:ipv4-address;
      description "The link's ip address";
    }
    leaf is-unnumbered {
      type boolean;
      description "TRUE if the link is unnumbered";
    }
    leaf has-protection {
      type boolean;
      description "TRUE if the link is protected";
    }
    leaf capability {
      type uint32;
      description "The link's protection capability";
    }
    leaf working-priority {
      type uint32;
      description "The link's working priority";
    }
    leaf resource-provider {
      type Resource-provider;
      description "The link's resource provider";
    }
    leaf is-resource-provider-installed {
      type boolean;
      description "TRUE if the resource provider is installed";
    }
    leaf bandwidth-units {
      type Bandwidth-unit-enum;
      description "The bandwidth units";
    }
    leaf physical-bandwidth {
      type uint64;
      description "The link's physical bandwidth";
    }
    leaf bcm-id {
      type uint16;
      description "Bandwidth Constraints Model ID";
    }
    leaf maximum-reservable-bandwidth {
      type uint64;
      description "The link's maximum reservable BW";
    }
    leaf last-flooded-effective-maximum-reservable-bandwidth {
      type uint64;
      description "Last flooded max reservable bandwidth effective";
    }
    leaf incoming-reservable-bandwidth-percentage {
      type uint8;
      description "Incoming reserved BW in %";
    }
    leaf outgoing-reservable-bandwidth-percentage {
      type uint8;
      description "Outgoing reserved BW in %";
    }
    leaf maximum-reservable-pool0-bandwidth {
      type uint64;
      description "The link's maximum reservable pool0 BW";
    }
    leaf incoming-reservable-pool0-bandwidth-percentage {
      type uint8;
      description "Incoming reserved pool0 BW in %";
    }
    leaf outgoing-reservable-pool0-bandwidth-percentage {
      type uint8;
      description "Outgoing reserved pool0 BW in %";
    }
    leaf maximum-reservable-pool1-bandwidth {
      type uint64;
      description "The link's maximum reservable pool1 BW";
    }
    leaf incoming-reservable-pool1-bandwidth-percentage {
      type uint8;
      description "Incoming reserved pool1 BW in %";
    }
    leaf outgoing-reservable-pool1-bandwidth-percentage {
      type uint8;
      description "Outgoing reserved pool1 BW in %";
    }
    leaf inbound-admission-method {
      type Admission-policy;
      description "Deprecated";
    }
    leaf outbound-admission-method {
      type Admission-policy;
      description "Deprecated";
    }
    leaf igp-neighbors {
      type uint16;
      description "The link's neighbor count";
    }

    list shared-risk-link-group {
      description "The link's shared risk link groups";
      uses MPLS-SRLG-INFO;
    }

    list interface-switching-capability-descriptor {
      description "The link's switching capability descriptor";
      uses MPLS-LM-INTF-SWITCHING-CAP-INFO;
    }

    list flooded-areas {
      description "List of areas into which the link is flooded";
      uses MPLS-LM-FLOODED-AREA;
    }
  }

  grouping MPLS-LM-BW-ALLOC-LINK-INFO {
    description "Bandwidth allocation information for a given link";

    container link-common {
      description "The link's common info";
      uses MPLS-LM-COMMON-LINK-INFO;
    }

    container upstream-bandwidth {
      description "BW info in the upstream direction";
      uses MPLS-LM-BW-LINK-DIR-BW-INFO;
    }

    container downstream-bandwidth {
      description "BW info in the dnstream direction";
      uses MPLS-LM-BW-LINK-DIR-BW-INFO;
    }
    leaf total-bandwidth-descriptors {
      type uint16;
      description "Number of total BW descriptors";
    }
    leaf bandwidth-descriptors {
      type uint16;
      description "Number of BW descriptor for the given pool";
    }
    leaf bandwidth-pool {
      type Bandwidth-type-enum;
      description "type of the BW pool";
    }
    leaf flooding-up-thresholds-are-default {
      type boolean;
      description "TRUE if the up-threshold are default";
    }
    leaf flooding-down-thresholds-are-default {
      type boolean;
      description "TRUE if the down-threshold are default";
    }
    leaf flooding-up-thresholds-are-global {
      type boolean;
      description "TRUE if the up-threshold are global";
    }
    leaf flooding-down-thresholds-are-global {
      type boolean;
      description "TRUE if the down-threshold are global";
    }
    list flooding-up-threshold {
      description "Flooding up-thresholds";
        leaf entry {
                  type uint8;

                  description "Flooding up-thresholds";
        }
    }
    list flooding-down-threshold {
      description "Flooding down-thresholds";
        leaf entry {
                  type uint8;

                  description "Flooding down-thresholds";
        }
    }
  }

  grouping MPLS-LM-BW-ALLOC-COMMON-INFO {
    description "Common information about bandwidth allocation";
    leaf is-role-standby {
      type boolean;
      description "TRUE if Role is Standby, Active otherwise";
    }
    leaf links {
      type uint16;
      description "Number of links";
    }
    leaf bandwidth-hold-time {
      type uint16;
      units "second";
      description "How long to hold the bandwidth (seconds)";
    }
  }

  grouping MPLS-LM-STATS-LINK-INFO {
    description "Statistics for a link";

    container incoming-path-statistics {
      description "Deprecated";
      uses MPLS-LM-STATS-COUNTERS;
    }

    container incoming-reservation-statistics {
      description "Deprecated";
      uses MPLS-LM-STATS-COUNTERS;
    }

    container outgoing-path-statistics {
      description "Deprecated";
      uses MPLS-LM-STATS-COUNTERS;
    }

    container outgoing-reservation-statistics {
      description "Deprecated";
      uses MPLS-LM-STATS-COUNTERS;
    }

    container incoming-path-statistics32-bit {
      description "Incoming PATH counters";
      uses MPLS-LM-STATS-COUNTERS-32-BIT;
    }

    container incoming-reservation-statistics32-bit {
      description "Incoming RESV counters";
      uses MPLS-LM-STATS-COUNTERS-32-BIT;
    }

    container outgoing-path-statistics32-bit {
      description "Outgoing PATH counters";
      uses MPLS-LM-STATS-COUNTERS-32-BIT;
    }

    container outgoing-reservation-statistics32-bit {
      description "Outgoing RESV counters";
      uses MPLS-LM-STATS-COUNTERS-32-BIT;
    }
    leaf interface-name-xr {
      type string;
      description "Link name";
    }
    leaf link-address {
      type inet:ipv4-address;
      description "Link's ip address";
    }
  }

  grouping MPLS-LM-STATS-COUNTERS-32-BIT {
    description "Statistics for Setup and Tear processing (32 bit)";
    leaf setup-requests {
      type uint32;
      description "Setup requests";
    }
    leaf setup-errors {
      type uint32;
      description "Setup errors";
    }
    leaf setup-admits {
      type uint32;
      description "Setup admits";
    }
    leaf setup-rejects {
      type uint32;
      description "Setup rejects";
    }
    leaf tear-requests {
      type uint32;
      description "Tear requests";
    }
    leaf tear-errors {
      type uint32;
      description "Tear errors";
    }
    leaf tear-preempts {
      type uint32;
      description "Tear preempts";
    }
  }

  grouping MPLS-LM-STATS-COUNTERS {
    description
      "DEPRECATED, use of mpls_lm_stats_counters_32_bit
      recommended";
    leaf setup-requests {
      type uint16;
      description "Deprecated";
    }
    leaf setup-errors {
      type uint16;
      description "Deprecated";
    }
    leaf setup-admits {
      type uint16;
      description "Deprecated";
    }
    leaf setup-rejects {
      type uint16;
      description "Deprecated";
    }
    leaf tear-requests {
      type uint16;
      description "Deprecated";
    }
    leaf tear-errors {
      type uint16;
      description "Deprecated";
    }
    leaf tear-preempts {
      type uint16;
      description "Deprecated";
    }
  }

  grouping MPLS-LM-STATS-SUMMARY-INFO {
    description "Statistics for Path and Reservation processing";

    container path-statistics {
      description "Deprecated";
      uses MPLS-LM-STATS-COUNTERS;
    }

    container reservation-statistics {
      description "Deprecated";
      uses MPLS-LM-STATS-COUNTERS;
    }

    container path-statistics32-bit {
      description "Path counters (32-bit)";
      uses MPLS-LM-STATS-COUNTERS-32-BIT;
    }

    container reservation-statistics32-bit {
      description "Reservation counters (32-bit)";
      uses MPLS-LM-STATS-COUNTERS-32-BIT;
    }
    leaf is-role-standby {
      type boolean;
      description "TRUE if Role is Standby, Active otherwise";
    }
  }

  grouping MPLS-LM-ADV-LINK-RESV-BW {
    description "Information about a link bandwidth";
    leaf priority {
      type uint8;
      description "The priority level of this bandwidth";
    }
    leaf pool0-bandwidth {
      type uint32;
      description "The reservable pool0 BW at this priority";
    }
    leaf pool1-bandwidth {
      type uint32;
      description "The reservable pool1 BW at this priority";
    }
  }

  grouping MPLS-LM-ADV-FLOODED-LINK {
    description "Information about a flooded link";

    container odu-link-capabilities {
      description "ODU Link Capabilities";
      uses ODU-LINK-CAPABILITIES;
    }
    leaf link-id {
      type uint16;
      description "The link's id";
    }
    leaf interface-name {
      type string;
      description "The link's interface name";
    }
    leaf link-address {
      type inet:ipv4-address;
      description "The link's IPv4 address";
    }
    leaf subnet-type {
      type Igp-subnet;
      description "The link's subnet type";
    }
    leaf outgoing-interface-id {
      type uint32;
      description "The link's outgoing interface's id";
    }
    leaf is-designated-router {
      type boolean;
      description "TRUE if the link belongs to a desig. router";
    }
    leaf designated-router-igp-id {
      type string;
      description "IGP id of the designated router";
    }
    leaf neighbor-igp-id {
      type string;
      description "The neighbor's IGP id";
    }
    leaf igp-neighbor-address {
      type inet:ipv4-address;
      description "The neighbor's ip address";
    }
    leaf incoming-interface-id {
      type uint32;
      description "The link's incoming interface's id";
    }
    leaf te-metric {
      type uint32;
      description "The link's TE metric";
    }
    leaf igp-metric {
      type uint32;
      description "The link's IGP metric";
    }
    leaf uni-link-delay {
      type uint32;
      description "Unidirectional Link Delay in micro-sec";
    }
    leaf bandwidth-units {
      type Bandwidth-unit-enum;
      description "The link's bandwidth units";
    }
    leaf physical-bandwidth {
      type uint32;
      description "The link's physical BW";
    }
    leaf bcm-id {
      type uint16;
      description "Bandwidth Constraints Model ID";
    }
    leaf link-maximum-reservable-bandwidth {
      type uint32;
      description "The link's maximum reservable BW";
    }
    leaf reservable-pool0-bandwidth {
      type uint32;
      description "The link's reservable pool0 BW";
    }
    leaf reservable-pool1-bandwidth {
      type uint32;
      description "The link's reservable pool1 BW";
    }
    leaf is-receiving-reservable-bandwidth-enabled {
      type boolean;
      description "TRUE if receiving reservable BW is enabled";
    }
    leaf receiving-direction {
      type Link-direction-enum;
      description "Upstream or Downstream";
    }
    leaf is-transmitting-reservable-bandwidth-enabled {
      type boolean;
      description "TRUE if transmitting reservable BW is enabled";
    }
    leaf transmitting-direction {
      type Link-direction-enum;
      description "Upstream or Downstream";
    }
    leaf affinity-attribute-flags {
      type uint32;
      description "Deprecated";
    }
    list extended-affinity-attribute-flag {
      description "The link's extended affinity bits";
        leaf entry {
                  type uint32;

                  description "The link's extended affinity bits";
        }
    }

    list shared-risk-link-group {
      description "The link's shared risk link groups";
      uses MPLS-SRLG-INFO;
    }

    list receiving-reservable-bandwidth {
      max-elements "8";
      description
        "Receiving reservable BW at each priority
        level(priority 0 to priority 7)";
      uses MPLS-LM-ADV-LINK-RESV-BW;
    }

    list transmitting-reservable-bandwidth {
      max-elements "8";
      description
        "Transmitting reservable BW at each priority
        level (priority 0 to priority 7)";
      uses MPLS-LM-ADV-LINK-RESV-BW;
    }
  }

  grouping MPLS-LM-ADV-CONFIGURED-AREA {
    description "The information about an advertized area";
    leaf igp-area-id {
      type string;
      description "The area id";
    }
    leaf protocol {
      type Igp-protocol;
      description "The IGP protocol running over this area";
    }
    leaf system-id {
      type string;
      description "The node's system id";
    }
    leaf router-id {
      type inet:ipv4-address;
      description "The node's router ID";
    }

    list flooded-link {
      description "The array of flooded links in this area";
      uses MPLS-LM-ADV-FLOODED-LINK;
    }
  }

  grouping MPLS-LM-ADVERTISEMENT-INFO {
    description "Information about all the advertized areas";
    leaf flooding-status-message {
      type string;
      description "Flooding status: ready or reason";
    }
    leaf last-flooding-time {
      type uint32;
      units "second";
      description "Time elapsed since last flooding in seconds";
    }
    leaf last-flooding-trigger {
      type Flooding-trigger;
      description "Trigger for last flooding";
    }
    leaf next-flooding-time {
      type uint32;
      units "second";
      description "Time remained for next flooding in seconds";
    }
    leaf ds-te-mode {
      type Rrr-dste-migration-mode;
      description "DS-TE Mode";
    }

    list advertized-areas {
      description "Advertising info for all the IGP areas";
      uses MPLS-LM-ADV-CONFIGURED-AREA;
    }
  }

  grouping MPLS-LM-PREEMPTED-LSP {
    description "Preempted LSP info";
    leaf tunnel-id {
      type uint16;
      description "Tunnel ID";
    }
    leaf lsp-id {
      type uint16;
      description "LSP ID";
    }
    leaf source-address {
      type inet:ipv4-address;
      description "Source";
    }
    leaf destination-address {
      type inet:ipv4-address;
      description "Destination";
    }
    leaf requested-bandwidth {
      type uint64;
      description "The path's requested bandwidth";
    }
    leaf setup-priority {
      type uint8;
      description "The path's setup priority";
    }
    leaf hold-priority {
      type uint8;
      description "The path's hold priority";
    }
    leaf bandwidth-type {
      type uint8;
      description "The path's bandwidth type; 0:BC0, 1:BC1, so on";
    }
    leaf soft-preempted {
      type boolean;
      description "TRUE is the preemption is a soft preemption";
    }
    leaf soft-preemption-timeout {
      type uint16;
      units "second";
      description
        "If the soft preemption is underway, this value
        indicates the number of seconds before hard
        preemption is triggered";
    }
    leaf bandwidth-preempted {
      type boolean;
      description "LSPs bandwidth is already preempted";
    }
    leaf soft-preempted-fr-rrewrite {
      type boolean;
      description "FRR-rewrite is done during soft preemption";
    }
  }

  grouping MPLS-LM-PREEMPTION-EVENT {
    description "Preemption event info";
    leaf tunnel-id {
      type uint16;
      description "Tunnel ID";
    }
    leaf lsp-id {
      type uint16;
      description "LSP ID";
    }
    leaf source-address {
      type inet:ipv4-address;
      description "Source";
    }
    leaf destination-address {
      type inet:ipv4-address;
      description "Destination";
    }
    leaf requested-bandwidth {
      type uint64;
      description "The path's requested bandwidth";
    }
    leaf setup-priority {
      type uint8;
      description "The path's setup priority";
    }
    leaf hold-priority {
      type uint8;
      description "The path's hold priority";
    }
    leaf bandwidth-type {
      type uint8;
      description "The path's bandwidth type; 0:CT0, 1:CT1, so on";
    }
    leaf old-bandwidth-bc0 {
      type uint64;
      description "Old BW for BC0";
    }
    leaf old-bandwidth-bc1 {
      type uint64;
      description "Old BW for BC1";
    }
    leaf new-bandwidth-bc0 {
      type uint64;
      description "New BW for BC0";
    }
    leaf new-bandwidth-bc1 {
      type uint64;
      description "New BW for BC1";
    }
    leaf bandwidth-overshoot0 {
      type uint64;
      description "BW Overshoot for BC0";
    }
    leaf bandwidth-overshoot1 {
      type uint64;
      description "BW Overshoot for BC1";
    }
    leaf interface-name {
      type string;
      description "Interface name";
    }
    leaf event-time {
      type uint32;
      units "second";
      description
        "Event time; seconds elapsed since January 1,
        1970";
    }
    leaf ls-ps {
      type uint16;
      description
        "Number of LSPs (not all may be present in the
        list)";
    }
    leaf soft-preempted-ls-ps {
      type uint16;
      description "Number of LSPs softly preempted";
    }
    leaf soft-preempted-ls-ps-fr-rrewrite {
      type uint16;
      description
        "Number of LSPs softly preempted with traffic
        switched to backup";
    }
    leaf hard-preempted-ls-ps {
      type uint16;
      description "Number of LSPs hardly preempted";
    }
    leaf total-preempted-bandwidth-bc0 {
      type uint64;
      description "Total amount of preempted class 0 bandwidth";
    }
    leaf total-preempted-bandwidth-bc1 {
      type uint64;
      description "Total amount of preempted class 1 bandwidth";
    }
    leaf softly-preempted-bandwidth-bc0 {
      type uint64;
      description "Amount of softly preempted class 0 bandwidth";
    }
    leaf softly-preempted-bandwidth-bc1 {
      type uint64;
      description "Amount of softly preempted class 1 bandwidth";
    }
    leaf soft-preempted-fr-rrewrite-bandwidth-bc0 {
      type uint64;
      description
        "Amount of softly preempted FRR RW class 0
        bandwidth";
    }
    leaf soft-preempted-fr-rrewrite-bandwidth-bc1 {
      type uint64;
      description
        "Amount of softly preempted FRR RW class 1
        bandwidth";
    }
    leaf hard-preempted-bandwidth-bc0 {
      type uint64;
      description "Amount of hard preempted class 0 bandwidth";
    }
    leaf hard-preempted-bandwidth-bc1 {
      type uint64;
      description "Amount of hard preempted class 1 bandwidth";
    }
    leaf tunnels {
      type uint16;
      description "Number of Tunnels";
    }
    leaf soft-preempted-tunnels {
      type uint16;
      description "Number of Tunnels softly preempted";
    }
    leaf soft-preempted-tunnels-fr-rrewrite {
      type uint16;
      description
        "Number of Tunnels softly preempted with traffic
        switched to backup";
    }
    leaf hard-preempted-tunnels {
      type uint16;
      description "Number of Tunnels hardly preempted";
    }

    list lsp {
      description "List of preempted LSPs";
      uses MPLS-LM-PREEMPTED-LSP;
    }
  }

  grouping MPLS-LM-IGP-NBR-INFO {
    description "Neighbor information";
    leaf interface-name {
      type string;
      description
        "The interface on which this neighbor is
        discovered";
    }
    leaf neighbor-id {
      type string;
      description "The neighbor's id";
    }
    leaf area-id {
      type string;
      description "The area id";
    }
    leaf neighbor-address {
      type inet:ipv4-address;
      description "The neighbor's IP address";
    }
  }

  grouping MPLS-LM-IGP-NBRS-LINK-INFO {
    description "Neighbor information based on the link";

    list neighbor {
      description "Neighbors of the specified link id";
      uses MPLS-LM-IGP-NBR-INFO;
    }
  }

  grouping MPLS-TE-AFFINITY-MAP-BAG {
    description "A set of affinity maps";

    list affinity-map-array {
      description "Affinity map array";
      uses MPLS-TE-AFFINITY-MAP-INFO;
    }
  }

  grouping TE-AUTO-TUN-EXP-PATH-HOP {
    description "Auto Tunnel Explicit Path Hop";
    leaf hop-type {
      type Te-auto-tun-exp-path-hop;
      description "Hop Type";
    }
    leaf ipv4-address {
      type inet:ipv4-address;
      description "IPv4 Address";
    }
    leaf mpls-label {
      type uint32;
      description "MPLS Label";
    }
  }

  grouping TE-AUTO-TUN-REQ-EXP-PATH-TUN-INFO {
    description "Auto tunnel request explicit path tunnel info";
    leaf tunnel-id {
      type uint32;
      description "Tunnel ID";
    }
    leaf tunnel-up {
      type boolean;
      description "Tunnel Up";
    }
    leaf ipv6-caps {
      type boolean;
      description "IPv6 Capsulation";
    }
  }

  grouping TE-AUTO-TUN-REQ-EXP-PATH {
    description "Auto Tunnel Explicit Path";

    container tunnel-info {
      description "Auto tunnel info";
      uses TE-AUTO-TUN-REQ-EXP-PATH-TUN-INFO;
    }
    leaf context-id {
      type uint32;
      description "Explicit Path Context ID";
    }
    leaf path-weight {
      type uint32;
      description "Path Weight";
    }
    leaf is-stale {
      type boolean;
      description "Is Stale";
    }
    leaf is-synced {
      type boolean;
      description "Is Synced";
    }
    leaf programmed-in-fib {
      type boolean;
      description "Programmed in FIB";
    }

    list hops {
      description "Path Hops";
      uses TE-AUTO-TUN-EXP-PATH-HOP;
    }
  }

  grouping TE-END-POINT {
    description "TE End Point";
    leaf address-family-type {
      type Mpls-te-afi;
      description "AddressFamilyType";
    }
    leaf ipv4-address {
      when "../address-family-type = 'ipv4-unicast'" {
        description "../AddressFamilyType = 'IPv4Unicast'";
      }
      type inet:ipv4-address;
      description "IPv4 Address";
    }
    leaf ipv6-address {
      when "../address-family-type = 'ipv6-unicast'" {
        description "../AddressFamilyType = 'IPv6Unicast'";
      }
      type In-addr-ipv6;
      description "IPv6 Address";
    }
  }

  grouping TE-SERVICE-SR-POLICY {
    description "Auto Tunnel Request Context";

    container end-point-xr {
      description "End Point";
      uses TE-END-POINT;
    }
    leaf sr-policy-id {
      type uint32;
      description "SR Policy ID";
    }
    leaf policy-active {
      type boolean;
      description "Policy Active";
    }
    leaf client-id-xr {
      type uint32;
      description "Client ID";
    }
    leaf client-name {
      type string;
      description "Client Name";
    }
    leaf color-xr {
      type uint32;
      description "Color";
    }
    leaf distinguisher-xr {
      type uint32;
      description "SR Policy Distinguisher value";
    }
    leaf ipv6-caps {
      type boolean;
      description "IPv6 Capsulation";
    }
    leaf binding-sid-context-id {
      type uint32;
      description "Binding SID Context ID";
    }
    leaf requested-binding-sid {
      type uint32;
      description "Requested Binding SID";
    }
    leaf binding-sid-request-pending {
      type boolean;
      description "Binding SID Request Pending";
    }
    leaf allocated-binding-sid {
      type uint32;
      description "Allocated Binding SID";
    }
    leaf rewrite-request-pending {
      type boolean;
      description "Rewrite Requeste Pending";
    }
    leaf rewrite-done {
      type boolean;
      description "Rewrite Done";
    }
    leaf is-stale {
      type boolean;
      description "Is Stale";
    }
    leaf is-synced {
      type boolean;
      description "Is Synced";
    }
    leaf notify-time {
      type uint32;
      description "Notify Time";
    }
    leaf notify-state-is-active {
      type boolean;
      description "Notify State Is Active";
    }
    leaf creation-time {
      type uint64;
      units "nanosecond";
      description
        "SR policy structure creation timestamp
        (clocktime in nsecs)";
    }

    list explicit-path {
      description "Explicit Paths";
      uses TE-AUTO-TUN-REQ-EXP-PATH;
    }
  }

  grouping MPLS-TE-BFD-SUMMARY {
    description "TE BFD Summary Info";
    leaf tunnel-count-total {
      type uint16;
      description "Total number of tunnel interface";
    }
    leaf tunnel-count-bfd-enabled {
      type uint16;
      description "Number of tunnel interface with BFD enabled";
    }
    leaf tunnel-count-session-up {
      type uint16;
      description "Number of tunnel with BFD session in up state";
    }
    leaf tunnel-count-sbfd-enabled {
      type uint16;
      description "Number of tunnel interface with SBFD enabled";
    }
    leaf tunnel-count-sbfd-session-up {
      type uint16;
      description "Number of tunnel with SBFD session in up state";
    }
    leaf head-lsp-count-session-created {
      type uint16;
      description "Number of head end LSP with BFD session created";
    }
    leaf head-lsp-count-up {
      type uint16;
      description
        "Number of head end LSP with BFD session in up
        state";
    }
    leaf tail-lsp-count-session-created {
      type uint16;
      description "Number of tail end LSP with BFD session created";
    }
    leaf tail-lsp-count-session-up {
      type uint16;
      description
        "Number of tail end LSP with BFD session in up
        state";
    }
    leaf head-lsp-count-sbfd-session-created {
      type uint16;
      description
        "Number of head end LSP with SBFD session created";
    }
    leaf head-lsp-count-sbfd-up {
      type uint16;
      description
        "Number of head end LSP with SBFD session in up
        state";
    }
    leaf link-count-bfd-enabled {
      type uint16;
      description "Number of link with BFD enabled";
    }
    leaf link-count-session-created {
      type uint16;
      description "Number of link with BFD session created";
    }
    leaf link-count-session-up {
      type uint16;
      description "Number of link with BFD session in state Up";
    }
  }

  grouping MPLS-TE-TAIL-BFD-LSP-INFO {
    description "TE Tail End BFDOverLSP Info";

    container lsp-fec {
      description "FEC for the LSP";
      uses TE-LSP-FEC;
    }
    leaf signaled-name {
      type string;
      description "Signaled Name";
    }
    leaf bfd-session-state {
      type Te-bfd-lsp-session-state;
      description "BFD Session State";
    }
  }

  grouping MPLS-TE-HEAD-BFD-LSP-INFO {
    description "TE Head End BFDOverLSP Info";
    leaf lsp-id {
      type uint16;
      description "LSP ID";
    }
    leaf bfd-session-state {
      type Te-bfd-lsp-session-state;
      description "BFD Session State";
    }
  }

  grouping MPLS-TE-HEAD-BFD-VIF-INFO {
    description "TE Head End Tunnel BFD Info";

    container current-lspbfd-info {
      description "Current LSP BFD Info";
      uses MPLS-TE-HEAD-BFD-LSP-INFO;
    }

    container standby-lspbfd-info {
      description "Standby LSP BFD Info";
      uses MPLS-TE-HEAD-BFD-LSP-INFO;
    }

    container reoptimized-lspbfd-info {
      description "Reoptimized LSP BFD Info";
      uses MPLS-TE-HEAD-BFD-LSP-INFO;
    }
    leaf tunnel-name-xr {
      type string;
      description "Tunnel name";
    }
    leaf destination-address {
      type inet:ipv4-address;
      description "Destination Address";
    }
    leaf lspbfd-type {
      type Te-vif-bfd;
      description "LSP BFD type";
    }
  }

  grouping TE-LSP-OOR-STATS {
    description "LSP OOR statistics";
    leaf transitions {
      type uint32;
      description "Number of transitions to this state";
    }
    leaf rejected-ls-ps-number {
      type uint32;
      description "Number of LSPs that were rejected in this state";
    }
    leaf accepted-ls-ps-number {
      type uint32;
      description "Number of LSPs that were accepted in this state";
    }
    leaf accepted-reopt-ls-ps-number {
      type uint32;
      description
        "Number of Reoptimize LSPs that were accepted in
        this state";
    }
    leaf rejected-reopt-ls-ps-number {
      type uint32;
      description
        "Number of Reoptimize LSPs that were rejected in
        this state";
    }
  }

  grouping TE-LSP-OOR-STATE-INFO {
    description "LSP OOR State Information";

    container statistics {
      description "LSP OOR Statistics";
      uses TE-LSP-OOR-STATS;
    }
    leaf lsp-oor-state {
      type Lsp-oor-state;
      description
        "The LSP-OOR state that this information belongs
        to";
    }
    leaf threshold-transit-all {
      type uint32;
      description
        "The number of transit LSPs that triggers OOR
        state transition";
    }
    leaf threshold-transit-unprotected {
      type uint32;
      description
        "The number of unprotected transit LSPs that
        triggers OOR state transition";
    }
    leaf te-metric-penalty {
      type uint32;
      description
        "The TE metric penalty when the link is in this
        LSP OOR state";
    }
    leaf available-bw-percentage {
      type uint32;
      units "percentage";
      description
        "The flooded percentage of available bandwidth
        advertized when the link is in this LSP OOR
        state";
    }
    leaf transition-duration {
      type uint32;
      units "minute";
      description
        "Recovery in minutes after the green LSP OOR
        state is entered.";
    }
    leaf minimum-lsp-bandwidth {
      type uint32;
      description
        "Minimum LSP bandwidth so the LSP is admitted
        when the link is in this LSP OOR state";
    }
    leaf accept-reopt {
      type boolean;
      description
        "Make-before-break is allowed for LSPs
        reoptimizing over the same link in the LSP OOR
        state";
    }
  }

  grouping TE-LSP-OOR-INFO {
    description "LSP OOR parameters for MPLS-TE";
    leaf transit-lsp-total-count {
      type uint32;
      description "Number of all transit LSPs on the router";
    }
    leaf transit-lsp-unprotected-count {
      type uint32;
      description
        "Number of unprotected transit LSPs on the router";
    }
    leaf lsp-oor-state {
      type Lsp-oor-state;
      description "The current LSP OOR state";
    }
    leaf lsp-oor-timestamp {
      type uint32;
      description "Timestamp when the OOR state last changed";
    }
    leaf lsp-oor-green-recovery-time {
      type uint32;
      units "second";
      description
        "Time Remaining in Green Recovery State (seconds)";
    }

    list lsp-oor-state-xr {
      max-elements "3";
      description "Array of LSP OOR info per state";
      uses TE-LSP-OOR-STATE-INFO;
    }
  }

  grouping MPLS-TE-SR-S2L-PATH-BAG {
    description "Segment-Routing S2L path";
    leaf is-primary {
      type boolean;
      description "True if path is primary";
    }
    leaf is-backup {
      type boolean;
      description "True if path is backup";
    }
    leaf outgoing-interface {
      type string;
      description "Outgoing Interface Name";
    }
    leaf path-id {
      type uint32;
      description "Path Identifier";
    }
    leaf backup-path-id {
      type uint32;
      description "Backup Path Identifier";
    }
    leaf next-hop {
      type inet:ipv4-address;
      description "Next hop";
    }
    list outgoing-labels-stack {
      description "Outgoing Labels Stack";
        leaf entry {
                  type uint32;

                  description "Outgoing Labels Stack";
        }
    }
  }

  grouping MPLS-TE-S2L-FORWARDING-S2L-ID-BAG {
    description "S2L Forwarding identifiers";
    leaf destination-address {
      type inet:ipv4-address;
      description "Destination";
    }
    leaf sub-group-id {
      type uint16;
      description "S2L Sub-Group ID";
    }
    leaf sub-group-original-id {
      type inet:ipv4-address;
      description "S2L Sub-Group Originator ID";
    }
  }

  grouping TE-S2L-OUTPUT-RW-FIELDS-BAG {
    description "An entry of output label rewrite data";

    container primary-s2l {
      description "Properties of the S2L rewrite";
      uses TE-S2L-OUTPUT-RW-OUTPUT-INFO-BAG;
    }

    container backup-tunnel-rewrite {
      description "Properties of the S2L's backup tunnel rewrite";
      uses TE-S2L-OUTPUT-RW-OUTPUT-INFO-BAG;
    }
    leaf timestamp {
      type uint32;
      units "second";
      description "Time stamp of the entry (secs since 1/1/70)";
    }
    leaf out-rewrite-role {
      type Mpls-te-tunnel-role;
      description "Role of the associated S2L";
    }
    leaf label {
      type uint32;
      description "Local label of the rewrite";
    }
    leaf backup-active {
      type boolean;
      description "Backup is active";
    }
    leaf s2l-source {
      type inet:ipv4-address;
      description "Source of the S2L";
    }
    leaf explicit-null {
      type Te-s2l-output-rw-explicit-null;
      description "Imposition of explicit NULL";
    }
    leaf protocol-transported {
      type uint16;
      description "Protocol transported in the S2L";
    }
  }

  grouping TE-S2L-OUTPUT-RW-FEC-SUBFAMILY-BAG {
    description "LMRIB S2L Output label rewrite FEC subfamily";

    container lsp-fec {
      description "LSP FEC";
      uses TE-LSP-FEC;
    }
    leaf next-hop-address {
      type inet:ipv4-address;
      description "Next hop address";
    }
    leaf previous-hop-address {
      type inet:ipv4-address;
      description "Previous hop address";
    }
    leaf next-next-hop-address {
      type inet:ipv4-address;
      description "Next Next hop address";
    }
  }

  grouping MPLS-TE-S2L-OUTPUT-RW-BAG {
    description "S2L output rewrite";

    container subfamily {
      description "Subfamily identifiers";
      uses TE-S2L-OUTPUT-RW-FEC-SUBFAMILY-BAG;
    }

    container successful-rewrite {
      description "Successful rewrite details";
      uses TE-S2L-OUTPUT-RW-FIELDS-BAG;
    }

    container failed-rewrite {
      description "Failed rewrite details";
      uses TE-S2L-OUTPUT-RW-FIELDS-BAG;
    }

    container pending-rewrite {
      description "Pending rewrite details";
      uses TE-S2L-OUTPUT-RW-FIELDS-BAG;
    }
  }

  grouping MPLS-TE-S2L-FORWARDING-BAG {
    description "Output label forwarding details for S2Ls";

    container s2l-output-rewrite {
      description "Output rewrite shared between S2Ls";
      uses MPLS-TE-S2L-OUTPUT-RW-BAG;
    }
    leaf original-input-interface {
      type string;
      description "Input interface of the S2Ls";
    }
    leaf output-interface-name {
      type string;
      description "The output interface of the S2Ls";
    }
    leaf backup-tunnel-name {
      type string;
      description "Backup tunnel name";
    }
    leaf is-segment-routing {
      type boolean;
      description "TRUE if the s2l path is Segment-Routing";
    }

    list s2l {
      description
        "Unique identifiers for the S2L sharing the
        rewrite";
      uses MPLS-TE-S2L-FORWARDING-S2L-ID-BAG;
    }

    list s2lsr-path {
      description "Segment-Routing Paths";
      uses MPLS-TE-SR-S2L-PATH-BAG;
    }
  }

  grouping TE-S2L-TUN-RW-FIELDS-P2MP-BAG {
    description "LMRIB Tunnel rewrite fields";
    leaf local-label {
      type uint32;
      description "Local Label";
    }
  }

  grouping TE-S2L-OUTPUT-RW-OUTPUT-INFO-BAG {
    description "Output rewrite tunnel information";
    leaf physica-interface-name {
      type xr:Interface-name;
      description "Physical interface associated with the entry";
    }
    leaf tunnel-interface-name {
      type xr:Interface-name;
      description "Interface handle of the associated tunnel";
    }
    leaf parent-interface-name {
      type xr:Interface-name;
      description "Interface name of the parent intf";
    }
    leaf next-hop-address {
      type inet:ipv4-address;
      description "Next hop address associated with the entry";
    }
    leaf out-label {
      type uint32;
      description "Output label associated with the entry";
    }
    list sr-label-stack {
      description "Segment-Routing labels stack";
        leaf entry {
                  type uint32;

                  description "Segment-Routing labels stack";
        }
    }
  }

  grouping TE-S2L-TUN-RW-FIELDS-P2P-BAG {
    description "LSD Tunnel rewrite fields";

    container primary-s2l {
      description "Properties of the primary S2L of tunnel rewrite";
      uses TE-S2L-OUTPUT-RW-OUTPUT-INFO-BAG;
    }

    container backup-tunnel-rewrite {
      description
        "Properties of the S2L's backup for tunnel
        rewrite";
      uses TE-S2L-OUTPUT-RW-OUTPUT-INFO-BAG;
    }
    leaf local-label {
      type uint32;
      description "Local label of the tunnel rewrite";
    }
    leaf tunnel-id {
      type uint16;
      description "Tunnel ID for this rewrite data";
    }
    leaf source-pe {
      type inet:ipv4-address;
      description "source address of the tunnel";
    }
    leaf destination-address {
      type inet:ipv4-address;
      description "Destination";
    }
    leaf extended-tunnel-id {
      type inet:ipv4-address;
      description "Extended Tunnel ID";
    }
    leaf backup-active {
      type boolean;
      description "FRR is active on the backup tunnel";
    }
    leaf original-input-interface {
      type string;
      description "Input interface of the S2Ls";
    }
    leaf previous-hop-address {
      type inet:ipv4-address;
      description "Previous hop";
    }
    leaf output-interface-name {
      type string;
      description "The output interface of the S2Ls";
    }
    leaf backup-tunnel-name {
      type string;
      description "Backup tunnel name";
    }
  }

  grouping TE-S2L-TUN-RW-FIELD-CTYPE-BAG {
    description "C-type-specific LSP FEC data";

    container p2p-tunnel-rewrite {
      when "../fec-ctype = 'mpls-lib-c-type-ipv4-p2p-tunnel'" {
        description
          "../FEC_CType = 'MPLS_LIB_CTYPE_IPV4_P2P_TUNNEL'";
      }
      description "Tunnel rewrite data specific to P2P";
      uses TE-S2L-TUN-RW-FIELDS-P2P-BAG;
    }

    container p2mp-tunnel-rewrite {
      when "../fec-ctype = 'mpls-lib-c-type-ipv4-p2mp-tunnel'" {
        description
          "../FEC_CType =
          'MPLS_LIB_CTYPE_IPV4_P2MP_TUNNEL'";
      }
      description "Tunnel rewrite data specific to P2MP";
      uses TE-S2L-TUN-RW-FIELDS-P2MP-BAG;
    }
    leaf fec-ctype {
      type Mpls-lib-c;
      description "FEC CType";
    }
  }

  grouping TE-S2L-TUN-RW-FIELDS-BAG {
    description "LMRIB S2L Tunnel rewrite fields";

    container tunnel-rewrite {
      description "Union of p2p and p2mp tun rewrite data";
      uses TE-S2L-TUN-RW-FIELD-CTYPE-BAG;
    }
    leaf timestamp {
      type uint32;
      description "Time stamp of the entry";
    }
  }

  grouping MPLS-TE-S2L-TUN-RW-BAG {
    description "LMRIB S2L Tunnel rewrite";

    container successful-rewrite {
      description "Successful rewrite details";
      uses TE-S2L-TUN-RW-FIELDS-BAG;
    }

    container failed-rewrite {
      description "Failed rewrite details";
      uses TE-S2L-TUN-RW-FIELDS-BAG;
    }

    container pending-rewrite {
      description "Pending rewrite details";
      uses TE-S2L-TUN-RW-FIELDS-BAG;
    }
    leaf tunnel-interface {
      type string;
      description "Tunnel interface name";
    }
    leaf tunnel-signal-name {
      type string;
      description "Tunnel signaled-name";
    }
    leaf is-segment-routing {
      type boolean;
      description "TRUE if the s2l path is Segment-Routing";
    }
  }

  grouping TE-PP-SW-LOG-BAG {
    description
      "The full log of the path protection switchover
      events";
    leaf path-protection-switchovers {
      type uint32;
      description
        "Total number of path protection switchover
        events. This could be more than the entries in
        the array";
    }
    leaf maximum-switchover-millisec {
      type uint32;
      units "millisecond";
      description
        "The maximum delay for a switchover in
        milliseconds";
    }
    leaf average-switchover-millisec {
      type uint32;
      units "millisecond";
      description
        "The average delay for a switchover in
        milliseconds";
    }

    list path-protection-switchover-entry {
      description "The array of path protection switchover entries";
      uses TE-PP-SW-LOG-ENTRY-BAG;
    }
  }

  grouping TUNNEL-MAX-INFO {
    description "Tunnel maximum information bag";
    leaf current-maximum-tunnels {
      type uint32;
      description "Current Maximum Tunnels";
    }
    leaf current-maximum-destinations {
      type uint32;
      description "Current Maximum Destinations";
    }
    leaf current-maximum-p2mp-tunnels {
      type uint32;
      description "Current Maximum P2MP Tunnel Count";
    }
    leaf current-maximum-p2mp-destnation-per-tunnel {
      type uint32;
      description
        "Current Maximum P2MP Destinations Per Tunnel
        Count";
    }
    leaf absolute-maximum {
      type uint32;
      description "Absolute Maximum";
    }
    leaf current-maximum-autobackups {
      type uint32;
      description "Current Maximum Autotunnel Backups Allowed";
    }
    leaf current-maximum-auto-mesh {
      type uint32;
      description "Current Maximum Autotunnel Mesh Allowed";
    }
    leaf current-tunnel-count {
      type uint32;
      description "Current tunnel count";
    }
    leaf current-destination-count {
      type uint32;
      description "Current Destination Count";
    }
    leaf current-p2mp-tunnel-count {
      type uint32;
      description "Current P2MP tunnel count";
    }
    leaf current-p2mp-destnation-per-tunnel-count {
      type uint32;
      description "Current P2MP Destination per tunnel count";
    }
    leaf is-autobackup-range-configured {
      type boolean;
      description "TRUE if the autobackup range is configured";
    }
    leaf current-autobackups {
      type uint32;
      description "Current Autotunnel Backup count";
    }
    leaf is-auto-mesh-range-configured {
      type boolean;
      description "TRUE if the automesh range is configured";
    }
    leaf current-auto-mesh {
      type uint32;
      description "Current Autotunnel Mesh count";
    }
    leaf current-maximum-gmpls-unitunnels {
      type uint32;
      description "Current Maximum GMPLS-UNI Tunnel Count";
    }
    leaf current-gmpls-uni {
      type uint32;
      description "Current GMPLS-UNI tunnel count";
    }
  }

  grouping MPLS-TE-S2L-SR-OUTGOING-FWD-INFO {
    description "Segment-routing outgoing fowarding info";
    leaf lsp-output-interface {
      type string;
      description "Output interface of LSP";
    }
    leaf lsp-output-label {
      type uint32;
      description "Output label of the LSP";
    }
  }

  grouping MPLS-TE-PATH-PROTECTION-LSP {
    description "MPLS TE Path Protected LSP Information";
    leaf lsp-uptime {
      type uint32;
      description "LSP Uptime";
    }
    leaf path-protection-lsp-id {
      type uint32;
      description "LSP ID ";
    }
    leaf lsp-local-label {
      type uint32;
      description "Local label ";
    }
    leaf lsp-output-interface {
      type string;
      description "Output interface of LSP";
    }
    leaf lsp-output-label {
      type uint32;
      description "Output label of the LSP";
    }
    leaf lsp-state {
      type Mpls-te-tunnel-state;
      description "LSP State";
    }

    list srlsp-outgoing-info {
      description "Segment-routing iutgoing info of LSP";
      uses MPLS-TE-S2L-SR-OUTGOING-FWD-INFO;
    }

    list lsp-hop {
      description "Path used by LSP";
      uses RSVP-MGMT-ERO-SUBOBJ;
    }
  }

  grouping MPLS-TE-PATH-PROTECTION {
    description "MPLS TE Path Protected Information";

    container path-protection {
      description "Path Protect Info";
      uses MPLS-TE-PP-INFO;
    }

    container current-lsp {
      description " Current LSP info";
      uses MPLS-TE-PATH-PROTECTION-LSP;
    }

    container standby-lsp {
      description " Standby LSP info";
      uses MPLS-TE-PATH-PROTECTION-LSP;
    }
    leaf is-tunnel-up {
      type boolean;
      description "Tunnel UP";
    }
    leaf source-address {
      type inet:ipv4-address;
      description "Source";
    }
    leaf destination-address {
      type inet:ipv4-address;
      description "Destination";
    }
    leaf extended-tunnel-id {
      type inet:ipv4-address;
      description "Extended Tunnel ID";
    }
  }

  grouping MPLS-TE-AUTOTUN-P2P-INFO {
    description "P2P auto-tunnel summary per client information";
    leaf auto-p2p-tunnel {
      type uint32;
      description "Total number of client P2P auto-tunnels";
    }
    leaf up-auto-p2p-tunnels {
      type uint32;
      description
        "Total number of client P2P auto-tunnels that are
        up";
    }
    leaf down-auto-p2p-tunnels {
      type uint32;
      description
        "Total number of client P2P auto-tunnels that are
        down";
    }
  }

  grouping MPLS-TE-AUTOTUN-P2MP-INFO {
    description "P2MP auto-tunnel summary per client information";
    leaf auto-p2mp-tunnel {
      type uint32;
      description "Total number of client P2MP auto-tunnels";
    }
    leaf auto-p2mp-destinations {
      type uint32;
      description
        "Total number of client P2MP auto-tunnel
        destinations";
    }
    leaf up-auto-p2mp-destinations {
      type uint32;
      description
        "Total number of client P2MP auto-tunnel
        destinations that are up";
    }
    leaf down-auto-p2mp-destinations {
      type uint32;
      description
        "Total number of client P2MP auto-tunnel
        destinations that are down";
    }
    leaf up-auto-p2mp-tunnels {
      type uint32;
      description
        "Total number of client P2MP auto-tunnels that
        are up";
    }
    leaf down-auto-p2mp-tunnels {
      type uint32;
      description
        "Total number of client P2MP auto-tunnels that
        are down";
    }
    leaf frr-auto-p2mp-tunnels {
      type uint32;
      description
        "Total number of client P2MP auto-tunnels that
        are FRR enabled";
    }
  }

  grouping MPLS-TE-AUTOTUN-SVR-INFO {
    description "Auto-tunnel server client summary";

    container p2mp-info {
      description "P2MP info for a client";
      uses MPLS-TE-AUTOTUN-P2MP-INFO;
    }

    container p2p-info {
      description "P2P info for a client";
      uses MPLS-TE-AUTOTUN-P2P-INFO;
    }
    leaf protocol-type {
      type Te-serv-tun-client;
      description "Client's protocol type";
    }
    leaf client-instance-name {
      type string;
      description "Client Instance name";
    }
    leaf client-id {
      type uint32;
      description "Client ID";
    }
  }

  grouping MPLS-TE-AUTOTUN-SVR-SUMMARY-INFO {
    description "Auto-tunnel server summary information";

    container total-auto-p2mp-tunnels {
      description "Total number of P2MP auto-tunnels";
      uses MPLS-TE-AUTOTUN-P2MP-INFO;
    }

    container total-auto-p2p-tunnels {
      description "Total number of P2P auto-tunnels";
      uses MPLS-TE-AUTOTUN-P2P-INFO;
    }

    list clients-summary {
      description "List of auto-tunnel server clients";
      uses MPLS-TE-AUTOTUN-SVR-INFO;
    }
  }

  grouping TE-CONV-TBL-SUMMARY-BAG {
    description "TE tunnels convergence summary information bag";
    leaf tunnel-frr-active-count {
      type uint32;
      description "FRR active Tunnel count";
    }
    leaf tunnel-frr-total-count {
      type uint32;
      description "FRR triggered Tunnel count";
    }
    leaf tunnel-converged-count {
      type uint32;
      description "Tunnel converged count";
    }
    leaf tunnel-total-convergence-complete-time {
      type uint64;
      units "nanosecond";
      description
        "Tunnel convergence complete timestamp (clocktime
        in nsecs)";
    }
  }

  grouping MPLS-TE-GMPLS-NNI-SUMMARY-INFO {
    description "GMPLS-NNI summary information";
    leaf heads-up {
      type uint32;
      description "Tunnel heads in up state";
    }
    leaf heads-down {
      type uint32;
      description "Tunnel heads in down state";
    }
    leaf mids-up {
      type uint32;
      description "Tunnel mids in up state";
    }
    leaf mids-down {
      type uint32;
      description "Tunnel mids in down state";
    }
    leaf tails-up {
      type uint32;
      description "Tunnel tails in up state";
    }
    leaf tails-down {
      type uint32;
      description "Tunnel tails in down state";
    }
  }

  grouping MPLS-TE-GMPLS-UNI-SUMMARY-INFO {
    description "GMPLS-UNI summary information";
    leaf heads-up {
      type uint32;
      description "Tunnel heads in up state";
    }
    leaf heads-down {
      type uint32;
      description "Tunnel heads in down state";
    }
    leaf tails-up {
      type uint32;
      description "Tunnel tails in up state";
    }
    leaf tails-down {
      type uint32;
      description "Tunnel tails in down state";
    }
  }

  grouping MPLS-TE-TUNNELS-SUMMARY-INFO-BAG {
    description "MPLS TE Tunnel Summary Information";

    container autobackup-summary {
      description "Autobackup summary";
      uses MPLS-TE-AUTOTUN-BACKUP-SUMMARY-INFO;
    }

    container auto-mesh-summary {
      description "Automesh summary";
      uses MPLS-TE-AUTOTUN-MESH-SUMMARY-INFO;
    }

    container auto-mesh-one-hop-summary {
      description "Automesh Onehop summary";
      uses MPLS-TE-AUTOTUN-MESH-ONEHOP-SUMMARY-INFO;
    }

    container gmpls-uni-summary {
      description "GMPLS-UNI summary";
      uses MPLS-TE-GMPLS-UNI-SUMMARY-INFO;
    }

    container gmpls-nni-summary {
      description "GMPLS-NNI summary";
      uses MPLS-TE-GMPLS-NNI-SUMMARY-INFO;
    }

    container current-tunnel-convergence-summary {
      description "Current Tunnel convergemce summary information";
      uses TE-CONV-TBL-SUMMARY-BAG;
    }

    container last-tunnel-convergence-summary {
      description "Last Tunnel convergemce summary information";
      uses TE-CONV-TBL-SUMMARY-BAG;
    }

    container auto-tun-server-summary {
      description "Auto-tunnel server tunnel summary";
      uses MPLS-TE-AUTOTUN-SVR-SUMMARY-INFO;
    }
    leaf pcalc-tie-breaker-type {
      type Te-path-selection-tiebreaker;
      description "PCALC tiebreaker type";
    }
    leaf pcalc-tiebreaker {
      type uint32;
      description "Deprecated - replaced by PCALCTiebreakerType";
    }
    leaf tiebreaker-qualifier {
      type Mpls-te-metric-qualifier;
      description
        "Describes how the path selection tiebreaker was
        specified:default, or globally set";
    }
    leaf te-process-status {
      type Mpls-te-tunnels-process-status;
      description "Status of te_control";
    }
    leaf is-rsvp-process-enabled {
      type boolean;
      description "Status of rsvp";
    }
    leaf is-forwarding-enabled {
      type boolean;
      description "TRUE if forwarding is enabled";
    }
    leaf activated-heads {
      type uint32;
      description "Total tunnel heads activated";
    }
    leaf deactivated-heads {
      type uint32;
      description "Total tunnel heads deactivated";
    }
    leaf recovered-heads {
      type uint32;
      description "Number of heads recovered";
    }
    leaf is-periodic-reoptimization-on {
      type boolean;
      description "TRUE if periodic reoptimization is on";
    }
    leaf reoptimization-period {
      type uint32;
      units "second";
      description "Reoptimization period in seconds";
    }
    leaf next-reoptimization-timer {
      type uint32;
      units "second";
      description "Time left till next reoptimization (seconds)";
    }
    leaf auto-bandwidth-tunnels {
      type uint32;
      description "Counter with number of auto-bw enabled tunnels";
    }
    leaf auto-bandwidth-collection-period {
      type uint32;
      units "minute";
      description "Collection period in minutes";
    }
    leaf is-promotion-on {
      type boolean;
      description "TRUE if periodic frr promotion is on";
    }
    leaf promotion-period {
      type uint32;
      units "second";
      description "FRR promotion period in seconds";
    }
    leaf next-promotion-timer {
      type uint32;
      units "second";
      description "Time left till next FRR promotion (seconds)";
    }
    leaf tunnel-check-period {
      type uint32;
      units "second";
      description "Tunnel head check period (seconds)";
    }
    leaf next-check-time {
      type uint32;
      units "second";
      description "Time left till next FRR promotion (seconds)";
    }
    leaf tunnel-verify-period {
      type uint32;
      units "second";
      description "Tunnel head verify period (seconds)";
    }
    leaf next-verify-timer {
      type uint32;
      units "second";
      description "Time left till next FRR promotion (seconds)";
    }
    leaf frr-head-tunnels {
      type uint32;
      description "FRR tunnels in Up state at head end";
    }
    leaf protected-head-tunnels {
      type uint32;
      description "FRR protected tunnels in Up state at head end";
    }
    leaf rerouted-head-tunnels {
      type uint32;
      description "FRR rerouted tunnels in Up state at head end";
    }
    leaf frr-mid-point-tunnels {
      type uint32;
      description "FRR tunnels at mid point";
    }
    leaf protected-mid-point-tunnels {
      type uint32;
      description "FRR protected tunnels at mid point";
    }
    leaf rerouted-mid-point-tunnels {
      type uint32;
      description "FRR rerouted tunnels at mid point";
    }
    leaf link-protected-tunnels {
      type uint32;
      description "FRR link protected tunnels";
    }
    leaf node-protected-tunnels {
      type uint32;
      description "FRR node protected tunnels";
    }
    leaf bw-protected-tunnels {
      type uint32;
      description "FRR BW protected tunnels";
    }
    leaf frr-p2p-head-tunnels {
      type uint32;
      description "P2P FRR tunnels in Up state at head end";
    }
    leaf protected-p2p-head-tunnels {
      type uint32;
      description
        "P2P FRR protected tunnels in Up state at head
        end";
    }
    leaf rerouted-p2p-head-tunnels {
      type uint32;
      description
        "P2P FRR rerouted tunnels in Up state at head end";
    }
    leaf frr-p2p-mid-point-tunnels {
      type uint32;
      description "P2P FRR tunnels at mid point";
    }
    leaf protected-p2p-mid-point-tunnels {
      type uint32;
      description "P2P FRR protected tunnels at mid point";
    }
    leaf rerouted-p2p-mid-point-tunnels {
      type uint32;
      description "P2P FRR rerouted tunnels at mid point";
    }
    leaf link-protected-p2p-tunnels {
      type uint32;
      description "P2P FRR link protected tunnels";
    }
    leaf node-protected-p2p-tunnels {
      type uint32;
      description "P2P FRR node protected tunnels";
    }
    leaf bw-protected-p2p-tunnels {
      type uint32;
      description "P2P FRR BW protected tunnels";
    }
    leaf backup-tunnels {
      type uint32;
      description "FRR backup tunnels in Up state";
    }
    leaf backups-assigned {
      type uint32;
      description "FRR backup tunnels assigned";
    }
    leaf frr-protected-interfaces {
      type uint32;
      description "FRR Protected Interfaces";
    }
    leaf rerouted-interfaces {
      type uint32;
      description "FRR Rerouted Interfaces";
    }
    leaf p2p-head-tunnels {
      type uint32;
      description "p2p Tunnel interfaces";
    }
    leaf up-p2p-head-tunnels {
      type uint32;
      description "p2p Tunnel interfaces in Up state";
    }
    leaf dynamic-up-p2p-head-tunnels {
      type uint32;
      description "p2p Tunnel up via a dynamic path";
    }
    leaf frr-config-p2p-head-tunnels {
      type uint32;
      description "p2p Tunnel interfaces with FRR configuration";
    }
    leaf p2p-head-destinations {
      type uint32;
      description "p2p Destinations at Head";
    }
    leaf p2p-head-destinations-up {
      type uint32;
      description "p2p Destinations in Up state at Head";
    }
    leaf bw-protected-p2p-s2-ls {
      type uint32;
      description "p2p S2Ls BW Protected";
    }
    leaf link-protected-p2p-s2-ls {
      type uint32;
      description "p2p S2Ls Link Protected";
    }
    leaf up-p2p-head-s2-ls {
      type uint32;
      description "p2p S2Ls in Up state at Head";
    }
    leaf proceeding-p2p-head-s2-ls {
      type uint32;
      description "p2p S2Ls in signalling-proceeding state at Head";
    }
    leaf recovering-p2p-head-s2-ls {
      type uint32;
      description "p2p S2Ls recovering at Head";
    }
    leaf frr-p2p-head-s2-ls {
      type uint32;
      description "p2p S2Ls with FRR requested at Head";
    }
    leaf protected-p2p-head-s2-ls {
      type uint32;
      description "p2p S2Ls FRR Protected at Head";
    }
    leaf rerouted-p2p-head-s2-ls {
      type uint32;
      description "p2p S2Ls FRR Rerouted at Head";
    }
    leaf p2p-mid-point-s2-ls {
      type uint32;
      description "p2p S2Ls at Mid";
    }
    leaf up-p2p-mid-point-s2-ls {
      type uint32;
      description "p2p S2Ls in Up state at Mid";
    }
    leaf proceeding-p2p-mid-point-s2-ls {
      type uint32;
      description "p2p S2Ls in signalling=proceeding state at Mid";
    }
    leaf frr-p2p-mid-point-s2-ls {
      type uint32;
      description "p2p S2Ls with FRR requested at Mid";
    }
    leaf protected-p2p-mid-point-s2-ls {
      type uint32;
      description "p2p S2Ls FRR Protected at Mid";
    }
    leaf rerouted-p2p-mid-point-s2-ls {
      type uint32;
      description "p2p S2Ls FRR Rerouted at Mid";
    }
    leaf p2p-tail-s2-ls {
      type uint32;
      description "p2p S2Ls at Tail";
    }
    leaf up-p2p-tail-s2-ls {
      type uint32;
      description "p2p S2Ls in Up state at Tail";
    }
    leaf p2p-tail-tunnels {
      type uint32;
      description "p2p Tunnel tail interfaces";
    }
    leaf path-protect-configured-tunnels {
      type uint16;
      description "Tunnels configured with Path Protect";
    }
    leaf path-protect-configured-tunnels-up {
      type uint16;
      description "Path Protect configured tunnels connected/up";
    }
    leaf path-protect-configured-tunnels-standby-up {
      type uint16;
      description "Tunnels with standby LSP up";
    }
    leaf link-diverse-paths {
      type uint16;
      description "Link diverse paths";
    }
    leaf node-diverse-paths {
      type uint16;
      description "Node diverse paths";
    }
    leaf link-and-node-diverse-paths {
      type uint16;
      description "Link and Node diverse paths";
    }
    leaf user-defined-paths {
      type uint16;
      description "User defined paths";
    }
    leaf p2mp-head-tunnels {
      type uint32;
      description "P2MP Tunnel interfaces";
    }
    leaf up-p2mp-head-tunnels {
      type uint32;
      description "P2MP Tunnel interfaces in Up state";
    }
    leaf frr-config-p2mp-head-tunnels {
      type uint32;
      description "P2MP Tunnel interfaces with FRR configuration";
    }
    leaf p2mp-head-destinations {
      type uint32;
      description "P2MP Destinations at Head";
    }
    leaf up-p2mp-head-destinations {
      type uint32;
      description "P2MP Destinations in Up state at Head";
    }
    leaf bw-protected-p2mp-s2-ls {
      type uint32;
      description "P2MP S2Ls BW Protected";
    }
    leaf link-protected-p2mp-s2-ls {
      type uint32;
      description "P2MP S2Ls Link Protected";
    }
    leaf up-p2mp-head-s2-ls {
      type uint32;
      description "P2MP S2Ls in Up state at Head";
    }
    leaf proceeding-p2mp-head-s2-ls {
      type uint32;
      description
        "P2MP S2Ls in signalling-proceeding state at Head";
    }
    leaf frr-p2mp-head-s2-ls {
      type uint32;
      description "P2MP S2Ls with FRR requested at Head";
    }
    leaf protected-p2mp-head-s2-ls {
      type uint32;
      description "P2MP S2Ls FRR Protected at Head";
    }
    leaf rerouted-p2mp-head-s2-ls {
      type uint32;
      description "P2MP S2Ls FRR Rerouted at Head";
    }
    leaf p2mp-mid-point-s2-ls {
      type uint32;
      description "P2MP S2Ls at Mid";
    }
    leaf up-p2mp-mid-point-s2-ls {
      type uint32;
      description "P2MP S2Ls in Up state at Mid";
    }
    leaf proceeding-p2mp-mid-point-s2-ls {
      type uint32;
      description "P2MP S2Ls in signalling=proceeding state at Mid";
    }
    leaf frr-p2mp-mid-point-s2-ls {
      type uint32;
      description "P2MP S2Ls with FRR requested at Mid";
    }
    leaf protected-p2mp-mid-point-s2-ls {
      type uint32;
      description "P2MP S2Ls FRR Protected at Mid";
    }
    leaf rerouted-p2mp-mid-point-s2-ls {
      type uint32;
      description "P2MP S2Ls FRR Rerouted at Mid";
    }
    leaf p2mp-tail-s2-ls {
      type uint32;
      description "P2MP S2Ls at Tail";
    }
    leaf up-p2mp-tail-s2-ls {
      type uint32;
      description "P2MP S2Ls in Up state at Tail";
    }
    leaf bidir-head-tunnels {
      type uint32;
      description "Bidirectional Head Tunnel interfaces";
    }
    leaf bidir-head-tunnels-up {
      type uint32;
      description "Connected Bidirectional Head Tunnel interfaces";
    }
    leaf bidir-head-tunnels-associated {
      type uint32;
      description "Associated Bidirectional Head Tunnels";
    }
    leaf bidir-head-tunnels-corouted {
      type uint32;
      description "Corouted Bidirectional Head Tunnels";
    }
    leaf bidir-head-ls-ps-up {
      type uint32;
      description "Connected Bidirectional Head Tunnel interfaces";
    }
    leaf bidir-head-ls-ps-proceeding {
      type uint32;
      description "Proceeding Bidirectional Head LSPs";
    }
    leaf bidir-head-ls-ps-associated {
      type uint32;
      description "Associated Bidirectional Head LSPs";
    }
    leaf bidir-head-ls-ps-standby {
      type uint32;
      description "Standby Bidirectional Head LSPs";
    }
    leaf bidir-mid-tunnels {
      type uint32;
      description "Bidirectional Mid Tunnel interfaces";
    }
    leaf bidir-mid-tunnels-up {
      type uint32;
      description "Connected Bidirectional Mid Tunnel interfaces";
    }
    leaf bidir-mid-ls-ps-proceeding {
      type uint32;
      description "Proceeding Bidirectional Mid LSPs";
    }
    leaf bidir-mid-ls-ps-associated {
      type uint32;
      description "Associated Bidirectional Mid LSPs";
    }
    leaf bidir-mid-ls-ps-standby {
      type uint32;
      description "Standby Bidirectional Mid LSPs";
    }
    leaf bidir-tail-ls-ps {
      type uint32;
      description "Bidirectional Tail LSPs";
    }
    leaf bidir-tail-ls-ps-up {
      type uint32;
      description "Connected Bidirectional Tail LSPs";
    }
    leaf bidir-tail-ls-ps-proceeding {
      type uint32;
      description "Proceeding Bidirectional Tail LSPs";
    }
    leaf bidir-tail-ls-ps-associated {
      type uint32;
      description "Associated Bidirectional Tail LSPs";
    }
    leaf bidir-tail-ls-ps-standby {
      type uint32;
      description "Standby Bidirectional Tail LSPs";
    }
    leaf bidir-tail-ls-ps-corouted {
      type uint32;
      description "Corouted Bidirectional Tail LSPs";
    }
  }

  grouping MPLS-TE-TUNNELS-AUTOBW-BRIEF {
    description "MPLS TE Tunnel AutoBandwidth Brief Information";

    container auto-bandwidth-status {
      description "Tunnels's AutoBandwidth Status information";
      uses MPLS-TE-TUNNELS-AUTOBW-STATUS;
    }
    leaf tunnel-name-xr {
      type string;
      description "Tunnel name";
    }
    leaf signaled-name {
      type string;
      description "Tunnel signaled name";
    }
    leaf tunnel-lsp-id {
      type uint32;
      description "Tunnel Lsp Id";
    }
    leaf bandwidth-applications {
      type uint32;
      description
        "Total number of bandwidth applications requested
        by auto-bw";
    }
    leaf last-bandwidth-applied {
      type uint32;
      description
        "Last bandwidth requested by auto-bw for the
        tunnel";
    }
    leaf tunnel-requested-bandwidth {
      type uint32;
      description "Requested Bandwidth for the tunnel";
    }
    leaf signalled-bandwidth {
      type uint32;
      description "Signalled bandwidth for the tunnel";
    }
    leaf highest-bandwidth {
      type uint32;
      description
        "Highest bandwidth registered within current
        application period";
    }
    leaf last-sample-bandwidth {
      type uint32;
      description "Last sample bandwidth collected";
    }
    leaf samples-collected {
      type uint32;
      description
        "Number of samples collected within current
        application period";
    }
    leaf time-left-application {
      type uint32;
      description
        "Time left until next auto-bw application
        algorithm is performed";
    }
  }

  grouping MPLS-TE-FLEX-LSP-REV-LSP {
    description "MPLS TE Flex LSP Reverse LSP information";

    container reverse-lsp-fec {
      description "Reverse Associated Bidir LSP FEC";
      uses TE-LSP-FEC;
    }

    container association {
      description "Association Object";
      uses MPLS-TE-S2L-ASSOCIATION-OBJECT;
    }

    container protection {
      description "Protection Object";
      uses MPLS-TE-S2L-PROTECTION-OBJECT;
    }
    leaf reverse-lsp-present {
      type boolean;
      description "Reverse Associated Bidir LSP Present";
    }
    leaf reverse-lsp-connected {
      type boolean;
      description "Reverse Associated Bidir LSP Connected";
    }
  }

  grouping MPLS-TE-FLEX-LSP-LSP {
    description "MPLS TE FLEX LSP Information";

    container flex-info {
      description "Flex Info";
      uses MPLS-TE-S2L-FLEX-INFO;
    }

    container association {
      description "Association Object";
      uses MPLS-TE-S2L-ASSOCIATION-OBJECT;
    }

    container protection {
      description "Protection Object";
      uses MPLS-TE-S2L-PROTECTION-OBJECT;
    }

    container reverse-lsp {
      description "Reverse LSP information";
      uses MPLS-TE-FLEX-LSP-REV-LSP;
    }
    leaf is-operational {
      type boolean;
      description "Operational";
    }
    leaf lsp-uptime {
      type uint32;
      description "LSP Uptime";
    }
    leaf path-protection-lsp-id {
      type uint32;
      description "LSP ID ";
    }
    leaf lsp-mode {
      type Mpls-te-lsp-mode;
      description "LSP mode";
    }
    leaf lsp-local-label {
      type uint32;
      description "Local label ";
    }
    leaf lsp-output-interface {
      type string;
      description "Output interface of LSP";
    }
    leaf lsp-output-label {
      type uint32;
      description "Output label of the LSP";
    }
    leaf lsp-state {
      type Mpls-te-tunnel-state;
      description "LSP State";
    }

    list lsp-hop {
      description "Path used by LSP";
      uses RSVP-MGMT-ERO-SUBOBJ;
    }
  }

  grouping MPLS-TE-FLEX-LSP {
    description "MPLS TE Flex LSP Information";

    container working-lsp {
      description " Working LSP info";
      uses MPLS-TE-FLEX-LSP-LSP;
    }

    container protect-lsp {
      description " Protect LSP info";
      uses MPLS-TE-FLEX-LSP-LSP;
    }
    leaf is-tunnel-up {
      type boolean;
      description "Tunnel UP";
    }
    leaf tun-id {
      type uint16;
      description "Tunnel ID";
    }
    leaf source-address {
      type inet:ipv4-address;
      description "Source";
    }
    leaf destination-address {
      type inet:ipv4-address;
      description "Destination";
    }
    leaf extended-tunnel-id {
      type inet:ipv4-address;
      description "Extended Tunnel ID";
    }
  }

  grouping MPLS-TE-FASTREROUTE-PROMOTION-BAG {
    description "MPLS TE Fast Reroute Promotion Information";
    leaf promotion-period {
      type uint32;
      units "second";
      description "Promotion period in seconds";
    }
    leaf remaining-time {
      type uint32;
      units "second";
      description "Remaining time for next promotion in seconds";
    }
    leaf is-configured {
      type boolean;
      description "Indicate if periodic promotion is configured ";
    }
  }

  grouping MPLS-TE-FASTREROUTE-PROTECTION-BAG {
    description "MPLS TE Fast Reroute Protected LSP Information";
    leaf source-address-xr {
      type inet:ipv4-address;
      description "Source";
    }
    leaf destination-address-xr {
      type inet:ipv4-address;
      description "Destination";
    }
    leaf tunnel-id-xr {
      type uint32;
      description "Tunnel ID";
    }
    leaf extended-tunnel-id-xr {
      type inet:ipv4-address;
      description "Extended Tunnel ID";
    }
    leaf tunnel-name {
      type string;
      description "Tunnel Name";
    }
    leaf tunnel-instance {
      type uint32;
      description "Tunnel instance";
    }
    leaf role {
      type Mpls-te-tunnel-role;
      description "Role of LSP";
    }
    leaf admin-status {
      type Mpls-te-tunnel-state;
      description "Tunnel Admin status";
    }
    leaf operation-status {
      type Mpls-te-tunnel-state;
      description "Tunnel operational status";
    }
    leaf is-signalled {
      type boolean;
      description "Indicates whether signalled";
    }
    leaf is-frr-requested {
      type boolean;
      description "TRUE if frr protection is on";
    }
    leaf outbound-frr-state {
      type Mpls-te-frr-state;
      description "Indicates outbound FRR state";
    }
    leaf inbound-frr-state {
      type Mpls-te-frr-state;
      description "Indicates inbound FRR state";
    }
    leaf output-interface-lsp {
      type string;
      description "Output intface of the LSP";
    }
    leaf output-label {
      type uint32;
      description "Output label";
    }
    leaf next-hop-address {
      type inet:ipv4-address;
      description "Next hop";
    }
    leaf frr-output-tunnel-interface {
      type string;
      description "FRR output tunnel intface";
    }
    leaf frr-output-label {
      type uint32;
      description "FRR output label";
    }
    leaf backup-status {
      type Mpls-te-backup-status;
      description "Backup status";
    }
    leaf bandwidth-pool-type {
      type Mpls-te-bw-pool;
      description "Bandwidth pool type";
    }
    leaf bandwidth-limit-type {
      type Mpls-te-bw-limit;
      description "Bandwidth limit type";
    }
    leaf original-input-interface {
      type string;
      description "Input intface of the LSP";
    }
    leaf input-label {
      type uint32;
      description "Input label";
    }
    leaf previous-hop-address {
      type inet:ipv4-address;
      description "Previous hop";
    }
    leaf backup-bandwidth {
      type uint32;
      description "Backup bandwidth";
    }
    leaf frr-output-interface {
      type string;
      description "Output interface of bkup tunnel";
    }
    leaf backup-next-hop-address {
      type inet:ipv4-address;
      description "S2L Nexthop of the backup tunnel";
    }
    leaf lsp-bandwidth-type {
      type Mpls-te-bw-pool;
      description "LSP bandwidth type";
    }
    leaf sharing-type {
      type Mpls-te-frr-sharing;
      description "Outgoing i/f Sharing type";
    }
    leaf is-p2mp-tunnel {
      type boolean;
      description "Is P2P or P2MP Tunnel";
    }
    leaf sub-group-original-id {
      type inet:ipv4-address;
      description "S2L Sub-Group Originator ID";
    }
    leaf sub-group-id-xr {
      type uint16;
      description "S2L Sub-Group ID";
    }
    leaf p2mp-id-xr {
      type uint32;
      description "S2L P2MP ID";
    }
  }

  grouping MPLS-TE-FASTREROUTE-BAG {
    description "MPLS TE Fast Reroute Information";
    leaf backup-tunnel-id {
      type uint32;
      description "Backup tunnel ID";
    }
    leaf backup-tunnel-name-xr {
      type string;
      description "Backup tunnel name";
    }
    leaf backup-status {
      type Mpls-te-backup-status;
      description "Backup state";
    }
    leaf backup-type {
      type Mpls-te-backup;
      description "Backup type";
    }
    leaf backup-usage {
      type Mpls-te-backup-usage;
      description "Backup usage";
    }
    leaf prot-interface-autobackup-config {
      type Auto-backup-protection;
      description "Protected interface Autobackup config";
    }
    leaf prot-interface-srlg-config {
      type Auto-backup-srlg-mode;
      description "Protected interface SRLG config";
    }
    leaf tunnel-attribute-set-name {
      type string;
      description "Attribute Set Name";
    }
    leaf has-attribute-set {
      type boolean;
      description
        "TRUE if the auto-backup has an attribute set
        defined";
    }
    leaf is-attribute-set-in-db {
      type boolean;
      description
        "Flag to indicate the existence of attribute set
        found in database";
    }
    leaf recreate-timer-is-running {
      type boolean;
      description "Indicates if the recreate timer is running";
    }
    leaf recreate-remaining-time {
      type uint32;
      units "second";
      description "Time Remaining in Recreate Timer (seconds)";
    }
    leaf source-address {
      type inet:ipv4-address;
      description "Backup's source";
    }
    leaf destination-address {
      type inet:ipv4-address;
      description "Backup's destination";
    }
    leaf general-status {
      type Mpls-te-tunnel-state;
      description "Backup's general status";
    }
    leaf connection-status {
      type Mpls-te-tunnel-state;
      description "Backup's connection's status";
    }
    leaf output-interface-name {
      type string;
      description "The output intf of the tunnel";
    }
    leaf bandwidth-pool-type {
      type Mpls-te-bw-pool;
      description "Bandwidth pool type";
    }
    leaf bandwidth-limit-type {
      type Mpls-te-bw-limit;
      description "Bandwidth limit type";
    }
    leaf bandwidth {
      type uint32;
      units "kbit/s";
      description "Bandwidth (kbps)";
    }
    leaf tunnel-instance {
      type uint32;
      description "Tunnel instance";
    }
    leaf in-use-bandwidth {
      type uint32;
      units "kbit/s";
      description "Bandwidth currently in use (kbps)";
    }
    leaf soft-preempted-in-use-bandwidth {
      type uint32;
      units "kbit/s";
      description
        "Bandwidth soft preempted and rerouted over the
        backup(kbps)";
    }
    leaf ls-ps {
      type uint32;
      description "Number of LSPs";
    }
    leaf s2l-families {
      type uint32;
      description "Number of S2L Families";
    }
    leaf s2-ls {
      type uint32;
      description "Number of P2MP S2Ls";
    }
    leaf frr-active-ls-ps {
      type uint32;
      description "Number of LSPs in FRR active state";
    }
    leaf frr-active-soft-preempted-ls-ps {
      type uint32;
      description
        "Number of soft preempted LSPs routed over backup";
    }
  }

  grouping TE-TUNNEL-AUTOROUTE-DEST {
    description "TE TUNNEL AUTOROUTE DEST";
    leaf prefix-address {
      type inet:ipv4-address;
      description "PrefixAddress";
    }
    leaf prefix-length {
      type uint32;
      description "PrefixLength";
    }
    leaf metric {
      type uint32;
      description "Metric";
    }
    leaf install-time {
      type uint32;
      description "InstallTime";
    }
    leaf interface-handle {
      type xr:Interface-name;
      description "InterfaceHandle";
    }
  }

  grouping TE-TUNNEL-AUTOROUTE-DESTINATIONS {
    description "TE TUNNEL AUTOROUTE DESTINATIONS";
    leaf tunnel-id-xr {
      type uint16;
      description "tunnel id xr";
    }
    leaf tunnel-name {
      type string;
      description "Tunnel name";
    }

    list tunnel-autoroute-dest {
      description "tunnel autoroute dest";
      uses TE-TUNNEL-AUTOROUTE-DEST;
    }
  }

  grouping TE-SYNC-STATUS-MASTER-INFO {
    description "Master Sync status information";

    container idt {
      description "Sync status IDT information";
      uses TE-SYNC-IDT-INFO;
    }
  }

  grouping TE-S2L-PENDING-INFO {
    description "Sync pending S2L information";
    leaf pending-reason {
      type Te-sync-pending-reason;
      description "Pending reason";
    }
    leaf signaled-name {
      type string;
      description "Signaled name";
    }
    leaf s2l-role {
      type Mpls-te-tunnel-role;
      description "S2L role";
    }
  }

  grouping TE-VIF-PENDING-INFO {
    description "Sync pending VIF information";
    leaf pending-reason {
      type Te-sync-pending-reason;
      description "Pending reason";
    }
    leaf tunnel-name {
      type string;
      description "Tunnel name";
    }
  }

  grouping TE-IDT-STATUS {
    description "IDT status information";
    leaf is-ready-status {
      type boolean;
      description "Ready status";
    }
    leaf reason {
      type Te-sync-not-ready-reason;
      description "Not ready reason";
    }
    leaf idt-start-time {
      type uint32;
      units "second";
      description "IDT start timestampe in seconds";
    }
    leaf idt-end-time {
      type uint32;
      units "second";
      description "IDT end timestampe in seconds";
    }
    leaf declare-time {
      type uint32;
      units "second";
      description "Declare ready timestampe in seconds";
    }
    leaf withdraw-time {
      type uint32;
      units "second";
      description "Withdraw ready timestampe in seconds";
    }
  }

  grouping TE-SYNC-IDT-INFO {
    description "Sync Status information";

    container current-idt-info {
      description "Current IDT information";
      uses TE-IDT-STATUS;
    }

    container previous-idt-status {
      description "Previous IDT information";
      uses TE-IDT-STATUS;
    }
  }

  grouping TE-SYNC-STATUS-SLAVE-INFO {
    description "Sync status slave Information";

    container idt {
      description "Sync status IDT information";
      uses TE-SYNC-IDT-INFO;
    }
    leaf insync-tunnels {
      type uint32;
      description "Tunnels in sync";
    }
    leaf insync-sub-ls-ps {
      type uint32;
      description "Sub-LSPs in sync";
    }
    leaf pending-tunnels {
      type uint32;
      description "Tunnels in sync pending";
    }
    leaf pending-sub-ls-ps {
      type uint32;
      description "Sub-LSPs in sync pending";
    }

    list vif-pending {
      description "Pending tunnels details";
      uses TE-VIF-PENDING-INFO;
    }

    list s2l-pending {
      description "Pending sub-LSPs details";
      uses TE-S2L-PENDING-INFO;
    }
  }

  grouping TE-SYNC-STATUS-INFO {
    description
      "Sync information for the NSR and ISSU based on
      master or slave role";

    container slave-sync-information {
      when "../sync-show-type = 'slave-sync-status-show'" {
        description "../SyncShowType = 'SlaveSyncStatusShow'";
      }
      description "Slave sync information";
      uses TE-SYNC-STATUS-SLAVE-INFO;
    }

    container master-sync-information {
      when "../sync-show-type = 'master-sync-status-show'" {
        description "../SyncShowType = 'MasterSyncStatusShow'";
      }
      description "Master sync information";
      uses TE-SYNC-STATUS-MASTER-INFO;
    }
    leaf sync-show-type {
      type Te-sync-status-show;
      description "SyncShowType";
    }
  }

  grouping TE-NSR-ISSU-STATUS-INFO {
    description "NSR/ISSU sync status information";

    container sync-status-information {
      description "Sync information for the NSR and ISSU";
      uses TE-SYNC-STATUS-INFO;
    }
    leaf role {
      type Te-proc-role;
      description "Process role";
    }
  }

  grouping MPLS-TE-DSTE-CLASS {
    description "A DSTE class";
    leaf class-number {
      type uint8;
      description "The DS-TE class number from 0 to 7";
    }
    leaf class-type {
      type uint8;
      description "The class type of the TE class";
    }
    leaf priority {
      type uint8;
      description "The priority of the TE class";
    }
    leaf class-status {
      type Mpls-te-dste-class-status;
      description "The status of the TE class";
    }
  }

  grouping MPLS-TE-DSTE-CLASSES {
    description " A set of DSTE classes";

    list te-class {
      max-elements "8";
      description "te class";
      uses MPLS-TE-DSTE-CLASS;
    }
  }

  grouping MPLS-TE-TOPO-SRLG-LINK {
    description "SRLG link address data";

    container link-address-generic {
      description "Link address";
      uses TE-ADDR;
    }
    leaf link-address {
      type inet:ipv4-address;
      description "Link address";
    }
    leaf te-router-id {
      type inet:ipv4-address;
      description "Link TE router-id";
    }
  }

  grouping MPLS-TE-TOPO-SRLG-AREA {
    description "A MPLS TE topology link in a SRLG";
    leaf igp-type {
      type Igp-protocol;
      description "IGP type";
    }
    leaf igp-instance {
      type string;
      description "IGP Instance name";
    }
    leaf igp-area {
      type uint32;
      description "IGP Area ID";
    }
    leaf igp-area-format {
      type Igp-ospf-area-format;
      description "IGP-area format";
    }

    list srlg-link {
      description "Links in this SRLG/area";
      uses MPLS-TE-TOPO-SRLG-LINK;
    }
  }

  grouping MPLS-TE-TOPO-SRLG {
    description "A SRLG entry in the MPLS TE topology";
    leaf srlg-name {
      type string;
      description "SRLG name";
    }
    leaf admin-weight {
      type uint32;
      description
        "The admin weight that is added to the link if
        the SRLG is shared with the protected link";
    }

    list srlg-areas {
      description "Topology areas in this SRLG";
      uses MPLS-TE-TOPO-SRLG-AREA;
    }
  }

  grouping MPLS-TE-TOPO-CFG-SRLG-LINK {
    description "A link associated with configured SRLG";
    leaf local-address {
      type inet:ipv4-address;
      description "Local address";
    }
    leaf remote-address {
      type inet:ipv4-address;
      description "Remote address";
    }
  }

  grouping MPLS-TE-TOPO-CFG-SRLG {
    description "A configured SRLG entry";
    leaf srlg-number-xr {
      type uint32;
      description "SRLG number";
    }
    leaf srlg-name {
      type string;
      description "SRLG name";
    }
    leaf admin-weight {
      type uint32;
      description
        "The admin weight that is added to the link if
        the SRLG is shared with the protected link";
    }
    leaf is-admin-weight-configured {
      type boolean;
      description
        "Set to TRUE if the admin weight is explicitely
        configured";
    }

    list srlg-link {
      description "Link associated with the SRLG";
      uses MPLS-TE-TOPO-CFG-SRLG-LINK;
    }
  }

  grouping MPLS-TE-TOPOLOGY-PATH-BAG {
    description "MPLS TE Topology Path Information";

    container affinity {
      description "Affinity";
      uses MPLS-TE-TUNNELS-AFFINITY-INFO;
    }
    leaf tunnel-id-xr {
      type uint32;
      description "The tunnel ID to which this path belong";
    }
    leaf destination-address-xr {
      type inet:ipv4-address;
      description "The path's destination";
    }
    leaf is-partial-path {
      type boolean;
      description "TRUE if path is partial";
    }
    leaf is-full-path {
      type boolean;
      description "TRUE if path is full";
    }
    leaf is-topology-checked {
      type boolean;
      description "TRUE if checking the topology is enabled";
    }
    leaf is-segment-routing-db-checked {
      type boolean;
      description
        "TRUE if checking the Segment-Routing DB is
        enabled";
    }
    leaf requested-bandwidth {
      type uint64;
      description "The path's requested bandwidth";
    }
    leaf bandwidth-type {
      type uint64;
      description "The path's bandwidth type";
    }
    leaf mininum-bandwidth {
      type uint64;
      description "The path's minimum bandwidth";
    }
    leaf accumulated-admin-weight {
      type uint64;
      description "The path's accumulated admin weight";
    }
    leaf setup-priority-xr {
      type uint32;
      description "The path's setup priority";
    }
    leaf hold-priority-xr {
      type uint32;
      description "The path's hold priority";
    }
    leaf node-hop-count {
      type uint8;
      description "Path hop count";
    }
    leaf exclude-srlg-address {
      type inet:ipv4-address;
      description "The Exclude SRLG IP Addr";
    }
    list hop {
      description "The path's array of hops";
        leaf entry {
                  type inet:ipv4-address;

                  description "The path's array of hops";
        }
    }

    list shared-risk-link-group {
      description "The path's excluded srlg groups";
      uses MPLS-SRLG-INFO;
    }

    list sr-segment {
      description "The path's array of Segment-Routing segments";
      uses TE-S2L-SR-PATH-HOP;
    }
  }

  grouping MPLS-TE-AREA-INFO {
    description "Global information for an MPLS-TE area";

    container local-sid-and-srbg {
      description "Local SID and SRBG";
      uses TE-SR-NODE-INFO;
    }
    leaf protocol {
      type Igp-protocol;
      description "Protocol used";
    }
    leaf node-id {
      type string;
      description "The node's IGP id";
    }
    leaf area-id {
      type string;
      description "The area's id";
    }
  }

  grouping MPLS-TE-TOPOLOGY-GLOBAL-INFO-BAG {
    description "MPLS TE Topology Global Information";
    leaf hold-down-interval {
      type uint32;
      units "second";
      description
        "Interval in seconds to hold down a neighbor
        after a signalling error";
    }
    leaf link-add-remove-count {
      type uint32;
      description "Link add/remove counter";
    }
    leaf local-model-id {
      type uint32;
      description "Local BC Model ID";
    }

    list areas {
      description "Information for areas";
      uses MPLS-TE-AREA-INFO;
    }
  }

  grouping MPLS-TE-LSP-WRAP-PROTECTION-BAG {
    description "MPLS TE LSP Wrap Protected LSP Information";
    leaf source-address-xr {
      type inet:ipv4-address;
      description "Source";
    }
    leaf destination-address-xr {
      type inet:ipv4-address;
      description "Destination";
    }
    leaf tunnel-id-xr {
      type uint16;
      description "Tunnel ID";
    }
    leaf extended-tunnel-id-xr {
      type inet:ipv4-address;
      description "Extended Tunnel ID";
    }
    leaf tunnel-name {
      type string;
      description "Tunnel Name";
    }
    leaf tunnel-instance {
      type uint32;
      description "Tunnel instance";
    }
    leaf lsp-wrap-protection-enable {
      type boolean;
      description "LSP Wrap protection enabled";
    }
    leaf lsp-wrap-protection-label {
      type uint32;
      description "LSP Wrap Merge Point Label";
    }
    leaf reverse-egress-interface {
      type string;
      description "Reverse Egress Interface";
    }
    leaf reverse-lsp-label {
      type uint32;
      description "Reverse LSP label";
    }
    leaf lsp-wrap-protection-state {
      type Mpls-te-lsp-wrap-state;
      description "LSP wrap protection state";
    }
    leaf sub-group-original-id {
      type inet:ipv4-address;
      description "S2L Sub-Group Originator ID";
    }
    leaf sub-group-id-xr {
      type uint16;
      description "S2L Sub-Group ID";
    }
    leaf p2mp-id-xr {
      type uint32;
      description "S2L P2MP ID";
    }
  }

  grouping TE-NEXTHOP-PATH {
    description "TE NEXTHOP PATH";
    leaf interface {
      type xr:Interface-name;
      description "Interface";
    }
    leaf address {
      type inet:ipv4-address;
      description "Address";
    }
    leaf abr-address {
      type inet:ipv4-address;
      description "ABRAddress";
    }
  }

  grouping TE-RIB-ROUTE-BAG {
    description "TE RIB ROUTE BAG";
    leaf route-protocol-name {
      type string;
      description "RouteProtocolName";
    }
    leaf route-distance {
      type uint32;
      description "RouteDistance";
    }
    leaf route-metric {
      type uint32;
      description "RouteMetric";
    }
    leaf last-update-time {
      type uint32;
      description "LastUpdateTime";
    }
    leaf is-registered {
      type boolean;
      description "IsRegistered";
    }
    leaf is-stale {
      type boolean;
      description "IsStale";
    }
    leaf is-default {
      type boolean;
      description "IsDefault";
    }
    leaf is-connected {
      type boolean;
      description "IsConnected";
    }
    leaf is-populated {
      type boolean;
      description "IsPopulated";
    }
    leaf route-type {
      type uint16;
      description "RouteType";
    }

    list next-hop-path {
      description "next hop path";
      uses TE-NEXTHOP-PATH;
    }
  }

  grouping TE-TUNNEL-PATH {
    description "TE TUNNEL PATH";
    leaf tunnel-id {
      type uint16;
      description "TunnelID";
    }
    leaf interface-handle {
      type xr:Interface-name;
      description "InterfaceHandle";
    }
    leaf install-time {
      type uint32;
      description "InstallTime";
    }
    leaf installed-metric {
      type uint32;
      description "InstalledMetric";
    }
  }

  grouping TE-NEXTHOP-ROUTE {
    description "TE NEXTHOP ROUTE";

    container active-route {
      description "active route";
      uses TE-RIB-ROUTE-BAG;
    }

    container backup-route {
      description "backup route";
      uses TE-RIB-ROUTE-BAG;
    }
    leaf prefix-address-xr {
      type inet:ipv4-address;
      description "prefix address xr";
    }
    leaf prefix-length-xr {
      type uint32;
      description "prefix length xr";
    }
    leaf exact-match {
      type boolean;
      description "ExactMatch";
    }
    leaf create-time {
      type uint32;
      description "CreateTime";
    }
    leaf last-used-time {
      type uint32;
      description "LastUsedTime";
    }
    leaf expire-time {
      type uint32;
      description "ExpireTime";
    }
    leaf installed-tunnel-path-num {
      type uint32;
      description "InstalledTunnelPathNum";
    }

    list tunnel-path {
      description "tunnel path";
      uses TE-TUNNEL-PATH;
    }
  }

  grouping TE-SH-IGP-AREA-STATS {
    description "Statistics for an IGP-area";
    leaf area-adjacency-request-messages {
      type uint32;
      description "Number of adjacency request messages sent";
    }
    leaf area-adjacency-announce-messages {
      type uint32;
      description
        "Number of adjacency announcement messages
        received";
    }
    leaf area-flood-messages {
      type uint32;
      description "Number of local LSA floods sent";
    }
    leaf area-lsa-announce-messages {
      type uint32;
      description "Number of LSA announcement messages received";
    }
    leaf area-lsa-fragment-announce-messages {
      type uint32;
      description
        "Number of LSA fragment announcement messages
        received";
    }
    leaf area-lsa-delete-messages {
      type uint32;
      description "Number of LSA delete messages received";
    }
    leaf area-lsa-fragment-delete-messages {
      type uint32;
      description "Number of LSA fragment delete messages received";
    }
    leaf area-tunnel-announce-messages {
      type uint32;
      description "Number of tunnel announcement messages sent";
    }
  }

  grouping TE-SH-IGP-AREA-ACTIVE {
    description "Data relating to an active IGP area";

    container area-statistics {
      description "Area communication statistics";
      uses TE-SH-IGP-AREA-STATS;
    }
    leaf interfaces-count {
      type uint32;
      description "Number of interfaces running over this area";
    }
    leaf link-idt-received {
      type boolean;
      description
        "Flag to indicate IDT for link adjacencies was
        received";
    }
    leaf topology-idt-received {
      type boolean;
      description "Flag to indicate IDT topology was received";
    }
    leaf sr-strict {
      type boolean;
      description "Flag to indicate if the area is SR strict";
    }
    leaf p2p-heads-count {
      type uint32;
      description
        "Number of p2p tunnel heads whose path was
        calculated over this area";
    }
    leaf p2p-autoroute-announced-count {
      type uint32;
      description
        "Number of p2p tunnel heads which have been
        autoroute-announced into this area";
    }
    leaf p2p-forwarding-adjacency-count {
      type uint32;
      description
        "Number of p2p tunnel heads which have been
        announced as forwarding adjacencies in this area";
    }
    leaf p2mp-destination-count {
      type uint32;
      description
        "Number of P2MP destinations whose path was
        calculated over this area";
    }
    leaf tunnel-loose-hops {
      type uint32;
      description
        "Number of tunnels with a loose hop ERO expanded
        in this area";
    }
  }

  grouping TE-SH-IGP-AREA {
    description "An IGP area";

    container active-data {
      description "Data which applies only to an active area";
      uses TE-SH-IGP-AREA-ACTIVE;
    }
    leaf area-index {
      type uint32;
      description "Internal area index";
    }
    leaf area-number {
      type uint32;
      description "Area number";
    }
    leaf area-format {
      type Igp-ospf-area-format;
      description "IGP Area Format";
    }
    leaf is-config-ready {
      type boolean;
      description
        "Indicates whether or not the area is correctly
        configured under the IGP submode to run TE";
    }
  }

  grouping TE-SH-IGP {
    description "An IGP instance";
    leaf igp-type {
      type Igp-protocol;
      description "IGP type";
    }
    leaf instance-name {
      type string;
      description " The IGP instance name";
    }
    leaf igp-system-id {
      type string;
      description
        " The IGP instance's system/router-id; interpret
        appropriately depending on IGP type";
    }
    leaf configured-te-router-id {
      type inet:ipv4-address;
      description "Configured TE router-id";
    }
    leaf global-router-id {
      type inet:ipv4-address;
      description "Global router-id";
    }
    leaf globall-router-id-optical {
      type inet:ipv4-address;
      description "Global router-id for GMPLS (optical TE)";
    }
    leaf in-use-te-router-id {
      type inet:ipv4-address;
      description "TE router-id in use";
    }
    leaf is-connection-up {
      type boolean;
      description
        "Flag to indicate whether the IGP connection is
        open or not";
    }
    leaf connection-up-count {
      type uint32;
      description "Number of times IGP connection has gone up";
    }
    leaf connection-down-count {
      type uint32;
      description "Number of times IGP connection has gone down";
    }
    list secondary-router-id {
      description "Secondary router-ids";
        leaf entry {
                  type inet:ipv4-address;

                  description "Secondary router-ids";
        }
    }

    list area {
      description "IGP area information";
      uses TE-SH-IGP-AREA;
    }
  }

  grouping MPLS-TE-FWD-ADJ-INFO {
    description "A forwarding-adjacency";
    leaf tunnel-name {
      type string;
      description "The tunnel name";
    }
    leaf traffic-share {
      type uint32;
      description "Traffic Share";
    }
    leaf hold-time {
      type uint32;
      units "second";
      description "Hold time in seconds";
    }
    leaf is-adjacency-up {
      type boolean;
      description "True if adj is up";
    }

    list ig-ps {
      description "List of IGPs to which it is announced";
      uses MPLS-TE-AREA-AFI-INFO;
    }
  }

  grouping MPLS-TE-FWD-ADJ-BAG {
    description " A list of forwarding-adjacencies";
    leaf adjacencies {
      type uint32;
      description "Number of Forwarding Adjacencies";
    }
    leaf ipv6-adjacencies {
      type uint32;
      description "Number of IPv6 Forwarding Adjacencies";
    }
    leaf destination-address-xr {
      type inet:ipv4-address;
      description "The tunnel destination";
    }

    list forward-adjacency {
      description "Forwarding-adjacency list";
      uses MPLS-TE-FWD-ADJ-INFO;
    }
  }

  grouping MPLS-TE-AUTOTUN-BACKUP-CONFIG-INFO {
    description
      "Auto-tunnel backup feature configuration
      information";
    leaf is-configured {
      type boolean;
      description
        "Indicate if auto-tunnel bacukp feature is
        configured ";
    }
    leaf interface-count {
      type uint32;
      description
        "Number of TE link interfaces with auto-tunnel
        backup configured";
    }
    leaf unused-removal-timeout-configured {
      type uint32;
      units "second";
      description
        "Configured value of unused removal timer in
        seconds";
    }
    leaf min-tunnel-id {
      type uint16;
      description "Lower bound of configured tunnel ID range";
    }
    leaf max-tunnel-id {
      type uint16;
      description "Upper bound of configured tunnel ID range";
    }
  }

  grouping MPLS-TE-AUTOTUN-BACKUP-SUMMARY-INFO {
    description "Autotunnel backup summary information";
    leaf autobackups {
      type uint32;
      description "Total number of autobackup tunnels";
    }
    leaf up-autobackups {
      type uint32;
      description "Total number of autobackup tunnels that are up";
    }
    leaf down-autobackups {
      type uint32;
      description
        "Total number of autobackup tunnels that are down";
    }
    leaf unused-autobackups {
      type uint32;
      description
        "Total number of autobackup tunnels that are
        unused";
    }
    leaf next-hop-autobackups {
      type uint32;
      description
        "Total number of autobackup tunnels that are NHOP";
    }
    leaf next-next-hop-autobackups {
      type uint32;
      description
        "Total number of autobackup tunnels that are
        NNHOP";
    }
    leaf srlg-strict-autobackups {
      type uint32;
      description
        "Total number of autobackup tunnels that are
        using SRLG strict";
    }
    leaf srlg-preferred-autobackups {
      type uint32;
      description
        "Total number of autobackup tunnels that are
        using SRLG preferred";
    }
    leaf srlg-weighted-autobackups {
      type uint32;
      description
        "Total number of autobackup tunnels that are
        using weighted SRLG";
    }
    leaf next-hop-autobackup-protected-ls-ps {
      type uint32;
      description
        "Total number of autobackup protected LSPs with
        NHOP and no SRLG";
    }
    leaf next-next-hop-autobackup-protected-ls-ps {
      type uint32;
      description
        "Total number of autobackup protected LSPs with
        NNHOP and no SRLG";
    }
    leaf next-hop-srlg-autobackup-protected-ls-ps {
      type uint32;
      description
        "Total number of autobackup protected LSPs with
        NHOP and SRLG";
    }
    leaf next-next-hop-srlg-autobackup-protected-ls-ps {
      type uint32;
      description
        "Total number of autobackup protected LSPs with
        NNHOP and SRLG";
    }
    leaf next-hop-autobackup-protected-s2l-families {
      type uint32;
      description
        "Total number of autobackup protected S2L
        Families with NHOP and no SRLG";
    }
    leaf next-next-hop-autobackup-protected-s2l-families {
      type uint32;
      description
        "Total number of autobackup protected S2L
        Families with NNHOP and no SRLG";
    }
    leaf next-hop-srlg-autobackup-protected-s2l-families {
      type uint32;
      description
        "Total number of autobackup protected S2L
        Families with NHOP and SRLG";
    }
    leaf next-next-hop-srlg-autobackup-protected-s2l-families {
      type uint32;
      description
        "Total number of autobackup protected S2L
        Families with NNHOP and SRLG";
    }
    leaf next-hop-autobackup-protected-s2-ls {
      type uint32;
      description
        "Total number of autobackup protected S2Ls with
        NHOP and no SRLG";
    }
    leaf next-next-hop-autobackup-protected-s2-ls {
      type uint32;
      description
        "Total number of autobackup protected S2Ls with
        NNHOP and no SRLG";
    }
    leaf next-hop-srlg-autobackup-protected-s2-ls {
      type uint32;
      description
        "Total number of autobackup protected S2Ls with
        NHOP and SRLG";
    }
    leaf next-next-hop-srlg-autobackup-protected-s2-ls {
      type uint32;
      description
        "Total number of autobackup protected S2Ls with
        NNHOP and SRLG";
    }
  }

  grouping MPLS-TE-AUTOTUN-BACKUP-TUNNEL-INFO {
    description "Auto-tunnel backup brief tunnel information";
    leaf tunnel-name {
      type string;
      description "Tunnel Name";
    }
    leaf operational-status {
      type Mpls-te-tunnel-state;
      description "Tunnel operational status";
    }
    leaf srlg-mode {
      type Auto-backup-srlg-mode;
      description "SRLG exclude mode for this auto-tunnel backup";
    }
    leaf atb-protection-type {
      type Auto-backup-protection;
      description
        "Type of protection offered by this auto-tunnel
        backup";
    }
    leaf protected-flows {
      type uint32;
      description "Number of protected flows";
    }
    leaf protected-interface-name {
      type string;
      description "Interface protected by this auto-tunnel backup";
    }
    leaf protected-router-id {
      type inet:ipv4-address;
      description
        "Router ID of node protected by this auto-tunnel
        backup";
    }
  }

  grouping MPLS-TE-AUTOTUN-MESH-ONEHOP-SUMMARY-INFO {
    description "Autotunnel mesh onehop summary information";
    leaf auto-mesh-one-hop-tunnels {
      type uint32;
      description "Total number of automesh onehop tunnels";
    }
    leaf up-auto-mesh-one-hop-tunnels {
      type uint32;
      description
        "Total number of automesh onehop tunnels that are
        up";
    }
    leaf down-auto-mesh-one-hop-tunnels {
      type uint32;
      description
        "Total number of automesh onehop tunnels that are
        down";
    }
    leaf frr-auto-mesh-tunnels {
      type uint32;
      description
        "Total number of automesh onehop tunnels that are
        FRR enabled";
    }
    leaf auto-mesh-one-hop-groups {
      type uint32;
      description "Total number of automesh onehop mesh-groups";
    }
    leaf auto-mesh-one-hop-destinations {
      type uint32;
      description "Total number of automesh onehop destinations";
    }
  }

  grouping MPLS-TE-AUTOMESH-ONEHOP-TUNNEL {
    description "TE Automesh Onehop Tunnel";
    leaf tunnel-id {
      type uint16;
      description "Tunnel ID";
    }
    leaf destination-address {
      type inet:ipv4-address;
      description "Destination Address";
    }
    leaf tunnel-lspid {
      type uint16;
      description "LSP ID";
    }
    leaf mesh-group-id {
      type uint32;
      description "Meshgroup ID";
    }
    leaf tunnel-state {
      type Mpls-te-tunnel-state;
      description "Tunnel state";
    }
  }

  grouping MPLS-TE-AUTOMESH-ONEHOP-INTERFACE {
    description "TE Automesh Onehop Interface";
    leaf interface-name-xr {
      type string;
      description "Interface name";
    }

    list tunnel {
      description "Onehop tunnels created for this interface";
      uses MPLS-TE-AUTOMESH-ONEHOP-TUNNEL;
    }
  }

  grouping MPLS-TE-AUTOTUN-MESH-CONFIG-INFO {
    description
      "Auto-tunnel mesh feature configuration
      information";
    leaf is-configured {
      type boolean;
      description
        "Indicate if auto-tunnel mesh feature is
        configured ";
    }
    leaf unused-removal-timeout-configured {
      type uint32;
      units "second";
      description
        "Configured value of unused removal timer in
        seconds";
    }
    leaf min-tunnel-id {
      type uint16;
      description "Lower bound of configured tunnel ID range";
    }
    leaf max-tunnel-id {
      type uint16;
      description "Upper bound of configured tunnel ID range";
    }
  }

  grouping MPLS-TE-AUTOTUN-MESH-SUMMARY-INFO {
    description "Autotunnel mesh summary information";
    leaf auto-mesh-tunnels {
      type uint32;
      description "Total number of automesh tunnels";
    }
    leaf up-auto-mesh-tunnels {
      type uint32;
      description "Total number of automesh tunnels that are up";
    }
    leaf down-auto-mesh-tunnels {
      type uint32;
      description "Total number of automesh tunnels that are down";
    }
    leaf frr-auto-mesh-tunnels {
      type uint32;
      description
        "Total number of automesh tunnels that are FRR
        enabled";
    }
    leaf auto-mesh-groups {
      type uint32;
      description "Total number of automesh mesh-groups";
    }
    leaf auto-mesh-destinations {
      type uint32;
      description "Total number of automesh destinations";
    }
  }

  grouping MPLS-TE-MESHGROUP-DEST {
    description "TE Meshgroup destination info";
    leaf destination-address {
      type inet:ipv4-address;
      description "Destination address";
    }
    leaf tunnel-id {
      type uint16;
      description "Tunnel ID";
    }
    leaf operational-status {
      type Mpls-te-tunnel-state;
      description "Tunnel operational status";
    }
    leaf remaining-time {
      type uint32;
      units "second";
      description "Remaining time for unused timer in seconds";
    }
  }

  grouping MPLS-TE-MESHGROUP {
    description "TE Meshgroup info";
    leaf mesh-group-id-xr {
      type uint32;
      description "Meshgroup ID";
    }
    leaf is-meshgroup-disabled {
      type boolean;
      description "Is the meshgroup disabled";
    }
    leaf attribute-set-name {
      type string;
      description "Attribute set name";
    }
    leaf is-attribute-set-configured {
      type boolean;
      description
        "Is any attribute-set associated to this
        meshgroup";
    }
    leaf is-attribute-set-in-db {
      type boolean;
      description
        "Flag to indicate the existence of attribute set
        found in database";
    }
    leaf destination-list-name {
      type string;
      description "Destination List name";
    }
    leaf is-destination-list-configured {
      type boolean;
      description
        "Is any destiantion-list associated to this
        meshgroup";
    }
    leaf destination-list-type {
      type Te-acl;
      description "Type of the  destlist";
    }
    leaf remaining-time {
      type uint32;
      units "second";
      description "Remaining time for recreate timer in seconds";
    }
    leaf auto-mesh-tunnels {
      type uint32;
      description "Total number of automesh tunnels";
    }
    leaf auto-mesh-total-destinations {
      type uint32;
      description "Total number of destinations";
    }
    leaf up-auto-mesh-tunnels {
      type uint32;
      description "Total number of automesh tunnels that are up";
    }
    leaf down-auto-mesh-tunnels {
      type uint32;
      description "Total number of automesh tunnels that are down";
    }
    leaf frr-auto-mesh-tunnels {
      type uint32;
      description
        "Total number of automesh tunnels that are FRR
        enabled";
    }
    leaf auto-mesh-group-type {
      type Te-meshgroup;
      description "Meshgroup Type";
    }

    list destination {
      description "List of destinations for this meshgroup";
      uses MPLS-TE-MESHGROUP-DEST;
    }
  }

  grouping MPLS-TE-AUTOTUN-PCC-SUMMARY-INFO {
    description
      "Stateful PCE client auto-tunnel summary
      information";
    leaf pcc-auto-tunnel {
      type uint32;
      description
        "Total number of stateful PCE client auto-tunnels";
    }
    leaf up-pcc-auto-tunnels {
      type uint32;
      description
        "Total number of stateful PCE client auto-tunnels
        that are up";
    }
    leaf down-pcc-auto-tunnels {
      type uint32;
      description
        "Total number of stateful PCE client auto-tunnels
        that are down";
    }
  }

  grouping MPLS-TE-P2MP-TIMER-B {
    description "Description of a P2MP timer";
    leaf timer-type {
      type Mpls-te-p2mp-timer;
      description "Timer Type";
    }
    leaf timer-name {
      type string;
      description "Timer Name";
    }
    leaf start-time {
      type uint32;
      units "second";
      description "Date when timer was last started in seconds";
    }
    leaf expiry-time {
      type uint32;
      units "second";
      description "Date when the timer last expired in seconds";
    }
    leaf stop-time {
      type uint32;
      units "second";
      description "Date when the timer was last stopped in seconds";
    }
    leaf duration {
      type uint32;
      units "second";
      description "The expiry delay in seconds";
    }
    leaf is-running {
      type boolean;
      description "True if the timer is running";
    }
  }

  grouping MPLS-TE-P2MP-TIMERS-B {
    description "Description of P2MP timers";

    list p2mp-timer {
      max-elements "30";
      description "Description of all P2MP timers";
      uses MPLS-TE-P2MP-TIMER-B;
    }
  }

  grouping MPLS-TE-AREA-AFI-INFO {
    description "IGP area information including AFI";
    leaf igp-area-id {
      type string;
      description "The IGP Instance and Area ID";
    }
    leaf afi {
      type Mpls-te-afi;
      description "AFI";
    }
  }

  grouping MPLS-TE-AUTOROUTE-BAG {
    description "MPLS TE Autoroute Information";
    leaf tunnel-name {
      type string;
      description "The tunnel name";
    }
    leaf tunnel-sig-name {
      type string;
      description "The tunnel signaled-name";
    }
    leaf tunnel-loadshare {
      type uint32;
      description "Tunnel loadshare";
    }
    leaf announce-type {
      type Mpls-te-tunnel-announce;
      description "Announcement type";
    }
    leaf next-hop-address {
      type inet:ipv4-address;
      description "The tunnel destination";
    }
    leaf mode {
      type Igpte-aa-metric-mode;
      description "Autoroute mode";
    }
    leaf igp-metric {
      type int32;
      description "IGP metric";
    }
    leaf hold-time {
      type uint32;
      units "second";
      description "Hold time in seconds";
    }
    leaf area-format {
      type Igp-ospf-area-format;
      description "IGP Area Format";
    }
    leaf is-auto-mesh-aa {
      type boolean;
      description "True if this is auto-tunnel mesh AA";
    }
    leaf is-sr {
      type boolean;
      description "True if this is a segment routing tunnel";
    }
    leaf is-sr-strict {
      type boolean;
      description "True if this is a strict SID SR tunnel";
    }
    leaf mesh-group-idaa {
      type uint32;
      description "MeshGroup ID for AA";
    }
    leaf is-exclude-segment-routing {
      type boolean;
      description
        "True if autoroute-announce has exclude
        segment-routing option";
    }

    list ig-ps {
      description "List of IGPs to which it is announced";
      uses MPLS-TE-AREA-AFI-INFO;
    }
  }

  grouping MPLS-TE-ANNOUNCEMENT-DEST-BAG {
    description
      "The summary info of announcements for a
      destination and an IGP area";
    leaf igp-type {
      type Igp-protocol;
      description "IGP type";
    }
    leaf igp-instance {
      type string;
      description "IGP Instance name";
    }
    leaf igp-area {
      type uint32;
      description "IGP Area ID";
    }
    leaf destination {
      type inet:ipv4-address;
      description "Destination";
    }
    leaf announced-tunnels-count {
      type uint16;
      description "The number of announced tunnels";
    }
    leaf autorouted-tunnels-count {
      type uint16;
      description
        "The number of tunnels that are announced as
        shortcuts";
    }
    leaf forwarding-adjacency-tunnels-count {
      type uint16;
      description
        "The number of tunnels that are announced as
        forwarding adjacencies";
    }
    leaf area-format {
      type Igp-ospf-area-format;
      description
        "The format for the area: IPv4 address or a
        positive integer";
    }

    list total-tunnel {
      description "Announced tunnels for this destination";
      uses MPLS-TE-AUTOROUTE-BAG;
    }
  }

  grouping MPLS-TE-TOPOLOGY-LINK-LOSS {
    description "MPLS TE Link Loss Attribute";
    leaf anomalous-bit {
      type boolean;
      description "Anomalous (A) Bit";
    }
    leaf loss-value {
      type uint32;
      description "Loss Value";
    }
  }

  grouping MPLS-TE-TOPOLOGY-LINK-MIN-MAX-DELAY {
    description "MPLS TE Link Loss Attribute";
    leaf anomalous-bit {
      type boolean;
      description "Anomalous (A) Bit";
    }
    leaf minimum-delay {
      type uint32;
      description "Mimimum measured link delay value in usec";
    }
    leaf maximum-delay {
      type uint32;
      description "Maximum measured link delay value in usec";
    }
  }

  grouping MPLS-TE-TOPOLOGY-LINK-BW-STD-DETAIL {
    description "Detailed DSTE bandwidth information for a link";
    list topo-link-std-bw-allocated {
      max-elements "8";

      description "Link's allocated bandwidth per class";
        leaf entry {
                  type uint32;

                  description "Link's allocated bandwidth per class";
        }
    }
    list topo-link-std-bw-available {
      max-elements "8";

      description "Link's available bandwidth per class";
        leaf entry {
                  type uint32;

                  description "Link's available bandwidth per class";
        }
    }
  }

  grouping MPLS-TE-TOPOLOGY-LINK-BW-STD {
    description
      "IETF_standard bandwidth information for a link
      belonging to a node in the MPLS TE topology";

    container topo-link-std-bw-detail {
      description "Detailed bandwidth information for this link";
      uses MPLS-TE-TOPOLOGY-LINK-BW-STD-DETAIL;
    }
    leaf topo-link-std-bw-physical {
      type uint32;
      description "The link's physical bandwidth";
    }
    leaf topo-link-std-bw-res-max {
      type uint32;
      description "The link's maximum reservable bandwidth";
    }
    leaf topo-link-std-bw-res-pool0 {
      type uint32;
      description "The link's reservable BC0 bandwidth";
    }
    leaf topo-link-std-bw-res-pool1 {
      type uint32;
      description "The link's reservable BC1 bandwidth";
    }
  }

  grouping MPLS-TE-TOPOLOGY-LINK-BW-PRESTD-DETAIL {
    description
      "Detailed pre-standard bandwidth information for a
      link";
    list topology-link-prestandard-bandwidth-allocated {
      max-elements "8";

      description

        "Link's allocated bandwidth at priority levels

        (priority 0 to priority 7)";
        leaf entry {
                  type uint32;

                  description

        "Link's allocated bandwidth at priority levels

        (priority 0 to priority 7)";
        }
    }
    list topology-link-prestandard-bandwidth-available-global {
      max-elements "8";

      description

        "Link's available global-pool bandwidth at

        priority levels (priority 0 to priority 7)";
        leaf entry {
                  type uint32;

                  description

        "Link's available global-pool bandwidth at

        priority levels (priority 0 to priority 7)";
        }
    }
    list topology-link-prestandard-bandwidth-available-subpool {
      max-elements "8";

      description

        "Link's available sub-pool bandwidth at priority

        levels (priority 0 to priority 7)";
        leaf entry {
                  type uint32;

                  description

        "Link's available sub-pool bandwidth at priority

        levels (priority 0 to priority 7)";
        }
    }
  }

  grouping MPLS-TE-TOPOLOGY-LINK-BW-PRESTD {
    description
      "Pre-standard bandwidth information for a link
      belonging to a node in the MPLS TE topology";

    container topology-link-prestandard-bandwidth-detail {
      description "Detailed bandwidth information for this link";
      uses MPLS-TE-TOPOLOGY-LINK-BW-PRESTD-DETAIL;
    }
    leaf topology-link-prestandard-bandwidth-physical {
      type uint32;
      description "The link's physical bandwidth";
    }
    leaf topology-link-prestandard-bandwidth-reservation-global {
      type uint32;
      description "The link's reservable global bandwidth";
    }
    leaf topology-link-prestandard-bandwidth-reservation-subpool {
      type uint32;
      description "The link's reservable subpool bandwidth";
    }
  }

  grouping MPLS-TE-TOPOLOGY-LINK-BW {
    description "Bandwidth information for a link";

    container topology-link-bandwidth-prestandard {
      when "../bandwidth-migration-mode ="+
        " 'rrr-dste-mode-prestandard'" {
          description
            "../BandwidthMigrationMode =
            'RRR_DSTEModePrestandard'";
      }
      description
        "Pre-standard bandwidth information for this link";
      uses MPLS-TE-TOPOLOGY-LINK-BW-PRESTD;
    }

    container topology-link-bandwidth-standard {
      when "../bandwidth-migration-mode ="+
        " 'rrr-dste-mode-standard'" {
          description
            "../BandwidthMigrationMode =
            'RRR_DSTEModeStandard'";
      }
      description
        "IETF-standard bandwidth information for this
        link";
      uses MPLS-TE-TOPOLOGY-LINK-BW-STD;
    }
    leaf bandwidth-migration-mode {
      type Rrr-dste-migration-mode;
      description "BandwidthMigrationMode";
    }
  }

  grouping MPLS-TE-TOPOLOGY-LINK {
    description
      "A link belonging to a node in the MPLS TE
      topology";

    container topology-link-bandwidth {
      description "Bandwidth information for this link";
      uses MPLS-TE-TOPOLOGY-LINK-BW;
    }

    container odu-link-capabilities {
      description "ODU Link Capabilities";
      uses ODU-LINK-CAPABILITIES;
    }

    container min-max-delay {
      description "Minimum and maximum measured link delay";
      uses MPLS-TE-TOPOLOGY-LINK-MIN-MAX-DELAY;
    }

    container loss {
      description "Link Loss";
      uses MPLS-TE-TOPOLOGY-LINK-LOSS;
    }
    leaf topology-link-type {
      type Igp-subnet;
      description "Link type";
    }
    leaf topology-link-interface-address {
      type inet:ipv4-address;
      description "Link's local interface address";
    }
    leaf topology-link-interface-id {
      type uint32;
      description "Link's local interface ID";
    }
    leaf topology-link-neighbor-address {
      type inet:ipv4-address;
      description "Link's neighbor interface address";
    }
    leaf topology-link-neighbor-id {
      type uint32;
      description "Link's neighbor interface ID";
    }
    leaf topology-link-neighbor-system-id {
      type string;
      description "System id of neighbor";
    }
    leaf topology-link-neighbor-node-id {
      type uint32;
      description "Node id of neighbor";
    }
    leaf topology-link-neighbor-generation {
      type uint32;
      description "Neighbor's link version counter";
    }
    leaf topology-link-fragment-id {
      type uint32;
      description "Neighbor's link version counter";
    }
    leaf topology-link-te-metric {
      type uint32;
      description "The link's TE metric";
    }
    leaf topology-link-igp-metric {
      type uint32;
      description "The link's IGP metric";
    }
    leaf topology-link-uni-delay {
      type uint32;
      description "Unidirectional Link Delay in micro-sec";
    }
    leaf topology-link-affinity-bits {
      type uint32;
      description "Deprecated";
    }
    leaf topology-link-switching-capability {
      type uint8;
      description "The link's switching capability";
    }
    leaf topology-link-encoding {
      type uint8;
      description "The link's encoding";
    }
    leaf topology-link-bandwidth-model {
      type Igpte-lib-bw-model;
      description "The link's topology bandwidth model";
    }
    leaf delay-variation {
      type uint32;
      description "Delay Variation";
    }
    leaf residual-bandwidth {
      type uint32;
      description "Residual Bandwidth (kbytes per seconds)";
    }
    leaf available-bandwidth {
      type uint32;
      units "byte/s";
      description "Available Bandwidth (kbytes per second)";
    }
    leaf utilized-bandwidth {
      type uint32;
      units "byte/s";
      description "Utilized Bandwidth (kbytes per second)";
    }
    list topology-link-extended-affinity-bit {
      description "The link's affinity bits (colors)";
        leaf entry {
                  type uint32;

                  description "The link's affinity bits (colors)";
        }
    }

    list shared-risk-link-group {
      description "The link's shared risk link groups";
      uses MPLS-SRLG-INFO;
    }

    list adjacency-sid {
      description "Adjacency SIDs assigned for adjacency nodes";
      uses TE-SR-ADJ-SID;
    }
  }

  grouping MPLS-TE-TOPOLOGY-NODE {
    description "A node in the MPLS TE topology";

    container topology-node-sid-and-srbg {
      description "This node's SID and SRBG information";
      uses TE-SR-NODE-INFO;
    }
    leaf topology-node-te-router-id {
      type inet:ipv4-address;
      description
        "The node's TE router-id. Not set for network
        nodes";
    }
    leaf topology-node-overloaded {
      type boolean;
      description
        "Flag to indicate whether this node is overloaded";
    }

    list topology-node-link {
      description "This node's link information";
      uses MPLS-TE-TOPOLOGY-LINK;
    }
  }

  grouping TE-FIB-NH-PATH-BAG {
    description "TE FIB NH PATH BAG";
    leaf interface {
      type xr:Interface-name;
      description "Outgoing Interface";
    }
    leaf next-hop-address {
      type inet:ipv4-address;
      description "Next Hop Address";
    }
    leaf path-id {
      type uint32;
      description "Path ID";
    }
    leaf backup-path-id {
      type uint32;
      description "Backup Path Identifier";
    }
    leaf pure-backup {
      type boolean;
      description "Pure Backup";
    }
    list label-stack {
      description "Outgoing Label Stack";
        leaf entry {
                  type uint32;

                  description "Outgoing Label Stack";
        }
    }
  }

  grouping TE-TARGET-ADDR {
    description "TE Target Address Union";
    leaf type {
      type Te-target-addr;
      description "type";
    }
    leaf ip-address {
      when "../type = 'te-target-type-ipv4'" {
        description "../type = 'TETargetTypeIPv4'";
      }
      type inet:ipv4-address;
      description "IPv4 Address";
    }
    leaf label {
      when "../type = 'te-target-type-label'" {
        description "../type = 'TETargetTypeLabel'";
      }
      type uint32;
      description "MPLS Label";
    }
  }

  grouping TE-FIB-NH-ROUTE-BAG {
    description "TE FIB NH ROUTE BAG";

    container target-address {
      description "Next Hop Target Address";
      uses TE-TARGET-ADDR;
    }
    leaf prefix-addr {
      type inet:ipv4-address;
      description "Deprecated - replaced by TargetAddress";
    }
    leaf create-time {
      type uint32;
      description "Create Time";
    }
    leaf last-used-time {
      type uint32;
      description "Last Used Time";
    }
    leaf last-update-time {
      type uint32;
      description "Last Update Time";
    }
    leaf expire-time {
      type uint32;
      description "Expire Time";
    }
    leaf is-registered {
      type boolean;
      description "Is Registered";
    }
    leaf is-notified {
      type boolean;
      description "Is Notified";
    }
    leaf is-stale {
      type boolean;
      description "Is Stale";
    }
    leaf route-version {
      type uint64;
      description "Route version";
    }

    list next-hop-path {
      description "Next Hop Paths";
      uses TE-FIB-NH-PATH-BAG;
    }
  }

  grouping NODE-ID {
    description "NODE ID";
    leaf node-id {
      type string;
      description "Node Identifier";
    }
  }

  grouping TE-SR-BACKUP-PATH {
    description "Segment-Routing backup path";
    leaf outgoing-interface {
      type string;
      description "Outgoing Interface Name";
    }
    leaf next-hop {
      type inet:ipv4-address;
      description "Next hop";
    }
    list outgoing-labels-stack {
      description "Outgoing Labels Stack";
        leaf entry {
                  type uint32;

                  description "Outgoing Labels Stack";
        }
    }
    list outgoing-strict-labels-stack {
      description "Outgoing Labels Stack for Strict SPF";
        leaf entry {
                  type uint32;

                  description "Outgoing Labels Stack for Strict SPF";
        }
    }
  }

  grouping TE-SR-PRIMARY-PATH {
    description "Segment-Routing primary path";
    leaf outgoing-interface {
      type string;
      description "Outgoing Interface Name";
    }
    leaf outgoing-label {
      type uint32;
      description "Outgoing Label";
    }
    leaf outgoing-strict-label {
      type uint32;
      description "Outgoing Label for Strict SPF";
    }
    leaf next-hop {
      type inet:ipv4-address;
      description "Next hop";
    }
    leaf path-id {
      type uint32;
      description "Path Identifier";
    }
    leaf backup-path-id {
      type uint32;
      description "Backup Path Identifier";
    }
  }

  grouping TE-SR-PATH {
    description "Segment-Routing path";

    container primary-path {
      description "Primary Segment-Routing Path";
      uses TE-SR-PRIMARY-PATH;
    }

    container backup-path {
      description "Backup Segment-Routing Path";
      uses TE-SR-BACKUP-PATH;
    }
    leaf has-backup-path {
      type boolean;
      description "Backup Path is available";
    }
  }

  grouping TE-SR-PREFIX {
    description "MPLS TE Segment-Routing Prefix information";

    container igp-area {
      description "An IGP area where the prefix belongs to";
      uses TE-SR-IGP-AREA;
    }
    leaf prefix-xr {
      type inet:ipv4-address;
      description "Prefix";
    }
    leaf prefix-length-xr {
      type uint8;
      description "Length of the prefix";
    }
    leaf prefix-sid {
      type uint32;
      description "Segment-Routing prefix SID";
    }
    leaf prefix-strict-sid {
      type uint32;
      description "Segment-Routing prefix Strict SID";
    }
    leaf flag-r {
      type boolean;
      description "Prefix-SID subTLV R-flag";
    }
    leaf flag-n {
      type boolean;
      description "Prefix-SID subTLV N-flag";
    }
    leaf flag-p {
      type boolean;
      description "Prefix-SID subTLV P-flag";
    }
    leaf flag-e {
      type boolean;
      description "Prefix-SID subTLV E-flag";
    }
    leaf flag-v {
      type boolean;
      description "Prefix-SID subTLV V-flag";
    }
    leaf flag-l {
      type boolean;
      description "Prefix-SID subTLV L-flag";
    }
    leaf strict-flag-p {
      type boolean;
      description "Prefix-SID subTLV P-flag for strict SID";
    }
    leaf strict-flag-e {
      type boolean;
      description "Prefix-SID subTLV E-flag for strict SID";
    }
    leaf strict-flag-v {
      type boolean;
      description "Prefix-SID subTLV V-flag for strict SID";
    }
    leaf strict-flag-l {
      type boolean;
      description "Prefix-SID subTLV L-flag for strict SID";
    }

    list sr-path {
      description "Segment-Routing paths to prefix";
      uses TE-SR-PATH;
    }

    list advertizing-node {
      description "Advertizing nodes";
      uses NODE-ID;
    }

    list strict-advertizing-node {
      description "Advertizing nodes for Strict SPF";
      uses NODE-ID;
    }
  }

  grouping TE-SR-ADJ-SID {
    description "A link's Segment-Routing Adjacency information";
    leaf adjacency-sid {
      type uint32;
      description
        "The adjacency SID assigned for the topology node";
    }
    leaf link-type {
      type Igp-subnet;
      description "Link Type";
    }
    leaf local-addr {
      type inet:ipv4-address;
      description "Local Address";
    }
    leaf remote-addr {
      type inet:ipv4-address;
      description "Remote Address";
    }
    leaf nbr-node-igpid {
      type string;
      description "The neighbor node's IGP ID";
    }
    leaf nbr-node-te-router-id {
      type inet:ipv4-address;
      description "The neigbor node's TE router-id";
    }
    leaf flag-f {
      type boolean;
      description "IGP Flag F";
    }
    leaf flag-b {
      type boolean;
      description "IGP Flag B";
    }
    leaf flag-v {
      type boolean;
      description "IGP Flag V";
    }
    leaf flag-l {
      type boolean;
      description "IGP Flag L";
    }
    leaf flag-s {
      type boolean;
      description "IGP Flag S";
    }
  }

  grouping TE-SR-LINK-INFO {
    description "A link belonging to a node";
    leaf topology-link-type {
      type Igp-subnet;
      description "Link type";
    }
    leaf topology-link-interface-address {
      type inet:ipv4-address;
      description "Link's local interface address";
    }
    leaf topology-link-interface-id {
      type uint32;
      description "Link's local interface ID";
    }
    leaf topology-link-neighbor-address {
      type inet:ipv4-address;
      description "Link's neighbor interface address";
    }
    leaf topology-link-neighbor-id {
      type uint32;
      description "Link's neighbor interface ID";
    }
    leaf topology-link-neighbor-system-id {
      type string;
      description "System id of neighbor";
    }
    leaf topology-link-neighbor-node-id {
      type uint32;
      description "Node id of neighbor";
    }
    leaf topology-link-neighbor-generation {
      type uint32;
      description "Neighbor's link version counter";
    }
    leaf topology-link-fragment-id {
      type uint32;
      description "Neighbor's link version counter";
    }
    leaf topology-link-te-metric {
      type uint32;
      description "The link's TE metric";
    }
    leaf topology-link-igp-metric {
      type uint32;
      description "The link's IGP metric";
    }
    list topology-link-extended-affinity-bit {
      description "The link's affinity bits (colors)";
        leaf entry {
                  type uint32;

                  description "The link's affinity bits (colors)";
        }
    }

    list shared-risk-link-group {
      description "The link's shared risk link groups";
      uses MPLS-SRLG-INFO;
    }

    list adjacency-sids {
      description "Adjacency SIDs assigned for adjacency nodes";
      uses TE-SR-ADJ-SID;
    }
  }

  grouping TE-SR-NODE-INFO {
    description "MPLS TE Node's Segment-Routing Information";
    leaf segment-id {
      type uint32;
      description "Segment-Routing Node-SID";
    }
    leaf segment-id-local-absolute-value {
      type uint32;
      description "Node-SID local absolute value";
    }
    leaf srgb-start {
      type uint32;
      description "Segment-Routring global block start value";
    }
    leaf srgb-size {
      type uint32;
      description "Segment-Routing global block size";
    }
  }

  grouping TE-SR-NODE {
    description "MPLS TE Segment-Routing Node topology information";

    container igp-area {
      description "IGP area which this node belongs to";
      uses TE-SR-IGP-AREA;
    }

    container sr-node-info {
      description "Segment-Routing Node information";
      uses TE-SR-NODE-INFO;
    }
    leaf local-node-igp-id {
      type string;
      description "The local node's IGP id formatted as string";
    }
    leaf topology-node-is-router {
      type boolean;
      description
        "TRUE if this is a router node; FALSE if it's a
        network node";
    }
    leaf local-node-te-router-id {
      type inet:ipv4-address;
      description "The local node's TE router-id";
    }
    leaf topology-node-overloaded {
      type boolean;
      description
        "Flag to indicate whether this node is overloaded";
    }

    list node-link {
      description "This node's link information";
      uses TE-SR-LINK-INFO;
    }
  }

  grouping TE-SR-IGP-AREA {
    description "A IGP area information for Segment-Routing";
    leaf segment-routing-enabled {
      type boolean;
      description
        "True if the Segment-Routing is enabled in this
        area";
    }
    leaf strict-spf-enabled {
      type boolean;
      description "True if the strict SPF is enabled in this area";
    }
    leaf igp-type {
      type Igp-protocol;
      description "IGP type";
    }
    leaf igp-instance-xr {
      type string;
      description "IGP Instance name";
    }
    leaf igp-area {
      type uint32;
      description "IGP Area ID";
    }
    leaf igp-area-format {
      type Igp-ospf-area-format;
      description "IGP-area format";
    }
  }

  grouping MPLS-TE-TUNNEL-FLEX-INFO {
    description "TE Tunnel FlexLSP Information";
    leaf fault-ldi-lockout {
      type boolean;
      description "Fault LDI Lockout";
    }
    leaf fault-ldi {
      type boolean;
      description "Fault LDI";
    }
    leaf fault-lkr {
      type boolean;
      description "Fault LKR";
    }
    leaf fault-ais {
      type boolean;
      description "Fault AIS";
    }
    leaf fault-time {
      type uint32;
      description "Fault Time";
    }
    leaf fault-in-label {
      type uint32;
      description "Fault In Label";
    }
    leaf is-lockout {
      type boolean;
      description "Lockout Status";
    }
    leaf lockout-timestamp {
      type uint32;
      description "The timestamp when the lockout is set";
    }
    leaf lockout-lsp-id {
      type uint16;
      description "The LSP ID of the locked out LSP";
    }
    leaf origination {
      type Flex-lsp-lockout-origination;
      description "Flex LSP Lockout Origination Source";
    }
  }

  grouping TE-VIF-CONVERGENCE-INFO {
    description "TE tunnel convergence related information";

    container convergence-lsp {
      description "TE LSP convergence related information";
      uses TE-LSP-CONVERGENCE-INFO;
    }
    leaf is-convergence-in-progress {
      type boolean;
      description "TE convergence in progress";
    }
    leaf frr-trigger-time {
      type uint64;
      description "FRR trigger time";
    }
    leaf pcalc-complete-time {
      type uint64;
      units "nanosecond";
      description
        "Path computation completion timestamp (clocktime
        in nsecs)";
    }
    leaf convergence-complete-time {
      type uint64;
      description "TE convergence completion time";
    }
    leaf binding-label-rewrite-time {
      type uint64;
      units "nanosecond";
      description "Binding label timestamp (clocktime in nsecs)";
    }
    leaf vif-creation-time {
      type uint64;
      units "nanosecond";
      description "Vif creation timestamp (clocktime in nsecs)";
    }
  }

  grouping MPLS-TE-TUNNELS-REVERSE-ERO-ERROR-BAG {
    description "MPLS TE Tunnel Reverse ERO Error Information";
    leaf reverse-lsp-id {
      type uint16;
      description "Reverse LSP ID";
    }
    leaf path-reject-reason-bw {
      type boolean;
      description "Path Reject due to bw";
    }
    leaf path-reject-reason-affinity {
      type boolean;
      description "Path Reject due to affinity";
    }
    leaf path-reject-reason-ip-addr {
      type boolean;
      description "Path Reject due to IP address";
    }
    leaf path-reject-reason-reverse-link {
      type boolean;
      description "Path Reject due to reverse link";
    }
    leaf path-reject-reason-ixcd {
      type boolean;
      description "Path Reject due to IXCD";
    }
    leaf path-reject-reason-holddown {
      type boolean;
      description "Path Reject due to holddown";
    }
    leaf path-reject-reason-exclude-node {
      type boolean;
      description "Path Reject due to exclude node";
    }
    leaf path-reject-reason-exclude-link {
      type boolean;
      description "Path Reject due to exclude link";
    }
    leaf path-reject-reason-exclude-srlg {
      type boolean;
      description "Path Reject due to exclude SRLG";
    }
    leaf path-reject-reason-hop-limit {
      type boolean;
      description "Path Reject due to hop limit";
    }
    leaf path-reject-reason-node-ol-unknown {
      type boolean;
      description "Path Reject due to unknown node overload";
    }
    leaf path-reject-reason-node-ol-head {
      type boolean;
      description "Path Reject due to head node overload";
    }
    leaf path-reject-reason-node-ol-mid {
      type boolean;
      description "Path Reject due to mid node overload";
    }
    leaf path-reject-reason-node-ol-tail {
      type boolean;
      description "Path Reject due to head node overload";
    }
    leaf path-reject-reason-reverse-bw {
      type boolean;
      description "Path Reject due to reverse bw";
    }
    leaf path-reject-reason-node-unreachable {
      type boolean;
      description "Path Reject due to unreachable node";
    }
    leaf path-option-index {
      type uint16;
      description "Path Option Index";
    }
    leaf path-option-type {
      type Mte-path-option;
      description "Path Option Type";
    }
    leaf ero-reject-reason {
      type Te-rev-ero-reject-reasons;
      description "Reverse ERO Reject Reason";
    }

    list path-calculation-error {
      description "Path Computation Information";
      uses MPLS-TE-P2MP-PCALC-ERROR;
    }
  }

  grouping MPLS-TE-TUNNEL-BIDIR-INFO {
    description "MPLS TE Tunnel Bidir Information";

    container reverse-ero-error-current {
      description "Reverse ERO Error Current LSP";
      uses MPLS-TE-TUNNELS-REVERSE-ERO-ERROR-BAG;
    }

    container reverse-ero-error-reopt {
      description "Reverse ERO Error Reopt LSP";
      uses MPLS-TE-TUNNELS-REVERSE-ERO-ERROR-BAG;
    }

    container reverse-ero-error-standby {
      description "Reverse ERO Error Standby LSP";
      uses MPLS-TE-TUNNELS-REVERSE-ERO-ERROR-BAG;
    }

    container reverse-ero-error-standby-reopt {
      description "Reverse ERO Error Standby Reopt LSP";
      uses MPLS-TE-TUNNELS-REVERSE-ERO-ERROR-BAG;
    }
    leaf reverse-bandwidth {
      type uint32;
      units "kbit/s";
      description "Reverse Bandwidth value in kbps";
    }
    leaf reverse-bandwidth-standby {
      type uint32;
      units "kbit/s";
      description "Reverse Bandwidth value for standby in kbps";
    }
  }

  grouping MPLS-TE-TUNNEL-RESTORATION-INFO {
    description "Restoration info of tunnel";
    leaf revert-option {
      type Te-pnr-revert-options;
      description "Revertive or non-revertive";
    }
    leaf diverse-lsp {
      type Mpls-te-lsp-mode;
      description "LSP from which restoration LSP is DIVERSED";
    }
    leaf diversity-type {
      type Te-pp-diversity;
      description "Restoration path diversity type";
    }
  }

  grouping MPLS-TE-TUNNEL-APS-INFO {
    description "APS Protection Info of tunnel";

    container protection-profile {
      description "Protection Profile Information of tunnel";
      uses MPLS-TE-ATTRIBUTE-SET-APS-PP;
    }
    leaf active-lsp {
      type Mpls-te-lsp-mode;
      description "Active LSP for Incoming Data";
    }
    leaf diversity-type {
      type Te-pp-diversity;
      description "Standby path diversity type";
    }
  }

  grouping MPLS-TE-TUNNEL-OTN-BIDIR-INFO {
    description "Bidirectional Tunnel Information";

    container aps {
      description "APS Protection Info";
      uses MPLS-TE-TUNNEL-APS-INFO;
    }

    container restoration {
      description "Restoration Info";
      uses MPLS-TE-TUNNEL-RESTORATION-INFO;
    }
  }

  grouping MPLS-TE-PATH-OPTION-DAMPENING-INFO {
    description "MPLS TE Path Option Dampening Information";
    leaf option-index {
      type uint32;
      description "Path option index";
    }
    leaf hold-down-time {
      type uint32;
      description "Hold down time in second";
    }
    leaf remained-time {
      type uint32;
      description "Remained time to resignal in second";
    }
    leaf backoff-count {
      type uint32;
      description "Backoff count";
    }
  }

  grouping MPLS-TE-TUNNEL-BFD-INFO {
    description "MPLS TE Tunnel BFD Session Information";

    container event-counters {
      description "Per tunnel BFD session event counters";
      uses MPLS-TE-BFD-LSP-COUNTERS;
    }
    leaf bfd-session-up {
      type boolean;
      description "Tunnel BFD session state up or down";
    }
    leaf session-up-time {
      type uint32;
      units "second";
      description "Time in seconds since the last session state up";
    }
    leaf failure-diagnostic-code {
      type uint32;
      description "BFD session failure diagnostic code";
    }
    leaf failure-reason {
      type string;
      description "BFD session failure reason";
    }
    leaf minimum-session-up-interval {
      type uint32;
      description
        "Minimum time in mini second for session to come
        up";
    }
    leaf maximum-session-up-interval {
      type uint32;
      description
        "Maximum time in mini second for session to come
        up";
    }

    list dampening-info {
      description "Path option dampening info";
      uses MPLS-TE-PATH-OPTION-DAMPENING-INFO;
    }
  }

  grouping MPLS-TE-TUNNEL-VIF-DIVERSITY-INFO {
    description "Circuit diversity information";
    leaf tunnel-id {
      type uint16;
      description "Dependent Tunnel ID";
    }
  }

  grouping MPLS-TE-TUNNEL-STATIC-UNI-INFO {
    description "static UNI info for both head and tail";

    container term-interface-srlg {
      description "Termination Interface SRLG";
      uses TE-TERM-INTERFACE-SRLG-CB;
    }
    leaf client-port {
      type string;
      description "Ingress Client Port";
    }
    leaf client-if-handle {
      type xr:Interface-name;
      description "Ingress Client Port Ifhandle";
    }
    leaf client-odu-name {
      type string;
      description "Client Odu Name";
    }
    leaf client-odu-if-handle {
      type xr:Interface-name;
      description "Client Odu Interface";
    }
    leaf cross-connect-id {
      type uint32;
      description "Cross connect id";
    }
    leaf is-connected {
      type boolean;
      description "True if client port is connected";
    }
    leaf uptime {
      type uint32;
      description "Client Port Uptime";
    }
    leaf local-termination {
      type Mpls-te-termination;
      description "Local Termination Type";
    }
    leaf static-uni-type {
      type Mpls-te-uni;
      description "Static uni type";
    }
    leaf term-client-port {
      type string;
      description "Termination Ingress Client Port";
    }
    leaf term-client-if-handle {
      type xr:Interface-name;
      description "Termination Ingress Client Port Ifhandle";
    }
  }

  grouping MPLS-TE-TUNNEL-OTN-INFO {
    description "OTN tunnel's OTN technology information";

    container bandwidth-cfg {
      description "Configured OTN Bandwidth for tunnel";
      uses TE-ODU-V3-BW;
    }
    leaf config-bit-rate {
      type uint32;
      units "kbit/s";
      description "Configured OTN Bandwidth in kbps";
    }
  }

  grouping MPLS-TE-TRANSPORT-TUNNEL-INFO {
    description "Transport Tunnel information";

    container otn {
      description "Info Related to OTN technology in S2L";
      uses MPLS-TE-TUNNEL-OTN-INFO;
    }

    container static-uni {
      description "Tunnel Static UNI Info";
      uses MPLS-TE-TUNNEL-STATIC-UNI-INFO;
    }

    container egress-static-uni {
      description "Tunnel EgressStatic UNI Info";
      uses MPLS-TE-TUNNEL-EGRESS-STATIC-UNI-INFO;
    }
    leaf status-homepath-working {
      type boolean;
      description "Status of working homepath";
    }

    list homepath-ero {
      description "Homepath ero for working lsp";
      uses RSVP-MGMT-ERO-SUBOBJ;
    }

    list diversity-info {
      description "Diversity Info";
      uses MPLS-TE-TUNNEL-VIF-DIVERSITY-INFO;
    }
  }

  grouping MPLS-TE-MGMT-WDM-UNI-TUNNEL-INFO {
    description "GMPLS WDM-UNI tunnel information";
    leaf tunnel-state {
      type Mpls-te-tunnel-state;
      description "Tunnel state";
    }
    leaf tunnel-role {
      type Mpls-te-tunnel-role;
      description "Tunnel Role";
    }
    leaf tunnel-id {
      type uint16;
      description "Tunnel ID";
    }
    leaf lsp-id {
      type uint16;
      description "LSP ID";
    }
    leaf local-optical-router-id {
      type inet:ipv4-address;
      description "Local optical router id";
    }
    leaf remote-optical-router-id {
      type inet:ipv4-address;
      description "Remote optical router id";
    }
    leaf controlled-interface {
      type string;
      description "Interface being controlled";
    }
    leaf source-address {
      type inet:ipv4-address;
      description "Source address";
    }
    leaf destination-address {
      type inet:ipv4-address;
      description "Destination address";
    }
    leaf extended-tunnel-id {
      type inet:ipv4-address;
      description "Extended tunnel-id";
    }
    leaf label-origin {
      type Mpls-te-mgmt-gmpls-label-origin;
      description "Label origin";
    }
    leaf srlg-discovery {
      type boolean;
      description "SRLG-discovery enabled";
    }
  }

  grouping MPLS-TE-SOFT-PREEMPTION-HEAD-COUNTERS {
    description "Headend Soft Preemption Counters";
    leaf soft-preemption-events {
      type uint32;
      description "The number of soft preemption events";
    }
    leaf reopt-completed-ls-ps {
      type uint32;
      description
        "The number of soft preempted LSPs that were torn
        down by the ingress router after the reopt LSP
        was successfully setup.";
    }
    leaf torn-down-ls-ps {
      type uint32;
      description
        "The number of soft preempted LSPs that were torn
        down by the              headend or any remote
        node before the reoptimization is done.";
    }
    leaf path-protection-switchover-ls-ps {
      type uint32;
      description
        "The number of soft preempted LSPs that were
        switched over to a             standby LSP.";
    }
    leaf frr-triggered-ls-ps {
      type uint32;
      description
        "The number of soft preempted LSPs that were fast
        rerouted at the             headend or any
        remote node before the reoptimization is done.";
    }
    leaf time-in-preemption-pending-min {
      type uint16;
      units "second";
      description
        "The minimum time in seconds that an LSP was in
        preemption pending state";
    }
    leaf time-in-preemption-pending-max {
      type uint16;
      units "second";
      description
        "The maximum time in seconds that an LSP was in
        preemption pending state";
    }
    leaf time-in-preemption-pending-avg {
      type uint16;
      units "second";
      description
        "The average time in seconds that an LSP was in
        preemption pending state";
    }
  }

  grouping MPLS-TE-SOFT-PREEMPTION-PATH-ERROR {
    description "Information for a soft preemption path error";
    leaf timestamp {
      type uint32;
      description
        "The POSIX timestamp when the soft preemption
        error is received";
    }
    leaf preempting-link-address {
      type inet:ipv4-address;
      description
        "The address of the link where the preemption
        happened";
    }
  }

  grouping MPLS-TE-SOFT-PREEMPTION-TUNNEL-INFO {
    description "Headend Soft Preemption Tunnel Info";

    container soft-preemption-counters {
      description
        "The soft preemption counters for this tunnel
        head";
      uses MPLS-TE-SOFT-PREEMPTION-HEAD-COUNTERS;
    }
    leaf status {
      type Mpls-te-soft-preemption-state;
      description "The preemption state";
    }
    leaf time-in-preemption-pending {
      type uint16;
      units "second";
      description
        "The number of seconds that were spent in the
        preemption-pending state";
    }
    leaf preemption-pending-resolution {
      type Mpls-te-soft-preemption-resolution;
      description
        "Indicates how the soft preemption operation
        ended";
    }

    list soft-preemption-path-error {
      description
        "The array of soft preemption path errors info
        received for the LSP that is being soft
        preempted";
      uses MPLS-TE-SOFT-PREEMPTION-PATH-ERROR;
    }
  }

  grouping MPLS-TE-PCE-DELEGATION-INFO {
    description "MPLS TE PCE Delegation Information";
    leaf plsp-id {
      type uint32;
      description "PLSP ID";
    }
    leaf symbolic-name {
      type string;
      description "Symbolic name";
    }
    leaf owner-address {
      type inet:ipv4-address;
      description "Address of owner node";
    }
    leaf operationally-up {
      type boolean;
      description "Operationally up";
    }
  }

  grouping MPLS-TE-AUTOPCC-INFO {
    description "MPLS TE Auto-PCC Information";
    leaf owner-address {
      type inet:ipv4-address;
      description "Address of owner node";
    }
    leaf creator-address {
      type inet:ipv4-address;
      description "Address of creating node";
    }
    leaf has-creator-id {
      type boolean;
      description "Indicates if the ID of the creating node is set";
    }
    leaf creator-id {
      type string;
      description "ID of creating node";
    }
    leaf plspid {
      type uint32;
      description "PLSP ID";
    }
    leaf symbolic-name {
      type string;
      description "Symbolic name";
    }
    leaf operationally-up {
      type boolean;
      description "Operationally up";
    }
  }

  grouping MPLS-TE-AUTOMESH-INFO {
    description "MPLS TE Automesh Information";
    leaf mesh-group-id {
      type uint32;
      description "Auto-mesh tunnel Mesh Group ID";
    }
    leaf tunnel-destination-list-name {
      type string;
      description "Destination List name";
    }
    leaf is-tunnel-unused-timer-running {
      type boolean;
      description "Flag to indicate whether unused timer running";
    }
    leaf remaining-unused-time {
      type uint32;
      units "second";
      description "Remaining time for unused timer in seconds";
    }
    leaf mesh-group-type {
      type Te-meshgroup;
      description "Auto-tunnel mesh group type";
    }
  }

  grouping MPLS-TE-IEP-HOP-BAG {
    description "MPLS IEP Hop information";
    leaf hop-index {
      type uint32;
      description "Hop Index";
    }
    leaf iep-hop-type {
      type Mpls-te-iep-hop;
      description "IEP type";
    }
    leaf iep-hop-address {
      type inet:ipv4-address;
      description "IEP Hop Address";
    }
  }

  grouping MPLS-TE-IEP-BAG {
    description "MPLS TE IEP";
    leaf path-option-id {
      type uint32;
      description "Path option ID this IEP is associated with";
    }

    list iep-hop {
      description "IEP Hop List";
      uses MPLS-TE-IEP-HOP-BAG;
    }
  }

  grouping MPLS-TE-WSRLG-HOP-BAG {
    description
      "Weighted SRLG info for a hop of the autobackup
      tunnel";
    leaf from-address {
      type inet:ipv4-address;
      description "Local IP address";
    }
    leaf to-address {
      type inet:ipv4-address;
      description "Remote IP address";
    }
    leaf aggregate-admin-weight {
      type uint64;
      description
        "Sum of the admin weights for all the common SRLG
        values";
    }
    list common-srlg {
      description

        "Common SRLG between this hop and the protected

        interface";
        leaf entry {
                  type uint32;

                  description

        "Common SRLG between this hop and the protected

        interface";
        }
    }
  }

  grouping MPLS-TE-WSRLG-VALUE-BAG {
    description "MPLS TE weighted SRLGs";
    leaf srlg {
      type uint32;
      description "SRLG number";
    }
    leaf srlg-name {
      type string;
      description "SRLG name";
    }
    leaf admin-weight {
      type uint32;
      description "Admin weight";
    }
  }

  grouping MPLS-TE-WSRLG-INFO-BAG {
    description
      "MPLS TE weighted SRLG information for the
      autobackup tunnels";

    list protected-interface-srlg {
      description
        "SRLG values and admin weight penalties of the
        protected interface";
      uses MPLS-TE-WSRLG-VALUE-BAG;
    }

    list weighted-srlg-hop {
      description
        "Autobackup hops and the common SRLG with the
        protected interface";
      uses MPLS-TE-WSRLG-HOP-BAG;
    }
  }

  grouping MPLS-TE-AUTOBACKUP-INFO {
    description "MPLS TE Autobackup Information";

    container weighted-srlg-info {
      description "Weighted SRLG info for the autobackup tunnel";
      uses MPLS-TE-WSRLG-INFO-BAG;
    }
    leaf protected-ls-ps {
      type uint32;
      description "Number Of Protected LSPs";
    }
    leaf protected-s2-ls {
      type uint32;
      description "Number of Protected S2Ls";
    }
    leaf sharing-families {
      type uint32;
      description "Number of S2L Sharing Families";
    }
    leaf ab-protection-type {
      type Auto-backup-protection;
      description "Protection type";
    }
    leaf is-using-srlg {
      type boolean;
      description "Indicates whether SRLG Path Option is in use";
    }
    leaf srlg-prot-type {
      type Auto-backup-srlg-mode;
      description "SRLG Protection Type";
    }
    leaf ab-protected-interface {
      type string;
      description "Protected Interface";
    }
    leaf protected-address {
      type inet:ipv4-address;
      description "Protected Address";
    }
    leaf tunnel-attribute-set-name {
      type string;
      description "AttributeSet name";
    }
    leaf is-unused-removal-timer-running {
      type boolean;
      description
        "Indicates if the unused removal timer is running";
    }
    leaf unused-removal-remaining-time {
      type uint32;
      units "second";
      description
        "Time Remaining in Unused Removal Time in seconds";
    }

    list iep {
      description
        "List of IEPs for the path options on this tunnel";
      uses MPLS-TE-IEP-BAG;
    }
  }

  grouping TE-PP-SW-LOG-ENTRY-BAG {
    description "Path protection log entry";
    leaf path-protection-switchover-event-index {
      type uint32;
      description
        "The index number of the path protection switch
        over event";
    }
    leaf path-protection-tunnel-id {
      type uint16;
      description
        "The ID of the tunnel that experienced switchover";
    }
    leaf from-lsp-id {
      type uint16;
      description
        "The LSP ID from which the traffic was switched
        over";
    }
    leaf to-lsp-id {
      type uint16;
      description
        "The LSP ID to which the traffic was switched
        over";
    }
    leaf date-of-error-detection {
      type uint32;
      units "second";
      description
        "The date when the error that caused the
        switchover was detected. This date is the number
        of seconds since Jan 1st 1970";
    }
    leaf date-of-error-detection-millisec {
      type uint32;
      units "millisecond";
      description
        "The milliseconds offset of the date when the
        error that caused  the switchover was detected.";
    }
    leaf switchover-duration-millisec {
      type uint32;
      units "millisecond";
      description
        "The time in milliseconds between the detection
        of the error and switching the traffic";
    }
    leaf path-protection-switchover-reason {
      type Te-p2mp-s2l-deletion-subcause;
      description
        "The reason that caused the path protection
        switchover";
    }
  }

  grouping MPLS-TE-PP-INFO {
    description "MPLS TE Path Protected Switchover Information";

    container switchover {
      description "Path Protected Switchover Information";
      uses TE-PP-SW-LOG-ENTRY-BAG;
    }
    leaf time-of-switchover-sec {
      type uint32;
      units "second";
      description
        "The date when the switchover was completed. This
        date is the number of seconds since Jan 1st 1970";
    }
    leaf switchover-total {
      type uint16;
      description "Number of times switchover occurred";
    }
    leaf switchover-ready {
      type uint16;
      description "Total times, Standby LSP ready for use";
    }
    leaf standby-reoptimized-number {
      type uint16;
      description "Number of times the standby LSP was reoptimized";
    }
    leaf switchover-reason {
      type uint16;
      description "Reason for last switchover";
    }
    leaf diversity-type {
      type Te-pp-diversity;
      description "Standby path diversity type";
    }
    leaf is-path-protect-configured {
      type boolean;
      description "Is Path Protection Configured";
    }
    leaf path-protection-protected-by-id {
      type uint32;
      description
        "The path option ID (level/index) of the
        configured explicit protecting path";
    }
    leaf valid-path-protection-path-option-exists {
      type boolean;
      description
        "Flag to indicate whether tunnel has a
        path-option which is valid for path-protection";
    }
    leaf is-path-protect-switch-over-underway {
      type boolean;
      description "Is Switchover Underway";
    }
    leaf reoptimization-time-remaining {
      type uint32;
      units "second";
      description
        "Remaining time until path protection
        reoptimization (seconds)";
    }
  }

  grouping MPLS-TE-TUNNELS-TUNNEL-LAST-REOPT-FAIL-INFO {
    description
      "Last re-opt failure reason/information if
      applicable";
    leaf re-opt-last-fail-reason {
      type Mpls-te-reopt-decision-reason;
      description
        "Reason (if any) for the last re-opt attempt
        failure";
    }
    leaf re-opt-failed-destination {
      type inet:ipv4-address;
      description
        "First tunnel destination (if any) in re-opt LSP
        that failed to come up";
    }
    leaf re-opt-failed-timestamp {
      type uint32;
      units "second";
      description
        "Time stamp of the last re-opt failure. (seconds
        since Jan. 1, 1970)";
    }
  }

  grouping MPLS-TE-TUNNELS-HISTORY-STANDBY-SETUP {
    description "History information for standby setup";
    leaf standby-lsp-uptime {
      type uint32;
      units "second";
      description "Time in seconds since the standby LSP was up";
    }
    leaf standby-setup-timer {
      type uint32;
      units "second";
      description
        "Time in seconds until the next attempt to
        connect this setup";
    }
    leaf protection-role {
      type Te-lsp-path-protection-role;
      description "Path Protection Role";
    }
  }

  grouping MPLS-TE-TUNNELS-HISTORY-OTHER-SETUP {
    description "History information for additional GMPLS setup";
    leaf path-option-index {
      type uint32;
      description "Path option index for the additional setup";
    }
    leaf other-setup-error {
      type string;
      description "The last error for the additional setup";
    }
  }

  grouping MPLS-TE-TUNNELS-HISTORY-PREVIOUS-PROTECT {
    description
      "History information for previous protecting GMPLS
      current setup";
    leaf previous-protect-path-option {
      type string;
      description "The previous protect setup path option";
    }
    leaf previous-protect-tunnel-instance {
      type uint32;
      description "The previous protect setup's instance";
    }
    leaf previous-protect-fail-reason {
      type string;
      description "Reason for the previous protect setup's failure";
    }
    leaf previous-protect-setup-last-error {
      type string;
      description "The last error for the previous setup";
    }
  }

  grouping MPLS-TE-TUNNELS-HISTORY-PREVIOUS {
    description "History information for previous current setup";
    leaf previous-path-option {
      type string;
      description "The previous setup path option";
    }
    leaf previous-tunnel-instance {
      type uint32;
      description "The previous setup's instance";
    }
    leaf previous-fail-reason {
      type string;
      description "Reason for the previous setup's failure";
    }
    leaf previous-setup-last-error {
      type string;
      description "The last error for the previous setup";
    }
  }

  grouping MPLS-TE-TUNNELS-HISTORY-PATH-PROTECT {
    description "History information for protecting setup";
    leaf protecting-setup-uptime {
      type uint32;
      units "second";
      description
        "Time in seconds since the protecting setup came
        up";
    }
    leaf protecting-setup-timer {
      type uint32;
      units "second";
      description
        "Time in seconds until the next attempt to
        connect the protecting setup";
    }
    leaf protecting-setup-last-error {
      type string;
      description
        "The last error for the protecting setup (for
        display purposes only)";
    }
  }

  grouping MPLS-TE-TUNNELS-HISTORY-REOPT {
    description "History information for reoptimized setup";
    leaf reoptimized-setup-uptime {
      type uint32;
      units "second";
      description "Time in seconds since the reopt setup came up";
    }
    leaf reoptimized-setup-timer {
      type uint32;
      units "second";
      description
        "Time in seconds until the next attempt to
        connect the reopt setup";
    }
    leaf reoptimized-setup-last-error {
      type string;
      description "The last error for the reopt setup";
    }
    leaf protection-role {
      type Te-lsp-path-protection-role;
      description "Path Protection Role";
    }
  }

  grouping MPLS-TE-TUNNELS-HISTORY-CURRENT-CONNECTED {
    description "History information for currently connected setup";
    leaf current-lsp-uptime {
      type uint32;
      units "second";
      description "Time in seconds since the current LSP was up";
    }
    leaf current-uptime {
      type uint32;
      units "second";
      description "Time in seconds since the tunnel was up";
    }
  }

  grouping MPLS-TE-TUNNELS-HISTORY-CURRENT {
    description "History information for current setup";

    container connected-uptimes {
      description "Uptimes for connected setup";
      uses MPLS-TE-TUNNELS-HISTORY-CURRENT-CONNECTED;
    }
    leaf current-setup-timer {
      type uint32;
      units "second";
      description
        "Time in seconds until the next attempt to
        connect this setup";
    }
    leaf selection-reason {
      type string;
      description
        "The reason why this setup is selected. For
        display purposes only.";
    }
    leaf current-setup-last-error {
      type string;
      description "The last error for the current setup";
    }
    leaf protection-role {
      type Te-lsp-path-protection-role;
      description "Path Protection Role";
    }
  }

  grouping MPLS-TE-TUNNELS-HISTORY-BAG {
    description "MPLS TE Tunnel History Information";

    container current-setup {
      description "Current setup data";
      uses MPLS-TE-TUNNELS-HISTORY-CURRENT;
    }

    container reopt-setup {
      description "Reoptimized setup data";
      uses MPLS-TE-TUNNELS-HISTORY-REOPT;
    }

    container gmpls-path-protect-setup {
      description "GMPLS protecting setup data";
      uses MPLS-TE-TUNNELS-HISTORY-PATH-PROTECT;
    }

    container previous-setup {
      description "Previous setup data";
      uses MPLS-TE-TUNNELS-HISTORY-PREVIOUS;
    }

    container previous-gmpls-path-protect-setup {
      description "Previous GMPLS protecting setup data";
      uses MPLS-TE-TUNNELS-HISTORY-PREVIOUS-PROTECT;
    }

    container gmpls-other-setup {
      description "GMPLS additional setup data";
      uses MPLS-TE-TUNNELS-HISTORY-OTHER-SETUP;
    }

    container gmpls-other-protect-setup {
      description "GMPLS additional protecting setup data";
      uses MPLS-TE-TUNNELS-HISTORY-OTHER-SETUP;
    }

    container standby-setup {
      description "Standby setup data";
      uses MPLS-TE-TUNNELS-HISTORY-STANDBY-SETUP;
    }

    container standby-reopt-setup {
      description "Standby Reopt setup data";
      uses MPLS-TE-TUNNELS-HISTORY-REOPT;
    }

    container last-re-opt-fail {
      description "Last re-opt attempt failure information";
      uses MPLS-TE-TUNNELS-TUNNEL-LAST-REOPT-FAIL-INFO;
    }

    container last-stdby-re-opt-fail {
      description "Last standby re-opt attempt failure information";
      uses MPLS-TE-TUNNELS-TUNNEL-LAST-REOPT-FAIL-INFO;
    }
  }

  grouping MPLS-TE-AUTOCAPACITY-CLONE {
    description "Brief information about a clone tunnel";
    leaf name {
      type string;
      description "Name of the clone";
    }
    leaf creation-timestamp {
      type uint32;
      description
        "The timestamp when this clone was created
        relative to Jan 1, 1970";
    }
    leaf state {
      type Mte-tunnel-oper-state;
      description "The interface state of the cloned tunnel";
    }
    leaf signaled-bandwidth {
      type uint32;
      units "kbit/s";
      description "The signaled bandwidth (kbps) of the clone";
    }
    leaf current-bandwidth-demand {
      type uint32;
      units "kbit/s";
      description
        "The current demand (kbps) read from the traffic
        stats for the clone";
    }
  }

  grouping MPLS-TE-AUTOCAPACITY-STATS {
    description "Statistics for auto-capacity";
    leaf splits {
      type uint32;
      description "Count of splits events";
    }
    leaf merges {
      type uint32;
      description "Count of merges events";
    }
    leaf total-clones-created {
      type uint32;
      description "Total clones created";
    }
    leaf total-clones-deleted {
      type uint32;
      description "Total clones deleted";
    }
    leaf high-watermark-clones {
      type uint32;
      description
        "Highest number of clones reached at any point in
        time";
    }
  }

  grouping MPLS-TE-AUTOCAPACITY-CONFIG {
    description "Configured properties of auto-capacity";
    leaf minimum-clones {
      type uint32;
      description "The minimum number of clones";
    }
    leaf maximum-clones {
      type uint32;
      description "The maximum number of clones";
    }
    leaf merge-bandwidth {
      type uint32;
      units "kbit/s";
      description "The merge bandwidth in kbps";
    }
    leaf split-bandwidth {
      type uint32;
      units "kbit/s";
      description "The split bandwidth in kbps";
    }
    leaf nominal-bandwidth {
      type uint32;
      units "kbit/s";
      description
        "The optimal or nominal bandwidth for the clones
        in kbps";
    }
  }

  grouping MPLS-TE-AUTOCAPACITY {
    description "Auto-capacity information for TE tunnels";

    container auto-capacity-configuration {
      description "The configured properties of auto-capacity";
      uses MPLS-TE-AUTOCAPACITY-CONFIG;
    }

    container auto-capacity-stats {
      description "The statistic of auto-capacity";
      uses MPLS-TE-AUTOCAPACITY-STATS;
    }

    list clone {
      description "Table of clones";
      uses MPLS-TE-AUTOCAPACITY-CLONE;
    }
  }

  grouping MPLS-TE-TUNNELS-AUTOBW-OPER {
    description
      "MPLS TE Tunnel AutoBandwidth Operational
      Information";
    leaf last-bandwidth-applied {
      type uint32;
      description
        "Last bandwidth requested by auto-bw for the
        tunnel";
    }
    leaf bandwidth-pool-type {
      type Mpls-te-bw-pool;
      description "Bandwidth pool type";
    }
    leaf bandwidth-applications {
      type uint32;
      description
        "Total number of bandwidth applications requested
        by auto-bw";
    }
    leaf last-application-trigger {
      type Te-autobw-app-trigger;
      description "The reason causing the last BW application";
    }
    leaf application-jitter {
      type uint32;
      description
        "Amount of time introduced to delay first
        application so that not all tunnels may signal
        BW at the same time";
    }
    leaf time-left-application {
      type uint32;
      description
        "Time left until next auto-bw application
        algorithm is performed";
    }
    leaf samples-collected {
      type uint32;
      description
        "Number of samples collected within current
        application period";
    }
    leaf time-left-collection {
      type uint32;
      description
        "Time left until next auto-bw data collection is
        performed";
    }
    leaf highest-bandwidth {
      type uint32;
      description
        "Highest bandwidth registered within current
        application period";
    }
    leaf underflow-highest-bandwidth {
      type uint32;
      description
        "Highest sample collected during an underflow
        sequence";
    }
    leaf threshold-overflows {
      type uint32;
      description
        "counter for current consecutive collections
        exceeding threshold";
    }
    leaf overflow-early-bw-applications {
      type uint32;
      description
        "tunnel counter for number of bandwidth
        applications due to overflow";
    }
    leaf threshold-underflows {
      type uint32;
      description
        "counter for current consecutive collections
        exceeding threshold";
    }
    leaf underflow-early-bw-applications {
      type uint32;
      description
        "tunnel counter for number of bandwidth
        applications due to underflow";
    }
    leaf collect-only-requested-bandwidth {
      type uint32;
      description "Collect-only Requested Bandwidth for the tunnel";
    }
    leaf application-reject-reason {
      type Te-autobw-app-rej;
      description "Current application reject reason";
    }
    leaf resignal-last-bandwidth-expire-time {
      type uint32;
      description
        "Timestamp when the resignal last bandwidth will
        expire and tunnel will use configured bandwidth
        to setup";
    }
  }

  grouping MPLS-TE-TUNNELS-AUTOBW-CONFIG {
    description
      "MPLS TE Tunnel AutoBandwidth Configuration
      Information";
    leaf is-auto-bandwidth-collect-only {
      type boolean;
      description "TRUE if auto-bw collection-only is enabled";
    }
    leaf minimum-bandwidth {
      type uint32;
      description "Minimum bandwidth auto-bw can apply";
    }
    leaf maximum-bandwidth {
      type uint32;
      description "Maximum bandwidth auto-bw can apply";
    }
    leaf application-frequency {
      type uint32;
      units "minute";
      description
        "Auto-bw application frequency for the tunnel
        (mins)";
    }
    leaf collection-frequency {
      type uint32;
      description "Global auto-bw collection frequency";
    }
    leaf adjustment-threshold-percent {
      type uint32;
      description
        "Bandwidth change threshold needed to trigger
        bandwidth adjustment";
    }
    leaf adjustment-threshold-value {
      type uint32;
      units "kbit/s";
      description
        "Bandwidth change value (kbps) needed to trigger
        bandwidth adjustment";
    }
    leaf overflow-threshold-percent {
      type uint32;
      description
        "Bandwidth change threshold needed to count a
        collection towards overflow limit allowed";
    }
    leaf overflow-threshold-value {
      type uint32;
      description
        "Bandwidth change value needed to count a
        collection towards overflow limit allowed";
    }
    leaf overflow-threshold-limit {
      type uint32;
      description
        "Limit of consecutive collections exceeding
        threshold to trigger an immediate overflow
        bandwidth adjustment";
    }
    leaf underflow-threshold-percent {
      type uint32;
      description
        "Bandwidth change threshold needed to count a
        collection towards underflow limit allowed";
    }
    leaf underflow-threshold-value {
      type uint32;
      description
        "Bandwidth change value needed to count a
        collection towards underflow limit allowed";
    }
    leaf underflow-threshold-limit {
      type uint32;
      description
        "Limit of consecutive collections exceeding
        threshold to trigger an immediate underflow
        bandwidth adjustment";
    }
    leaf resignal-last-bandwidth-enabled {
      type boolean;
      description "TRUE if resignal last bandwidth is enabled";
    }
    leaf resignal-last-bandwidth-timeout {
      type uint32;
      units "second";
      description
        "The configured time-out value in seconds for
        resignal  last bandwidth after tunnel down";
    }
  }

  grouping MPLS-TE-TUNNELS-AUTOBW-STATUS {
    description "MPLS TE Tunnel AutoBandwidth Status Information";
    leaf is-auto-bandwidth-enabled {
      type boolean;
      description "TRUE if auto-bw is enabled for the tunnel";
    }
    leaf reactivation-time {
      type uint32;
      description
        "Time until auto-bw gets activated if activation
        has been delayed due to failover";
    }
  }

  grouping MPLS-TE-P2P-INFO-BAG {
    description "P2P tunnel data";

    container auto-bandwidth-status {
      description "Tunnels's AutoBandwidth Status information";
      uses MPLS-TE-TUNNELS-AUTOBW-STATUS;
    }

    container auto-bandwidth-config {
      description
        "Tunnels's AutoBandwidth Configuration
        information";
      uses MPLS-TE-TUNNELS-AUTOBW-CONFIG;
    }

    container auto-bandwidth-oper {
      description "Tunnels's AutoBandwidth Operational information";
      uses MPLS-TE-TUNNELS-AUTOBW-OPER;
    }
    leaf is-bidirectional {
      type boolean;
      description "TRUE if the tunnel is bidirectional";
    }
  }

  grouping MPLS-TE-INTERAREA-REOPT-INFO {
    description
      "Counter and time information for reoptimization
      of interarea tunnels";
    leaf sent-path-queries {
      type uint16;
      description "Number of better path queries sent";
    }
    leaf time-since-last-query-sent {
      type uint32;
      units "second";
      description
        "Time since the last better path query was sent
        (seconds)";
    }
    leaf received-preferred-path-errors {
      type uint16;
      description "Number of received Preferred Path Exists Error";
    }
    leaf time-since-last-preferred-path-error {
      type uint32;
      units "second";
      description
        "Time since last Preferred Path Exists error
        received (seconds)";
    }
    leaf received-preferred-tree-errors {
      type uint16;
      description "Number of received Preferred Tree Exists Error";
    }
    leaf time-since-last-preferred-tree-error {
      type uint32;
      units "second";
      description
        "Time since last Preferred Tree Exists error
        received (seconds)";
    }
    leaf preferred-path-error-node {
      type inet:ipv4-address;
      description
        "Address of the preferred path error generating
        node";
    }
    leaf preferred-tree-error-node {
      type inet:ipv4-address;
      description
        "Address of the preferred tree error generating
        node";
    }
  }

  grouping MPLS-TE-P2MP-DEST {
    description "A P2MP destination";

    container inter-area-reoptimization {
      description
        "The timing and count information of interarea
        reoptimization.";
      uses MPLS-TE-INTERAREA-REOPT-INFO;
    }
    leaf destination-address {
      type inet:ipv4-address;
      description "Destination address";
    }
    leaf destination-state {
      type Te-destination-state;
      description "The state of the destination";
    }
    leaf active-path-option-index {
      type uint32;
      description "Index of active path option";
    }
    leaf path-option-exhausted {
      type boolean;
      description "Path options are exhausted";
    }
    leaf uptime {
      type uint32;
      units "second";
      description "Time in seconds since the destination was up";
    }
    leaf path-change-time {
      type uint32;
      description "Last path change time";
    }
    leaf total-uptime {
      type uint32;
      description "Unused";
    }
    leaf s2l-exist {
      type boolean;
      description "Dest state may not be up but S2L may exist";
    }
    leaf destination-deletion-cause {
      type Te-p2mp-s2l-deletion-cause;
      description "Destination deletion cause";
    }
    leaf destination-deletion-sub-cause {
      type Te-p2mp-s2l-deletion-subcause;
      description "Destination deletion subcause";
    }
    leaf destination-deletion-timestamp {
      type uint32;
      units "second";
      description "Destination deletion timestamp in seconds";
    }
    leaf is-inter-area {
      type boolean;
      description
        "Indicates whether this destination is in
        different area";
    }

    list path-option-entry {
      description "Deprecated; replaced by PathOption";
      uses MPLS-TE-P2MP-PATH-OPTION;
    }

    list path-option {
      description "Destination's list of path options";
      uses MPLS-TE-P2MP-PATH-OPTION;
    }
  }

  grouping MPLS-TE-TUNNEL-LOGGING {
    description "Tunnel Logging Attributes";
    leaf all {
      type boolean;
      description "All tunnel logging enabled";
    }
    leaf reoptimize {
      type boolean;
      description "Reoptimization Logging";
    }
    leaf state {
      type boolean;
      description "State Logging";
    }
    leaf reroute {
      type boolean;
      description "Reroute logging";
    }
    leaf bandwidth-change {
      type boolean;
      description "Bandwidth change logging";
    }
    leaf switchover {
      type boolean;
      description "Path protection switchover logging";
    }
    leaf record-route {
      type boolean;
      description "Record route logging";
    }
    leaf path-calculation-failure {
      type boolean;
      description "Path calculation failure logging";
    }
    leaf reoptimization-attempt {
      type boolean;
      description "Reoptimization attempt logging";
    }
    leaf insufficient-bandwidth {
      type boolean;
      description "Insufficient bandwidth logging";
    }
  }

  grouping MPLS-TE-AUTOROUTE-DESTINATION-BAG {
    description "An Autoroute destination";
    leaf destination-address {
      type inet:ipv4-address;
      description "Destination address";
    }
    leaf prefix-length {
      type uint16;
      description "Prefix length";
    }
  }

  grouping MPLS-TE-TUNNEL-BFD-CONFIG-INFO {
    description "BFD configuration info for a tunnel";
    leaf bfd-fast-detecting-enabled {
      type boolean;
      description "Deprecated";
    }
    leaf bfd-type {
      type Te-vif-bfd;
      description "BFD Type";
    }
    leaf min-interval {
      type uint32;
      units "millisecond";
      description "Hello interval in milliseconds";
    }
    leaf min-interval-default {
      type boolean;
      description "Is default hello interval";
    }
    leaf multiplier {
      type uint8;
      description "Multiplier";
    }
    leaf multiplier-default {
      type boolean;
      description "Is default multiplier";
    }
    leaf bring-up-timeout {
      type uint16;
      description "Bring Up Timeout in second";
    }
    leaf bring-up-timeout-default {
      type boolean;
      description "Is default bring up timeout";
    }
    leaf dampening-initial-wait {
      type uint32;
      units "millisecond";
      description "Dampening initial wait time in milliseconds";
    }
    leaf dampening-initial-wait-default {
      type boolean;
      description "Is default dampening inital wait time";
    }
    leaf dampening-max-wait {
      type uint32;
      units "millisecond";
      description "Dampening max wait time in milliseconds";
    }
    leaf dampening-max-wait-default {
      type boolean;
      description "Is default dampening max wait time";
    }
    leaf dampening-secondary-wait {
      type uint32;
      units "millisecond";
      description "Dampening secondary wait time in milliseconds";
    }
    leaf dampening-secondary-wait-default {
      type boolean;
      description "Is default dampening secondary wait time";
    }
    leaf periodic-lsp-ping-disabled {
      type boolean;
      description "Periodic LSP Ping disabled";
    }
    leaf periodic-lsp-ping-interval {
      type uint32;
      units "second";
      description "Periodic LSP Ping interval in seconds";
    }
    leaf periodic-lsp-ping-interval-default {
      type boolean;
      description "Is default LSP Ping interval";
    }
    leaf bfd-session-down-action {
      type Mpls-te-bfd-session-down-action1;
      description "BFD Session Down Action";
    }
    leaf bfd-session-down-reopt-timeout {
      type uint32;
      description "BFD Session Down Reopt Timeout";
    }
    leaf bfd-encap-mode {
      type Te-vif-bfd-encap-mode;
      description "BFD Encap Mode";
    }
    leaf sbfd-target-id {
      type inet:ipv4-address;
      description "SBFD Target ID";
    }
  }

  grouping MPLS-TE-TUNNEL-BIDIR-CONFIG-INFO {
    description "Bidirectional configuration info for a tunnel";
    leaf association-type {
      type uint16;
      description "Association Type (RFC 7751)";
    }
    leaf association-id {
      type uint16;
      description "The association ID";
    }
    leaf association-source {
      type inet:ipv4-address;
      description "The association source";
    }
    leaf association-global-id {
      type uint32;
      description "The association global ID";
    }
    leaf association-corouted {
      type boolean;
      description "Is the association co-routed";
    }
  }

  grouping MPLS-TE-P2MP-TUN-CFG-BAG {
    description "Configured P2MP tunnel data";

    container affinity {
      description "Affinity";
      uses MPLS-TE-TUNNELS-AFFINITY-INFO;
    }

    container bidirectional-config {
      description "Bidirectional Configuration Information";
      uses MPLS-TE-TUNNEL-BIDIR-CONFIG-INFO;
    }

    container bfd-config {
      description "BFD Configuration Information";
      uses MPLS-TE-TUNNEL-BFD-CONFIG-INFO;
    }

    container logging {
      description "Logging configuration";
      uses MPLS-TE-TUNNEL-LOGGING;
    }
    leaf tunnel-name {
      type string;
      description "Tunnel name";
    }
    leaf tunnel-id {
      type uint32;
      description "Tunnel id";
    }
    leaf is-p2mp {
      type boolean;
      description "True if tunnel is a P2MP tunnel";
    }
    leaf signaled-name {
      type string;
      description "Signaled name";
    }
    leaf configured-bandwidth {
      type uint32;
      description "Configured Bandwidth";
    }
    leaf interface-configured-bandwidth {
      type uint32;
      description "Configured Interface Bandwidth";
    }
    leaf bandwidth-type {
      type Mpls-te-bw-pool;
      description "The bandwidth type";
    }
    leaf setup-priority {
      type uint8;
      description "Setup priority";
    }
    leaf hold-priority {
      type uint8;
      description "Hold priority";
    }
    leaf policy-class {
      type uint8;
      description "deprecated";
    }
    leaf forward-class {
      type uint32;
      description "Forward class";
    }
    leaf is-forward-class-configured {
      type boolean;
      description "True if Forward class is configured";
    }
    leaf backup-bandwidth {
      type uint32;
      description "Backup bandwidth";
    }
    leaf backup-bandwidth-flags {
      type uint8;
      description "Backup bandwidth flags";
    }
    leaf config-load-share {
      type uint32;
      description "Config loadshare";
    }
    leaf payload-type {
      type uint16;
      description "Payload type";
    }
    leaf is-in-config {
      type boolean;
      description "Is in config";
    }
    leaf explicit-null-imposition {
      type boolean;
      description "Imposition of Explicit NULL";
    }
    leaf fast-reroute {
      type boolean;
      description "Fast reroute enabled";
    }
    leaf is-backup-tunnel {
      type boolean;
      description "TRUE if this is a backup tunnel";
    }
    leaf record-route {
      type boolean;
      description "Record route";
    }
    leaf srlg-discovery {
      type boolean;
      description "SRLG-discovery enabled";
    }
    leaf path-protection-enabled {
      type boolean;
      description "Path Protection enabled";
    }
    leaf hop-limit {
      type uint8;
      description "Hop Limit";
    }
    leaf cost-limit {
      type uint32;
      description "Cost limit on the tunnel path";
    }
    leaf cost-limit-global {
      type uint32;
      description "Global Cost Limit";
    }
    leaf delay-limit {
      type uint32;
      description "Delay limit on the tunnel path (usec)";
    }
    leaf delay-limit-global {
      type uint32;
      description "Global Delay Limit (usec)";
    }
    leaf path-invalidation-timeout-source {
      type uint32;
      description "Path invalidation timeout configuration source";
    }
    leaf path-invalidation-timeout {
      type uint32;
      description
        "Path invalidation timeout interval on the tunnel
        path";
    }
    leaf path-invalidation-action-source {
      type uint32;
      description "Path invalidation action configuration source";
    }
    leaf path-invalidation-action {
      type uint32;
      description "Path invalidation action on the tunnel path";
    }
    leaf soft-preempt {
      type boolean;
      description "Soft preemption enabled";
    }
    leaf disable-affinity-failure-reopt {
      type boolean;
      description "DisableAffinityFailureReopt";
    }
    leaf affinity-failure-reopt-timer {
      type uint32;
      description "AffinityFailureReoptTimer";
    }
    leaf segment-routing-path-selection {
      type Te-s2l-sr-path-selection;
      description "Segment-Routing path selection type";
    }
    list policy-class-entry {
      description "PBTS policy classes";
        leaf entry {
                  type uint8;

                  description "PBTS policy classes";
        }
    }

    list autoroute-destination {
      description "Autoroute Destinations list";
      uses MPLS-TE-AUTOROUTE-DESTINATION-BAG;
    }
  }

  grouping MPLS-TE-P2MP-TUNNEL-BAG {
    description "P2MP tunnel data";

    container config {
      description "Configuration data";
      uses MPLS-TE-P2MP-TUN-CFG-BAG;
    }

    container tunnel-current-lsp {
      description "Current LSP";
      uses MPLS-TE-P2MP-LSP;
    }

    container reoptimized-p2mp-lsp {
      description "Reopt LSP";
      uses MPLS-TE-P2MP-LSP;
    }

    container tunnel-standby-lsp {
      description "Standby LSP";
      uses MPLS-TE-P2MP-LSP;
    }

    container reoptimized-standby-p2mp-lsp {
      description "Standby Reopt LSP";
      uses MPLS-TE-P2MP-LSP;
    }

    container tunnel-restoration-lsp {
      description "Restoration LSP";
      uses MPLS-TE-P2MP-LSP;
    }

    container delay-clean-pp-lsp {
      description "Delay Clean PP LSP";
      uses MPLS-TE-P2MP-LSP;
    }

    container cleaned-lsp {
      description "Cleaned LSP";
      uses MPLS-TE-P2MP-LSP;
    }

    container p2p-info {
      description "P2P specific info";
      uses MPLS-TE-P2P-INFO-BAG;
    }

    container auto-capacity {
      description "Auto-capacity Info";
      uses MPLS-TE-AUTOCAPACITY;
    }

    container history {
      description "Tunnel history";
      uses MPLS-TE-TUNNELS-HISTORY-BAG;
    }

    container path-protection {
      description "Path Protect Info";
      uses MPLS-TE-PP-INFO;
    }

    container auto-backup {
      description "Autobackup Information";
      uses MPLS-TE-AUTOBACKUP-INFO;
    }

    container auto-mesh {
      description "Automesh Information";
      uses MPLS-TE-AUTOMESH-INFO;
    }

    container auto-pcc {
      description "Auto-PCC Information";
      uses MPLS-TE-AUTOPCC-INFO;
    }

    container pce-delegation {
      description "PCE Delegation information";
      uses MPLS-TE-PCE-DELEGATION-INFO;
    }

    container soft-preemption {
      description
        "Tunnel head soft preemption info. This is NULL
        if soft preemption is not configured";
      uses MPLS-TE-SOFT-PREEMPTION-TUNNEL-INFO;
    }

    container wdm-unitunnel {
      description
        "WDM-UNI tunnel data. Only exists for WDM-UNI
        tunnels";
      uses MPLS-TE-MGMT-WDM-UNI-TUNNEL-INFO;
    }

    container transport-tunnel-info {
      description
        "Transport tunnel data. Only exists for Transport
        tunnels";
      uses MPLS-TE-TRANSPORT-TUNNEL-INFO;
    }

    container bfd-info {
      description
        "BFD session info. This is NULL if BFD is not
        configured";
      uses MPLS-TE-TUNNEL-BFD-INFO;
    }

    container otn-bidir {
      description "OTN bidir info";
      uses MPLS-TE-TUNNEL-OTN-BIDIR-INFO;
    }

    container bidir {
      description "Bidir info";
      uses MPLS-TE-TUNNEL-BIDIR-INFO;
    }

    container xro-attribute-set {
      description "XRO attribute-set";
      uses MPLS-TE-ATTRIBUTE-SET;
    }

    container te-tunnel-convergence {
      description "TE tunnel convergence related information";
      uses TE-VIF-CONVERGENCE-INFO;
    }

    container flex-info {
      description "Flex Info";
      uses MPLS-TE-TUNNEL-FLEX-INFO;
    }
    leaf role-standby {
      type boolean;
      description "TRUE if Role is Standby, Active otherwise";
    }
    leaf tunnel-interface-name {
      type xr:Interface-name;
      description "Interface handle of the associated tunnel";
    }
    leaf admin-state {
      type Mte-tunnel-admin-state;
      description "Administrative State";
    }
    leaf operational-state {
      type Mte-tunnel-oper-state;
      description "Operational State";
    }
    leaf operational-state-changes {
      type uint32;
      description "Counters for operational state changes";
    }
    leaf signaled-name {
      type string;
      description "Signaled Name";
    }
    leaf fail-reason {
      type Mpls-mte-tunnel-fail-reason;
      description "The reason why failure occurred";
    }
    leaf destination-up-count {
      type uint32;
      description "Count of up destinations";
    }
    leaf destination-disabled-count {
      type uint32;
      description "Count of disabled destinations";
    }
    leaf destination-down-count {
      type uint32;
      description "Count of down destinations";
    }
    leaf re-opt-hold-down-timer-remaining {
      type uint32;
      units "second";
      description
        "Backup hold-down timer remaining time in seconds";
    }
    leaf bandwidth-requested {
      type uint32;
      description "Bandwidth Requested";
    }
    leaf bandwidth-type {
      type Mpls-te-bw-pool;
      description "The requested bandwidth type";
    }
    leaf is-node-protected {
      type boolean;
      description "Node Protection Enabled or Disabled";
    }
    leaf is-bandwidth-protect {
      type boolean;
      description "BW Protection Enabled or Disabled";
    }
    leaf tunnel-recovering {
      type boolean;
      description "Tunnel recovering";
    }
    leaf reroute-pending {
      type boolean;
      description "ReroutePending";
    }
    leaf explicit-path-change {
      type boolean;
      description
        "Explicit-path inuse by the current LSP has been
        modified";
    }
    leaf path-option-change {
      type boolean;
      description
        "Path-Option inuse by the current LSP has been
        modified";
    }
    leaf affinity-failure-reopt-disabled {
      type boolean;
      description "AffinityFailureReoptDisabled";
    }
    leaf affinity-failure-reopt-time-remained {
      type uint32;
      description "AffinityFailureReoptTimeRemained";
    }
    leaf affinity-failure-delayed-tear-time-remained {
      type uint32;
      description "Affinity Failure LSP tear down time remaining";
    }
    leaf invalidation-time-remained {
      type uint32;
      description "Path invalidation time remaining";
    }
    leaf drop-mode {
      type boolean;
      description "True if tunnel is in drop mode";
    }
    leaf auto-route {
      type boolean;
      description "IGP Auto route announce enabled";
    }
    leaf forwarding-adjacency {
      type boolean;
      description "IGP forwarding adjacency enabled";
    }
    leaf load-share-factor {
      type uint32;
      description "The specified loadsharing for the tunnel";
    }
    leaf load-share-type {
      type Mpls-te-loadshare;
      description "Loadsharing type";
    }
    leaf create-time {
      type uint32;
      description "Time at which the tunnel was created";
    }
    leaf uptime {
      type uint32;
      units "second";
      description "Time in seconds since the tunnel was up";
    }
    leaf metric-type {
      type Mpls-te-metric;
      description "The path selection metric";
    }
    leaf tie-breaker {
      type Te-path-selection-tiebreaker;
      description "The path selection tiebreaker";
    }
    leaf tiebreaker-type {
      type uint32;
      description "Deprecated - replaced by Tiebreaker";
    }
    leaf tiebreaker-qualifier {
      type Mpls-te-metric-qualifier;
      description
        "Describes how the path selection tiebreaker was
        specified: default, globally set, or per
        interface";
    }
    leaf metric-qualifier {
      type Mpls-te-metric-qualifier;
      description
        "Describe how the metric was specified: default,
        globally set, or per interface";
    }
    leaf is-hop-limit-ignore {
      type boolean;
      description "Is Hop-limit ignored";
    }
    leaf hop-limit-ignored-reason {
      type Te-hop-limit-ignore;
      description "Hop-limit ignored reason";
    }
    leaf outbound-frr-state {
      type Mpls-te-frr-state;
      description "Indicates outbound FRR state";
    }
    leaf area-id {
      type string;
      description
        "Indicates the protocol and area used to find
        Outgoing ERO";
    }
    leaf pce-fail-reason {
      type Mpls-te-pce-fail-reasons;
      description "Failure reason for PCE-based tunnels";
    }
    leaf snmp-index {
      type uint32;
      description "SNMP index for interface";
    }
    leaf is-inter-area-tunnel {
      type boolean;
      description
        "Indicates whether this tunnel spans multiple
        areas.";
    }
    leaf is-auto-backup {
      type boolean;
      description
        "Indicates whether this is an automatically
        generated backup tunnel";
    }
    leaf is-auto-pcc {
      type boolean;
      description
        "Indicates whether this is an automatic PCC
        tunnel";
    }
    leaf is-pce-delegated {
      type boolean;
      description
        "Indicates whether this tunnel is delegated to a
        PCE server or not";
    }
    leaf tunnel-attribute-set-name {
      type string;
      description "AttributeSet name";
    }
    leaf tunnel-attribute-set-type {
      type Tunnel-attribute-set;
      description "AttributeSet type";
    }
    leaf xro-attribute-set-name {
      type string;
      description "Configured XRO attribute-set name";
    }
    leaf is-passive {
      type boolean;
      description "True for passive tunnel";
    }
    leaf passive-tunnel-name {
      type string;
      description "Passive tunnel name";
    }
    leaf binding-label-exists {
      type boolean;
      description "True, if binding label exists";
    }
    leaf binding-label {
      type uint32;
      description "Binding Label";
    }
    leaf last-hop-ifindex {
      type uint32;
      description "Termination destination ifindex";
    }
    leaf is-named {
      type boolean;
      description "Indicates whether this tunnel is named";
    }
    leaf lsp-wrap-protection-enabled {
      type boolean;
      description "Lsp-wrap Protection enabled";
    }
    leaf lsp-wrap-label {
      type uint32;
      description "Lsp-wrap label value";
    }
    leaf is-interface {
      type boolean;
      description "True for tunnel head";
    }
    leaf last-path-change {
      type uint32;
      units "second";
      description "Time in seconds since the last path change";
    }
    leaf persistent-bytes {
      type uint64;
      units "byte";
      description
        "Persistent forwarding statistics for number of
        bytes. Clear counters will not reset the counter";
    }
    leaf persistent-packets {
      type uint64;
      description
        "Persistent forwarding statistics for Number of
        packets. Clear counters will not reset the
        counter";
    }
    leaf autoroute-announce-exclude-segment-routing {
      type boolean;
      description
        "Indicates whether this tunnel is autoroute
        announced with exclude segment-routing option";
    }
    leaf last-working-lsp-id {
      type uint16;
      description "LSP-id of last working LSP";
    }

    list destination {
      description "Destinations array";
      uses MPLS-TE-P2MP-DEST;
    }
  }

  grouping MPLS-TE-PATH-METRICS {
    description "Path metrics info";
    leaf te-metric {
      type uint64;
      description "Path TE Metric";
    }
    leaf igp-metric {
      type uint64;
      description "Path IGP Metric";
    }
    leaf delay-metric {
      type uint64;
      description "Path Delay Metric";
    }
  }

  grouping MPLS-TE-S2L-DIVERSITY-INFO {
    description "S2l Diversity info";
    leaf diversity-type {
      type Te-pp-diversity;
      description "S2L path diversity type";
    }
  }

  grouping TUNNEL-MIDPOINT-LSP-WRAP-INFO-BAG {
    description "Midpoint LSP Wrap Protection LSP Info";
    leaf lsp-wrap-protection-enable {
      type boolean;
      description "LSP Wrap protection enabled";
    }
    leaf lsp-wrap-protection-label {
      type uint32;
      description "LSP Wrap Merge Point Label";
    }
    leaf reverse-egress-interface {
      type string;
      description "Reverse Egress Interface";
    }
    leaf reverse-lsp-label {
      type uint32;
      description "Reverse LSP label";
    }
    leaf lsp-wrap-protection-state {
      type Mpls-te-lsp-wrap-state;
      description "LSP wrap protection state";
    }
  }

  grouping TE-S2L-SR-PATH-HOP {
    description "TE Segment-Routing S2L path hop";
    leaf sid-type {
      type Te-sr-sid;
      description "Type of the SID";
    }
    leaf has-ip-addresses {
      type boolean;
      description "Node has IP addresses specified";
    }
    leaf local-addr {
      type inet:ipv4-address;
      description "Local IP address of adjacency or Node ID";
    }
    leaf remote-addr {
      type inet:ipv4-address;
      description "Remote IP address of adjacency";
    }
    leaf has-mpls-label {
      type boolean;
      description "Hop has MPLS label specified";
    }
    leaf mpls-label-value {
      type uint32;
      description "The MPLS label value";
    }
    leaf has-entropy-label {
      type boolean;
      description "Hop has EL specified";
    }
  }

  grouping MPLS-TE-S2L-FLEX-INFO {
    description "TE Per-S2L FlexLSP Information";

    container flex-fec {
      description "FEC for the FlexLSP Entry";
      uses TE-S2L-FEC;
    }
    leaf entry-exists {
      type boolean;
      description "FlexLSP Entry Exists";
    }
    leaf in-label {
      type uint32;
      description "In Label";
    }
    leaf bfd-created {
      type boolean;
      description "GAL BFD Session Created";
    }
    leaf bfd-up {
      type boolean;
      description "GAL BFD Session Up";
    }
    leaf oam-created {
      type boolean;
      description "OAM Entry Created";
    }
    leaf bfd-next-hop {
      type inet:ipv4-address;
      description "BFD Next Hop";
    }
    leaf bfd-tun-ifh {
      type xr:Interface-name;
      description "BFD Tunnel Interface Handle";
    }
    leaf bfd-out-ifh {
      type xr:Interface-name;
      description "BFD Out Interface Handle";
    }
    leaf bfd-int-label {
      type uint32;
      description "BFD Internal Label";
    }
    leaf bfd-egress-label {
      type uint32;
      description "BFD Egress Label";
    }
    leaf fault-ldi-lockout {
      type boolean;
      description "Fault LDI Lockout";
    }
    leaf fault-ldi {
      type boolean;
      description "Fault LDI";
    }
    leaf fault-lkr {
      type boolean;
      description "Fault LKR";
    }
    leaf fault-ais {
      type boolean;
      description "Fault AIS";
    }
    leaf fault-time {
      type uint32;
      description "Fault Time";
    }
  }

  grouping MPLS-TE-S2L-PROTECTION-OBJECT {
    description "TE Protection Object";
    leaf s2l-secondary {
      type boolean;
      description " S2L Protection Secondary Bit";
    }
    leaf s2l-protecting {
      type boolean;
      description " S2L Protection Protecting Bit";
    }
    leaf s2l-notification {
      type boolean;
      description " S2L Protection Notification Bit";
    }
    leaf s2l-operational {
      type boolean;
      description " S2L Protection Operational Bit";
    }
    leaf enhanced {
      type boolean;
      description "Indicates Enhanced Protection Scheme";
    }
    leaf ded1-plus1 {
      type boolean;
      description "Dedicated 1+1 Protection";
    }
    leaf ded1-to1 {
      type boolean;
      description "Dedicated 1:1 Protection";
    }
    leaf shared {
      type boolean;
      description "Shared Link Layer Protection";
    }
    leaf link-unprotected {
      type boolean;
      description "LSP should not use any Link Layer Protection";
    }
    leaf extra-traffic {
      type boolean;
      description
        "LSP should use Links that are protecting other
        (primary) traffic";
    }
    leaf any {
      type boolean;
      description "Any";
    }
    leaf rerouting {
      type boolean;
      description "Full Rerouting";
    }
    leaf rerouting-no-et {
      type boolean;
      description "Rerouting Without Extra-Traffic";
    }
    leaf one-to-n-protection-et {
      type boolean;
      description "1:N Protection with Extra-Traffic";
    }
    leaf one-plus-one-uni {
      type boolean;
      description "1+1 Unidirectional Protection";
    }
    leaf one-plus-one-bi {
      type boolean;
      description "1+1 Bidirectional Protection";
    }
    leaf lsp-unprotected {
      type boolean;
      description "LSP Flags Unprotected";
    }
  }

  grouping MPLS-TE-S2L-ASSOCIATION-OBJECT {
    description "TE Association Object";
    leaf s2l-association-type {
      type uint16;
      description
        "S2L Association Type                         
        (draft-ietf-ccamp-mpls-tp-rsvpte-ext-associated-lsp)";
    }
    leaf s2l-association-tie-role {
      type Te-association-tie-role;
      description "S2L Association Tie Role";
    }
    leaf s2l-association-id {
      type uint16;
      description "S2L Association ID";
    }
    leaf s2l-association-source {
      type inet:ipv4-address;
      description "S2L Association Source";
    }
    leaf s2l-global-source {
      type uint32;
      description "S2L Global Source";
    }
    list s2l-extended-id {
      description "S2L Extended ID Array";
        leaf entry {
                  type uint32;

                  description "S2L Extended ID Array";
        }
    }
  }

  grouping TE-S2L-SRLG-COLLECT-INFO {
    description "SRLG-collection information";
    leaf srlg-collect-type {
      type Te-srlg-collect-request;
      description "SRLG-collection mechanism";
    }
    list discovered-srlg {
      description "Discovered SRLGs";
        leaf entry {
                  type uint32;

                  description "Discovered SRLGs";
        }
    }
  }

  grouping MPLS-TE-TAIL-BFD-INFO {
    description "TE Tail-end BFD information";

    container session-info {
      description "BFD Session Info";
      uses MPLS-TE-BFD-SESSION-INFO;
    }
    leaf failure-diagnostic-code {
      type uint32;
      description "BFD session failure diagnostic code";
    }
    leaf failure-reason {
      type string;
      description "BFD session failure reason";
    }
    leaf local-discriminator {
      type uint32;
      description "BFD Local Discriminator";
    }
    leaf remote-discriminator {
      type uint32;
      description "BFD Remote Discrminator";
    }
    leaf min-interval {
      type uint32;
      description "Hello interval in mini second";
    }
    leaf min-interval-default {
      type boolean;
      description "Is default hello interval";
    }
    leaf multiplier {
      type uint8;
      description "Multiplier";
    }
    leaf multiplier-default {
      type boolean;
      description "Is default multiplier";
    }
  }

  grouping MPLS-TE-BFD-DELETION-HISTORY {
    description "TE Tunnel BFD Session Deletion History";
    leaf lsp-id {
      type uint16;
      description "LSP ID of the BFD session get deleted";
    }
    leaf deletion-time {
      type uint32;
      description "Time stamp of the BFD session get deleted";
    }
    leaf deletion-reason {
      type string;
      description "Reason for the BFD session get deleted";
    }
    leaf deletion-diagnostic-code {
      type uint32;
      description "Diagnostic Code for the BFD session get deleted";
    }
  }

  grouping MPLS-TE-BFD-SESSION-INFO {
    description "TE BFD Session Info";
    leaf state {
      type Te-bfd-lsp-session-state;
      description "BFD session state";
    }
    leaf state-change-time {
      type uint32;
      units "second";
      description
        "Time in seconds since the last session state
        change";
    }
  }

  grouping MPLS-TE-HEAD-BFD-INFO {
    description "TE Head-end BFD information";

    container session-info {
      description "BFD Session Info";
      uses MPLS-TE-BFD-SESSION-INFO;
    }

    container deletion-history {
      description "BFD Session Deletion History";
      uses MPLS-TE-BFD-DELETION-HISTORY;
    }
    leaf creation-time {
      type uint32;
      units "second";
      description "Time in seconds since the BFD session created";
    }
    leaf lspbfd-type {
      type Te-vif-bfd;
      description "LSP BFD type";
    }
    leaf is-redundant {
      type boolean;
      description "sBFD session is redundant";
    }
    leaf bfd-reverse-path-stale {
      type boolean;
      description
        "The BFD reverse path is stale compared to
        configuration";
    }
    list bfd-reverse-path-label {
      description "BFD reverse path labels";
        leaf entry {
                  type uint32;

                  description "BFD reverse path labels";
        }
    }
  }

  grouping TE-PVT-PROT-OBJ {
    description "Private Protection information signaled";
    leaf sbit {
      type boolean;
      description "Secondary bit";
    }
    leaf pbit {
      type boolean;
      description "Protecting bit";
    }
    leaf nbit {
      type boolean;
      description "Notification bit ";
    }
    leaf obit {
      type boolean;
      description "Operational bit";
    }
    leaf protect-type {
      type Te-protect;
      description "LSP Protect Type";
    }
    leaf is-wtr-present {
      type boolean;
      description "Is Wait-to-Restore timeout present";
    }
    leaf wtr-timeout {
      type uint32;
      description "Wait-to-Restore timeout";
    }
    leaf is-hopresent {
      type boolean;
      description "Is Hold-Off timeout present";
    }
    leaf ho-timeout {
      type uint32;
      description "Hold-Off timeout";
    }
    leaf is-snc-mode-present {
      type boolean;
      description "Is SNC mode present";
    }
    leaf snc-mode {
      type Te-aps-snc-mode;
      description "SNC mode";
    }
    leaf tcm-id {
      type uint32;
      description "TCM ID";
    }
    leaf path-prot-profile-type {
      type Te-path-prot-profile;
      description "Path protection profile type";
    }
  }

  grouping MPLS-TE-S2L-APS-INFO {
    description "APS Protection Info of S2L";

    container protection-info {
      description "Protection Info";
      uses TE-PVT-PROT-OBJ;
    }
  }

  grouping TE-ODU-FLEX-GFP-F-NON-RES-INFO {
    description
      "ODU flex info for non-resizable GFP-F framing
      type";
    leaf bit-rate {
      type uint32;
      description "Bit rate in kbit/s";
    }
  }

  grouping TE-ODU-FLEX-GFP-F-RES-INFO {
    description "ODU flex info for resizable GFP-F framing type";
    leaf bit-rate {
      type uint32;
      description "Bit rate in kbit/s";
    }
  }

  grouping TE-ODU-FLEX-CBR-INFO {
    description "ODU flex info for CBR framing type";
    leaf bit-rate {
      type uint32;
      description "Bit rate in kbit/s";
    }
    leaf tolerance {
      type uint16;
      description "Tolerance";
    }
  }

  grouping TE-ODU-V3-BW {
    description "ODU bandwidth union";

    container odu-flex-cbr {
      when "../odu-level = 'te-odu-level-flex-cbr'" {
        description "../ODULevel = 'TE_ODULevelFlexCBR'";
      }
      description "Odu flex CBR info";
      uses TE-ODU-FLEX-CBR-INFO;
    }

    container odu-flex-gfp-f-res {
      when "../odu-level = 'te-odu-level-flex-gfpf-resizeable'" {
        description "../ODULevel = 'TE_ODULevelFlexGFPFResizeable'";
      }
      description "Odu flex GFP-F resizable info";
      uses TE-ODU-FLEX-GFP-F-RES-INFO;
    }

    container odu-flex-gfp-f-non-res {
      when "../odu-level = 'te-odu-level-flex-gfpf-non-resizable'" {
        description
          "../ODULevel = 'TE_ODULevelFlexGFPFNonResizable'";
      }
      description "Odu flex GFP-F non-resizable info";
      uses TE-ODU-FLEX-GFP-F-NON-RES-INFO;
    }
    leaf odu-level {
      type Te-odu-level;
      description "ODULevel";
    }
  }

  grouping MPLS-TE-S2L-OTN-INFO {
    description "OTN S2L's Controllers' information";

    container bandwidth {
      description "OTN Bandwidth for s2l";
      uses TE-ODU-V3-BW;
    }

    container labels {
      description "Labels";
      uses MPLS-TE-MGMT-GMPLS-LABELS;
    }
    leaf incoming-controller {
      type string;
      description "Incoming Controller";
    }
    leaf incoming-controller-state {
      type Te-controller-state;
      description "State of Incoming Controller";
    }
    leaf incoming-sub-controller {
      type string;
      description "Incoming Sub Controller";
    }
    leaf incoming-sub-controller-state {
      type Te-controller-state;
      description "State of Incoming Sub Controller";
    }
    leaf outgoing-controller {
      type string;
      description "Outgoing Controller";
    }
    leaf outgoing-controller-state {
      type Te-controller-state;
      description "State of Outgoing Controller";
    }
    leaf outgoing-sub-controller {
      type string;
      description "Outgoing Sub Controller";
    }
    leaf outgoing-sub-controller-state {
      type Te-controller-state;
      description "State of Outgoing Sub Controller";
    }
    leaf cross-connect-id {
      type uint32;
      description "Cross connect id";
    }
    leaf is-connected {
      type boolean;
      description "True if subcontrollers are connected";
    }
    leaf uptime {
      type uint32;
      description "XC Uptime";
    }
    leaf outgoing-controller-ifhandle {
      type xr:Interface-name;
      description "Outgoing Controller Ifhandle";
    }
    leaf outgoing-sub-controller-ifhandle {
      type xr:Interface-name;
      description "Outgoing Sub Controller Ifhandle";
    }
    leaf incoming-controller-ifhandle {
      type xr:Interface-name;
      description "Incoming Controller Ifhandle";
    }
    leaf incoming-sub-controller-ifhandle {
      type xr:Interface-name;
      description "Incoming Sub Controller Ifhandle";
    }
    leaf gpid {
      type uint16;
      description "Gpid Payload";
    }
  }

  grouping MPLS-TE-OTN-S2L-INFO {
    description "OTN S2l information";

    container otn {
      description "Info Related to OTN technology in S2L";
      uses MPLS-TE-S2L-OTN-INFO;
    }

    container aps {
      description "APS Info for OTN S2L";
      uses MPLS-TE-S2L-APS-INFO;
    }
  }

  grouping MPLS-TE-MGMT-G709-OTN-FIXED-SIZE-LABEL {
    description "GMPLS G709 OTN fixed-size Label";
    leaf tpn {
      type uint16;
      description "Tributary time slot";
    }
    leaf bit-map-length {
      type uint16;
      description "Bit map length";
    }
    list bit-map {
      description "Bit Map";
        leaf entry {
                  type uint8;

                  description "Bit Map";
        }
    }
  }

  grouping MPLS-TE-MGMT-WDM-FIXED-GRID-LABEL {
    description "GMPLS WDM fixed-grid Label";
    leaf label-set {
      type boolean;
      description "Flag to indicate whether label is set";
    }
    leaf grid {
      type Gmpls-uni-mgmt-wdm-grid;
      description "Grid";
    }
    leaf channel-spacing {
      type Gmpls-uni-mgmt-dwdm-cs;
      description "Channel spacing";
    }
    leaf identifier {
      type uint16;
      description "Identifier";
    }
    leaf channel {
      type int16;
      description "Channel Number";
    }
  }

  grouping MPLS-TE-MGMT-GMPLS-LABEL {
    description "A GMPLS label";

    container wdm {
      when "../label-type = 'fixed-wdm'" {
        description "../LabelType = 'FixedWDM'";
      }
      description "Fixed-grid WDM label";
      uses MPLS-TE-MGMT-WDM-FIXED-GRID-LABEL;
    }

    container otn {
      when "../label-type = 'fixed-g709otn'" {
        description "../LabelType = 'FixedG709OTN'";
      }
      description "Fixed-size G09 OTN label";
      uses MPLS-TE-MGMT-G709-OTN-FIXED-SIZE-LABEL;
    }
    leaf label-type {
      type Mpls-te-mgmt-gmpls-label;
      description "LabelType";
    }
  }

  grouping MPLS-TE-MGMT-GMPLS-LABELS {
    description "GMPLS Labels";

    container path-ingress-label {
      description "Path message (upstream) ingress label";
      uses MPLS-TE-MGMT-GMPLS-LABEL;
    }

    container path-egress-label {
      description "Path message (upstream) egress label";
      uses MPLS-TE-MGMT-GMPLS-LABEL;
    }

    container resv-ingress-label {
      description "Resv message (downstream) ingress label";
      uses MPLS-TE-MGMT-GMPLS-LABEL;
    }

    container resv-egress-label {
      description "Resv message (downstream) egress label";
      uses MPLS-TE-MGMT-GMPLS-LABEL;
    }
  }

  grouping MPLS-TE-SOFT-PREEMPTION-LSP-INFO {
    description "Midpoint Soft Preemption LSP Info";
    leaf status {
      type Mpls-te-soft-preemption-state;
      description
        "The current state of the soft preemption
        operation";
    }
    leaf soft-preemption-timestamp {
      type uint32;
      description
        "The POSIX timestamp when the soft preemption
        occurred";
    }
    leaf soft-preemption-link {
      type string;
      description
        "Name of the link where the soft preemption
        occurred";
    }
    leaf preempting-link-address {
      type inet:ipv4-address;
      description
        "The address of the link where the preemption
        happened";
    }
    leaf time-to-hard-preemption {
      type uint16;
      units "second";
      description
        "The number of seconds until hard preemption is
        triggered";
    }
    leaf fr-rrewrite {
      type boolean;
      description "FRR-rewrite during soft preemption";
    }
    leaf fr-rrewrite-tunnel-name {
      type string;
      description "The tunnel name of the backup";
    }
  }

  grouping TE-LSP-CONVERGENCE-INFO {
    description "TE LSP convergence related information";
    leaf path-in {
      type uint64;
      units "nanosecond";
      description "LSP RSVP Path-in timestamp (clocktime in nsecs)";
    }
    leaf path-out {
      type uint64;
      units "nanosecond";
      description "LSP RSVP Path-in timestamp (clocktime in nsecs)";
    }
    leaf resv-in {
      type uint64;
      units "nanosecond";
      description "LSP RSVP Resv-in timestamp (clocktime in nsecs)";
    }
    leaf resv-out {
      type uint64;
      units "nanosecond";
      description
        "LSP RSVP Resv-out timestamp (clocktime in nsecs)";
    }
    leaf label-rewrite {
      type uint64;
      units "nanosecond";
      description
        "LSP Label rewrite timestamp (clocktime in nsecs)";
    }
    leaf tunnel-rewrite {
      type uint64;
      units "nanosecond";
      description "Tunnel rewrite timestamp (clocktime in nsecs)";
    }
    leaf creation-time {
      type uint64;
      units "nanosecond";
      description "Tunnel creation timestamp (clocktime in nsecs)";
    }
  }

  grouping TE-MGMT-G709-OTN-FSPEC {
    description "TE G709 OTN FSpec";
    leaf signal-type {
      type uint8;
      description "Signal Type";
    }
    leaf nmc-or-tolerance {
      type uint16;
      description "NMC or Tolerance";
    }
    leaf nvc {
      type uint16;
      description "Number of Virtual Components";
    }
    leaf multiplier {
      type uint16;
      description "Multiplier";
    }
    leaf bit-rate {
      type uint32;
      units "kbit/s";
      description "Bit Rate in kbps";
    }
  }

  grouping TE-MGMT-GENERIC-FSPEC {
    description "Union of different TE generic FSpec types";

    container otnfspec {
      when "../fspec-type = 'te-generic-fspec-type-g709otn'" {
        description "../FSpecType = 'TEGenericFSpecTypeG709OTN'";
      }
      description "TE FSpec for G709 OTN";
      uses TE-MGMT-G709-OTN-FSPEC;
    }
    leaf fspec-type {
      type Te-mgmt-generic-fspec;
      description "FSpecType";
    }
  }

  grouping TE-MGMT-G709-OTN-TSPEC {
    description "TE G709 OTN TSpec";
    leaf signal-type {
      type uint8;
      description "Signal Type";
    }
    leaf nmc-or-tolerance {
      type uint16;
      description "NMC or Tolerance";
    }
    leaf nvc {
      type uint16;
      description "Number of Virtual Components";
    }
    leaf multiplier {
      type uint16;
      description "Multiplier";
    }
    leaf bit-rate {
      type uint32;
      units "kbit/s";
      description "Bit Rate in kbps";
    }
  }

  grouping TE-MGMT-GENERIC-TSPEC {
    description "Union of different TE generic TSpec types";

    container otntspec {
      when "../tspec-type = 'te-generic-tspec-type-g709otn'" {
        description "../TSpecType = 'TEGenericTSpecTypeG709OTN'";
      }
      description "TE TSpec for G709 OTN";
      uses TE-MGMT-G709-OTN-TSPEC;
    }
    leaf tspec-type {
      type Te-mgmt-generic-tspec;
      description "TSpecType";
    }
  }

  grouping BANDWIDTH-SPEC-BAG {
    description "Bandwidth information of a flow";
    leaf average-rate {
      type uint64;
      units "kbit/s";
      description "Average bandwidth in  kbps";
    }
    leaf maximum-burst {
      type uint64;
      units "byte";
      description "Maximum burst of data in bytes";
    }
    leaf peak-rate {
      type uint64;
      units "kbit/s";
      description "Peak rate in  kbps";
    }
  }

  grouping TUNNEL-HOP-INFO {
    description "Hop information";
    leaf hop-address {
      type inet:ipv4-address;
      description "Hop address";
    }
    leaf hop-affinity {
      type uint32;
      description "Deprecated";
    }
    list hop-extended-affinity {
      description "Hop affinity";
        leaf entry {
                  type uint32;

                  description "Hop affinity";
        }
    }
  }

  grouping RSVP-MGMT-RRO-SRLG-SUBOBJ {
    description "RSVP RRO SRLG subobject";
    list srl-gs {
      description "The RRO Subobject SRLGs";
        leaf entry {
                  type uint32;

                  description "The RRO Subobject SRLGs";
        }
    }
  }

  grouping RSVP-MGMT-RRO-UNNUMBERED-SUBOBJ-FLAGS {
    description "RSVP RRO UNNUMBERED Subobject Flags";
    leaf is-protection-available {
      type boolean;
      description "Local Protection Available";
    }
    leaf is-protection-in-use {
      type boolean;
      description "Local Protection In Use";
    }
    leaf is-bandwidth-protected {
      type boolean;
      description "Bandwidth Protection Available";
    }
    leaf is-node-protection-available {
      type boolean;
      description "Node Protection Available";
    }
    leaf is-node-id {
      type boolean;
      description "Node ID In Use";
    }
  }

  grouping RSVP-MGMT-RRO-UNNUMBERED-SUBOBJ {
    description "RSVP RRO Unnumbered subobject";

    container flags {
      description "The RRO Subobject Unnumbered Flags";
      uses RSVP-MGMT-RRO-UNNUMBERED-SUBOBJ-FLAGS;
    }
    leaf interface-address {
      type inet:ipv4-address;
      description "The RRO Interface Address";
    }
    leaf interface-id {
      type uint32;
      description "The RRO Interface ID";
    }
  }

  grouping RSVP-MGMT-RRO-LABEL-SUBOBJ-FLAGS {
    description "RSVP RRO Label Subobject Flags";
    leaf is-global-label {
      type boolean;
      description "Label is Global across all interfaces";
    }
  }

  grouping RSVP-MGMT-RRO-LABEL-SUBOBJ {
    description "RSVP RRO Label subobject";

    container flags {
      description "The RRO Subobject Label Flags";
      uses RSVP-MGMT-RRO-LABEL-SUBOBJ-FLAGS;
    }
    leaf label {
      type uint32;
      description "The RRO Subobject Label Value";
    }
    leaf is-label-variable-length {
      type boolean;
      description "Is the RRO Subobject Label Variable Length";
    }
    list variable-length-label {
      description "The RRO Subobject Variable Length Label";
        leaf entry {
                  type uint32;

                  description "The RRO Subobject Variable Length Label";
        }
    }
  }

  grouping RSVP-MGMT-RRO-IPV4-SUBOBJ-FLAGS {
    description "RSVP RRO IPV4 Subobject Flags";
    leaf is-protection-available {
      type boolean;
      description "Local Protection Available";
    }
    leaf is-protection-in-use {
      type boolean;
      description "Local Protection In Use";
    }
    leaf is-bandwidth-protected {
      type boolean;
      description "Bandwidth Protection Available";
    }
    leaf is-node-protection-available {
      type boolean;
      description "Node Protection Available";
    }
    leaf is-node-id {
      type boolean;
      description "Node ID In Use";
    }
  }

  grouping RSVP-MGMT-RRO-IPV4-SUBOBJ {
    description "RSVP RRO IPV4 subobject";

    container flags {
      description "The RRO IPV4 Subobject Flags";
      uses RSVP-MGMT-RRO-IPV4-SUBOBJ-FLAGS;
    }
    leaf rro-address {
      type inet:ipv4-address;
      description "The RRO IPV4 Address";
    }
  }

  grouping RSVP-MGMT-RRO-SUBOBJ {
    description "Union of the different RSVP RRO types";

    container ipv4rro-sub-object {
      when "../rro-type = 'ipv4rro-type'" {
        description "../RROType = 'IPv4RROType'";
      }
      description "IPV4 RRO Sub Object";
      uses RSVP-MGMT-RRO-IPV4-SUBOBJ;
    }

    container label-rro-sub-object {
      when "../rro-type = 'label-rro-type'" {
        description "../RROType = 'LabelRROType'";
      }
      description "Label RRO Sub Object";
      uses RSVP-MGMT-RRO-LABEL-SUBOBJ;
    }

    container unnumbered-rro-sub-object {
      when "../rro-type = 'unnumbered-rro-type'" {
        description "../RROType = 'UnnumberedRROType'";
      }
      description "Unnumbered RRO Sub Object";
      uses RSVP-MGMT-RRO-UNNUMBERED-SUBOBJ;
    }

    container srlg-rro-sub-object {
      when "../rro-type = 'srlg-rro-type'" {
        description "../RROType = 'SRLG_RROType'";
      }
      description "SRLG RRO Sub Object";
      uses RSVP-MGMT-RRO-SRLG-SUBOBJ;
    }
    leaf rro-type {
      type Rsvp-mgmt-rro-subobj;
      description "RROType";
    }
  }

  grouping RSVP-MGMT-ERO-UNNUM-SUBOBJ {
    description "RSVP ERO UNNUM subobject";
    leaf is-strict-route {
      type boolean;
      description "ERO Entry Is Strict";
    }
    leaf ero-interface-id {
      type uint32;
      description "The Interface ID in ERO";
    }
    leaf ero-router-id {
      type inet:ipv4-address;
      description "The Router ID in ERO";
    }
    leaf status {
      type Rsvp-mgmt-ero-subobj-status;
      description "Status of ERO";
    }
  }

  grouping RSVP-MGMT-ERO-IPV4-SUBOBJ {
    description "RSVP ERO IPV4 subobject";
    leaf is-strict-route {
      type boolean;
      description "ERO Entry Is Strict";
    }
    leaf ero-address {
      type inet:ipv4-address;
      description "The ERO IPV4 Address";
    }
    leaf prefix-length {
      type uint8;
      description "ERO Prefix Length";
    }
  }

  grouping RSVP-MGMT-ERO-SUBOBJ {
    description "Union of the different RSVP ERO types";

    container ipv4ero-sub-object {
      when "../ero-type = 'rsvp-mgmt-ero-type-ipv4'" {
        description "../EROType = 'RSVP_MGMT_ERO_TYPE_IPv4'";
      }
      description "IPV4 ERO Sub Object";
      uses RSVP-MGMT-ERO-IPV4-SUBOBJ;
    }

    container unnumbered-ero-sub-object {
      when "../ero-type = 'rsvp-mgmt-ero-type-un-num'" {
        description "../EROType = 'RSVP_MGMT_ERO_TYPE_UNNUM'";
      }
      description "Unnumbered ERO Sub Object";
      uses RSVP-MGMT-ERO-UNNUM-SUBOBJ;
    }
    leaf ero-type {
      type Rsvp-mgmt-ero-subobj;
      description "EROType";
    }
  }

  grouping MPLS-TE-P2MP-SIG-ERROR {
    description "P2MP signalling error";
    leaf error-node {
      type uint32;
      description "Source address of the error generating node";
    }
    leaf error {
      type uint8;
      description "Path Error code";
    }
    leaf sub-code {
      type uint16;
      description "Path Error subcode";
    }
    leaf lsp-mode {
      type Mpls-te-lsp-mode;
      description "LSPMode";
    }
    leaf log-time {
      type uint32;
      units "second";
      description
        "Time in seconds when the error message is logged";
    }
    leaf signalling-lsp-id {
      type uint16;
      description "LSP-id for which the error was received";
    }
    leaf error-message {
      type string;
      description "Error message (for display purposes only)";
    }
    leaf reverse-lsp {
      type boolean;
      description "Indicates if error is on the reverse LSP";
    }
  }

  grouping MPLS-TE-P2MP-PCALC-ERROR {
    description "Path computation error information";
    leaf error-message {
      type string;
      description "Error message (for display purposes only)";
    }
    leaf lsp-mode {
      type Mpls-te-lsp-mode;
      description "LSP Mode";
    }
    leaf log-time {
      type uint32;
      units "second";
      description
        "Time in seconds seconds (since Jan. 1, 1970)
        when the error message is logged";
    }
  }

  grouping MPLS-TE-ATTRIBUTE-SET-SR-PREPEND-ENTRY {
    description "TE segment routing prepend entry";
    leaf type {
      type Te-attribute-set-sr-prepend;
      description "Prepend Type";
    }
    leaf index {
      type uint32;
      description "Prepend index";
    }
    leaf next-label {
      type uint32;
      description "Prepend next label";
    }
  }

  grouping MPLS-TE-ATTRIBUTE-SET-SR-PREPEND-LIST {
    description "TE segment routing prepend list";

    list prepend-entry {
      description "List of prepend entries";
      uses MPLS-TE-ATTRIBUTE-SET-SR-PREPEND-ENTRY;
    }
  }

  grouping MPLS-TE-ATTRIBUTE-SET-P2P-TE {
    description "TE P2P-TE Attribute Set";

    container affinity {
      description "Affinity";
      uses MPLS-TE-TUNNELS-AFFINITY-INFO;
    }

    container logging {
      description "Logging attributes";
      uses MPLS-TE-LOGGING-ATTRIBUTES;
    }

    container prepend-list {
      description "SR prepend list";
      uses MPLS-TE-ATTRIBUTE-SET-SR-PREPEND-LIST;
    }
    leaf is-affinity-configured {
      type boolean;
      description "Is affinity configured";
    }
    leaf path-selection-segment-routing-adjacency-protection {
      type Te-s2l-sr-path-selection;
      description "Path selection segment-routing type";
    }
    leaf is-path-selection-segment-routing-adjacency-protection-configured {
      type boolean;
      description "Is path selection segment routing configured";
    }
    leaf path-invalidation-timeout {
      type uint32;
      description "Path invalidation timeout on the tunnel path";
    }
    leaf path-selection-invalidation-action {
      type Te-path-inval-action;
      description "Path invalidation action";
    }
    leaf is-path-invalidation-timeout-configured {
      type boolean;
      description "Is Path Invalidation timeout configured";
    }
    leaf is-path-invalidation-action-configured {
      type boolean;
      description "Is Path Invalidation action configured";
    }
    leaf path-selection-metric {
      type Mpls-te-metric;
      description "Path selection metric type";
    }
    leaf is-path-selection-metric-configured {
      type boolean;
      description "Is path selection metric configured";
    }
    leaf path-selection-segment-routing-margin {
      type uint32;
      description "Path selection margin";
    }
    leaf is-path-selection-segment-routing-margin-relative {
      type boolean;
      description "Path selection margin is_relative";
    }
    leaf is-path-selection-segment-routing-margin-configured {
      type boolean;
      description "Is path selection margin configured";
    }
    leaf path-selection-segment-routing-segment-limit {
      type uint32;
      description "Is path selection segment limit configured";
    }
    leaf is-path-selection-segment-routing-segment-limit-configured {
      type boolean;
      description "Is path selection segment limit configured";
    }
    leaf is-path-select-configured {
      type boolean;
      description
        "Is any of the path selection parameters
        configured";
    }
    leaf is-prepend-list-configured {
      type boolean;
      description "Is SR prepend list configured";
    }
    leaf is-pce-configured {
      type boolean;
      description "Is PCE Configured";
    }
    leaf is-pce-disj-source-configured {
      type boolean;
      description "Is PCE Disjoint Path Source Configured";
    }
    leaf is-pce-disj-type-configured {
      type boolean;
      description "Is PCE Disjoint Path Type Configured";
    }
    leaf is-pce-disj-group-id-configured {
      type boolean;
      description "Is PCE Disjoint Path Group ID Configured";
    }
    leaf pcedp-source-address {
      type uint32;
      description "PCE Disjoint Path Source Address";
    }
    leaf pcedp-type {
      type Te-pce-disjoint;
      description "PCE Disjoint Path Type";
    }
    leaf pcedp-group-id {
      type uint32;
      description "PCE Disjoint Path Group ID";
    }
    leaf is-pceb-dj-source-configured {
      type boolean;
      description "Is PCE Bidirectional Source Configured";
    }
    leaf is-pcebd-group-id-configured {
      type boolean;
      description "Is PCE Bidirectional Group ID Configured";
    }
    leaf pcebd-source-address {
      type uint32;
      description "PCE Bidirectional Source Address";
    }
    leaf pcebd-group-id {
      type uint32;
      description "PCE Bidirectional Group ID";
    }
    list tunnel-id {
      description "Tunnel ID";
        leaf entry {
                  type uint16;

                  description "Tunnel ID";
        }
    }
  }

  grouping MPLS-TE-ATTRIBUTE-SET-APS-PP {
    description "TE OTN path protection attribute set";

    container revert-schedule {
      description "Revert Schedule";
      uses TE-REVERT-SCH;
    }
    leaf snc-mode {
      type Te-aps-snc-mode;
      description "Sub-network Connection Mode";
    }
    leaf tcm-id {
      type uint32;
      description "Sub-network Connection Monitoring Mode";
    }
    leaf protection-type {
      type Te-protect;
      description "Protection Type";
    }
    leaf protection-mode {
      type Te-pnr-revert-options;
      description "Protection Restoration Mode";
    }
    leaf wait-to-restore-time {
      type uint32;
      description "Wait to restore time";
    }
    leaf hold-off-time {
      type uint32;
      description "Hold-off time";
    }
    leaf path-prot-profile-type {
      type Te-path-prot-profile;
      description "Path Protection Profile Type";
    }
    leaf restoration-style {
      type Te-restoration-style;
      description "Restoration Style";
    }
  }

  grouping MPLS-TE-ATTRIBUTE-SET-P2MP-TE {
    description "TE P2MP-TE Attribute Set";

    container affinity {
      description "Affinity";
      uses MPLS-TE-TUNNELS-AFFINITY-INFO;
    }
    leaf fast-reroute {
      type boolean;
      description "Fast reroute";
    }
    leaf frr-bandwidth-protection {
      type boolean;
      description "FRR bandwidth protection";
    }
    leaf setup-priority {
      type uint8;
      description "Setup priority";
    }
    leaf hold-priority {
      type uint8;
      description "Hold priority";
    }
    leaf is-priority-configured {
      type boolean;
      description "Is priority configured";
    }
    leaf configured-bandwidth {
      type uint32;
      units "kbit/s";
      description "Bandwidth value in kbps";
    }
    leaf dste-class-type {
      type uint8;
      description "DSTE Class";
    }
    leaf is-bandwidth-configured {
      type boolean;
      description "Is bandwidth configured";
    }
    leaf is-affinity-configured {
      type boolean;
      description "Is affinity configured";
    }
    list tunnel-id {
      description "Tunnel ID";
        leaf entry {
                  type uint16;

                  description "Tunnel ID";
        }
    }
  }

  grouping MPLS-TE-ATTRIBUTE-SET-XRO {
    description "TE XRO attribute set";

    container xro {
      description "The XRO specified by this attribute-set";
      uses TE-XRO;
    }
  }

  grouping MPLS-TE-ATTRIBUTE-SET-AUTO-MESH {
    description "TE Auto-mesh Attribute Set";

    container affinity {
      description "Affinity";
      uses MPLS-TE-TUNNELS-AFFINITY-INFO;
    }

    container logging {
      description "Logging attributes";
      uses MPLS-TE-LOGGING-ATTRIBUTES;
    }
    leaf configured-bandwidth {
      type uint32;
      units "kbit/s";
      description "Bandwidth value in kbps";
    }
    leaf dste-class-type {
      type uint8;
      description "DSTE Class";
    }
    leaf is-bandwidth-configured {
      type boolean;
      description "Is bandwidth configured";
    }
    leaf setup-priority {
      type uint8;
      description "Setup priority";
    }
    leaf hold-priority {
      type uint8;
      description "Hold priority";
    }
    leaf is-priority-configured {
      type boolean;
      description "Is priority configured";
    }
    leaf policy-class {
      type uint8;
      description "deprecated";
    }
    leaf is-policyclass-configured {
      type boolean;
      description "Is policy class configured";
    }
    leaf forward-class {
      type uint32;
      description "Forward class";
    }
    leaf is-forward-class-configured {
      type boolean;
      description "True if forward-class is configured";
    }
    leaf is-affinity-configured {
      type boolean;
      description "Is affinity configured";
    }
    leaf fast-reroute {
      type boolean;
      description "Fast reroute";
    }
    leaf frr-node-protection {
      type boolean;
      description "FRR Node protection";
    }
    leaf frr-bandwidth-protection {
      type boolean;
      description "FRR bandwidth protection";
    }
    leaf record-route {
      type boolean;
      description "Record route";
    }
    leaf auto-bandwidth-collect {
      type boolean;
      description "Auto bandwidth collect only";
    }
    leaf auto-route-announce {
      type boolean;
      description "Announce auto route to IGP";
    }
    leaf soft-preemption-configured {
      type boolean;
      description "Soft preemption is configured";
    }
    leaf bandwidth {
      type uint32;
      description "IM bandwidth";
    }
    leaf load-share {
      type uint32;
      description "Load Share";
    }
    leaf is-interface-bw-configured {
      type boolean;
      description "Is Interface BW configured";
    }
    list policy-class-entry {
      description "PBTS policy classes";
        leaf entry {
                  type uint8;

                  description "PBTS policy classes";
        }
    }
    list mesh-group-id {
      description "Meshgroup ID";
        leaf entry {
                  type uint32;

                  description "Meshgroup ID";
        }
    }
    list tunnel-id {
      description "Tunnel ID";
        leaf entry {
                  type uint16;

                  description "Tunnel ID";
        }
    }
  }

  grouping MPLS-TE-PROTECTED-IF-NAME-STR {
    description "TE Protected Interface Name String";
    leaf protected-interface {
      type string;
      description "Protected Interface Name";
    }
  }

  grouping MPLS-TE-LOGGING-ATTRIBUTES {
    description "TE Logging Attributes";
    leaf lsp-state {
      type boolean;
      description
        "LSP State logging: TRUE - enabled, FALSE -
        disabled";
    }
    leaf s2l-state {
      type boolean;
      description
        "S2L State logging: TRUE - enabled, FALSE -
        disabled";
    }
    leaf lsp-re-route {
      type boolean;
      description
        "LSP re-route logging: TRUE - enabled, FALSE -
        disabled";
    }
    leaf lsp-re-opt {
      type boolean;
      description
        "LSP re-optimization logging: TRUE - enabled,
        FALSE - disabled";
    }
    leaf lsp-insufficient-bw {
      type boolean;
      description
        "LSP insufficient bandwidth logging: TRUE -
        enabled, FALSE - disabled";
    }
    leaf lsp-bandwidth-change {
      type boolean;
      description
        "LSP bandwidth change logging: TRUE - enabled,
        FALSE - disabled";
    }
    leaf lsp-pcalc-failure-logging-enabled {
      type boolean;
      description
        "LSP pcalc failure logging: TRUE - enabled, FALSE
        - disabled";
    }
    leaf all-logging-enabled {
      type boolean;
      description
        "All logging option: TRUE - enabled, FALSE -
        disabled";
    }
  }

  grouping MPLS-TE-ATTRIBUTE-SET-SIG-NAME {
    description "Attribute set signalled name";
    leaf name {
      type string;
      description "Signalled name";
    }
    leaf source-type {
      type Te-sig-name-append;
      description "Source address or name";
    }
    leaf protected-interface-type {
      type Te-sig-name-append;
      description "Protected interface address or name";
    }
    leaf is-mp-addresses {
      type boolean;
      description "MP address appended";
    }
  }

  grouping MPLS-TE-ATTRIBUTE-SET-AUTO-BACKUP {
    description "TE Auto-backup Attribute Set";

    container signalled-name {
      description "Signalled name";
      uses MPLS-TE-ATTRIBUTE-SET-SIG-NAME;
    }

    container affinity {
      description "Affinity";
      uses MPLS-TE-TUNNELS-AFFINITY-INFO;
    }

    container logging {
      description "Logging attributes";
      uses MPLS-TE-LOGGING-ATTRIBUTES;
    }
    leaf is-signalled-name-configured {
      type boolean;
      description "Is signalled name configured";
    }
    leaf setup-priority {
      type uint8;
      description "Setup priority";
    }
    leaf hold-priority {
      type uint8;
      description "Hold priority";
    }
    leaf is-priority-configured {
      type boolean;
      description "Is priority configured";
    }
    leaf policy-class {
      type uint8;
      description "deprecated";
    }
    leaf is-policyclass-configured {
      type boolean;
      description "Is policy class configured";
    }
    leaf is-affinity-configured {
      type boolean;
      description "Is affinity configured";
    }
    leaf record-route {
      type boolean;
      description "Record route";
    }
    list policy-class-entry {
      description "PBTS policy classes";
        leaf entry {
                  type uint8;

                  description "PBTS policy classes";
        }
    }
    list tunnel-id {
      description "Tunnel ID";
        leaf entry {
                  type uint16;

                  description "Tunnel ID";
        }
    }

    list protected-interface {
      description "Array of Protected Interface Names";
      uses MPLS-TE-PROTECTED-IF-NAME-STR;
    }
  }

  grouping MPLS-TE-ATTRIBUTE-SET-BFD-REV-PATH {
    description "TE segment routing path list";
    leaf path-type {
      type Te-bfd-reverse-path;
      description "BFD reverse path type";
    }
    leaf binding-label {
      type uint32;
      description "BFD reverse path binding label";
    }
  }

  grouping MPLS-TE-ATTRIBUTE-SET-VERSION {
    description "TE attribute set versioning info";
    leaf attribute-type {
      type string;
      description "Attribute Type";
    }
    leaf generation {
      type uint32;
      description "Generation";
    }
    leaf is-default {
      type boolean;
      description "Is default";
    }
  }

  grouping MPLS-TE-ATTRIBUTE-SET-PATH-OPTION {
    description "TE Path Option Attribute Set";

    container affinity {
      description "Affinity";
      uses MPLS-TE-TUNNELS-AFFINITY-INFO;
    }

    container bfd-reverse-path {
      description "BFD reverse path";
      uses MPLS-TE-ATTRIBUTE-SET-BFD-REV-PATH;
    }
    leaf configured-bandwidth {
      type uint32;
      units "kbit/s";
      description "Bandwidth value in kbps";
    }
    leaf cost-limit {
      type uint32;
      description "Cost limit on the tunnel path";
    }
    leaf dste-class-type {
      type uint8;
      description "DSTE Class";
    }
    leaf bandwidth-type {
      type Mpls-te-bw-pool;
      description "The bandwidth type";
    }
    leaf is-bandwidth-configured {
      type boolean;
      description "Is bandwidth configured";
    }
    leaf is-cost-limit-configured {
      type boolean;
      description "Is Cost Limit configured";
    }
    leaf is-affinity-configured {
      type boolean;
      description "Is affinity configured";
    }
    leaf generation {
      type uint32;
      description "Generation";
    }
    leaf path-invalidation-timeout {
      type uint32;
      description "Path invalidation interval on the tunnel path";
    }
    leaf path-invalidation-action {
      type uint32;
      description "Path invalidation action";
    }
    leaf is-path-invalidation-timeout-configured {
      type boolean;
      description "Is path invalidation timeout configured";
    }
    leaf is-path-invalidation-action-configured {
      type boolean;
      description "Is path invalidation action configured";
    }
    leaf exclude-list-name {
      type string;
      description "Exclude list name";
    }
    leaf is-exclude-list-name-configured {
      type boolean;
      description "Is exclude list name configured";
    }
    leaf is-pce-configured {
      type boolean;
      description "Is PCE Configured";
    }
    leaf is-pce-disj-source-configured {
      type boolean;
      description "Is PCE Disjoint Path Source Configured";
    }
    leaf is-pce-disj-type-configured {
      type boolean;
      description "Is PCE Disjoint Path Type Configured";
    }
    leaf is-pce-disj-group-id-configured {
      type boolean;
      description "Is PCE Disjoint Path Group ID Configured";
    }
    leaf pcedp-source-address {
      type uint32;
      description "PCE Disjoint Path Source Address";
    }
    leaf pcedp-type {
      type Te-pce-disjoint;
      description "PCE Disjoint Path Type";
    }
    leaf pcedp-group-id {
      type uint32;
      description "PCE Disjoint Path Group ID";
    }
    leaf is-pceb-dj-source-configured {
      type boolean;
      description "Is PCE Bidirectional Source Configured";
    }
    leaf is-pcebd-group-id-configured {
      type boolean;
      description "Is PCE Bidirectional Group ID Configured";
    }
    leaf pcebd-source-address {
      type uint32;
      description "PCE Bidirectional Source Address";
    }
    leaf pcebd-group-id {
      type uint32;
      description "PCE Bidirectional Group ID";
    }
    leaf is-bfd-reverse-pat-configured {
      type boolean;
      description "Is BFD reverse path configured";
    }
    leaf is-delay-limit-configured {
      type boolean;
      description "Is Delay Limit configured";
    }
    leaf delay-limit {
      type uint32;
      description
        "Delay limit on the tunnel path (usec) When delay
        limit is configured";
    }
    list tunnel-id {
      description "Tunnel ID";
        leaf entry {
                  type uint16;

                  description "Tunnel ID";
        }
    }

    list version-info {
      description "Version Info";
      uses MPLS-TE-ATTRIBUTE-SET-VERSION;
    }
  }

  grouping MPLS-TE-ATTRIBUTE-SET-UNION {
    description "TE Attribute Set Union";

    container attribute-set-path-option {
      when "../tunnel-attribute-set-type ="+
        " 'tunnel-attribute-set-path-option'" {
          description
            "../TunnelAttributeSetType =
            'TunnelAttributeSetPathOption'";
      }
      description "MPLS TE Path Option Attribute Set";
      uses MPLS-TE-ATTRIBUTE-SET-PATH-OPTION;
    }

    container attribute-set-autobackup {
      when "../tunnel-attribute-set-type ="+
        " 'tunnel-attribute-set-auto-backup'" {
          description
            "../TunnelAttributeSetType =
            'TunnelAttributeSetAutoBackup'";
      }
      description "MPLS TE Auto-backup Attribute Set";
      uses MPLS-TE-ATTRIBUTE-SET-AUTO-BACKUP;
    }

    container attribute-set-automesh {
      when "../tunnel-attribute-set-type ="+
        " 'tunnel-attribute-set-auto-mesh'" {
          description
            "../TunnelAttributeSetType =
            'TunnelAttributeSetAutoMesh'";
      }
      description "MPLS TE Auto-mesh Attribute Set";
      uses MPLS-TE-ATTRIBUTE-SET-AUTO-MESH;
    }

    container attribute-set-xro {
      when "../tunnel-attribute-set-type ="+
        " 'tunnel-attribute-set-xro'" {
          description
            "../TunnelAttributeSetType =
            'TunnelAttributeSetXRO'";
      }
      description "Attribute Set XRO";
      uses MPLS-TE-ATTRIBUTE-SET-XRO;
    }

    container attribute-set-p2mpte {
      when "../tunnel-attribute-set-type ="+
        " 'tunnel-attribute-set-p2mpte'" {
          description
            "../TunnelAttributeSetType =
            'TunnelAttributeSetP2MPTE'";
      }
      description "MPLS TE P2MP-TE Attribute Set";
      uses MPLS-TE-ATTRIBUTE-SET-P2MP-TE;
    }

    container attribute-set-aps-pp {
      when "../tunnel-attribute-set-type ="+
        " 'tunnel-attribute-aps-pp'" {
          description
            "../TunnelAttributeSetType =
            'TunnelAttributeAPS_PP'";
      }
      description "Attribute Set OTN APS Path Protection";
      uses MPLS-TE-ATTRIBUTE-SET-APS-PP;
    }

    container attribute-set-p2p-te {
      when "../tunnel-attribute-set-type ="+
        " 'tunnel-attribute-set-p2p-te'" {
          description
            "../TunnelAttributeSetType =
            'TunnelAttributeSetP2P_TE'";
      }
      description "MPLS TE P2P-TE Attribute Set";
      uses MPLS-TE-ATTRIBUTE-SET-P2P-TE;
    }
    leaf tunnel-attribute-set-type {
      type Tunnel-attribute-set;
      description "TunnelAttributeSetType";
    }
  }

  grouping MPLS-TE-ATTRIBUTE-SET {
    description "TE Attribute Set";

    container attribute-set-union {
      description "Union of Attribute Sets";
      uses MPLS-TE-ATTRIBUTE-SET-UNION;
    }
    leaf tunnel-attribute-set-name {
      type string;
      description "Attribute Set Name";
    }
    leaf tunnel-attribute-set-name-crc32 {
      type uint32;
      description "Attribute Set name CRC32 value";
    }
  }

  grouping MPLS-TE-P2MP-PATH-OPTION {
    description "P2MP path-option";

    container attribute-set {
      description "The path option attribute set used by this path";
      uses MPLS-TE-ATTRIBUTE-SET;
    }

    container xro-attribute-set {
      description "The XRO attribute set used by this path-option";
      uses MPLS-TE-ATTRIBUTE-SET;
    }
    leaf option-index-is-valid {
      type boolean;
      description "The path option index is valid";
    }
    leaf option-index {
      type uint32;
      description "Path option index";
    }
    leaf path-option-name {
      type string;
      description "Path option name";
    }
    leaf path-option-type {
      type Mpls-te-pathoption;
      description "Path option type";
    }
    leaf explicit-path-name {
      type string;
      description
        "Explicit Path Name, this is the key to table
        ExplicitPaths.NameTable";
    }
    leaf explicit-path-id {
      type uint16;
      description
        "Explicit Path ID, this is the key to table
        ExplicitPaths.IdentifierTable";
    }
    leaf holddown-duration {
      type uint16;
      units "second";
      description "Holddown Duration (seconds)";
    }
    leaf pce-address {
      type inet:ipv4-address;
      description "PCE server address";
    }
    leaf path-option-area-id {
      type string;
      description "The path-option area constraint";
    }
    leaf is-strict-explicit-path {
      type boolean;
      description "TRUE if explicit path is strict";
    }
    leaf is-helddown {
      type boolean;
      description "TRUE if path is helddown";
    }
    leaf is-lockdown {
      type boolean;
      description "TRUE if the path is locked down";
    }
    leaf is-verbatim {
      type boolean;
      description "TRUE if the path is verbatim";
    }
    leaf is-disabled {
      type boolean;
      description "TRUE if the path option is disabled";
    }
    leaf has-attribute-set {
      type boolean;
      description "TRUE if the path has an attribute set defined";
    }
    leaf attribute-set-found {
      type boolean;
      description
        "TRUE if the path has found the defined attribute
        set";
    }
    leaf has-xro-attribute-set {
      type boolean;
      description
        "TRUE if the path has an XRO attribute set
        configured";
    }
    leaf xro-attribute-set-found {
      type boolean;
      description "TRUE if the path's XRO attribute set is known";
    }
    leaf is-segment-routing {
      type boolean;
      description "TRUE if the path is Segment-Routing";
    }
    leaf protected-by-path-option-index {
      type uint32;
      description "Path option index for Protect path options";
    }
    leaf restored-from-path-option-index {
      type uint32;
      description "Path option index for Restore path options";
    }

    list path-calculation-error {
      description "Path computation information";
      uses MPLS-TE-P2MP-PCALC-ERROR;
    }

    list remerge-error {
      description "Path computation remerge resolve info";
      uses MPLS-TE-P2MP-PCALC-ERROR;
    }

    list signalling-error {
      description "Signalling information";
      uses MPLS-TE-P2MP-SIG-ERROR;
    }
  }

  grouping MPLS-TE-P2MP-S2L {
    description "A P2MP S2L";

    container s2l-fec {
      description "FEC for the S2L";
      uses TE-S2L-FEC;
    }

    container active-path-option {
      description
        "The path option used to find the path for this
        S2L";
      uses MPLS-TE-P2MP-PATH-OPTION;
    }

    container out-xro {
      description "Outgoing XRO for this S2L";
      uses TE-XRO;
    }

    container in-xro {
      description "Incoming XRO for this S2L";
      uses TE-XRO;
    }

    container tspec {
      description "The T spec info";
      uses BANDWIDTH-SPEC-BAG;
    }

    container generic-tspec {
      description "Generic TSpec";
      uses TE-MGMT-GENERIC-TSPEC;
    }

    container fspec {
      description "The F spec info";
      uses BANDWIDTH-SPEC-BAG;
    }

    container generic-fspec {
      description "Generic FSpec";
      uses TE-MGMT-GENERIC-FSPEC;
    }

    container next-hop-address-generic {
      description "Next hop address";
      uses TE-ADDR;
    }

    container previous-hop-address-generic {
      description "Previous hop address";
      uses TE-ADDR;
    }

    container incoming-address-generic {
      description "Incoming interface address";
      uses TE-ADDR;
    }

    container s2l-convergence {
      description "TE LSP convergence related information";
      uses TE-LSP-CONVERGENCE-INFO;
    }

    container soft-preemption {
      description "The soft preemption info for this LSP.";
      uses MPLS-TE-SOFT-PREEMPTION-LSP-INFO;
    }

    container gmpls-labels {
      description "GMPLS labels";
      uses MPLS-TE-MGMT-GMPLS-LABELS;
    }

    container otn-s2l {
      description "Otn S2L Information";
      uses MPLS-TE-OTN-S2L-INFO;
    }

    container head-end-bfd-info {
      description "The Head-end BFD info";
      uses MPLS-TE-HEAD-BFD-INFO;
    }

    container tail-end-bfd-info {
      description "The Tail-end BFD info";
      uses MPLS-TE-TAIL-BFD-INFO;
    }

    container srlg-collection {
      description "SRLG-collection data";
      uses TE-S2L-SRLG-COLLECT-INFO;
    }

    container association {
      description "Association Object";
      uses MPLS-TE-S2L-ASSOCIATION-OBJECT;
    }

    container protection {
      description "Protection Object";
      uses MPLS-TE-S2L-PROTECTION-OBJECT;
    }

    container reverse-lsp-fec {
      description "Reverse Associated Bidir LSP FEC";
      uses TE-LSP-FEC;
    }

    container reverse-tspec {
      description "The Reverse T spec info";
      uses BANDWIDTH-SPEC-BAG;
    }

    container flex-info {
      description "FlexLSP S2L Information";
      uses MPLS-TE-S2L-FLEX-INFO;
    }

    container lsp-wrap-info {
      description "Lsp Wrap  Related information";
      uses TUNNEL-MIDPOINT-LSP-WRAP-INFO-BAG;
    }

    container diversity-info {
      description "S2L Diversity Information";
      uses MPLS-TE-S2L-DIVERSITY-INFO;
    }

    container accumulated-path-metrics {
      description "Accumulated Path Metrics";
      uses MPLS-TE-PATH-METRICS;
    }

    container accumulated-reverse-path-metrics {
      description "Accumulated Reverse Path Metrics";
      uses MPLS-TE-PATH-METRICS;
    }
    leaf pcalc-area {
      type string;
      description "IGP-area in which the S2L path was calculated";
    }
    leaf is-expanded-ero {
      type boolean;
      description "TRUE if this LSR expanded a loose path";
    }
    leaf path-reeval-query-mid {
      type uint32;
      description
        "Loose path reevaluation query received at
        mid-point";
    }
    leaf time-since-last-query-received-mid {
      type uint32;
      description
        "Time since last reevaluation query received at
        mid-point";
    }
    leaf time-since-last-preferred-path-exists-send-mid {
      type uint32;
      description
        "Time since last preferred path exists msg send
        from mid-point";
    }
    leaf time-since-last-preferred-tree-exists-send-mid {
      type uint32;
      description
        "Time since last preferred tree exists msg send
        from mid-point";
    }
    leaf expanded-ero-area-id {
      type string;
      description
        "Indicates the protocol and area used to find
        Outgoing ERO";
    }
    leaf expanded-ero-affinity-bits {
      type uint32;
      description "The Outgoing ERO's affinity bits (colors)";
    }
    leaf expanded-ero-affinity-mask {
      type uint32;
      description "The Outgoing ERO's affinity mask (colors)";
    }
    leaf expanded-ero-metric-type {
      type Mpls-te-metric;
      description "The Outgoing ERO's selection metric";
    }
    leaf expanded-ero-metric {
      type uint32;
      description "The metric value of the expanded path";
    }
    leaf abr-auto-discovered {
      type inet:ipv4-address;
      description "Next ABR auto discovered";
    }
    leaf is-frr-enabled {
      type boolean;
      description "FRR Enabled or Disabled";
    }
    leaf is-node-protected {
      type boolean;
      description "Node Protection Enabled or Disabled";
    }
    leaf is-bandwidth-protect {
      type boolean;
      description "BW Protection Enabled or Disabled";
    }
    leaf path-rro-enabled {
      type boolean;
      description "Path RRO Enabled or Disabled";
    }
    leaf weight {
      type uint64;
      description "The path's weight";
    }
    leaf reverse-weight {
      type uint64;
      description "The reverse path weight";
    }
    leaf uptime {
      type uint32;
      units "second";
      description "Time in seconds since the tunnel was up";
    }
    leaf egress-interface {
      type string;
      description "Egress Interface";
    }
    leaf egress-interface-state {
      type Te-controller-state;
      description "State of Outgoing Interface";
    }
    leaf egress-interface-brief {
      type string;
      description "Egress Interface in brief format";
    }
    leaf ingress-interface {
      type string;
      description "Ingress Interface";
    }
    leaf ingress-interface-state {
      type Te-controller-state;
      description "State of Incoming Interface";
    }
    leaf ingress-interface-brief {
      type string;
      description "Ingress Interface in brief format";
    }
    leaf s2l-local-label {
      type uint32;
      description "Local label";
    }
    leaf s2l-out-label {
      type uint32;
      description "Outgoing label";
    }
    leaf outbound-frr-state {
      type Mpls-te-frr-state;
      description "Indicates outbound FRR state";
    }
    leaf frr-out-tunnel-interface {
      type string;
      description "FRR out tunnel intface";
    }
    leaf role {
      type Mpls-te-tunnel-role;
      description "Role of S2L";
    }
    leaf signalling-status {
      type Mpls-te-tunnels-signaling-status;
      description "Signaling status";
    }
    leaf local-router-id {
      type inet:ipv4-address;
      description "Local router id";
    }
    leaf upstream-router-id {
      type inet:ipv4-address;
      description "Upstream router id";
    }
    leaf downstream-router-id {
      type inet:ipv4-address;
      description "Downstream router id";
    }
    leaf next-hop-address {
      type inet:ipv4-address;
      description "Next hop address";
    }
    leaf next-next-hop-address {
      type inet:ipv4-address;
      description "Next next hop address";
    }
    leaf previous-hop-address {
      type inet:ipv4-address;
      description "Previous hop address";
    }
    leaf incoming-address {
      type inet:ipv4-address;
      description "Incoming interface address";
    }
    leaf backup-tunnel-interface {
      type xr:Interface-name;
      description "Interface handle of the backup tunnel";
    }
    leaf node-hop-count {
      type uint8;
      description "Hop count";
    }
    leaf is-optical {
      type boolean;
      description "Is Optical";
    }
    leaf s2l-reverse-ero-obj-present {
      type boolean;
      description " S2l Reverse ERO Object Present";
    }
    leaf reverse-lsp-present {
      type boolean;
      description "Reverse Associated Bidir LSP Present";
    }
    leaf reverse-lsp-connected {
      type boolean;
      description "Reverse Associated Bidir LSP Connected";
    }
    leaf reverse-lsp-name {
      type string;
      description "Reverse Associated Bidir LSP Name";
    }
    leaf s2l-reverse-tspec-obj-present {
      type boolean;
      description " S2L Reverse TSpec Object Present";
    }
    leaf path-using-strict-spf {
      type boolean;
      description "Path is using Strict SPF";
    }
    list s2l-reverse-lsp-sub-obj {
      description "Reverse LSP Sub Objects";
        leaf entry {
                  type uint8;

                  description "Reverse LSP Sub Objects";
        }
    }

    list shared-risk-link-group {
      description "The S2L's excluded srlg groups";
      uses MPLS-SRLG-INFO;
    }

    list out-ero {
      description "Outgoing ERO for this S2L";
      uses RSVP-MGMT-ERO-SUBOBJ;
    }

    list in-ero {
      description "Incoming ERO for this S2L";
      uses RSVP-MGMT-ERO-SUBOBJ;
    }

    list path-rro {
      description "Path RRO for this S2L";
      uses RSVP-MGMT-RRO-SUBOBJ;
    }

    list resv-rro {
      description "Resv RRO for this S2L";
      uses RSVP-MGMT-RRO-SUBOBJ;
    }

    list path-affinity-array {
      description "Tunnel's Path hops with affinity";
      uses TUNNEL-HOP-INFO;
    }

    list reverse-ero-in {
      description " Reverse Incoming ERO for this S2L";
      uses RSVP-MGMT-ERO-SUBOBJ;
    }

    list s2l-segment-routing-path {
      description "Segment-Routing S2L path info";
      uses TE-S2L-SR-PATH-HOP;
    }
  }

  grouping MPLS-TE-P2MP-LSP {
    description "A P2MP LSP";

    container lsp-fec {
      description "FEC for the LSP";
      uses TE-LSP-FEC;
    }
    leaf signaled-name {
      type string;
      description "Signaled Name";
    }
    leaf is-frr-failed {
      type boolean;
      description "P2MP LSP has FRR Failed";
    }
    leaf frr-active-reason {
      type uint32;
      description "P2MP LSP FRR active reason";
    }
    leaf lsp-bandwidth {
      type uint32;
      description "P2MP LSP Bandwidth";
    }
    leaf lsp-setup-priority {
      type uint8;
      description "LSP setup priority";
    }
    leaf lsp-hold-priority {
      type uint8;
      description "LSP hold priority";
    }
    leaf lsp-bandwidth-type {
      type Mpls-te-bw-pool;
      description "The LSP bandwidth type";
    }
    leaf dste-class-match {
      type boolean;
      description
        "Do the class type and priority match a DSTE
        class";
    }
    leaf dste-class-index {
      type uint8;
      description "Matching DSTE class index";
    }
    leaf type {
      type Mpls-te-lsp;
      description "The type of this LSP";
    }
    leaf uptime {
      type uint32;
      units "second";
      description "Time in seconds since the tunnel was up";
    }
    leaf s2-ls-up {
      type uint32;
      description "Number of connected S2Ls";
    }
    leaf s2-ls-proceeding {
      type uint32;
      description "Number of proceeding S2Ls";
    }
    leaf s2-ls-down {
      type uint32;
      description "Number of down S2Ls";
    }
    leaf reoptimize-reason {
      type Mpls-te-reopt-decision-reason;
      description "Reason for re-optimization";
    }
    leaf reoptimize-trigger {
      type Mte-reopt-trigger;
      description "Re-optimize trigger";
    }
    leaf timer-left {
      type uint32;
      units "second";
      description "Time in seconds left to take next action if any";
    }
    leaf is-passive {
      type boolean;
      description "True for passive tunnel";
    }
    leaf is-interface {
      type boolean;
      description "True for tunnel head";
    }
    leaf last-path-change {
      type uint32;
      units "second";
      description "Time in seconds since the last path change";
    }
    leaf persistent-bytes {
      type uint64;
      units "byte";
      description
        "Persistent forwarding statistics for number of
        bytes. Clear counters will not reset the counter";
    }
    leaf persistent-packets {
      type uint64;
      description
        "Persistent forwarding statistics for Number of
        packets. Clear counters will not reset the
        counter";
    }
    leaf protection-role {
      type Te-lsp-path-protection-role;
      description "Path Protection Role";
    }

    list s2l {
      description "array of S2L structures";
      uses MPLS-TE-P2MP-S2L;
    }
  }

  grouping MPLS-TE-P2MP-S2L-BRIEF {
    description "A P2MP S2L";

    container s2l-fec {
      description "FEC for the S2L";
      uses TE-S2L-FEC;
    }
    leaf uptime {
      type uint32;
      units "second";
      description "Time in seconds since the S2L was up";
    }
    leaf egress-interface {
      type string;
      description "Egress Interface";
    }
    leaf ingress-interface {
      type string;
      description "Ingress Interface";
    }
    leaf role {
      type Mpls-te-tunnel-role;
      description "Role of S2L";
    }
    leaf oper-state {
      type boolean;
      description "Oper state of S2L";
    }
  }

  grouping MPLS-TE-P2MP-LSP-BRIEF {
    description "A P2MP LSP";

    container lsp-fec {
      description "FEC for the LSP";
      uses TE-LSP-FEC;
    }
    leaf signaled-name {
      type string;
      description "Signaled Name";
    }
    leaf uptime {
      type uint32;
      units "second";
      description "Time in seconds since the LSP was up";
    }

    list s2l {
      description "array of S2L structures";
      uses MPLS-TE-P2MP-S2L-BRIEF;
    }
  }

  grouping TE-HW-OOR-STATS {
    description "HW OOR statistics";
    leaf hw-oor-state {
      type Hw-oor-state;
      description
        "The HW-OOR state that these statistics belong to";
    }
    leaf transitions {
      type uint32;
      description "Number of transitions to this state";
    }
    leaf node-protection-disable-number {
      type uint32;
      description
        "Number of times this OOR state disabled node
        protection assignment";
    }
    leaf rejected-ls-ps-number {
      type uint32;
      description "Number of LSPs that were rejected in this state";
    }
    leaf accepted-ls-ps-number {
      type uint32;
      description "Number of LSPs that were accepted in this state";
    }
    leaf accepted-reopt-ls-ps-number {
      type uint32;
      description
        "Number of Reoptimize LSPs that were accepted in
        this state";
    }
    leaf rejected-reopt-ls-ps-number {
      type uint32;
      description
        "Number of Reoptimize LSPs that were rejected in
        this state";
    }
  }

  grouping TE-HW-OOR-STATE-INFO {
    description "HW OOR State Information";

    container statistics {
      description "NPU HW OOR Statistics per state";
      uses TE-HW-OOR-STATS;
    }
    leaf hw-oor-state {
      type Hw-oor-state;
      description
        "The HW-OOR state that this information belong to";
    }
    leaf te-metric-penalty {
      type uint32;
      description
        "The TE metric penalty when the link is in this
        NPU HW OOR state";
    }
    leaf available-bw-percentage {
      type uint32;
      units "percentage";
      description
        "The flooded percentage of available bandwidth
        advertized when the link is in this  NPU HW OOR
        state";
    }
    leaf node-protection-disable {
      type boolean;
      description
        "Disable FRR node protection when the link is in
        this NPU HW OOR state";
    }
    leaf transition-duration {
      type uint32;
      units "minute";
      description
        "Recovery in minutes after the green OOR state is
        entered.";
    }
    leaf minimum-lsp-bandwidth {
      type uint32;
      description
        "Minimum LSP bandwidth so the LSP is admitted
        when the link is in this NPU HW OOR state";
    }
    leaf accept-reopt {
      type boolean;
      description
        "Make-before-break is allowed for LSPs
        reoptimizing over the same link in the NPU HW
        OOR state";
    }
  }

  grouping TE-HW-OOR-INFO {
    description "NPU HW OOR parameters for MPLS-TE";

    list hardware-out-of-resources-state {
      max-elements "3";
      description "Array of NPU HW OOR info per state";
      uses TE-HW-OOR-STATE-INFO;
    }
  }
}
