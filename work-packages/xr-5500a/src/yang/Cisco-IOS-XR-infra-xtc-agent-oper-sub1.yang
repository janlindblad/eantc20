submodule Cisco-IOS-XR-infra-xtc-agent-oper-sub1 {

  belongs-to Cisco-IOS-XR-infra-xtc-agent-oper {
    prefix Cisco-IOS-XR-infra-xtc-agent-oper;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR infra-xtc-agent package operational data.

     Copyright (c) 2013-2018 by Cisco Systems, Inc.
     All rights reserved.";

  revision "2018-11-28" {
    description
      "Various modifications to policy-related models for better compatibility with the IETF policy draft.";
  }

  revision "2017-09-11" {
    description
      "Initial version";
  }

  revision "2015-11-09" {
    description
      "IOS XR 6.0 revision.";
  }

  typedef Xtc-sid1 {
    type enumeration {
      enum sr-protected-adj-sid {
        value 1;
        description "Protected Adjacency SID";
      }
      enum sr-unprotected-adj-sid {
        value 2;
        description "Unprotected Adjacency SID";
      }
      enum sr-bgp-egress-peer-engineering-sid {
        value 3;
        description "BGP egress peer engineering SID";
      }
      enum sr-reqular-prefix-sid {
        value 4;
        description "Regular prefix SID";
      }
      enum sr-strict-prefix-sid {
        value 5;
        description "Strict prefix SID";
      }
    }
    description "XTC SID Types";
  }
  typedef Xtc-igp-info-id {
    type enumeration {
      enum isis {
        value 1;
        description "ISIS";
      }
      enum ospf {
        value 2;
        description "OSPF";
      }
      enum bgp {
        value 3;
        description "BGP";
      }
    }
    description "IGP IDs";
  }
  typedef Xtc-disjointness {
    type enumeration {
      enum no-disjointness {
        description "No Disjointness";
      }
      enum link-disjointness {
        description "Link disjointness";
      }
      enum node-disjointness {
        description "Node disjointness";
      }
      enum srlg-disjointness {
        description "SRLG disjointness";
      }
      enum srlg-node-disjointness {
        description "SRLG-Node disjointness";
      }
    }
    description "XTC policy path type";
  }
  typedef Xtc-policy-lsp-sm-state {
    type enumeration {
      enum unknown {
        description "Unknown";
      }
      enum initialized {
        description "Initialized";
      }
      enum deleted {
        description "Deleted";
      }
      enum programmed {
        description "Programmed; all forwarding rewrites created";
      }
      enum egress-paths-pending {
        description "Waiting for egress paths";
      }
      enum label-allocation-pending {
        description "Waiting for label allocation result";
      }
      enum label-allocation-cleanup-pending {
        description "Waiting for label free result";
      }
      enum label-rewrite-pending {
        description "Waiting for label rewrite create result";
      }
      enum label-rewrite-cleanup-pending {
        description "Waiting for label rewrite delete result";
      }
      enum bsid-allocation-pending {
        description "Waiting for BSID label allocation result";
      }
      enum bsid-allocation-cleanup-pending {
        description "Waiting for BSID label free result";
      }
      enum bsid-rewrite-pending {
        description "Waiting for BSID rewrite create result";
      }
      enum bsid-rewrite-cleanup-pending {
        description "Waiting for BSID rewrite delete result";
      }
      enum tunnel-rewrite-pending {
        description "Waiting for tunnel rewrite create result";
      }
      enum tunnel-rewrite-cleanup-pending {
        description "Waiting for tunnel rewrite delete result";
      }
      enum install-timer-pending {
        description "Waiting for install timer to expire";
      }
      enum cleanup-timer-pending {
        description "Waiting for cleanup timer to expire";
      }
    }
    description "XTC policy LSP FSM states";
  }
  typedef Xtc-sr-sid {
    type enumeration {
      enum ipv4-node-sid {
        description "IPv4 Node SID";
      }
      enum ipv4-adjacency-sid {
        description "IPv4 Adjacency SID";
      }
      enum unknown-sid {
        description "Unknown SID";
      }
    }
    description "XTC SR SID type";
  }
  typedef Xtc-policy-path {
    type enumeration {
      enum explicit {
        description "Explicit path";
      }
      enum dynamic {
        description "Dynamic path";
      }
      enum dynamic-pce {
        description "Dynamic PCE-based path";
      }
    }
    description "XTC policy path type";
  }
  typedef Xtc-policy-cpath-proto-origin {
    type enumeration {
      enum unknown {
        value 0;
        description "unknown";
      }
      enum pcep {
        value 10;
        description "pcep";
      }
      enum bgp {
        value 20;
        description "bgp";
      }
      enum configuration {
        value 30;
        description "configuration";
      }
    }
    description "Policy candidate path protocol origin";
  }
  typedef Xtc-sid {
    type enumeration {
      enum none {
        value 0;
        description "None";
      }
      enum mpls {
        value 1;
        description "MPLS";
      }
      enum ipv6 {
        value 2;
        description "IPv6";
      }
    }
    description "Xtc sid";
  }
  typedef Xtc-ipv6-address {
    type inet:ipv6-address;
    description "Xtc ipv6 address";
  }
  typedef Xtc-ipv4-address {
    type inet:ipv4-address;
    description "Xtc ipv4 address";
  }
  typedef Xtc-af-id {
    type enumeration {
      enum none {
        value 0;
        description "None";
      }
      enum ipv4 {
        value 1;
        description "IPv4";
      }
      enum ipv6 {
        value 2;
        description "IPv6";
      }
    }
    description "Xtc af id";
  }

  grouping XTC-PFX-ENTRY {
    description "XTC prefix etnry";

    container ip-address {
      description "Prefix IP address";
      uses XTC-IP-ADDR-TYPE;
    }
  }

  grouping XTC-PFX-BAG {
    description "XTC Prefix Information";

    container node-protocol-identifier {
      description "Node protocol identifier";
      uses XTC-NODE-PID-BAG;
    }
    leaf node-identifier-xr {
      type uint32;
      description "Node identifier";
    }

    list address {
      description "Prefix address";
      uses XTC-PFX-ENTRY;
    }
  }

  grouping XTC-TOPO-SUMMARY-BAG {
    description "XTC Topology Node Summary Information";
    leaf nodes {
      type uint32;
      description "Number of nodes";
    }
    leaf prefixes {
      type uint32;
      description "Number of prefixes";
    }
    leaf prefix-sids {
      type uint32;
      description "Number of prefix SIDs";
    }
    leaf links {
      type uint32;
      description "Number of links";
    }
    leaf adjacency-sids {
      type uint32;
      description "Number of adjacency SIDs";
    }
  }

  grouping XTC-IPV6-LINK-BAG {
    description "XTC IPv6 Link Information";

    container local-igp-information {
      description "Local node IGP information";
      uses XTC-IGP-INFO-BAG;
    }

    container remote-node-protocol-identifier {
      description "Remote node protocol identifier";
      uses XTC-NODE-PID-BAG;
    }
    leaf local-ipv6-address {
      type inet:ipv6-address;
      description "Local IPv6 address";
    }
    leaf remote-ipv6-address {
      type inet:ipv6-address;
      description "Remote IPv6 address";
    }
    leaf igp-metric {
      type uint32;
      description "IGP Metric";
    }
    leaf te-metric {
      type uint32;
      description "TE Metric";
    }
    leaf maximum-link-bandwidth {
      type uint64;
      description "Max link bandwidth";
    }
    leaf max-reservable-bandwidth {
      type uint64;
      description "Max Reservable bandwidth";
    }

    list adjacency-sid {
      description "Adjacency SIDs";
      uses XTC-SID-BAG;
    }
  }

  grouping XTC-LINK-PM-METRICS {
    description "Link performance metric information";
    leaf unidirectional-minimum-delay-microseconds {
      type uint32;
      units "microsecond";
      description "Min delay in microseconds";
    }
  }

  grouping XTC-IPV4-LINK-BAG {
    description "XTC IPv4 Link Information";

    container local-igp-information {
      description "Local node IGP information";
      uses XTC-IGP-INFO-BAG;
    }

    container remote-node-protocol-identifier {
      description "Remote node protocol identifier";
      uses XTC-NODE-PID-BAG;
    }

    container performance-metrics {
      description "Performance metrics";
      uses XTC-LINK-PM-METRICS;
    }
    leaf local-ipv4-address {
      type inet:ipv4-address;
      description "Local IPv4 address";
    }
    leaf remote-ipv4-address {
      type inet:ipv4-address;
      description "Remote IPv4 address";
    }
    leaf igp-metric {
      type uint32;
      description "IGP Metric";
    }
    leaf te-metric {
      type uint32;
      description "TE Metric";
    }
    leaf maximum-link-bandwidth {
      type uint64;
      description "Max link bandwidth";
    }
    leaf max-reservable-bandwidth {
      type uint64;
      description "Max Reservable bandwidth";
    }
    leaf administrative-groups {
      type uint32;
      description "Link admin-groups";
    }
    leaf-list extended-administrative-group {
      type uint32;
      description "Link Extended admin-groups";
    }
    leaf-list srlgs {
      type uint32;
      description "SRLG Values";
    }

    list adjacency-sid {
      description "Adjacency SIDs";
      uses XTC-SID-BAG;
    }
  }

  grouping XTC-SID-BAG {
    description "XTC SID bags";

    container sid-prefix {
      description "Prefix";
      uses XTC-IP-ADDR-TYPE;
    }
    leaf sid-type {
      type Xtc-sid1;
      description "SID Type";
    }
    leaf algorithm {
      type uint32;
      description "Prefix-SID algorithm number";
    }
    leaf mpls-label {
      type uint32;
      description "MPLS Label";
    }
  }

  grouping XTC-IGP-INFO-BGP {
    description "XTC BGP Information";
    leaf router-id {
      type Xtc-ipv4-address;
      description "BGP router ID";
    }
  }

  grouping XTC-IGP-INFO-OSPF {
    description "XTC OSPF Information";
    leaf router-id {
      type Xtc-ipv4-address;
      description "OSPF router ID";
    }
    leaf area {
      type uint32;
      description "OSPF area";
    }
  }

  grouping XTC-IGP-INFO-ISIS {
    description "XTC ISIS Information";
    leaf system-id {
      type string;
      description "ISIS system ID";
    }
    leaf level {
      type uint32;
      description "ISIS level";
    }
  }

  grouping XTC-IGP-INFO-TYPE {
    description "XTC IGP INFO TYPE";

    container isis {
      when "../igp-id = 'isis'" {
        description "../IGP_ID = 'ISIS'";
      }
      description "ISIS information";
      uses XTC-IGP-INFO-ISIS;
    }

    container ospf {
      when "../igp-id = 'ospf'" {
        description "../IGP_ID = 'OSPF'";
      }
      description "OSPF information";
      uses XTC-IGP-INFO-OSPF;
    }

    container bgp {
      when "../igp-id = 'bgp'" {
        description "../IGP_ID = 'BGP'";
      }
      description "BGP information";
      uses XTC-IGP-INFO-BGP;
    }
    leaf igp-id {
      type Xtc-igp-info-id;
      description "IGP ID";
    }
  }

  grouping XTC-IGP-INFO-BAG {
    description "XTC IGP information bag";

    container igp {
      description "IGP-specific information";
      uses XTC-IGP-INFO-TYPE;
    }
    leaf domain-identifier {
      type uint64;
      description "Domain identifier";
    }
  }

  grouping XTC-NODE-PID-BAG {
    description "XTC Node Protocol Identifier Information";
    leaf node-name {
      type string;
      description "Node Name";
    }
    leaf ipv4-bgp-router-id-set {
      type boolean;
      description "True if IPv4 BGP router ID is set";
    }
    leaf ipv4-bgp-router-id {
      type inet:ipv4-address;
      description "IPv4 TE router ID";
    }
    leaf ipv4te-router-id-set {
      type boolean;
      description "True if IPv4 TE router ID is set";
    }
    leaf ipv4te-router-id {
      type inet:ipv4-address;
      description "IPv4 BGP router ID";
    }

    list igp-information {
      description "IGP information";
      uses XTC-IGP-INFO-BAG;
    }
  }

  grouping XTC-TOPO-NODE-BAG {
    description "XTC Topology Node Information";

    container node-protocol-identifier {
      description "Node protocol identifier";
      uses XTC-NODE-PID-BAG;
    }
    leaf node-identifier-xr {
      type uint32;
      description "Node identifier";
    }
    leaf overload {
      type boolean;
      description "Node Overload Bit";
    }

    list prefix-sid {
      description "Prefix SIDs";
      uses XTC-SID-BAG;
    }

    list ipv4-link {
      description "IPv4 Link information";
      uses XTC-IPV4-LINK-BAG;
    }

    list ipv6-link {
      description "IPv6 Link information";
      uses XTC-IPV6-LINK-BAG;
    }
  }

  grouping XTC-CONTROLLER-POLICY-REQ-BAG {
    description "Controller policy request";

    container end-point {
      description "End point";
      uses XTC-IP-ADDR-TYPE;
    }
    leaf source-address-xr {
      type inet:ipv4-address;
      description "Source address";
    }
    leaf binding-sid {
      type uint32;
      description "Binding SID";
    }
    leaf preference {
      type uint32;
      description "Preference";
    }
    leaf color-xr {
      type uint32;
      description "Color";
    }
    leaf route-distinguisher-xr {
      type uint32;
      description "Route distinguisher";
    }
    leaf creation-time {
      type uint32;
      units "second";
      description "Creation time of the request in seconds";
    }
    leaf last-updated-time {
      type uint32;
      units "second";
      description "Last updated time of the request in seconds";
    }

    list segment-list {
      description "Segment lists";
      uses XTC-POLICY-SL-BAG;
    }
  }

  grouping XTC-DIST-INFO-BAG {
    description "Disjoint path information";
    leaf disjointness-type {
      type Xtc-disjointness;
      description "Disjointness type";
    }
    leaf group-id {
      type uint32;
      description "Group ID";
    }
    leaf sub-id {
      type uint32;
      description "Sub ID";
    }
  }

  grouping XTC-ON-DEMAND-COLOR-BAG {
    description "On-Demand Color information";

    container disjoint-path-info {
      description "Disjoint path information";
      uses XTC-DIST-INFO-BAG;
    }
    leaf color-xr {
      type uint32;
      description "Color";
    }
    leaf absolute-margin {
      type uint32;
      description "Absolute Metric Margin";
    }
    leaf relative-margin {
      type uint32;
      description " Relative Metric Margin";
    }
    leaf maximum-sid-depth {
      type uint32;
      description "Maximum SID Depth";
    }
  }

  grouping XTC-POLICY-SUMMARY-BAG {
    description "Policy summary information";
    leaf total-policy-count {
      type uint32;
      description "Total number of policies";
    }
    leaf up-policy-count {
      type uint32;
      description
        "Total number of policies that are operationally
        up";
    }
    leaf down-policy-count {
      type uint32;
      description
        "Total number of policies that are operationally
        down";
    }
    leaf total-candidate-path-count {
      type uint32;
      description "Total number of candidate paths";
    }
    leaf active-candidate-path-count {
      type uint32;
      description "Total number of candidate paths that are active";
    }
    leaf inactive-candidate-path-count {
      type uint32;
      description
        "Total number of candidate paths that are
        inactive";
    }
  }

  grouping XTC-FWDING-POLICY-PATH-BAG {
    description "Policy Forwarding path information";
    leaf outgoing-interface {
      type xr:Interface-name;
      description "Outgoing interface handle";
    }
    leaf next-hop-ipv4 {
      type Xtc-ipv4-address;
      description "IPv4 Next Hop";
    }
    leaf next-hop-table-id {
      type uint32;
      description "Table ID for nexthop address";
    }
    leaf is-protected {
      type boolean;
      description "Is this path protected ?";
    }
    leaf is-pure-bkup {
      type boolean;
      description "Is this path a pure backup ?";
    }
    leaf load-metric {
      type uint32;
      description "Path's load metric for load balancing";
    }
    leaf path-id {
      type uint8;
      description "path Id";
    }
    leaf bkup-path-id {
      type uint8;
      description "Backup path Id";
    }
    leaf segment-list-name {
      type string;
      description "Associated segment-list";
    }
    leaf are-stats-valid {
      type boolean;
      description "Are per path stats valid?";
    }
    leaf forwarding-stats-pkts {
      type uint64;
      description "Number of packets forwarded on this path";
    }
    leaf forwarding-stats-bytes {
      type uint64;
      units "byte";
      description "Number of bytes forwarded on this path";
    }
    leaf-list label-stack {
      type uint32;
      description "Path outgoing labels";
    }
  }

  grouping XTC-FWDING-POLICY-BAG {
    description "Policy forwarding information";

    container endpoint-address {
      description "Endpoint address";
      uses XTC-IP-ADDR-TYPE;
    }
    leaf policy-name {
      type string;
      description "Policy name";
    }
    leaf color {
      type uint32;
      description "Color";
    }
    leaf is-local-label-valid {
      type boolean;
      description "Is local label valid and allocated?";
    }
    leaf local-label {
      type uint32;
      description "Local label for SR MPLS policy";
    }
    leaf are-stats-valid {
      type boolean;
      description "Are policy stats valid?";
    }
    leaf forwarding-stats-pkts {
      type uint64;
      description "Number of packets forwarded";
    }
    leaf forwarding-stats-bytes {
      type uint64;
      units "byte";
      description "Number of bytes forwarded";
    }

    list paths {
      description "Forwarding paths";
      uses XTC-FWDING-POLICY-PATH-BAG;
    }
  }

  grouping XTC-EVENT-INFO {
    description "XTC Event information";
    leaf event-message {
      type string;
      description "Event message";
    }
    leaf time-stamp {
      type uint32;
      description "Event time, relative to Jan 1, 1970";
    }
  }

  grouping XTC-POLICY-LSP-BAG {
    description "XTC Policy LSP";

    container binding-sid {
      description "Binding SID information";
      uses XTC-POLICY-BSID-BAG;
    }

    container install-timer {
      description "Install timer information";
      uses XTC-TIMER-INFO;
    }

    container cleanup-timer {
      description "Cleanup timer information";
      uses XTC-TIMER-INFO;
    }
    leaf lsp-id {
      type uint16;
      description "LSP ID";
    }
    leaf policy-id {
      type uint16;
      description "Policy ID";
    }
    leaf local-label {
      type uint32;
      description "Local label of the LSP";
    }
    leaf state {
      type Xtc-policy-lsp-sm-state;
      description "Current LSP state";
    }
    leaf is-active-lsp {
      type boolean;
      description "Whether this is the active LSP";
    }
    leaf is-reoptimized-lsp {
      type boolean;
      description "Whether this is the reoptimized LSP";
    }
  }

  grouping XTC-PCC-INFO-BAG {
    description "XTC PCC info";

    container orphan-timer {
      description
        "Orphan timer for PCE-initiated candidate paths
        in orphan state";
      uses XTC-TIMER-INFO;
    }
    leaf symbolic-name {
      type string;
      description "Symbolic name of the PLSP";
    }
    leaf plsp-id {
      type uint32;
      description "PLSP-ID associated with the PCC info";
    }
    leaf is-orphan {
      type boolean;
      description "Whether the candidate path is in orphan state";
    }
  }

  grouping XTC-TIMER-INFO {
    description "XTC Timer information";
    leaf running {
      type boolean;
      description "Whether the timer is running";
    }
    leaf remaining-seconds {
      type int64;
      units "second";
      description "Number of remaining seconds";
    }
    leaf remaining-nano-seconds {
      type int64;
      units "nanosecond";
      description "Number of remaining nanoseconds";
    }
  }

  grouping XTC-SEGMENTS-BAG {
    description "XTC SEGMENTS BAG";
    leaf segment-algorithm {
      type uint8;
      description "Segment Algorithm";
    }
  }

  grouping XTC-PATH-METRICS-BAG {
    description "SR path metrics bag";
    leaf margin-relative {
      type uint32;
      description "Margin Relative";
    }
    leaf margin-absolute {
      type uint32;
      description "Margin Absolute";
    }
    leaf maximum-segments {
      type uint16;
      description "Maximum number of segments";
    }
    leaf accumulative-te-metric {
      type uint32;
      description "Accumulative TE metric";
    }
    leaf accumulative-igp-metric {
      type uint32;
      description "Accumulative IGP metric";
    }
    leaf accumulative-delay {
      type uint32;
      description "Accumulative delay";
    }
  }

  grouping XTC-AFFINITY-COLOR {
    description "XTC AFFINITY COLOR";
    leaf color {
      type string;
      description "An affinity color";
    }
  }

  grouping XTC-AFFINITY-CONSTRAINT {
    description "XTC AFFINITY CONSTRAINT";
    leaf type {
      type uint8;
      description "Affinity type";
    }
    leaf value {
      type uint32;
      description "Affinity value";
    }
    leaf-list extended-value {
      type uint32;
      description "Extended Affinity values";
    }

    list color {
      description "Colors";
      uses XTC-AFFINITY-COLOR;
    }
  }

  grouping XTC-PATH-CONSTRAINTS-BAG {
    description "XTC SR per candidate path metrics information";

    container path-metrics {
      description "Path metrics";
      uses XTC-PATH-METRICS-BAG;
    }

    container segments {
      description "Segments constraints";
      uses XTC-SEGMENTS-BAG;
    }

    list affinity-constraint {
      description "Affinity constraints list";
      uses XTC-AFFINITY-CONSTRAINT;
    }
  }

  grouping XTC-SR-HOP-TYPE {
    description "XTC SR hop";

    container sid {
      description "SID value";
      uses XTC-PREFIX-SID-TYPE;
    }

    container local-address {
      description "Local address";
      uses XTC-IP-ADDR-TYPE;
    }

    container remote-address {
      description "Remote address";
      uses XTC-IP-ADDR-TYPE;
    }
    leaf sid-type {
      type Xtc-sr-sid;
      description "SID type";
    }
    leaf algorithm {
      type uint8;
      description "Algorithim";
    }
  }

  grouping XTC-POLICY-SL-BAG {
    description "XTC policy segment list information bag";
    leaf name {
      type string;
      description "Explicit segment list name";
    }
    leaf type {
      type Xtc-policy-path;
      description "Segment list type";
    }
    leaf active {
      type boolean;
      description "Whether the segment list is active (used)";
    }
    leaf weight {
      type uint32;
      description "Weight of the segment list";
    }
    leaf metric-type {
      type uint8;
      description "Metric type of the segment list";
    }
    leaf metric-value {
      type uint64;
      description "Accumulated metric of the segment list";
    }
    leaf is-valid {
      type boolean;
      description "True if path is valid";
    }
    leaf pce-based-path {
      type boolean;
      description "True if the path is to be computed by PCE";
    }
    leaf pce-address {
      type inet:ipv4-address;
      description "Address of the PCE computed the path";
    }
    leaf error {
      type string;
      description "Error (for display only)";
    }

    list hops {
      description "SR hop list";
      uses XTC-SR-HOP-TYPE;
    }
  }

  grouping XTC-POLICY-CPATH-ORIGINATOR-BAG {
    description "XTC POLICY CPATH ORIGINATOR BAG";

    container node-address {
      description "Originator node address";
      uses XTC-IP-ADDR-TYPE;
    }
    leaf autonomous-system-number {
      type uint32;
      description "Originator Autonomous System Number";
    }
  }

  grouping XTC-POLICY-CPATH-BAG {
    description "XTC policy candidate path bag";

    container originator {
      description "Candidate path originator";
      uses XTC-POLICY-CPATH-ORIGINATOR-BAG;
    }

    container sr-path-constraints {
      description "SR candidate path constraints";
      uses XTC-PATH-CONSTRAINTS-BAG;
    }

    container requested-bsid {
      description "Requested binding SID";
      uses XTC-PREFIX-SID-TYPE;
    }

    container cleanup-timer {
      description
        "Cleanup timer if the candidate path is in the
        process of being cleaned up";
      uses XTC-TIMER-INFO;
    }

    container pcc-information {
      description "PCC PCEP-related information";
      uses XTC-PCC-INFO-BAG;
    }
    leaf name {
      type string;
      description "Candidate path name";
    }
    leaf preference {
      type uint32;
      description "Candidate path preference";
    }
    leaf protocol-originator {
      type Xtc-policy-cpath-proto-origin;
      description "Candidate path protocol origin";
    }
    leaf discriminator {
      type uint32;
      description "Candidate path discriminator";
    }
    leaf is-active {
      type boolean;
      description
        "Whether this is the currently active candidate
        path";
    }
    leaf is-reoptimizing {
      type boolean;
      description
        "Whether this is the candidate path that the
        policy is reoptimizing to";
    }
    leaf shutdown {
      type boolean;
      description
        "If set, the candidate path is administratively
        shutdown";
    }
    leaf error {
      type string;
      description "Candidate path error (for display only)";
    }

    list segment-list {
      description "Segment lists of the candidate path";
      uses XTC-POLICY-SL-BAG;
    }
  }

  grouping XTC-PREFIX-SID-TYPE {
    description "XTC PREFIX SID TYPE";
    leaf sid-type {
      type Xtc-sid;
      description "SIDType";
    }
    leaf label {
      when "../sid-type = 'mpls'" {
        description "../SIDType = 'MPLS'";
      }
      type uint32;
      description "MPLS label";
    }
    leaf ipv6 {
      when "../sid-type = 'ipv6'" {
        description "../SIDType = 'IPv6'";
      }
      type Xtc-ipv6-address;
      description "IPv6 address";
    }
  }

  grouping XTC-POLICY-BSID-BAG {
    description "XTC policy binding SID information";

    container value {
      description "Binding SID value";
      uses XTC-PREFIX-SID-TYPE;
    }
    leaf is-fallback-dynamic {
      type boolean;
      description "Whether the BSID is in fallback dynamic mode";
    }
    leaf is-within-srlb-range {
      type boolean;
      description "Whether the BSID is within SRLB range";
    }
  }

  grouping XTC-IP-ADDR-TYPE {
    description "XTC IP ADDR TYPE";
    leaf af-name {
      type Xtc-af-id;
      description "AFName";
    }
    leaf ipv4 {
      when "../af-name = 'ipv4'" {
        description "../AFName = 'IPv4'";
      }
      type Xtc-ipv4-address;
      description "IPv4 address type";
    }
    leaf ipv6 {
      when "../af-name = 'ipv6'" {
        description "../AFName = 'IPv6'";
      }
      type Xtc-ipv6-address;
      description "IPv6 address type";
    }
  }

  grouping XTC-POLICY-BAG {
    description "XTC policy information";

    container destination-address {
      description "Destination address";
      uses XTC-IP-ADDR-TYPE;
    }

    container binding-sid {
      description "Binding SID information";
      uses XTC-POLICY-BSID-BAG;
    }
    leaf policy-name {
      type string;
      description "Policy name";
    }
    leaf administrative-up {
      type uint32;
      description "Admin up";
    }
    leaf operational-up {
      type uint32;
      description "Operational up";
    }
    leaf color {
      type uint32;
      description "Color";
    }
    leaf transition-count {
      type uint32;
      description "Indicates number of up/down transitions";
    }
    leaf forward-class {
      type uint32;
      description "Forward class of the policy";
    }
    leaf up-time {
      type uint64;
      units "nanosecond";
      description "Policy up time in nano seconds";
    }
    leaf up-age {
      type uint64;
      units "nanosecond";
      description "Policy up age (since) in nano seconds";
    }
    leaf down-time {
      type uint64;
      units "nanosecond";
      description "Policy down time in nano seconds";
    }
    leaf down-age {
      type uint64;
      units "nanosecond";
      description "Policy down age (since) in nano seconds";
    }
    leaf steering-bgp-disabled {
      type boolean;
      description "Whether steering to BGP client is disabled";
    }
    leaf interface-handle {
      type uint32;
      description "Interface handle";
    }
    leaf profile-id {
      type uint16;
      description "Profile ID";
    }
    leaf ipv6-caps-enabled {
      type boolean;
      description "IPv6 caps enabled";
    }

    list candidate-path {
      description "Candidate paths";
      uses XTC-POLICY-CPATH-BAG;
    }

    list ls-ps {
      description "LSPs";
      uses XTC-POLICY-LSP-BAG;
    }

    list event-buffer {
      description "Policy Event buffer";
      uses XTC-EVENT-INFO;
    }
  }
}
