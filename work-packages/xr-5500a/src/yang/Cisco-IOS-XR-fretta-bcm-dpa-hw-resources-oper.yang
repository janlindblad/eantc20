module Cisco-IOS-XR-fretta-bcm-dpa-hw-resources-oper {

  /*** NAMESPACE / PREFIX DEFINITION ***/

  namespace "http://cisco.com/ns/yang"+
    "/Cisco-IOS-XR-fretta-bcm-dpa-hw-resources-oper";


  prefix "fretta-bcm-dpa-hw-resources-oper";

  /*** LINKAGE (IMPORTS / INCLUDES) ***/

  import Cisco-IOS-XR-types { prefix "xr"; }

  include Cisco-IOS-XR-fretta-bcm-dpa-hw-resources-oper-sub2 {
    revision-date 2015-11-09;
  }

  include Cisco-IOS-XR-fretta-bcm-dpa-hw-resources-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR fretta-bcm-dpa-hw-resources package operational data.

     This module contains definitions
     for the following management objects:
       dpa: Stats Data

     Copyright (c) 2013-2018 by Cisco Systems, Inc.
     All rights reserved.";

  revision "2015-11-09" {
    description
      "IOS XR 6.0 revision.";
  }

  typedef Max-trap-s {
    type uint32 {
      range "0..4294967295";
    }
    description "Max trap s";
  }
  typedef Resource {
    type enumeration {
      enum lem {
        value 0;
        description "lem";
      }
      enum lpm {
        value 1;
        description "lpm";
      }
      enum encap {
        value 2;
        description "encap";
      }
      enum ext-tcam-ipv4 {
        value 3;
        description "ext tcam ipv4";
      }
      enum ext-tcam-ipv6-short {
        value 4;
        description "ext tcam ipv6 short";
      }
      enum ext-tcam-ipv6-long {
        value 5;
        description "ext tcam ipv6 long";
      }
      enum fec {
        value 6;
        description "fec";
      }
      enum ecmpfec {
        value 7;
        description "ecmp fec";
      }
      enum ext-tcam-ipv6 {
        value 8;
        description "ext tcam ipv6";
      }
    }
    description "Resource";
  }
  typedef Max-lc-intf-hand-les {
    type uint32 {
      range "0..4294967295";
    }
    description "Max lc intf hand les";
  }

  container dpa {
    config false;
    description "Stats Data";

    container stats {
      description "Voq or Trap Data";

      container nodes {
        description "DPA data for available nodes";

        list node {
          key "node-name";
          description "DPA operational data for a particular node";

          container asic-statistics {
            description "ASIC statistics table";

            container asic-statistics-detail-for-npu-ids {
              description "Detailed ASIC statistics";

              list asic-statistics-detail-for-npu-id {
                key "npu-id";
                description
                  "Detailed ASIC statistics for a particular
                  NPU";
                leaf npu-id {
                  type uint32;
                  description "NPU number";
                }
                uses FIA-EDM-STATS-INFO;
              }
            }

            container asic-statistics-for-npu-ids {
              description "ASIC statistics";

              list asic-statistics-for-npu-id {
                key "npu-id";
                description "ASIC statistics for a particular NPU";
                leaf npu-id {
                  type uint32;
                  description "NPU number";
                }
                uses FIA-EDM-STATS-BRIEF-INFO;
              }
            }
          }

          container npu-numbers {
            description "Ingress Stats";

            list npu-number {
              key "npu-id";
              description "Stats for a particular npu";

              container display {
                description "show npu specific voq or trap stats";

                container trap-ids {
                  description "Trap stats for a particular npu";

                  list trap-id {
                    key "trap-id";
                    description "Filter by specific trap id";
                    leaf trap-id {
                      type Max-trap-s;
                      description "Trap ID";
                    }
                    uses DPA-TRAP-STATS;
                  }
                }

                container interface-handles {
                  description
                    "Voq stats grouped by interface handle";

                  list interface-handle {
                    key "interface-handle";
                    description
                      "Voq stats for a particular interface
                      handle";
                    leaf interface-handle {
                      type Max-lc-intf-hand-les;
                      description "Interface Handle";
                    }
                    uses DPA-VOQ-INTF-PORT;
                  }
                }

                container base-numbers {
                  description
                    "Voq stats grouped by voq base numbers";

                  list base-number {
                    key "base-number";
                    description
                      "Voq Base Number for a particular voq";
                    leaf base-number {
                      type Max-lc-intf-hand-les;
                      description "Interface handle";
                    }
                    uses DPA-VOQ-INTF-PORT;
                  }
                }
              }
              leaf npu-id {
                type uint32;
                description "Npu number";
              }
            }
          }

          container stats-resources-datas {
            description "OFA stats hw resources info ";

            list stats-resources-data {
              key "resource";
              description "Stats Hardware resources table";
              leaf resource {
                type Resource;
                description "Resource type";
              }
              uses OFA-SYSDB-STATS-HW-RESOURCE;
            }
          }

          container hw-resources-datas {
            description "OFA hw resources stats ";

            list hw-resources-data {
              key "resource";
              description "Hardware resources table";
              leaf resource {
                type Resource;
                description "Resource type";
              }
              uses OFA-SYSDB-HW-RESOURCE;
            }
          }
          leaf node-name {
            type xr:Node-id;
            description "Node ID";
          }
        }
      }
    }
  }
}
