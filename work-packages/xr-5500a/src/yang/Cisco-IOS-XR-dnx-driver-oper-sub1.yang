submodule Cisco-IOS-XR-dnx-driver-oper-sub1 {

  belongs-to Cisco-IOS-XR-dnx-driver-oper {
    prefix Cisco-IOS-XR-dnx-driver-oper;
  }

  /*** LINKAGE (IMPORTS / INCLUDES) ***/

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR dnx-driver package operational data.

     Copyright (c) 2013-2018 by Cisco Systems, Inc.
     All rights reserved.";

  revision "2017-08-29" {
    description
      "Changed blk and field info to be dynamic.";
  }

  revision "2015-11-09" {
    description
      "IOS XR 6.0 revision.";
  }

  typedef Asic-init-method {
    type enumeration {
      enum asic-init-method-unset {
        value -1;
        description "asic init method unset";
      }
      enum asic-init-method-no-reset {
        value 0;
        description "asic init method no reset";
      }
      enum asic-init-method-pon-reset {
        value 1;
        description "asic init method pon reset";
      }
      enum asic-init-method-pon-reset-on-intr {
        value 2;
        description "asic init method pon reset on intr";
      }
      enum asic-init-method-hard-reset {
        value 3;
        description "asic init method hard reset";
      }
      enum asic-init-method-warmboot {
        value 4;
        description "asic init method warmboot";
      }
      enum asic-init-method-issu-wb {
        value 5;
        description "asic init method issu wb";
      }
      enum asic-init-method-pci-shutdown {
        value 6;
        description "asic init method pci shutdown";
      }
      enum asic-init-method-quiesce {
        value 7;
        description "asic init method quiesce";
      }
      enum asic-init-method-issu-started {
        value 8;
        description "asic init method issu started";
      }
      enum asic-init-method-issu-rollback {
        value 9;
        description "asic init method issu rollback";
      }
      enum asic-init-method-issu-abort {
        value 10;
        description "asic init method issu abort";
      }
      enum asic-init-method-slice-cleanup {
        value 11;
        description "asic init method slice cleanup";
      }
      enum asic-init-method-lc-remove {
        value 12;
        description "asic init method lc remove";
      }
      enum asic-init-method-node-down {
        value 13;
        description "asic init method node down";
      }
      enum asic-init-method-intr {
        value 14;
        description "asic init method intr";
      }
      enum asic-init-method-board-reload {
        value 15;
        description "asic init method board reload";
      }
      enum asic-init-method-max {
        value 16;
        description "asic init method max";
      }
    }
    description "Asic init method";
  }
  typedef Asic-access-state {
    type enumeration {
      enum asic-state-unset {
        value -1;
        description "asic state unset";
      }
      enum asic-state-none {
        value 0;
        description "asic state none";
      }
      enum asic-state-device-off-line {
        value 1;
        description "asic state device off line";
      }
      enum asic-state-device-created {
        value 2;
        description "asic state device created";
      }
      enum asic-state-device-online {
        value 3;
        description "asic state device online";
      }
      enum asic-state-warmboot {
        value 4;
        description "asic state warmboot";
      }
      enum asic-state-de-init-start {
        value 5;
        description "asic state de init start";
      }
      enum asic-state-intr-de-init {
        value 6;
        description "asic state intr de init";
      }
      enum asic-state-bcm-detach {
        value 7;
        description "asic state bcm detach";
      }
      enum asic-state-soc-de-init {
        value 8;
        description "asic state soc de init";
      }
      enum asic-state-de-init-done {
        value 9;
        description "asic state de init done";
      }
      enum asic-state-soc-init {
        value 10;
        description "asic state soc init";
      }
      enum asic-state-bcm-init {
        value 11;
        description "asic state bcm init";
      }
      enum asic-state-intr-init {
        value 12;
        description "asic state intr init";
      }
      enum asic-state-soc-init-start {
        value 13;
        description "asic state soc init start";
      }
      enum asic-state-bcm-init-start {
        value 14;
        description "asic state bcm init start";
      }
      enum asic-state-intr-init-start {
        value 15;
        description "asic state intr init start";
      }
      enum asic-state-hard-reset {
        value 16;
        description "asic state hard reset";
      }
      enum asic-state-normal {
        value 17;
        description "asic state normal";
      }
      enum asic-state-exception {
        value 18;
        description "asic state exception";
      }
      enum asic-state-hp-attached {
        value 19;
        description "asic state hp attached";
      }
      enum asic-state-quiesce {
        value 20;
        description "asic state quiesce";
      }
      enum asic-state-issu-started {
        value 21;
        description "asic state issu started";
      }
      enum asic-state-issu-started-nn {
        value 22;
        description "asic state issu started nn";
      }
      enum asic-state-issu-abort {
        value 23;
        description "asic state issu abort";
      }
      enum asic-state-max {
        value 24;
        description "asic state max";
      }
    }
    description "Asic access state";
  }
  typedef Asic-oper-state {
    type enumeration {
      enum asic-oper-unset {
        value -1;
        description "asic oper unset";
      }
      enum asic-oper-unknown {
        value 0;
        description "asic oper unknown";
      }
      enum asic-oper-up {
        value 1;
        description "asic oper up";
      }
      enum asic-oper-down {
        value 2;
        description "asic oper down";
      }
      enum asic-card-down {
        value 3;
        description "asic card down";
      }
    }
    description "Asic oper state";
  }
  typedef Slice-state {
    type enumeration {
      enum slice-oper-unset {
        value -1;
        description "slice oper unset";
      }
      enum slice-oper-down {
        value 0;
        description "slice oper down";
      }
      enum slice-oper-up {
        value 1;
        description "slice oper up";
      }
      enum slice-oper-na {
        value 2;
        description "slice oper na";
      }
    }
    description "Slice state";
  }
  typedef Fc-mode {
    type enumeration {
      enum fc-mode-unset {
        value -1;
        description "fc mode unset";
      }
      enum fc-mode-unavail {
        value 0;
        description "fc mode unavail";
      }
      enum fc-mode-inband {
        value 1;
        description "fc mode inband";
      }
      enum fc-mode-oob {
        value 2;
        description "fc mode oob";
      }
    }
    description "Fc mode";
  }
  typedef Link-error-state {
    type enumeration {
      enum link-error-unset {
        value -1;
        description "link error unset";
      }
      enum link-error-none {
        value 0;
        description "link error none";
      }
      enum link-error-shut {
        value 1;
        description "link error shut";
      }
      enum link-error-max {
        value 2;
        description "link error max";
      }
    }
    description "Link error state";
  }
  typedef Oper-state {
    type enumeration {
      enum oper-unset {
        value -1;
        description "oper unset";
      }
      enum oper-unknown {
        value 0;
        description "oper unknown";
      }
      enum oper-up {
        value 1;
        description "oper up";
      }
      enum oper-down {
        value 2;
        description "oper down";
      }
      enum card-down {
        value 3;
        description "card down";
      }
    }
    description "Oper state";
  }
  typedef Admin-state {
    type enumeration {
      enum admin-unset {
        value -1;
        description "admin unset";
      }
      enum admin-up {
        value 0;
        description "admin up";
      }
      enum admin-down {
        value 1;
        description "admin down";
      }
    }
    description "Admin state";
  }
  typedef Link-stage {
    type enumeration {
      enum link-stage-unset {
        value -1;
        description "link stage unset";
      }
      enum link-stage-unused {
        value 0;
        description "link stage unused";
      }
      enum link-stage-fia {
        value 1;
        description "link stage fia";
      }
      enum link-stage-s1 {
        value 2;
        description "link stage s1";
      }
      enum link-stage-s2 {
        value 3;
        description "link stage s2";
      }
      enum link-stage-s3 {
        value 4;
        description "link stage s3";
      }
      enum link-stage-unknown {
        value 5;
        description "link stage unknown";
      }
    }
    description "Link stage";
  }
  typedef Link {
    type enumeration {
      enum link-type-unset {
        value -1;
        description "link type unset";
      }
      enum link-type-unavail {
        value 0;
        description "link type unavail";
      }
      enum link-type-tx {
        value 1;
        description "link type tx";
      }
      enum link-type-rx {
        value 2;
        description "link type rx";
      }
    }
    description "Link";
  }
  typedef Asic {
    type enumeration {
      enum asic-unset {
        value -1;
        description "asic unset";
      }
      enum asic-unavail {
        value 0;
        description "asic unavail";
      }
      enum asic-fia {
        value 1;
        description "asic fia";
      }
      enum asic-s123 {
        value 2;
        description "asic s123";
      }
      enum asic-s13 {
        value 3;
        description "asic s13";
      }
      enum asic-s2 {
        value 4;
        description "asic s2";
      }
      enum asic-b2b {
        value 5;
        description "asic b2b";
      }
      enum asic-type-unknown {
        value 6;
        description "asic type unknown";
      }
    }
    description "Asic";
  }
  typedef Rack {
    type enumeration {
      enum rack-type-unset {
        value -1;
        description "rack type unset";
      }
      enum rack-type-lcc {
        value 0;
        description "rack type lcc";
      }
      enum rack-type-fcc {
        value 1;
        description "rack type fcc";
      }
    }
    description "Rack";
  }

  grouping FIA-EDM-LINK-OVF-COUNTERS {
    description "FIA EDM LINK OVF COUNTERS";
    leaf tx-control-cells-counter {
      type string {
        length "0..6";
      }
      description "TX Control cells counter";
    }
    leaf tx-data-cell-counter {
      type string {
        length "0..6";
      }
      description "TX Data cell counter";
    }
    leaf tx-data-byte-counter {
      type string {
        length "0..6";
      }
      description "TX Data byte counter";
    }
    leaf rx-crc-errors-counter {
      type string {
        length "0..6";
      }
      description "RX CRC errors counter";
    }
    leaf rx-lfec-fec-correctable-error {
      type string {
        length "0..6";
      }
      description "RX LFEC FEC correctable error";
    }
    leaf rx-8b-10b-disparity-errors {
      type string {
        length "0..6";
      }
      description "RX 8b 10b disparity errors";
    }
    leaf rx-control-cells-counter {
      type string {
        length "0..6";
      }
      description "RX Control cells counter";
    }
    leaf rx-data-cell-counter {
      type string {
        length "0..6";
      }
      description "RX Data cell counter";
    }
    leaf rx-data-byte-counter {
      type string {
        length "0..6";
      }
      description "RX Data byte counter";
    }
    leaf rx-dropped-retransmitted-control {
      type string {
        length "0..6";
      }
      description "RX dropped retransmitted control";
    }
    leaf tx-asyn-fifo-rate {
      type string {
        length "0..6";
      }
      description "TX Asyn fifo rate";
    }
    leaf rx-asyn-fifo-rate {
      type string {
        length "0..6";
      }
      description "RX Asyn fifo rate";
    }
    leaf rx-lfec-fec-uncorrectable-errors {
      type string {
        length "0..6";
      }
      description "RX LFEC FEC uncorrectable errors";
    }
    leaf rx-8b-10b-code-errors {
      type string {
        length "0..6";
      }
      description "RX 8b 10b code errors";
    }
  }

  grouping FIA-EDM-LINK-COUNTERS {
    description "FIA EDM LINK COUNTERS";
    leaf tx-control-cells-counter {
      type uint64;
      description "TX Control cells counter";
    }
    leaf tx-data-cell-counter {
      type uint64;
      description "TX Data cell counter";
    }
    leaf tx-data-byte-counter {
      type uint64;
      description "TX Data byte counter";
    }
    leaf rx-crc-errors-counter {
      type uint64;
      description "RX CRC errors counter";
    }
    leaf rx-lfec-fec-correctable-error {
      type uint64;
      description "RX LFEC FEC correctable error";
    }
    leaf rx-8b-10b-disparity-errors {
      type uint64;
      description "RX 8b 10b disparity errors";
    }
    leaf rx-control-cells-counter {
      type uint64;
      description "RX Control cells counter";
    }
    leaf rx-data-cell-counter {
      type uint64;
      description "RX Data cell counter";
    }
    leaf rx-data-byte-counter {
      type uint64;
      description "RX Data byte counter";
    }
    leaf rx-dropped-retransmitted-control {
      type uint64;
      description "RX dropped retransmitted control";
    }
    leaf tx-asyn-fifo-rate {
      type uint64;
      description "TX Asyn fifo rate";
    }
    leaf rx-asyn-fifo-rate {
      type uint64;
      description "RX Asyn fifo rate";
    }
    leaf rx-lfec-fec-uncorrectable-errors {
      type uint64;
      description "RX LFEC FEC uncorrectable errors";
    }
    leaf rx-8b-10b-code-errors {
      type uint64;
      description "RX 8b 10b code errors";
    }
  }

  grouping FIA-EDM-LINK-ERROR-STATUS {
    description "FIA EDM LINK ERROR STATUS";
    leaf link-crc-error {
      type uint32;
      description "link crc error";
    }
    leaf link-size-error {
      type uint32;
      description "link size error";
    }
    leaf link-mis-align-error {
      type uint32;
      description "link mis align error";
    }
    leaf link-code-group-error {
      type uint32;
      description "link code group error";
    }
    leaf link-no-sig-lock-error {
      type uint32;
      description "link no sig lock error";
    }
    leaf link-no-sig-accept-error {
      type uint32;
      description "link no sig accept error";
    }
    leaf link-tokens-error {
      type uint32;
      description "link tokens error";
    }
    leaf error-token-count {
      type uint32;
      description "error token count";
    }
  }

  grouping FIA-EDM-STATS-ASIC-FMAC {
    description "FIA EDM STATS ASIC FMAC";

    container link-error-status {
      description "link error status";
      uses FIA-EDM-LINK-ERROR-STATUS;
    }

    container link-counters {
      description "link counters";
      uses FIA-EDM-LINK-COUNTERS;
    }

    container ovf-status {
      description "ovf status";
      uses FIA-EDM-LINK-OVF-COUNTERS;
    }
  }

  grouping FIA-EDM-STATS-ASIC-FMAC-INFO {
    description "FIA EDM STATS ASIC FMAC INFO";

    container aggr-stats {
      description "aggr stats";
      uses FIA-EDM-STATS-ASIC-FMAC;
    }

    container incr-stats {
      description "incr stats";
      uses FIA-EDM-STATS-ASIC-FMAC;
    }
    leaf valid {
      type boolean;
      description "valid";
    }
    leaf rack-no {
      type uint32;
      description "rack no";
    }
    leaf slot-no {
      type uint32;
      description "slot no";
    }
    leaf asic-instance {
      type uint32;
      description "asic instance";
    }
    leaf link-no {
      type uint32;
      description "link no";
    }
    leaf link-valid {
      type boolean;
      description "link valid";
    }
  }

  grouping FIA-EDM-DEVICE-STATS-OVF-PBC {
    description "FIA EDM DEVICE STATS OVF PBC";
    leaf cmic-cmc0-pkt-count-tx-pkt {
      type string {
        length "0..6";
      }
      description "CMIC Cmc0PktCountTxPkt";
    }
    leaf cmic-cmc0-pkt-count-rx-pkt {
      type string {
        length "0..6";
      }
      description "CMIC Cmc0PktCountRxPkt";
    }
    leaf nbi-stat-rx-bursts-err-cnt {
      type string {
        length "0..6";
      }
      description "NBI StatRxBurstsErrCnt";
    }
    leaf nbi-ecc-1b-err-cnt {
      type string {
        length "0..6";
      }
      description "NBI Ecc 1bErrCnt";
    }
    leaf nbi-ecc-2b-err-cnt {
      type string {
        length "0..6";
      }
      description "NBI Ecc 2bErrCnt";
    }
    leaf nbi-parity-err-cnt {
      type string {
        length "0..6";
      }
      description "NBI ParityErrCnt";
    }
    leaf nbi-rx-ilkn-crc32-err-cnt {
      type string {
        length "0..6";
      }
      description "NBI RxIlknCrc32ErrCnt";
    }
    leaf nbi-rx-ilkn0-crc24-err-cnt {
      type string {
        length "0..6";
      }
      description "NBI RxIlkn0Crc24ErrCnt";
    }
    leaf nbi-rx-ilkn0-burst-err-cnt {
      type string {
        length "0..6";
      }
      description "NBI RxIlkn0BurstErrCnt";
    }
    leaf nbi-rx-ilkn0-miss-sop-err-cnt {
      type string {
        length "0..6";
      }
      description "NBI RxIlkn0MissSopErrCnt";
    }
    leaf nbi-rx-ilkn0-miss-eop-err-cnt {
      type string {
        length "0..6";
      }
      description "NBI RxIlkn0MissEopErrCnt";
    }
    leaf nbi-rx-ilkn0-misaligned-cnt {
      type string {
        length "0..6";
      }
      description "NBI RxIlkn0MisalignedCnt";
    }
    leaf nbi-rx-ilkn1-crc24-err-cnt {
      type string {
        length "0..6";
      }
      description "NBI RxIlkn1Crc24ErrCnt";
    }
    leaf nbi-rx-ilkn1-burst-err-cnt {
      type string {
        length "0..6";
      }
      description "NBI RxIlkn1BurstErrCnt";
    }
    leaf nbi-rx-ilkn1-miss-sop-err-cnt {
      type string {
        length "0..6";
      }
      description "NBI RxIlkn1MissSopErrCnt";
    }
    leaf nbi-rx-ilkn1-miss-eop-err-cnt {
      type string {
        length "0..6";
      }
      description "NBI RxIlkn1MissEopErrCnt";
    }
    leaf nbi-rx-ilkn1-misaligned-cnt {
      type string {
        length "0..6";
      }
      description "NBI RxIlkn1MisalignedCnt";
    }
    leaf nbi-tx-ilkn1-flushed-bursts-cnt {
      type string {
        length "0..6";
      }
      description "NBI TxIlkn1FlushedBurstsCnt";
    }
    leaf nbi-rx-ilkn0-retrans-crc24-err-cnt {
      type string {
        length "0..6";
      }
      description "NBI RxIlkn0RetransCRC24ErrCnt";
    }
    leaf nbi-rx-ilkn0-retrans-retry-err-cnt {
      type string {
        length "0..6";
      }
      description "NBI RxIlkn0RetransRetryErrCnt";
    }
    leaf nbi-rx-ilkn0-retrans-wdog-err-cnt {
      type string {
        length "0..6";
      }
      description "NBI RxIlkn0RetransWdogErrCnt";
    }
    leaf nbi-rx-ilkn0-retrans-wrap-after-disc-err-cnt {
      type string {
        length "0..6";
      }
      description "NBI RxIlkn0RetransWrapAfterDiscErrCnt";
    }
    leaf nbi-rx-ilkn0-retrans-wrap-b4-disc-err-cnt {
      type string {
        length "0..6";
      }
      description "NBI RxIlkn0RetransWrapB4DiscErrCnt";
    }
    leaf nbi-rx-ilkn0-retrans-reached-timeout-err-cnt {
      type string {
        length "0..6";
      }
      description "NBI RxIlkn0RetransReachedTimeoutErrCnt";
    }
    leaf nbi-rx-ilkn1-retrans-crc24-err-cnt {
      type string {
        length "0..6";
      }
      description "NBI RxIlkn1RetransCRC24ErrCnt";
    }
    leaf nbi-rx-ilkn1-retrans-retry-err-cnt {
      type string {
        length "0..6";
      }
      description "NBI RxIlkn1RetransRetryErrCnt";
    }
    leaf nbi-rx-ilkn1-retrans-wdog-err-cnt {
      type string {
        length "0..6";
      }
      description "NBI RxIlkn1RetransWdogErrCnt";
    }
    leaf nbi-rx-ilkn1-retrans-wrap-after-disc-err-cnt {
      type string {
        length "0..6";
      }
      description "NBI RxIlkn1RetransWrapAfterDiscErrCnt";
    }
    leaf nbi-rx-ilkn1-retrans-wrap-b4-disc-err-cnt {
      type string {
        length "0..6";
      }
      description "NBI RxIlkn1RetransWrapB4DiscErrCnt";
    }
    leaf nbi-rx-ilkn1-retrans-reached-timeout-err-cnt {
      type string {
        length "0..6";
      }
      description "NBI RxIlkn1RetransReachedTimeoutErrCnt";
    }
    leaf nbi-stat-rx-frame-err-cnt {
      type string {
        length "0..6";
      }
      description "NBI StatRxFrameErrCnt";
    }
    leaf nbi-stat-tx-frame-err-cnt {
      type string {
        length "0..6";
      }
      description "NBI StatTxFrameErrCnt";
    }
    leaf nbi-rx-elk-err-bursts-cnt {
      type string {
        length "0..6";
      }
      description "NBI RxElkErrBurstsCnt";
    }
    leaf nbi-rx-num-thrown-eops {
      type string {
        length "0..6";
      }
      description "NBI RxNumThrownEops";
    }
    leaf nbi-rx-num-runts {
      type string {
        length "0..6";
      }
      description "NBI RxNumRunts";
    }
    leaf nbi-bist-tx-crc-err-bursts-cnt {
      type string {
        length "0..6";
      }
      description "NBI BistTxCrcErrBurstsCnt";
    }
    leaf nbi-bist-rx-err-length-bursts-cnt {
      type string {
        length "0..6";
      }
      description "NBI BistRxErrLengthBurstsCnt";
    }
    leaf nbi-bist-rx-err-burst-index-cnt {
      type string {
        length "0..6";
      }
      description "NBI BistRxErrBurstIndexCnt";
    }
    leaf nbi-bist-rx-err-bct-cnt {
      type string {
        length "0..6";
      }
      description "NBI BistRxErrBctCnt";
    }
    leaf nbi-bist-rx-err-data-cnt {
      type string {
        length "0..6";
      }
      description "NBI BistRxErrDataCnt";
    }
    leaf nbi-bist-rx-err-in-crc-err-cnt {
      type string {
        length "0..6";
      }
      description "NBI BistRxErrInCrcErrCnt";
    }
    leaf nbi-bist-rx-err-sob-cnt {
      type string {
        length "0..6";
      }
      description "NBI BistRxErrSobCnt";
    }
    leaf nbi-stat-tx-bursts-cnt {
      type string {
        length "0..6";
      }
      description "NBI StatTxBurstsCnt";
    }
    leaf nbi-stat-tx-total-leng-cnt {
      type string {
        length "0..6";
      }
      description "NBI StatTxTotalLengCnt";
    }
    leaf rxaui-total-tx-pkt-count {
      type string {
        length "0..6";
      }
      description "RXAUI TotalTxPktCount";
    }
    leaf rxaui-total-rx-pkt-count {
      type string {
        length "0..6";
      }
      description "RXAUI TotalRxPktCount";
    }
    leaf rxaui-rx-pkt-count-bcast-pkt {
      type string {
        length "0..6";
      }
      description "RXAUI RxPktCountBcastPkt";
    }
    leaf rxaui-tx-pkt-count-bcast-pkt {
      type string {
        length "0..6";
      }
      description "RXAUI TxPktCountBcastPkt";
    }
    leaf rxaui-rx-pkt-count-mcast-pkt {
      type string {
        length "0..6";
      }
      description "RXAUI RxPktCountMcastPkt";
    }
    leaf rxaui-tx-pkt-count-mcast-pkt {
      type string {
        length "0..6";
      }
      description "RXAUI TxPktCountMcastPkt";
    }
    leaf rxaui-rx-pkt-count-ucast-pkt {
      type string {
        length "0..6";
      }
      description "RXAUI RxPktCountUcastPkt";
    }
    leaf rxaui-tx-pkt-count-ucast-pkt {
      type string {
        length "0..6";
      }
      description "RXAUI TxPktCountUcastPkt";
    }
    leaf rxaui-rx-err-drop-pkt-cnt {
      type string {
        length "0..6";
      }
      description "RXAUI RxErrDropPktCnt";
    }
    leaf rxaui-tx-err-drop-pkt-cnt {
      type string {
        length "0..6";
      }
      description "RXAUI TxErrDropPktCnt";
    }
    leaf rxaui-byte-count-tx-pkt {
      type string {
        length "0..6";
      }
      description "RXAUI ByteCountTxPkt";
    }
    leaf rxaui-byte-count-rx-pkt {
      type string {
        length "0..6";
      }
      description "RXAUI ByteCountRxPkt";
    }
    leaf rxaui-rx-dscrd-pkt-cnt {
      type string {
        length "0..6";
      }
      description "RXAUI RxDscrdPktCnt";
    }
    leaf rxaui-tx-dscrd-pkt-cnt {
      type string {
        length "0..6";
      }
      description "RXAUI TxDscrdPktCnt";
    }
    leaf ire-nif-packet-counter {
      type string {
        length "0..6";
      }
      description "IRE NifPacketCounter";
    }
    leaf il-total-rx-pkt-count {
      type string {
        length "0..6";
      }
      description "IL TotalRxPktCount";
    }
    leaf il-total-tx-pkt-count {
      type string {
        length "0..6";
      }
      description "IL TotalTxPktCount";
    }
    leaf il-rx-err-drop-pkt-cnt {
      type string {
        length "0..6";
      }
      description "IL RxErrDropPktCnt";
    }
    leaf il-tx-err-drop-pkt-cnt {
      type string {
        length "0..6";
      }
      description "IL TxErrDropPktCnt";
    }
    leaf il-byte-count-tx-pkt {
      type string {
        length "0..6";
      }
      description "IL ByteCountTxPkt";
    }
    leaf il-byte-count-rx-pkt {
      type string {
        length "0..6";
      }
      description "IL ByteCountRxPkt";
    }
    leaf il-rx-dscrd-pkt-cnt {
      type string {
        length "0..6";
      }
      description "IL RxDscrdPktCnt";
    }
    leaf il-tx-dscrd-pkt-cnt {
      type string {
        length "0..6";
      }
      description "IL TxDscrdPktCnt";
    }
    leaf il-rx-pkt-count-bcast-pkt {
      type string {
        length "0..6";
      }
      description "IL RxPktCountBcastPkt";
    }
    leaf il-tx-pkt-count-bcast-pkt {
      type string {
        length "0..6";
      }
      description "IL TxPktCountBcastPkt";
    }
    leaf il-rx-pkt-count-mcast-pkt {
      type string {
        length "0..6";
      }
      description "IL RxPktCountMcastPkt";
    }
    leaf il-tx-pkt-count-mcast-pkt {
      type string {
        length "0..6";
      }
      description "IL TxPktCountMcastPkt";
    }
    leaf il-rx-pkt-count-ucast-pkt {
      type string {
        length "0..6";
      }
      description "IL RxPktCountUcastPkt";
    }
    leaf il-tx-pkt-count-ucast-pkt {
      type string {
        length "0..6";
      }
      description "IL TxPktCountUcastPkt";
    }
    leaf iqm-enq-pkt-cnt {
      type string {
        length "0..6";
      }
      description "IQM EnqPktCnt";
    }
    leaf iqm-enq-byte-cnt {
      type string {
        length "0..6";
      }
      description "IQM EnqByteCnt";
    }
    leaf iqm-deq-pkt-cnt {
      type string {
        length "0..6";
      }
      description "IQM DeqPktCnt";
    }
    leaf iqm-deq-byte-cnt {
      type string {
        length "0..6";
      }
      description "IQM DeqByteCnt";
    }
    leaf iqm-tot-dscrd-pkt-cnt {
      type string {
        length "0..6";
      }
      description "IQM TotDscrdPktCnt";
    }
    leaf iqm-tot-dscrd-byte-cnt {
      type string {
        length "0..6";
      }
      description "IQM TotDscrdByteCnt";
    }
    leaf iqm-ecc-1b-err-cnt {
      type string {
        length "0..6";
      }
      description "IQM Ecc 1bErrCnt";
    }
    leaf iqm-ecc-2b-err-cnt {
      type string {
        length "0..6";
      }
      description "IQM Ecc 2bErrCnt";
    }
    leaf iqm-parity-err-cnt {
      type string {
        length "0..6";
      }
      description "IQM ParityErrCnt";
    }
    leaf iqm-deq-delete-pkt-cnt {
      type string {
        length "0..6";
      }
      description "IQM DeqDeletePktCnt";
    }
    leaf iqm-ecn-dscrd-msk-pkt-cnt {
      type string {
        length "0..6";
      }
      description "IQM EcnDscrdMskPktCnt";
    }
    leaf iqm-q-tot-dscrd-pkt-cnt {
      type string {
        length "0..6";
      }
      description "IQM QTotDscrdPktCnt";
    }
    leaf iqm-q-deq-delete-pkt-cnt {
      type string {
        length "0..6";
      }
      description "IQM QDeqDeletePktCnt";
    }
    leaf iqm-rjct-db-pkt-cnt {
      type string {
        length "0..6";
      }
      description "IQM RjctDbPktCnt";
    }
    leaf iqm-rjct-bdb-pkt-cnt {
      type string {
        length "0..6";
      }
      description "IQM RjctBdbPktCnt";
    }
    leaf iqm-rjct-bdb-protct-pkt-cnt {
      type string {
        length "0..6";
      }
      description "IQM RjctBdbProtctPktCnt";
    }
    leaf iqm-rjct-oc-bd-pkt-cnt {
      type string {
        length "0..6";
      }
      description "IQM RjctOcBdPktCnt";
    }
    leaf iqm-rjct-sn-err-pkt-cnt {
      type string {
        length "0..6";
      }
      description "IQM RjctSnErrPktCnt";
    }
    leaf iqm-rjct-mc-err-pkt-cnt {
      type string {
        length "0..6";
      }
      description "IQM RjctMcErrPktCnt";
    }
    leaf iqm-rjct-rsrc-err-pkt-cnt {
      type string {
        length "0..6";
      }
      description "IQM RjctRsrcErrPktCnt";
    }
    leaf iqm-rjct-qnvalid-err-pkt-cnt {
      type string {
        length "0..6";
      }
      description "IQM RjctQnvalidErrPktCnt";
    }
    leaf iqm-rjct-cnm-pkt-cnt {
      type string {
        length "0..6";
      }
      description "IQM RjctCnmPktCnt";
    }
    leaf iqm-rjct-dyn-space-pkt-cnt {
      type string {
        length "0..6";
      }
      description "IQM RjctDynSpacePktCnt";
    }
    leaf ipt-fdt-pkt-cnt {
      type string {
        length "0..6";
      }
      description "IPT FdtPktCnt";
    }
    leaf ipt-ecc-1b-err-cnt {
      type string {
        length "0..6";
      }
      description "IPT Ecc 1bErrCnt";
    }
    leaf ipt-ecc-2b-err-cnt {
      type string {
        length "0..6";
      }
      description "IPT Ecc 2bErrCnt";
    }
    leaf ipt-parity-err-cnt {
      type string {
        length "0..6";
      }
      description "IPT ParityErrCnt";
    }
    leaf ipt-crc-err-cnt {
      type string {
        length "0..6";
      }
      description "IPT CrcErrCnt";
    }
    leaf ipt-crc-err-del-buff-cnt {
      type string {
        length "0..6";
      }
      description "IPT CrcErrDelBuffCnt";
    }
    leaf ipt-cpu-del-buff-cnt {
      type string {
        length "0..6";
      }
      description "IPT CpuDelBuffCnt";
    }
    leaf ipt-cpu-rel-buff-cnt {
      type string {
        length "0..6";
      }
      description "IPT CpuRelBuffCnt";
    }
    leaf ipt-crc-err-buff-fifo-full-cnt {
      type string {
        length "0..6";
      }
      description "IPT CrcErrBuffFifoFullCnt";
    }
    leaf fdt-data-cell-cnt {
      type string {
        length "0..6";
      }
      description "FDT DataCellCnt";
    }
    leaf fdt-data-byte-cnt {
      type string {
        length "0..6";
      }
      description "FDT DataByteCnt";
    }
    leaf fdt-crc-dropped-pck-cnt {
      type string {
        length "0..6";
      }
      description "FDT CrcDroppedPckCnt";
    }
    leaf fdt-invalid-destq-drop-cell-cnt {
      type string {
        length "0..6";
      }
      description "FDT invalid destq drop cell cnt";
    }
    leaf fdt-indirect-command-count {
      type string {
        length "0..6";
      }
      description "FDT IndirectCommandCount";
    }
    leaf fdt-ecc-1b-err-cnt {
      type string {
        length "0..6";
      }
      description "FDT Ecc 1bErrCnt";
    }
    leaf fdt-ecc-2b-err-cnt {
      type string {
        length "0..6";
      }
      description "FDT Ecc 2bErrCnt";
    }
    leaf fdt-parity-err-cnt {
      type string {
        length "0..6";
      }
      description "FDT ParityErrCnt";
    }
    leaf fdt-crc-dropped-cell-cnt {
      type string {
        length "0..6";
      }
      description "FDT CrcDroppedCellCnt";
    }
    leaf fcr-control-cell-cnt {
      type string {
        length "0..6";
      }
      description "FCR ControlCellCnt";
    }
    leaf fcr-cell-drop-cnt {
      type string {
        length "0..6";
      }
      description "FCR CellDropCnt";
    }
    leaf fcr-credit-cell-drop-cnt {
      type string {
        length "0..6";
      }
      description "FCR CreditCellDropCnt";
    }
    leaf fcr-fs-cell-drop-cnt {
      type string {
        length "0..6";
      }
      description "FCR FSCellDropCnt";
    }
    leaf fcr-rt-cell-drop-cnt {
      type string {
        length "0..6";
      }
      description "FCR RTCellDropCnt";
    }
    leaf fcr-ecc-1b-err-cnt {
      type string {
        length "0..6";
      }
      description "FCR Ecc 1bErrCnt";
    }
    leaf fcr-ecc-2b-err-cnt {
      type string {
        length "0..6";
      }
      description "FCR Ecc 2bErrCnt";
    }
    leaf fdr-data-cell-cnt {
      type string {
        length "0..6";
      }
      description "FDR DataCellCnt";
    }
    leaf fdr-data-byte-cnt {
      type string {
        length "0..6";
      }
      description "FDR DataByteCnt";
    }
    leaf fdr-crc-dropped-pck-cnt {
      type string {
        length "0..6";
      }
      description "FDR CrcDroppedPckCnt";
    }
    leaf fdr-p-pkt-cnt {
      type string {
        length "0..6";
      }
      description "FDR PPktCnt";
    }
    leaf fdr-prm-error-filter-cnt {
      type string {
        length "0..6";
      }
      description "FDR PrmErrorFilterCnt";
    }
    leaf fdr-sec-error-filter-cnt {
      type string {
        length "0..6";
      }
      description "FDR SecErrorFilterCnt";
    }
    leaf fdr-prm-ecc-1b-err-cnt {
      type string {
        length "0..6";
      }
      description "FDR PrmEcc 1bErrCnt";
    }
    leaf fdr-prm-ecc-2b-err-cnt {
      type string {
        length "0..6";
      }
      description "FDR PrmEcc 2bErrCnt";
    }
    leaf fdr-sec-ecc-1b-err-cnt {
      type string {
        length "0..6";
      }
      description "FDR SecEcc 1bErrCnt";
    }
    leaf fdr-sec-ecc-2b-err-cnt {
      type string {
        length "0..6";
      }
      description "FDR SecEcc 2bErrCnt";
    }
    leaf egq-ecc-1b-err-cnt {
      type string {
        length "0..6";
      }
      description "EGQ Ecc 1bErrCnt";
    }
    leaf egq-ecc-2b-err-cnt {
      type string {
        length "0..6";
      }
      description "EGQ Ecc 2bErrCnt";
    }
    leaf egq-parity-err-cnt {
      type string {
        length "0..6";
      }
      description "EGQ ParityErrCnt";
    }
    leaf egq-dbf-ecc-1b-err-cnt {
      type string {
        length "0..6";
      }
      description "EGQ DbfEcc 1bErrCnt";
    }
    leaf egq-dbf-ecc-2b-err-cnt {
      type string {
        length "0..6";
      }
      description "EGQ DbfEcc 2bErrCnt";
    }
    leaf egq-empty-mcid-counter {
      type string {
        length "0..6";
      }
      description "EGQ EmptyMcidCounter";
    }
    leaf egq-rqp-discard-packet-counter {
      type string {
        length "0..6";
      }
      description "EGQ RqpDiscardPacketCounter";
    }
    leaf egq-ehp-discard-packet-counter {
      type string {
        length "0..6";
      }
      description "EGQ EhpDiscardPacketCounter";
    }
    leaf egq-ipt-pkt-cnt {
      type string {
        length "0..6";
      }
      description "EGQ IptPktCnt";
    }
    leaf epni-epe-pkt-cnt {
      type string {
        length "0..6";
      }
      description "EPNI EpePktCnt";
    }
    leaf epni-epe-byte-cnt {
      type string {
        length "0..6";
      }
      description "EPNI EpeByteCnt";
    }
    leaf epni-epe-discard-pkt-cnt {
      type string {
        length "0..6";
      }
      description "EPNI EpeDiscardPktCnt";
    }
    leaf epni-ecc-1b-err-cnt {
      type string {
        length "0..6";
      }
      description "EPNI Ecc 1bErrCnt";
    }
    leaf epni-ecc-2b-err-cnt {
      type string {
        length "0..6";
      }
      description "EPNI Ecc 2bErrCnt";
    }
    leaf epni-parity-err-cnt {
      type string {
        length "0..6";
      }
      description "EPNI ParityErrCnt";
    }
    leaf egq-pqp-ucast-pkt-cnt {
      type string {
        length "0..6";
      }
      description "EGQ PqpUcastPktCnt";
    }
    leaf egq-pqp-ucast-h-pkt-cnt {
      type string {
        length "0..6";
      }
      description "EGQ PqpUcastHPktCnt";
    }
    leaf egq-pqp-ucast-l-pkt-cnt {
      type string {
        length "0..6";
      }
      description "EGQ PqpUcastLPktCnt";
    }
    leaf egq-pqp-ucast-bytes-cnt {
      type string {
        length "0..6";
      }
      description "EGQ PqpUcastBytesCnt";
    }
    leaf egq-pqp-ucast-discard-pkt-cnt {
      type string {
        length "0..6";
      }
      description "EGQ PqpUcastDiscardPktCnt";
    }
    leaf egq-pqp-mcast-pkt-cnt {
      type string {
        length "0..6";
      }
      description "EGQ PqpMcastPktCnt";
    }
    leaf egq-pqp-mcast-h-pkt-cnt {
      type string {
        length "0..6";
      }
      description "EGQ PqpMcastHPktCnt";
    }
    leaf egq-pqp-mcast-l-pkt-cnt {
      type string {
        length "0..6";
      }
      description "EGQ PqpMcastLPktCnt";
    }
    leaf egq-pqp-mcast-bytes-cnt {
      type string {
        length "0..6";
      }
      description "EGQ PqpMcastBytesCnt";
    }
    leaf egq-pqp-mcast-discard-pkt-cnt {
      type string {
        length "0..6";
      }
      description "EGQ PqpMcastDiscardPktCnt";
    }
    leaf fct-control-cell-cnt {
      type string {
        length "0..6";
      }
      description "FCT ControlCellCnt";
    }
    leaf fct-unrch-crdt-cnt {
      type string {
        length "0..6";
      }
      description "FCT UnrchCrdtCnt";
    }
    leaf idr-reassembly-errors {
      type string {
        length "0..6";
      }
      description "IDR ReassemblyErrors";
    }
    leaf idr-mmu-ecc-1b-err-cnt {
      type string {
        length "0..6";
      }
      description "IDR MmuEcc 1bErrCnt";
    }
    leaf idr-mmu-ecc-2b-err-cnt {
      type string {
        length "0..6";
      }
      description "IDR MmuEcc 2bErrCnt";
    }
    leaf idr-discarded-packets0-cnt {
      type string {
        length "0..6";
      }
      description "IDR DiscardedPackets0Cnt";
    }
    leaf idr-discarded-packets1-cnt {
      type string {
        length "0..6";
      }
      description "IDR DiscardedPackets1Cnt";
    }
    leaf idr-discarded-packets2-cnt {
      type string {
        length "0..6";
      }
      description "IDR DiscardedPackets2Cnt";
    }
    leaf idr-discarded-packets3-cnt {
      type string {
        length "0..6";
      }
      description "IDR DiscardedPackets3Cnt";
    }
    leaf idr-discarded-octets0-cnt {
      type string {
        length "0..6";
      }
      description "IDR DiscardedOctets0Cnt";
    }
    leaf idr-discarded-octets1-cnt {
      type string {
        length "0..6";
      }
      description "IDR DiscardedOctets1Cnt";
    }
    leaf idr-discarded-octets2-cnt {
      type string {
        length "0..6";
      }
      description "IDR DiscardedOctets2Cnt";
    }
    leaf idr-discarded-octets3-cnt {
      type string {
        length "0..6";
      }
      description "IDR DiscardedOctets3Cnt";
    }
    leaf mmu-ecc-1b-err-cnt {
      type string {
        length "0..6";
      }
      description "MMU Ecc 1bErrCnt";
    }
    leaf mmu-ecc-2b-err-cnt {
      type string {
        length "0..6";
      }
      description "MMU Ecc 2bErrCnt";
    }
    leaf oamp-parity-err-cnt {
      type string {
        length "0..6";
      }
      description "OAMP ParityErrCnt";
    }
    leaf oamp-ecc-1b-err-cnt {
      type string {
        length "0..6";
      }
      description "OAMP Ecc 1bErrCnt";
    }
    leaf oamp-ecc-2b-err-cnt {
      type string {
        length "0..6";
      }
      description "OAMP Ecc 2bErrCnt";
    }
    leaf crps-parity-err-cnt {
      type string {
        length "0..6";
      }
      description "CRPS ParityErrCnt";
    }
    leaf fmac0-kpcs0-tst-rx-err-cnt {
      type string {
        length "0..6";
      }
      description "FMAC0 Kpcs0TstRxErrCnt";
    }
    leaf fmac1-kpcs0-tst-rx-err-cnt {
      type string {
        length "0..6";
      }
      description "FMAC1 Kpcs0TstRxErrCnt";
    }
    leaf fmac2-kpcs0-tst-rx-err-cnt {
      type string {
        length "0..6";
      }
      description "FMAC2 Kpcs0TstRxErrCnt";
    }
    leaf fmac3-kpcs0-tst-rx-err-cnt {
      type string {
        length "0..6";
      }
      description "FMAC3 Kpcs0TstRxErrCnt";
    }
    leaf fmac4-kpcs0-tst-rx-err-cnt {
      type string {
        length "0..6";
      }
      description "FMAC4 Kpcs0TstRxErrCnt";
    }
    leaf fmac5-kpcs0-tst-rx-err-cnt {
      type string {
        length "0..6";
      }
      description "FMAC5 Kpcs0TstRxErrCnt";
    }
    leaf fmac6-kpcs0-tst-rx-err-cnt {
      type string {
        length "0..6";
      }
      description "FMAC6 Kpcs0TstRxErrCnt";
    }
    leaf fmac7-kpcs0-tst-rx-err-cnt {
      type string {
        length "0..6";
      }
      description "FMAC7 Kpcs0TstRxErrCnt";
    }
    leaf fmac8-kpcs0-tst-rx-err-cnt {
      type string {
        length "0..6";
      }
      description "FMAC8 Kpcs0TstRxErrCnt";
    }
    leaf fmac0-kpcs1-tst-rx-err-cnt {
      type string {
        length "0..6";
      }
      description "FMAC0 Kpcs1TstRxErrCnt";
    }
    leaf fmac1-kpcs1-tst-rx-err-cnt {
      type string {
        length "0..6";
      }
      description "FMAC1 Kpcs1TstRxErrCnt";
    }
    leaf fmac2-kpcs1-tst-rx-err-cnt {
      type string {
        length "0..6";
      }
      description "FMAC2 Kpcs1TstRxErrCnt";
    }
    leaf fmac3-kpcs1-tst-rx-err-cnt {
      type string {
        length "0..6";
      }
      description "FMAC3 Kpcs1TstRxErrCnt";
    }
    leaf fmac4-kpcs1-tst-rx-err-cnt {
      type string {
        length "0..6";
      }
      description "FMAC4 Kpcs1TstRxErrCnt";
    }
    leaf fmac5-kpcs1-tst-rx-err-cnt {
      type string {
        length "0..6";
      }
      description "FMAC5 Kpcs1TstRxErrCnt";
    }
    leaf fmac6-kpcs1-tst-rx-err-cnt {
      type string {
        length "0..6";
      }
      description "FMAC6 Kpcs1TstRxErrCnt";
    }
    leaf fmac7-kpcs1-tst-rx-err-cnt {
      type string {
        length "0..6";
      }
      description "FMAC7 Kpcs1TstRxErrCnt";
    }
    leaf fmac8-kpcs1-tst-rx-err-cnt {
      type string {
        length "0..6";
      }
      description "FMAC8 Kpcs1TstRxErrCnt";
    }
    leaf fmac0-kpcs2-tst-rx-err-cnt {
      type string {
        length "0..6";
      }
      description "FMAC0 Kpcs2TstRxErrCnt";
    }
    leaf fmac1-kpcs2-tst-rx-err-cnt {
      type string {
        length "0..6";
      }
      description "FMAC1 Kpcs2TstRxErrCnt";
    }
    leaf fmac2-kpcs2-tst-rx-err-cnt {
      type string {
        length "0..6";
      }
      description "FMAC2 Kpcs2TstRxErrCnt";
    }
    leaf fmac3-kpcs2-tst-rx-err-cnt {
      type string {
        length "0..6";
      }
      description "FMAC3 Kpcs2TstRxErrCnt";
    }
    leaf fmac4-kpcs2-tst-rx-err-cnt {
      type string {
        length "0..6";
      }
      description "FMAC4 Kpcs2TstRxErrCnt";
    }
    leaf fmac5-kpcs2-tst-rx-err-cnt {
      type string {
        length "0..6";
      }
      description "FMAC5 Kpcs2TstRxErrCnt";
    }
    leaf fmac6-kpcs2-tst-rx-err-cnt {
      type string {
        length "0..6";
      }
      description "FMAC6 Kpcs2TstRxErrCnt";
    }
    leaf fmac7-kpcs2-tst-rx-err-cnt {
      type string {
        length "0..6";
      }
      description "FMAC7 Kpcs2TstRxErrCnt";
    }
    leaf fmac8-kpcs2-tst-rx-err-cnt {
      type string {
        length "0..6";
      }
      description "FMAC8 Kpcs2TstRxErrCnt";
    }
    leaf fmac0-kpcs3-tst-rx-err-cnt {
      type string {
        length "0..6";
      }
      description "FMAC0 Kpcs3TstRxErrCnt";
    }
    leaf fmac1-kpcs3-tst-rx-err-cnt {
      type string {
        length "0..6";
      }
      description "FMAC1 Kpcs3TstRxErrCnt";
    }
    leaf fmac2-kpcs3-tst-rx-err-cnt {
      type string {
        length "0..6";
      }
      description "FMAC2 Kpcs3TstRxErrCnt";
    }
    leaf fmac3-kpcs3-tst-rx-err-cnt {
      type string {
        length "0..6";
      }
      description "FMAC3 Kpcs3TstRxErrCnt";
    }
    leaf fmac4-kpcs3-tst-rx-err-cnt {
      type string {
        length "0..6";
      }
      description "FMAC4 Kpcs3TstRxErrCnt";
    }
    leaf fmac5-kpcs3-tst-rx-err-cnt {
      type string {
        length "0..6";
      }
      description "FMAC5 Kpcs3TstRxErrCnt";
    }
    leaf fmac6-kpcs3-tst-rx-err-cnt {
      type string {
        length "0..6";
      }
      description "FMAC6 Kpcs3TstRxErrCnt";
    }
    leaf fmac7-kpcs3-tst-rx-err-cnt {
      type string {
        length "0..6";
      }
      description "FMAC7 Kpcs3TstRxErrCnt";
    }
    leaf fmac8-kpcs3-tst-rx-err-cnt {
      type string {
        length "0..6";
      }
      description "FMAC8 Kpcs3TstRxErrCnt";
    }
    leaf fmac0-tst0-err-cnt {
      type string {
        length "0..6";
      }
      description "FMAC0 Tst0ErrCnt";
    }
    leaf fmac1-tst0-err-cnt {
      type string {
        length "0..6";
      }
      description "FMAC1 Tst0ErrCnt";
    }
    leaf fmac2-tst0-err-cnt {
      type string {
        length "0..6";
      }
      description "FMAC2 Tst0ErrCnt";
    }
    leaf fmac3-tst0-err-cnt {
      type string {
        length "0..6";
      }
      description "FMAC3 Tst0ErrCnt";
    }
    leaf fmac4-tst0-err-cnt {
      type string {
        length "0..6";
      }
      description "FMAC4 Tst0ErrCnt";
    }
    leaf fmac5-tst0-err-cnt {
      type string {
        length "0..6";
      }
      description "FMAC5 Tst0ErrCnt";
    }
    leaf fmac6-tst0-err-cnt {
      type string {
        length "0..6";
      }
      description "FMAC6 Tst0ErrCnt";
    }
    leaf fmac7-tst0-err-cnt {
      type string {
        length "0..6";
      }
      description "FMAC7 Tst0ErrCnt";
    }
    leaf fmac8-tst0-err-cnt {
      type string {
        length "0..6";
      }
      description "FMAC8 Tst0ErrCnt";
    }
    leaf fmac0-tst1-err-cnt {
      type string {
        length "0..6";
      }
      description "FMAC0 Tst1ErrCnt";
    }
    leaf fmac1-tst1-err-cnt {
      type string {
        length "0..6";
      }
      description "FMAC1 Tst1ErrCnt";
    }
    leaf fmac2-tst1-err-cnt {
      type string {
        length "0..6";
      }
      description "FMAC2 Tst1ErrCnt";
    }
    leaf fmac3-tst1-err-cnt {
      type string {
        length "0..6";
      }
      description "FMAC3 Tst1ErrCnt";
    }
    leaf fmac4-tst1-err-cnt {
      type string {
        length "0..6";
      }
      description "FMAC4 Tst1ErrCnt";
    }
    leaf fmac5-tst1-err-cnt {
      type string {
        length "0..6";
      }
      description "FMAC5 Tst1ErrCnt";
    }
    leaf fmac6-tst1-err-cnt {
      type string {
        length "0..6";
      }
      description "FMAC6 Tst1ErrCnt";
    }
    leaf fmac7-tst1-err-cnt {
      type string {
        length "0..6";
      }
      description "FMAC7 Tst1ErrCnt";
    }
    leaf fmac8-tst1-err-cnt {
      type string {
        length "0..6";
      }
      description "FMAC8 Tst1ErrCnt";
    }
    leaf fmac0-tst2-err-cnt {
      type string {
        length "0..6";
      }
      description "FMAC0 Tst2ErrCnt";
    }
    leaf fmac1-tst2-err-cnt {
      type string {
        length "0..6";
      }
      description "FMAC1 Tst2ErrCnt";
    }
    leaf fmac2-tst2-err-cnt {
      type string {
        length "0..6";
      }
      description "FMAC2 Tst2ErrCnt";
    }
    leaf fmac3-tst2-err-cnt {
      type string {
        length "0..6";
      }
      description "FMAC3 Tst2ErrCnt";
    }
    leaf fmac4-tst2-err-cnt {
      type string {
        length "0..6";
      }
      description "FMAC4 Tst2ErrCnt";
    }
    leaf fmac5-tst2-err-cnt {
      type string {
        length "0..6";
      }
      description "FMAC5 Tst2ErrCnt";
    }
    leaf fmac6-tst2-err-cnt {
      type string {
        length "0..6";
      }
      description "FMAC6 Tst2ErrCnt";
    }
    leaf fmac7-tst2-err-cnt {
      type string {
        length "0..6";
      }
      description "FMAC7 Tst2ErrCnt";
    }
    leaf fmac8-tst2-err-cnt {
      type string {
        length "0..6";
      }
      description "FMAC8 Tst2ErrCnt";
    }
    leaf fmac0-tst3-err-cnt {
      type string {
        length "0..6";
      }
      description "FMAC0 Tst3ErrCnt";
    }
    leaf fmac1-tst3-err-cnt {
      type string {
        length "0..6";
      }
      description "FMAC1 Tst3ErrCnt";
    }
    leaf fmac2-tst3-err-cnt {
      type string {
        length "0..6";
      }
      description "FMAC2 Tst3ErrCnt";
    }
    leaf fmac3-tst3-err-cnt {
      type string {
        length "0..6";
      }
      description "FMAC3 Tst3ErrCnt";
    }
    leaf fmac4-tst3-err-cnt {
      type string {
        length "0..6";
      }
      description "FMAC4 Tst3ErrCnt";
    }
    leaf fmac5-tst3-err-cnt {
      type string {
        length "0..6";
      }
      description "FMAC5 Tst3ErrCnt";
    }
    leaf fmac6-tst3-err-cnt {
      type string {
        length "0..6";
      }
      description "FMAC6 Tst3ErrCnt";
    }
    leaf fmac7-tst3-err-cnt {
      type string {
        length "0..6";
      }
      description "FMAC7 Tst3ErrCnt";
    }
    leaf fmac8-tst3-err-cnt {
      type string {
        length "0..6";
      }
      description "FMAC8 Tst3ErrCnt";
    }
    leaf fmac0-ecc-1b-err-cnt {
      type string {
        length "0..6";
      }
      description "FMAC0 Ecc 1bErrCnt";
    }
    leaf fmac1-ecc-1b-err-cnt {
      type string {
        length "0..6";
      }
      description "FMAC1 Ecc 1bErrCnt";
    }
    leaf fmac2-ecc-1b-err-cnt {
      type string {
        length "0..6";
      }
      description "FMAC2 Ecc 1bErrCnt";
    }
    leaf fmac3-ecc-1b-err-cnt {
      type string {
        length "0..6";
      }
      description "FMAC3 Ecc 1bErrCnt";
    }
    leaf fmac4-ecc-1b-err-cnt {
      type string {
        length "0..6";
      }
      description "FMAC4 Ecc 1bErrCnt";
    }
    leaf fmac5-ecc-1b-err-cnt {
      type string {
        length "0..6";
      }
      description "FMAC5 Ecc 1bErrCnt";
    }
    leaf fmac6-ecc-1b-err-cnt {
      type string {
        length "0..6";
      }
      description "FMAC6 Ecc 1bErrCnt";
    }
    leaf fmac7-ecc-1b-err-cnt {
      type string {
        length "0..6";
      }
      description "FMAC7 Ecc 1bErrCnt";
    }
    leaf fmac8-ecc-1b-err-cnt {
      type string {
        length "0..6";
      }
      description "FMAC8 Ecc 1bErrCnt";
    }
    leaf fmac0-ecc-2b-err-cnt {
      type string {
        length "0..6";
      }
      description "FMAC0 Ecc 2bErrCnt";
    }
    leaf fmac1-ecc-2b-err-cnt {
      type string {
        length "0..6";
      }
      description "FMAC1 Ecc 2bErrCnt";
    }
    leaf fmac2-ecc-2b-err-cnt {
      type string {
        length "0..6";
      }
      description "FMAC2 Ecc 2bErrCnt";
    }
    leaf fmac3-ecc-2b-err-cnt {
      type string {
        length "0..6";
      }
      description "FMAC3 Ecc 2bErrCnt";
    }
    leaf fmac4-ecc-2b-err-cnt {
      type string {
        length "0..6";
      }
      description "FMAC4 Ecc 2bErrCnt";
    }
    leaf fmac5-ecc-2b-err-cnt {
      type string {
        length "0..6";
      }
      description "FMAC5 Ecc 2bErrCnt";
    }
    leaf fmac6-ecc-2b-err-cnt {
      type string {
        length "0..6";
      }
      description "FMAC6 Ecc 2bErrCnt";
    }
    leaf fmac7-ecc-2b-err-cnt {
      type string {
        length "0..6";
      }
      description "FMAC7 Ecc 2bErrCnt";
    }
    leaf fmac8-ecc-2b-err-cnt {
      type string {
        length "0..6";
      }
      description "FMAC8 Ecc 2bErrCnt";
    }
    leaf olp-incoming-bad-identifier-counter {
      type string {
        length "0..6";
      }
      description "OLP IncomingBadIdentifierCounter";
    }
    leaf olp-incoming-bad-reassembly-counter {
      type string {
        length "0..6";
      }
      description "OLP IncomingBadReassemblyCounter";
    }
    leaf cfc-parity-err-cnt {
      type string {
        length "0..6";
      }
      description "CFC ParityErrCnt";
    }
    leaf cfc-ilkn0-oob-rx-crc-err-cntr {
      type string {
        length "0..6";
      }
      description "CFC Ilkn0OobRxCrcErrCntr";
    }
    leaf cfc-ilkn1-oob-rx-crc-err-cntr {
      type string {
        length "0..6";
      }
      description "CFC Ilkn1OobRxCrcErrCntr";
    }
    leaf cfc-spi-oob-rx0-frm-err-cnt {
      type string {
        length "0..6";
      }
      description "CFC SpiOobRx0FrmErrCnt";
    }
    leaf cfc-spi-oob-rx0-dip2-err-cnt {
      type string {
        length "0..6";
      }
      description "CFC SpiOobRx0Dip2ErrCnt";
    }
    leaf cfc-spi-oob-rx1-frm-err-cnt {
      type string {
        length "0..6";
      }
      description "CFC SpiOobRx1FrmErrCnt";
    }
    leaf cfc-spi-oob-rx1-dip2-err-cnt {
      type string {
        length "0..6";
      }
      description "CFC SpiOobRx1Dip2ErrCnt";
    }
    leaf cgm-cgm-uc-pd-dropped-cnt {
      type string {
        length "0..6";
      }
      description "CGM CgmUcPdDroppedCnt";
    }
    leaf cgm-cgm-mc-rep-pd-dropped-cnt {
      type string {
        length "0..6";
      }
      description "CGM CgmMcRepPdDroppedCnt";
    }
    leaf cgm-cgm-uc-db-dropped-by-rqp-cnt {
      type string {
        length "0..6";
      }
      description "CGM CgmUcDbDroppedByRqpCnt";
    }
    leaf cgm-cgm-uc-db-dropped-by-pqp-cnt {
      type string {
        length "0..6";
      }
      description "CGM CgmUcDbDroppedByPqpCnt";
    }
    leaf cgm-cgm-mc-rep-db-dropped-cnt {
      type string {
        length "0..6";
      }
      description "CGM CgmMcRepDbDroppedCnt";
    }
    leaf cgm-cgm-mc-db-dropped-cnt {
      type string {
        length "0..6";
      }
      description "CGM CgmMcDbDroppedCnt";
    }
    leaf drca-full-err-cnt {
      type string {
        length "0..6";
      }
      description "DRCA FullErrCnt";
    }
    leaf drca-single-err-cnt {
      type string {
        length "0..6";
      }
      description "DRCA SingleErrCnt";
    }
    leaf drca-calib-bist-full-err-cnt {
      type string {
        length "0..6";
      }
      description "DRCA CalibBistFullErrCnt";
    }
    leaf drca-loopback-full-err-cnt {
      type string {
        length "0..6";
      }
      description "DRCA LoopbackFullErrCnt";
    }
    leaf drcb-full-err-cnt {
      type string {
        length "0..6";
      }
      description "DRCB FullErrCnt";
    }
    leaf drcb-single-err-cnt {
      type string {
        length "0..6";
      }
      description "DRCB SingleErrCnt";
    }
    leaf drcb-calib-bist-full-err-cnt {
      type string {
        length "0..6";
      }
      description "DRCB CalibBistFullErrCnt";
    }
    leaf drcb-loopback-full-err-cnt {
      type string {
        length "0..6";
      }
      description "DRCB LoopbackFullErrCnt";
    }
    leaf drcc-full-err-cnt {
      type string {
        length "0..6";
      }
      description "DRCC FullErrCnt";
    }
    leaf drcc-single-err-cnt {
      type string {
        length "0..6";
      }
      description "DRCC SingleErrCnt";
    }
    leaf drcc-calib-bist-full-err-cnt {
      type string {
        length "0..6";
      }
      description "DRCC CalibBistFullErrCnt";
    }
    leaf drcc-loopback-full-err-cnt {
      type string {
        length "0..6";
      }
      description "DRCC LoopbackFullErrCnt";
    }
    leaf drcd-full-err-cnt {
      type string {
        length "0..6";
      }
      description "DRCD FullErrCnt";
    }
    leaf drcd-single-err-cnt {
      type string {
        length "0..6";
      }
      description "DRCD SingleErrCnt";
    }
    leaf drcd-calib-bist-full-err-cnt {
      type string {
        length "0..6";
      }
      description "DRCD CalibBistFullErrCnt";
    }
    leaf drcd-loopback-full-err-cnt {
      type string {
        length "0..6";
      }
      description "DRCD LoopbackFullErrCnt";
    }
    leaf drce-full-err-cnt {
      type string {
        length "0..6";
      }
      description "DRCE FullErrCnt";
    }
    leaf drce-single-err-cnt {
      type string {
        length "0..6";
      }
      description "DRCE SingleErrCnt";
    }
    leaf drce-calib-bist-full-err-cnt {
      type string {
        length "0..6";
      }
      description "DRCE CalibBistFullErrCnt";
    }
    leaf drce-loopback-full-err-cnt {
      type string {
        length "0..6";
      }
      description "DRCE LoopbackFullErrCnt";
    }
    leaf drcf-full-err-cnt {
      type string {
        length "0..6";
      }
      description "DRCF FullErrCnt";
    }
    leaf drcf-single-err-cnt {
      type string {
        length "0..6";
      }
      description "DRCF SingleErrCnt";
    }
    leaf drcf-calib-bist-full-err-cnt {
      type string {
        length "0..6";
      }
      description "DRCF CalibBistFullErrCnt";
    }
    leaf drcf-loopback-full-err-cnt {
      type string {
        length "0..6";
      }
      description "DRCF LoopbackFullErrCnt";
    }
    leaf drcg-full-err-cnt {
      type string {
        length "0..6";
      }
      description "DRCG FullErrCnt";
    }
    leaf drcg-single-err-cnt {
      type string {
        length "0..6";
      }
      description "DRCG SingleErrCnt";
    }
    leaf drcg-calib-bist-full-err-cnt {
      type string {
        length "0..6";
      }
      description "DRCG CalibBistFullErrCnt";
    }
    leaf drcg-loopback-full-err-cnt {
      type string {
        length "0..6";
      }
      description "DRCG LoopbackFullErrCnt";
    }
    leaf drch-full-err-cnt {
      type string {
        length "0..6";
      }
      description "DRCH FullErrCnt";
    }
    leaf drch-single-err-cnt {
      type string {
        length "0..6";
      }
      description "DRCH SingleErrCnt";
    }
    leaf drch-calib-bist-full-err-cnt {
      type string {
        length "0..6";
      }
      description "DRCH CalibBistFullErrCnt";
    }
    leaf drch-loopback-full-err-cnt {
      type string {
        length "0..6";
      }
      description "DRCH LoopbackFullErrCnt";
    }
    leaf drcbroadcast-full-err-cnt {
      type string {
        length "0..6";
      }
      description "DRCBROADCAST FullErrCnt";
    }
    leaf drcbroadcast-single-err-cnt {
      type string {
        length "0..6";
      }
      description "DRCBROADCAST SingleErrCnt";
    }
    leaf drcbroadcast-calib-bist-full-err-cnt {
      type string {
        length "0..6";
      }
      description "DRCBROADCAST CalibBistFullErrCnt";
    }
    leaf drcbroadcast-loopback-full-err-cnt {
      type string {
        length "0..6";
      }
      description "DRCBROADCAST LoopbackFullErrCnt";
    }
  }

  grouping FIA-EDM-DEVICE-STATS-PBC-OTN {
    description "FIA EDM DEVICE STATS PBC OTN";
    leaf il-total-rx-pkt-count {
      type uint64;
      description "IL TotalRxPktCount";
    }
    leaf il-total-tx-pkt-count {
      type uint64;
      description "IL TotalTxPktCount";
    }
  }

  grouping FIA-EDM-DEVICE-STATS-PBC {
    description "FIA EDM DEVICE STATS PBC";
    leaf rx-internal-error {
      type uint64;
      description "RxInternalError";
    }
    leaf rx-internal-drop {
      type uint64;
      description "RxInternalDrop";
    }
    leaf tx-internal-error {
      type uint64;
      description "TxInternalError";
    }
    leaf tx-internal-drop {
      type uint64;
      description "TxInternalDrop";
    }
    leaf cmic-cmc0-pkt-count-tx-pkt {
      type uint64;
      description "CMIC Cmc0PktCountTxPkt";
    }
    leaf cmic-cmc0-pkt-count-rx-pkt {
      type uint64;
      description "CMIC Cmc0PktCountRxPkt";
    }
    leaf nbi-stat-rx-bursts-err-cnt {
      type uint64;
      description "NBI StatRxBurstsErrCnt";
    }
    leaf nbi-ecc-1b-err-cnt {
      type uint64;
      description "NBI Ecc 1bErrCnt";
    }
    leaf nbi-ecc-2b-err-cnt {
      type uint64;
      description "NBI Ecc 2bErrCnt";
    }
    leaf nbi-parity-err-cnt {
      type uint64;
      description "NBI ParityErrCnt";
    }
    leaf nbi-rx-ilkn-crc32-err-cnt {
      type uint64;
      description "NBI RxIlknCrc32ErrCnt";
    }
    leaf nbi-rx-ilkn0-crc24-err-cnt {
      type uint64;
      description "NBI RxIlkn0Crc24ErrCnt";
    }
    leaf nbi-rx-ilkn0-burst-err-cnt {
      type uint64;
      description "NBI RxIlkn0BurstErrCnt";
    }
    leaf nbi-rx-ilkn0-miss-sop-err-cnt {
      type uint64;
      description "NBI RxIlkn0MissSopErrCnt";
    }
    leaf nbi-rx-ilkn0-miss-eop-err-cnt {
      type uint64;
      description "NBI RxIlkn0MissEopErrCnt";
    }
    leaf nbi-rx-ilkn0-misaligned-cnt {
      type uint64;
      description "NBI RxIlkn0MisalignedCnt";
    }
    leaf nbi-rx-ilkn1-crc24-err-cnt {
      type uint64;
      description "NBI RxIlkn1Crc24ErrCnt";
    }
    leaf nbi-rx-ilkn1-burst-err-cnt {
      type uint64;
      description "NBI RxIlkn1BurstErrCnt";
    }
    leaf nbi-rx-ilkn1-miss-sop-err-cnt {
      type uint64;
      description "NBI RxIlkn1MissSopErrCnt";
    }
    leaf nbi-rx-ilkn1-miss-eop-err-cnt {
      type uint64;
      description "NBI RxIlkn1MissEopErrCnt";
    }
    leaf nbi-rx-ilkn1-misaligned-cnt {
      type uint64;
      description "NBI RxIlkn1MisalignedCnt";
    }
    leaf nbi-tx-ilkn1-flushed-bursts-cnt {
      type uint64;
      description "NBI TxIlkn1FlushedBurstsCnt";
    }
    leaf nbi-rx-ilkn0-retrans-crc24-err-cnt {
      type uint64;
      description "NBI RxIlkn0RetransCRC24ErrCnt";
    }
    leaf nbi-rx-ilkn0-retrans-retry-err-cnt {
      type uint64;
      description "NBI RxIlkn0RetransRetryErrCnt";
    }
    leaf nbi-rx-ilkn0-retrans-wdog-err-cnt {
      type uint64;
      description "NBI RxIlkn0RetransWdogErrCnt";
    }
    leaf nbi-rx-ilkn0-retrans-wrap-after-disc-err-cnt {
      type uint64;
      description "NBI RxIlkn0RetransWrapAfterDiscErrCnt";
    }
    leaf nbi-rx-ilkn0-retrans-wrap-b4-disc-err-cnt {
      type uint64;
      description "NBI RxIlkn0RetransWrapB4DiscErrCnt";
    }
    leaf nbi-rx-ilkn0-retrans-reached-timeout-err-cnt {
      type uint64;
      description "NBI RxIlkn0RetransReachedTimeoutErrCnt";
    }
    leaf nbi-rx-ilkn1-retrans-crc24-err-cnt {
      type uint64;
      description "NBI RxIlkn1RetransCRC24ErrCnt";
    }
    leaf nbi-rx-ilkn1-retrans-retry-err-cnt {
      type uint64;
      description "NBI RxIlkn1RetransRetryErrCnt";
    }
    leaf nbi-rx-ilkn1-retrans-wdog-err-cnt {
      type uint64;
      description "NBI RxIlkn1RetransWdogErrCnt";
    }
    leaf nbi-rx-ilkn1-retrans-wrap-after-disc-err-cnt {
      type uint64;
      description "NBI RxIlkn1RetransWrapAfterDiscErrCnt";
    }
    leaf nbi-rx-ilkn1-retrans-wrap-b4-disc-err-cnt {
      type uint64;
      description "NBI RxIlkn1RetransWrapB4DiscErrCnt";
    }
    leaf nbi-rx-ilkn1-retrans-reached-timeout-err-cnt {
      type uint64;
      description "NBI RxIlkn1RetransReachedTimeoutErrCnt";
    }
    leaf nbi-stat-rx-frame-err-cnt {
      type uint64;
      description "NBI StatRxFrameErrCnt";
    }
    leaf nbi-stat-tx-frame-err-cnt {
      type uint64;
      description "NBI StatTxFrameErrCnt";
    }
    leaf nbi-rx-elk-err-bursts-cnt {
      type uint64;
      description "NBI RxElkErrBurstsCnt";
    }
    leaf nbi-rx-num-thrown-eops {
      type uint64;
      description "NBI RxNumThrownEops";
    }
    leaf nbi-rx-num-runts {
      type uint64;
      description "NBI RxNumRunts";
    }
    leaf nbi-bist-tx-crc-err-bursts-cnt {
      type uint64;
      description "NBI BistTxCrcErrBurstsCnt";
    }
    leaf nbi-bist-rx-err-length-bursts-cnt {
      type uint64;
      description "NBI BistRxErrLengthBurstsCnt";
    }
    leaf nbi-bist-rx-err-burst-index-cnt {
      type uint64;
      description "NBI BistRxErrBurstIndexCnt";
    }
    leaf nbi-bist-rx-err-bct-cnt {
      type uint64;
      description "NBI BistRxErrBctCnt";
    }
    leaf nbi-bist-rx-err-data-cnt {
      type uint64;
      description "NBI BistRxErrDataCnt";
    }
    leaf nbi-bist-rx-err-in-crc-err-cnt {
      type uint64;
      description "NBI BistRxErrInCrcErrCnt";
    }
    leaf nbi-bist-rx-err-sob-cnt {
      type uint64;
      description "NBI BistRxErrSobCnt";
    }
    leaf nbi-stat-tx-bursts-cnt {
      type uint64;
      description "NBI StatTxBurstsCnt";
    }
    leaf nbi-stat-tx-total-leng-cnt {
      type uint64;
      description "NBI StatTxTotalLengCnt";
    }
    leaf rxaui-total-tx-pkt-count {
      type uint64;
      description "RXAUI TotalTxPktCount";
    }
    leaf rxaui-total-rx-pkt-count {
      type uint64;
      description "RXAUI TotalRxPktCount";
    }
    leaf rxaui-rx-pkt-count-bcast-pkt {
      type uint64;
      description "RXAUI RxPktCountBcastPkt";
    }
    leaf rxaui-tx-pkt-count-bcast-pkt {
      type uint64;
      description "RXAUI TxPktCountBcastPkt";
    }
    leaf rxaui-rx-pkt-count-mcast-pkt {
      type uint64;
      description "RXAUI RxPktCountMcastPkt";
    }
    leaf rxaui-tx-pkt-count-mcast-pkt {
      type uint64;
      description "RXAUI TxPktCountMcastPkt";
    }
    leaf rxaui-rx-pkt-count-ucast-pkt {
      type uint64;
      description "RXAUI RxPktCountUcastPkt";
    }
    leaf rxaui-tx-pkt-count-ucast-pkt {
      type uint64;
      description "RXAUI TxPktCountUcastPkt";
    }
    leaf rxaui-rx-err-drop-pkt-cnt {
      type uint64;
      description "RXAUI RxErrDropPktCnt";
    }
    leaf rxaui-tx-err-drop-pkt-cnt {
      type uint64;
      description "RXAUI TxErrDropPktCnt";
    }
    leaf rxaui-byte-count-tx-pkt {
      type uint64;
      description "RXAUI ByteCountTxPkt";
    }
    leaf rxaui-byte-count-rx-pkt {
      type uint64;
      description "RXAUI ByteCountRxPkt";
    }
    leaf rxaui-rx-dscrd-pkt-cnt {
      type uint64;
      description "RXAUI RxDscrdPktCnt";
    }
    leaf rxaui-tx-dscrd-pkt-cnt {
      type uint64;
      description "RXAUI TxDscrdPktCnt";
    }
    leaf ire-nif-packet-counter {
      type uint64;
      description "IRE NifPacketCounter";
    }
    leaf il-total-rx-pkt-count {
      type uint64;
      description "IL TotalRxPktCount";
    }
    leaf il-total-tx-pkt-count {
      type uint64;
      description "IL TotalTxPktCount";
    }
    leaf il-rx-err-drop-pkt-cnt {
      type uint64;
      description "IL RxErrDropPktCnt";
    }
    leaf il-tx-err-drop-pkt-cnt {
      type uint64;
      description "IL TxErrDropPktCnt";
    }
    leaf il-byte-count-tx-pkt {
      type uint64;
      description "IL ByteCountTxPkt";
    }
    leaf il-byte-count-rx-pkt {
      type uint64;
      description "IL ByteCountRxPkt";
    }
    leaf il-rx-dscrd-pkt-cnt {
      type uint64;
      description "IL RxDscrdPktCnt";
    }
    leaf il-tx-dscrd-pkt-cnt {
      type uint64;
      description "IL TxDscrdPktCnt";
    }
    leaf il-rx-pkt-count-bcast-pkt {
      type uint64;
      description "IL RxPktCountBcastPkt";
    }
    leaf il-tx-pkt-count-bcast-pkt {
      type uint64;
      description "IL TxPktCountBcastPkt";
    }
    leaf il-rx-pkt-count-mcast-pkt {
      type uint64;
      description "IL RxPktCountMcastPkt";
    }
    leaf il-tx-pkt-count-mcast-pkt {
      type uint64;
      description "IL TxPktCountMcastPkt";
    }
    leaf il-rx-pkt-count-ucast-pkt {
      type uint64;
      description "IL RxPktCountUcastPkt";
    }
    leaf il-tx-pkt-count-ucast-pkt {
      type uint64;
      description "IL TxPktCountUcastPkt";
    }
    leaf iqm-enq-pkt-cnt {
      type uint64;
      description "IQM EnqPktCnt";
    }
    leaf iqm-enq-byte-cnt {
      type uint64;
      description "IQM EnqByteCnt";
    }
    leaf iqm-deq-pkt-cnt {
      type uint64;
      description "IQM DeqPktCnt";
    }
    leaf iqm-deq-byte-cnt {
      type uint64;
      description "IQM DeqByteCnt";
    }
    leaf iqm-tot-dscrd-pkt-cnt {
      type uint64;
      description "IQM TotDscrdPktCnt";
    }
    leaf iqm-tot-dscrd-byte-cnt {
      type uint64;
      description "IQM TotDscrdByteCnt";
    }
    leaf iqm-ecc-1b-err-cnt {
      type uint64;
      description "IQM Ecc 1bErrCnt";
    }
    leaf iqm-ecc-2b-err-cnt {
      type uint64;
      description "IQM Ecc 2bErrCnt";
    }
    leaf iqm-parity-err-cnt {
      type uint64;
      description "IQM ParityErrCnt";
    }
    leaf iqm-deq-delete-pkt-cnt {
      type uint64;
      description "IQM DeqDeletePktCnt";
    }
    leaf iqm-ecn-dscrd-msk-pkt-cnt {
      type uint64;
      description "IQM EcnDscrdMskPktCnt";
    }
    leaf iqm-q-tot-dscrd-pkt-cnt {
      type uint64;
      description "IQM QTotDscrdPktCnt";
    }
    leaf iqm-q-deq-delete-pkt-cnt {
      type uint64;
      description "IQM QDeqDeletePktCnt";
    }
    leaf iqm-rjct-db-pkt-cnt {
      type uint64;
      description "IQM RjctDbPktCnt";
    }
    leaf iqm-rjct-bdb-pkt-cnt {
      type uint64;
      description "IQM RjctBdbPktCnt";
    }
    leaf iqm-rjct-bdb-protct-pkt-cnt {
      type uint64;
      description "IQM RjctBdbProtctPktCnt";
    }
    leaf iqm-rjct-oc-bd-pkt-cnt {
      type uint64;
      description "IQM RjctOcBdPktCnt";
    }
    leaf iqm-rjct-sn-err-pkt-cnt {
      type uint64;
      description "IQM RjctSnErrPktCnt";
    }
    leaf iqm-rjct-mc-err-pkt-cnt {
      type uint64;
      description "IQM RjctMcErrPktCnt";
    }
    leaf iqm-rjct-rsrc-err-pkt-cnt {
      type uint64;
      description "IQM RjctRsrcErrPktCnt";
    }
    leaf iqm-rjct-qnvalid-err-pkt-cnt {
      type uint64;
      description "IQM RjctQnvalidErrPktCnt";
    }
    leaf iqm-rjct-cnm-pkt-cnt {
      type uint64;
      description "IQM RjctCnmPktCnt";
    }
    leaf iqm-rjct-dyn-space-pkt-cnt {
      type uint64;
      description "IQM RjctDynSpacePktCnt";
    }
    leaf ipt-fdt-pkt-cnt {
      type uint64;
      description "IPT FdtPktCnt";
    }
    leaf ipt-ecc-1b-err-cnt {
      type uint64;
      description "IPT Ecc 1bErrCnt";
    }
    leaf ipt-ecc-2b-err-cnt {
      type uint64;
      description "IPT Ecc 2bErrCnt";
    }
    leaf ipt-parity-err-cnt {
      type uint64;
      description "IPT ParityErrCnt";
    }
    leaf ipt-crc-err-cnt {
      type uint64;
      description "IPT CrcErrCnt";
    }
    leaf ipt-crc-err-del-buff-cnt {
      type uint64;
      description "IPT CrcErrDelBuffCnt";
    }
    leaf ipt-cpu-del-buff-cnt {
      type uint64;
      description "IPT CpuDelBuffCnt";
    }
    leaf ipt-cpu-rel-buff-cnt {
      type uint64;
      description "IPT CpuRelBuffCnt";
    }
    leaf ipt-crc-err-buff-fifo-full-cnt {
      type uint64;
      description "IPT CrcErrBuffFifoFullCnt";
    }
    leaf fdt-data-cell-cnt {
      type uint64;
      description "FDT DataCellCnt";
    }
    leaf fdt-data-byte-cnt {
      type uint64;
      description "FDT DataByteCnt";
    }
    leaf fdt-crc-dropped-pck-cnt {
      type uint64;
      description "FDT CrcDroppedPckCnt";
    }
    leaf fdt-invalid-destq-drop-cell-cnt {
      type uint64;
      description "FDT invalid destq drop cell cnt";
    }
    leaf fdt-indirect-command-count {
      type uint64;
      description "FDT IndirectCommandCount";
    }
    leaf fdt-ecc-1b-err-cnt {
      type uint64;
      description "FDT Ecc 1bErrCnt";
    }
    leaf fdt-ecc-2b-err-cnt {
      type uint64;
      description "FDT Ecc 2bErrCnt";
    }
    leaf fdt-parity-err-cnt {
      type uint64;
      description "FDT ParityErrCnt";
    }
    leaf fdt-crc-dropped-cell-cnt {
      type uint64;
      description "FDT CrcDroppedCellCnt";
    }
    leaf fcr-control-cell-cnt {
      type uint64;
      description "FCR ControlCellCnt";
    }
    leaf fcr-cell-drop-cnt {
      type uint64;
      description "FCR CellDropCnt";
    }
    leaf fcr-credit-cell-drop-cnt {
      type uint64;
      description "FCR CreditCellDropCnt";
    }
    leaf fcr-fs-cell-drop-cnt {
      type uint64;
      description "FCR FSCellDropCnt";
    }
    leaf fcr-rt-cell-drop-cnt {
      type uint64;
      description "FCR RTCellDropCnt";
    }
    leaf fcr-ecc-1b-err-cnt {
      type uint64;
      description "FCR Ecc 1bErrCnt";
    }
    leaf fcr-ecc-2b-err-cnt {
      type uint64;
      description "FCR Ecc 2bErrCnt";
    }
    leaf fdr-data-cell-cnt {
      type uint64;
      description "FDR DataCellCnt";
    }
    leaf fdr-data-byte-cnt {
      type uint64;
      description "FDR DataByteCnt";
    }
    leaf fdr-crc-dropped-pck-cnt {
      type uint64;
      description "FDR CrcDroppedPckCnt";
    }
    leaf fdr-p-pkt-cnt {
      type uint64;
      description "FDR PPktCnt";
    }
    leaf fdr-prm-error-filter-cnt {
      type uint64;
      description "FDR PrmErrorFilterCnt";
    }
    leaf fdr-sec-error-filter-cnt {
      type uint64;
      description "FDR SecErrorFilterCnt";
    }
    leaf fdr-prm-ecc-1b-err-cnt {
      type uint64;
      description "FDR PrmEcc 1bErrCnt";
    }
    leaf fdr-prm-ecc-2b-err-cnt {
      type uint64;
      description "FDR PrmEcc 2bErrCnt";
    }
    leaf fdr-sec-ecc-1b-err-cnt {
      type uint64;
      description "FDR SecEcc 1bErrCnt";
    }
    leaf fdr-sec-ecc-2b-err-cnt {
      type uint64;
      description "FDR SecEcc 2bErrCnt";
    }
    leaf egq-ecc-1b-err-cnt {
      type uint64;
      description "EGQ Ecc 1bErrCnt";
    }
    leaf egq-ecc-2b-err-cnt {
      type uint64;
      description "EGQ Ecc 2bErrCnt";
    }
    leaf egq-parity-err-cnt {
      type uint64;
      description "EGQ ParityErrCnt";
    }
    leaf egq-dbf-ecc-1b-err-cnt {
      type uint64;
      description "EGQ DbfEcc 1bErrCnt";
    }
    leaf egq-dbf-ecc-2b-err-cnt {
      type uint64;
      description "EGQ DbfEcc 2bErrCnt";
    }
    leaf egq-empty-mcid-counter {
      type uint64;
      description "EGQ EmptyMcidCounter";
    }
    leaf egq-rqp-discard-packet-counter {
      type uint64;
      description "EGQ RqpDiscardPacketCounter";
    }
    leaf egq-ehp-discard-packet-counter {
      type uint64;
      description "EGQ EhpDiscardPacketCounter";
    }
    leaf egq-ipt-pkt-cnt {
      type uint64;
      description "EGQ IptPktCnt";
    }
    leaf epni-epe-pkt-cnt {
      type uint64;
      description "EPNI EpePktCnt";
    }
    leaf epni-epe-byte-cnt {
      type uint64;
      description "EPNI EpeByteCnt";
    }
    leaf epni-epe-discard-pkt-cnt {
      type uint64;
      description "EPNI EpeDiscardPktCnt";
    }
    leaf epni-ecc-1b-err-cnt {
      type uint64;
      description "EPNI Ecc 1bErrCnt";
    }
    leaf epni-ecc-2b-err-cnt {
      type uint64;
      description "EPNI Ecc 2bErrCnt";
    }
    leaf epni-parity-err-cnt {
      type uint64;
      description "EPNI ParityErrCnt";
    }
    leaf egq-pqp-ucast-pkt-cnt {
      type uint64;
      description "EGQ PqpUcastPktCnt";
    }
    leaf egq-pqp-ucast-h-pkt-cnt {
      type uint64;
      description "EGQ PqpUcastHPktCnt";
    }
    leaf egq-pqp-ucast-l-pkt-cnt {
      type uint64;
      description "EGQ PqpUcastLPktCnt";
    }
    leaf egq-pqp-ucast-bytes-cnt {
      type uint64;
      description "EGQ PqpUcastBytesCnt";
    }
    leaf egq-pqp-ucast-discard-pkt-cnt {
      type uint64;
      description "EGQ PqpUcastDiscardPktCnt";
    }
    leaf egq-pqp-mcast-pkt-cnt {
      type uint64;
      description "EGQ PqpMcastPktCnt";
    }
    leaf egq-pqp-mcast-h-pkt-cnt {
      type uint64;
      description "EGQ PqpMcastHPktCnt";
    }
    leaf egq-pqp-mcast-l-pkt-cnt {
      type uint64;
      description "EGQ PqpMcastLPktCnt";
    }
    leaf egq-pqp-mcast-bytes-cnt {
      type uint64;
      description "EGQ PqpMcastBytesCnt";
    }
    leaf egq-pqp-mcast-discard-pkt-cnt {
      type uint64;
      description "EGQ PqpMcastDiscardPktCnt";
    }
    leaf fct-control-cell-cnt {
      type uint64;
      description "FCT ControlCellCnt";
    }
    leaf fct-unrch-crdt-cnt {
      type uint64;
      description "FCT UnrchCrdtCnt";
    }
    leaf idr-reassembly-errors {
      type uint64;
      description "IDR ReassemblyErrors";
    }
    leaf idr-mmu-ecc-1b-err-cnt {
      type uint64;
      description "IDR MmuEcc 1bErrCnt";
    }
    leaf idr-mmu-ecc-2b-err-cnt {
      type uint64;
      description "IDR MmuEcc 2bErrCnt";
    }
    leaf idr-discarded-packets0-cnt {
      type uint64;
      description "IDR DiscardedPackets0Cnt";
    }
    leaf idr-discarded-packets1-cnt {
      type uint64;
      description "IDR DiscardedPackets1Cnt";
    }
    leaf idr-discarded-packets2-cnt {
      type uint64;
      description "IDR DiscardedPackets2Cnt";
    }
    leaf idr-discarded-packets3-cnt {
      type uint64;
      description "IDR DiscardedPackets3Cnt";
    }
    leaf idr-discarded-octets0-cnt {
      type uint64;
      description "IDR DiscardedOctets0Cnt";
    }
    leaf idr-discarded-octets1-cnt {
      type uint64;
      description "IDR DiscardedOctets1Cnt";
    }
    leaf idr-discarded-octets2-cnt {
      type uint64;
      description "IDR DiscardedOctets2Cnt";
    }
    leaf idr-discarded-octets3-cnt {
      type uint64;
      description "IDR DiscardedOctets3Cnt";
    }
    leaf mmu-ecc-1b-err-cnt {
      type uint64;
      description "MMU Ecc 1bErrCnt";
    }
    leaf mmu-ecc-2b-err-cnt {
      type uint64;
      description "MMU Ecc 2bErrCnt";
    }
    leaf oamp-parity-err-cnt {
      type uint64;
      description "OAMP ParityErrCnt";
    }
    leaf oamp-ecc-1b-err-cnt {
      type uint64;
      description "OAMP Ecc 1bErrCnt";
    }
    leaf oamp-ecc-2b-err-cnt {
      type uint64;
      description "OAMP Ecc 2bErrCnt";
    }
    leaf crps-parity-err-cnt {
      type uint64;
      description "CRPS ParityErrCnt";
    }
    leaf fmac0-kpcs0-tst-rx-err-cnt {
      type uint64;
      description "FMAC0 Kpcs0TstRxErrCnt";
    }
    leaf fmac1-kpcs0-tst-rx-err-cnt {
      type uint64;
      description "FMAC1 Kpcs0TstRxErrCnt";
    }
    leaf fmac2-kpcs0-tst-rx-err-cnt {
      type uint64;
      description "FMAC2 Kpcs0TstRxErrCnt";
    }
    leaf fmac3-kpcs0-tst-rx-err-cnt {
      type uint64;
      description "FMAC3 Kpcs0TstRxErrCnt";
    }
    leaf fmac4-kpcs0-tst-rx-err-cnt {
      type uint64;
      description "FMAC4 Kpcs0TstRxErrCnt";
    }
    leaf fmac5-kpcs0-tst-rx-err-cnt {
      type uint64;
      description "FMAC5 Kpcs0TstRxErrCnt";
    }
    leaf fmac6-kpcs0-tst-rx-err-cnt {
      type uint64;
      description "FMAC6 Kpcs0TstRxErrCnt";
    }
    leaf fmac7-kpcs0-tst-rx-err-cnt {
      type uint64;
      description "FMAC7 Kpcs0TstRxErrCnt";
    }
    leaf fmac8-kpcs0-tst-rx-err-cnt {
      type uint64;
      description "FMAC8 Kpcs0TstRxErrCnt";
    }
    leaf fmac0-kpcs1-tst-rx-err-cnt {
      type uint64;
      description "FMAC0 Kpcs1TstRxErrCnt";
    }
    leaf fmac1-kpcs1-tst-rx-err-cnt {
      type uint64;
      description "FMAC1 Kpcs1TstRxErrCnt";
    }
    leaf fmac2-kpcs1-tst-rx-err-cnt {
      type uint64;
      description "FMAC2 Kpcs1TstRxErrCnt";
    }
    leaf fmac3-kpcs1-tst-rx-err-cnt {
      type uint64;
      description "FMAC3 Kpcs1TstRxErrCnt";
    }
    leaf fmac4-kpcs1-tst-rx-err-cnt {
      type uint64;
      description "FMAC4 Kpcs1TstRxErrCnt";
    }
    leaf fmac5-kpcs1-tst-rx-err-cnt {
      type uint64;
      description "FMAC5 Kpcs1TstRxErrCnt";
    }
    leaf fmac6-kpcs1-tst-rx-err-cnt {
      type uint64;
      description "FMAC6 Kpcs1TstRxErrCnt";
    }
    leaf fmac7-kpcs1-tst-rx-err-cnt {
      type uint64;
      description "FMAC7 Kpcs1TstRxErrCnt";
    }
    leaf fmac8-kpcs1-tst-rx-err-cnt {
      type uint64;
      description "FMAC8 Kpcs1TstRxErrCnt";
    }
    leaf fmac0-kpcs2-tst-rx-err-cnt {
      type uint64;
      description "FMAC0 Kpcs2TstRxErrCnt";
    }
    leaf fmac1-kpcs2-tst-rx-err-cnt {
      type uint64;
      description "FMAC1 Kpcs2TstRxErrCnt";
    }
    leaf fmac2-kpcs2-tst-rx-err-cnt {
      type uint64;
      description "FMAC2 Kpcs2TstRxErrCnt";
    }
    leaf fmac3-kpcs2-tst-rx-err-cnt {
      type uint64;
      description "FMAC3 Kpcs2TstRxErrCnt";
    }
    leaf fmac4-kpcs2-tst-rx-err-cnt {
      type uint64;
      description "FMAC4 Kpcs2TstRxErrCnt";
    }
    leaf fmac5-kpcs2-tst-rx-err-cnt {
      type uint64;
      description "FMAC5 Kpcs2TstRxErrCnt";
    }
    leaf fmac6-kpcs2-tst-rx-err-cnt {
      type uint64;
      description "FMAC6 Kpcs2TstRxErrCnt";
    }
    leaf fmac7-kpcs2-tst-rx-err-cnt {
      type uint64;
      description "FMAC7 Kpcs2TstRxErrCnt";
    }
    leaf fmac8-kpcs2-tst-rx-err-cnt {
      type uint64;
      description "FMAC8 Kpcs2TstRxErrCnt";
    }
    leaf fmac0-kpcs3-tst-rx-err-cnt {
      type uint64;
      description "FMAC0 Kpcs3TstRxErrCnt";
    }
    leaf fmac1-kpcs3-tst-rx-err-cnt {
      type uint64;
      description "FMAC1 Kpcs3TstRxErrCnt";
    }
    leaf fmac2-kpcs3-tst-rx-err-cnt {
      type uint64;
      description "FMAC2 Kpcs3TstRxErrCnt";
    }
    leaf fmac3-kpcs3-tst-rx-err-cnt {
      type uint64;
      description "FMAC3 Kpcs3TstRxErrCnt";
    }
    leaf fmac4-kpcs3-tst-rx-err-cnt {
      type uint64;
      description "FMAC4 Kpcs3TstRxErrCnt";
    }
    leaf fmac5-kpcs3-tst-rx-err-cnt {
      type uint64;
      description "FMAC5 Kpcs3TstRxErrCnt";
    }
    leaf fmac6-kpcs3-tst-rx-err-cnt {
      type uint64;
      description "FMAC6 Kpcs3TstRxErrCnt";
    }
    leaf fmac7-kpcs3-tst-rx-err-cnt {
      type uint64;
      description "FMAC7 Kpcs3TstRxErrCnt";
    }
    leaf fmac8-kpcs3-tst-rx-err-cnt {
      type uint64;
      description "FMAC8 Kpcs3TstRxErrCnt";
    }
    leaf fmac0-tst0-err-cnt {
      type uint64;
      description "FMAC0 Tst0ErrCnt";
    }
    leaf fmac1-tst0-err-cnt {
      type uint64;
      description "FMAC1 Tst0ErrCnt";
    }
    leaf fmac2-tst0-err-cnt {
      type uint64;
      description "FMAC2 Tst0ErrCnt";
    }
    leaf fmac3-tst0-err-cnt {
      type uint64;
      description "FMAC3 Tst0ErrCnt";
    }
    leaf fmac4-tst0-err-cnt {
      type uint64;
      description "FMAC4 Tst0ErrCnt";
    }
    leaf fmac5-tst0-err-cnt {
      type uint64;
      description "FMAC5 Tst0ErrCnt";
    }
    leaf fmac6-tst0-err-cnt {
      type uint64;
      description "FMAC6 Tst0ErrCnt";
    }
    leaf fmac7-tst0-err-cnt {
      type uint64;
      description "FMAC7 Tst0ErrCnt";
    }
    leaf fmac8-tst0-err-cnt {
      type uint64;
      description "FMAC8 Tst0ErrCnt";
    }
    leaf fmac0-tst1-err-cnt {
      type uint64;
      description "FMAC0 Tst1ErrCnt";
    }
    leaf fmac1-tst1-err-cnt {
      type uint64;
      description "FMAC1 Tst1ErrCnt";
    }
    leaf fmac2-tst1-err-cnt {
      type uint64;
      description "FMAC2 Tst1ErrCnt";
    }
    leaf fmac3-tst1-err-cnt {
      type uint64;
      description "FMAC3 Tst1ErrCnt";
    }
    leaf fmac4-tst1-err-cnt {
      type uint64;
      description "FMAC4 Tst1ErrCnt";
    }
    leaf fmac5-tst1-err-cnt {
      type uint64;
      description "FMAC5 Tst1ErrCnt";
    }
    leaf fmac6-tst1-err-cnt {
      type uint64;
      description "FMAC6 Tst1ErrCnt";
    }
    leaf fmac7-tst1-err-cnt {
      type uint64;
      description "FMAC7 Tst1ErrCnt";
    }
    leaf fmac8-tst1-err-cnt {
      type uint64;
      description "FMAC8 Tst1ErrCnt";
    }
    leaf fmac0-tst2-err-cnt {
      type uint64;
      description "FMAC0 Tst2ErrCnt";
    }
    leaf fmac1-tst2-err-cnt {
      type uint64;
      description "FMAC1 Tst2ErrCnt";
    }
    leaf fmac2-tst2-err-cnt {
      type uint64;
      description "FMAC2 Tst2ErrCnt";
    }
    leaf fmac3-tst2-err-cnt {
      type uint64;
      description "FMAC3 Tst2ErrCnt";
    }
    leaf fmac4-tst2-err-cnt {
      type uint64;
      description "FMAC4 Tst2ErrCnt";
    }
    leaf fmac5-tst2-err-cnt {
      type uint64;
      description "FMAC5 Tst2ErrCnt";
    }
    leaf fmac6-tst2-err-cnt {
      type uint64;
      description "FMAC6 Tst2ErrCnt";
    }
    leaf fmac7-tst2-err-cnt {
      type uint64;
      description "FMAC7 Tst2ErrCnt";
    }
    leaf fmac8-tst2-err-cnt {
      type uint64;
      description "FMAC8 Tst2ErrCnt";
    }
    leaf fmac0-tst3-err-cnt {
      type uint64;
      description "FMAC0 Tst3ErrCnt";
    }
    leaf fmac1-tst3-err-cnt {
      type uint64;
      description "FMAC1 Tst3ErrCnt";
    }
    leaf fmac2-tst3-err-cnt {
      type uint64;
      description "FMAC2 Tst3ErrCnt";
    }
    leaf fmac3-tst3-err-cnt {
      type uint64;
      description "FMAC3 Tst3ErrCnt";
    }
    leaf fmac4-tst3-err-cnt {
      type uint64;
      description "FMAC4 Tst3ErrCnt";
    }
    leaf fmac5-tst3-err-cnt {
      type uint64;
      description "FMAC5 Tst3ErrCnt";
    }
    leaf fmac6-tst3-err-cnt {
      type uint64;
      description "FMAC6 Tst3ErrCnt";
    }
    leaf fmac7-tst3-err-cnt {
      type uint64;
      description "FMAC7 Tst3ErrCnt";
    }
    leaf fmac8-tst3-err-cnt {
      type uint64;
      description "FMAC8 Tst3ErrCnt";
    }
    leaf fmac0-ecc-1b-err-cnt {
      type uint64;
      description "FMAC0 Ecc 1bErrCnt";
    }
    leaf fmac1-ecc-1b-err-cnt {
      type uint64;
      description "FMAC1 Ecc 1bErrCnt";
    }
    leaf fmac2-ecc-1b-err-cnt {
      type uint64;
      description "FMAC2 Ecc 1bErrCnt";
    }
    leaf fmac3-ecc-1b-err-cnt {
      type uint64;
      description "FMAC3 Ecc 1bErrCnt";
    }
    leaf fmac4-ecc-1b-err-cnt {
      type uint64;
      description "FMAC4 Ecc 1bErrCnt";
    }
    leaf fmac5-ecc-1b-err-cnt {
      type uint64;
      description "FMAC5 Ecc 1bErrCnt";
    }
    leaf fmac6-ecc-1b-err-cnt {
      type uint64;
      description "FMAC6 Ecc 1bErrCnt";
    }
    leaf fmac7-ecc-1b-err-cnt {
      type uint64;
      description "FMAC7 Ecc 1bErrCnt";
    }
    leaf fmac8-ecc-1b-err-cnt {
      type uint64;
      description "FMAC8 Ecc 1bErrCnt";
    }
    leaf fmac0-ecc-2b-err-cnt {
      type uint64;
      description "FMAC0 Ecc 2bErrCnt";
    }
    leaf fmac1-ecc-2b-err-cnt {
      type uint64;
      description "FMAC1 Ecc 2bErrCnt";
    }
    leaf fmac2-ecc-2b-err-cnt {
      type uint64;
      description "FMAC2 Ecc 2bErrCnt";
    }
    leaf fmac3-ecc-2b-err-cnt {
      type uint64;
      description "FMAC3 Ecc 2bErrCnt";
    }
    leaf fmac4-ecc-2b-err-cnt {
      type uint64;
      description "FMAC4 Ecc 2bErrCnt";
    }
    leaf fmac5-ecc-2b-err-cnt {
      type uint64;
      description "FMAC5 Ecc 2bErrCnt";
    }
    leaf fmac6-ecc-2b-err-cnt {
      type uint64;
      description "FMAC6 Ecc 2bErrCnt";
    }
    leaf fmac7-ecc-2b-err-cnt {
      type uint64;
      description "FMAC7 Ecc 2bErrCnt";
    }
    leaf fmac8-ecc-2b-err-cnt {
      type uint64;
      description "FMAC8 Ecc 2bErrCnt";
    }
    leaf olp-incoming-bad-identifier-counter {
      type uint64;
      description "OLP IncomingBadIdentifierCounter";
    }
    leaf olp-incoming-bad-reassembly-counter {
      type uint64;
      description "OLP IncomingBadReassemblyCounter";
    }
    leaf cfc-parity-err-cnt {
      type uint64;
      description "CFC ParityErrCnt";
    }
    leaf cfc-ilkn0-oob-rx-crc-err-cntr {
      type uint64;
      description "CFC Ilkn0OobRxCrcErrCntr";
    }
    leaf cfc-ilkn1-oob-rx-crc-err-cntr {
      type uint64;
      description "CFC Ilkn1OobRxCrcErrCntr";
    }
    leaf cfc-spi-oob-rx0-frm-err-cnt {
      type uint64;
      description "CFC SpiOobRx0FrmErrCnt";
    }
    leaf cfc-spi-oob-rx0-dip2-err-cnt {
      type uint64;
      description "CFC SpiOobRx0Dip2ErrCnt";
    }
    leaf cfc-spi-oob-rx1-frm-err-cnt {
      type uint64;
      description "CFC SpiOobRx1FrmErrCnt";
    }
    leaf cfc-spi-oob-rx1-dip2-err-cnt {
      type uint64;
      description "CFC SpiOobRx1Dip2ErrCnt";
    }
    leaf cgm-cgm-uc-pd-dropped-cnt {
      type uint64;
      description "CGM CgmUcPdDroppedCnt";
    }
    leaf cgm-cgm-mc-rep-pd-dropped-cnt {
      type uint64;
      description "CGM CgmMcRepPdDroppedCnt";
    }
    leaf cgm-cgm-uc-db-dropped-by-rqp-cnt {
      type uint64;
      description "CGM CgmUcDbDroppedByRqpCnt";
    }
    leaf cgm-cgm-uc-db-dropped-by-pqp-cnt {
      type uint64;
      description "CGM CgmUcDbDroppedByPqpCnt";
    }
    leaf cgm-cgm-mc-rep-db-dropped-cnt {
      type uint64;
      description "CGM CgmMcRepDbDroppedCnt";
    }
    leaf cgm-cgm-mc-db-dropped-cnt {
      type uint64;
      description "CGM CgmMcDbDroppedCnt";
    }
    leaf drca-full-err-cnt {
      type uint64;
      description "DRCA FullErrCnt";
    }
    leaf drca-single-err-cnt {
      type uint64;
      description "DRCA SingleErrCnt";
    }
    leaf drca-calib-bist-full-err-cnt {
      type uint64;
      description "DRCA CalibBistFullErrCnt";
    }
    leaf drca-loopback-full-err-cnt {
      type uint64;
      description "DRCA LoopbackFullErrCnt";
    }
    leaf drcb-full-err-cnt {
      type uint64;
      description "DRCB FullErrCnt";
    }
    leaf drcb-single-err-cnt {
      type uint64;
      description "DRCB SingleErrCnt";
    }
    leaf drcb-calib-bist-full-err-cnt {
      type uint64;
      description "DRCB CalibBistFullErrCnt";
    }
    leaf drcb-loopback-full-err-cnt {
      type uint64;
      description "DRCB LoopbackFullErrCnt";
    }
    leaf drcc-full-err-cnt {
      type uint64;
      description "DRCC FullErrCnt";
    }
    leaf drcc-single-err-cnt {
      type uint64;
      description "DRCC SingleErrCnt";
    }
    leaf drcc-calib-bist-full-err-cnt {
      type uint64;
      description "DRCC CalibBistFullErrCnt";
    }
    leaf drcc-loopback-full-err-cnt {
      type uint64;
      description "DRCC LoopbackFullErrCnt";
    }
    leaf drcd-full-err-cnt {
      type uint64;
      description "DRCD FullErrCnt";
    }
    leaf drcd-single-err-cnt {
      type uint64;
      description "DRCD SingleErrCnt";
    }
    leaf drcd-calib-bist-full-err-cnt {
      type uint64;
      description "DRCD CalibBistFullErrCnt";
    }
    leaf drcd-loopback-full-err-cnt {
      type uint64;
      description "DRCD LoopbackFullErrCnt";
    }
    leaf drce-full-err-cnt {
      type uint64;
      description "DRCE FullErrCnt";
    }
    leaf drce-single-err-cnt {
      type uint64;
      description "DRCE SingleErrCnt";
    }
    leaf drce-calib-bist-full-err-cnt {
      type uint64;
      description "DRCE CalibBistFullErrCnt";
    }
    leaf drce-loopback-full-err-cnt {
      type uint64;
      description "DRCE LoopbackFullErrCnt";
    }
    leaf drcf-full-err-cnt {
      type uint64;
      description "DRCF FullErrCnt";
    }
    leaf drcf-single-err-cnt {
      type uint64;
      description "DRCF SingleErrCnt";
    }
    leaf drcf-calib-bist-full-err-cnt {
      type uint64;
      description "DRCF CalibBistFullErrCnt";
    }
    leaf drcf-loopback-full-err-cnt {
      type uint64;
      description "DRCF LoopbackFullErrCnt";
    }
    leaf drcg-full-err-cnt {
      type uint64;
      description "DRCG FullErrCnt";
    }
    leaf drcg-single-err-cnt {
      type uint64;
      description "DRCG SingleErrCnt";
    }
    leaf drcg-calib-bist-full-err-cnt {
      type uint64;
      description "DRCG CalibBistFullErrCnt";
    }
    leaf drcg-loopback-full-err-cnt {
      type uint64;
      description "DRCG LoopbackFullErrCnt";
    }
    leaf drch-full-err-cnt {
      type uint64;
      description "DRCH FullErrCnt";
    }
    leaf drch-single-err-cnt {
      type uint64;
      description "DRCH SingleErrCnt";
    }
    leaf drch-calib-bist-full-err-cnt {
      type uint64;
      description "DRCH CalibBistFullErrCnt";
    }
    leaf drch-loopback-full-err-cnt {
      type uint64;
      description "DRCH LoopbackFullErrCnt";
    }
    leaf drcbroadcast-full-err-cnt {
      type uint64;
      description "DRCBROADCAST FullErrCnt";
    }
    leaf drcbroadcast-single-err-cnt {
      type uint64;
      description "DRCBROADCAST SingleErrCnt";
    }
    leaf drcbroadcast-calib-bist-full-err-cnt {
      type uint64;
      description "DRCBROADCAST CalibBistFullErrCnt";
    }
    leaf drcbroadcast-loopback-full-err-cnt {
      type uint64;
      description "DRCBROADCAST LoopbackFullErrCnt";
    }
    leaf otn-mode {
      type uint32;
      description "otn mode";
    }
    leaf num-ports {
      type uint32;
      description "num ports";
    }

    list aggr-stats-otn {
      max-elements "160";
      description "aggr stats otn";
      uses FIA-EDM-DEVICE-STATS-PBC-OTN;
    }
  }

  grouping FIA-EDM-STATS-ASIC-PBC-INFO {
    description "FIA EDM STATS ASIC PBC INFO";

    container aggr-stats {
      description "aggr stats";
      uses FIA-EDM-DEVICE-STATS-PBC;
    }

    container ovf-status {
      description "ovf status";
      uses FIA-EDM-DEVICE-STATS-OVF-PBC;
    }
    leaf valid {
      type boolean;
      description "valid";
    }
    leaf rack-no {
      type uint32;
      description "rack no";
    }
    leaf slot-no {
      type uint32;
      description "slot no";
    }
    leaf asic-instance {
      type uint32;
      description "asic instance";
    }
    leaf chip-ver {
      type uint16;
      description "chip ver";
    }
  }

  grouping FIA-EDM-DIAG-SHELL-OUTPUT {
    description "FIA EDM DIAG SHELL OUTPUT";
    leaf output-xr {
      type string;
      description "output xr";
    }
  }

  grouping FIA-EDM-TXLINK-STATS {
    description "FIA EDM TXLINK STATS";
    leaf dummy {
      type uint32;
      description "dummy";
    }
  }

  grouping FIA-EDM-TXLINK {
    description "FIA EDM TXLINK";

    container this-link {
      description "this link";
      uses FIA-EDM-LINK-IDENTITY;
    }

    container far-end-link {
      description "far end link";
      uses FIA-EDM-LINK-IDENTITY;
    }

    container stats {
      description "stats";
      uses FIA-EDM-TXLINK-STATS;
    }

    container history {
      description "history";
      uses FIA-EDM-HISTORY;
    }
    leaf speed {
      type uint32;
      description "speed";
    }
    leaf stage {
      type uint8;
      description "stage";
    }
    leaf is-link-valid {
      type boolean;
      description "is link valid";
    }
    leaf is-conf-pending {
      type boolean;
      description "is conf pending";
    }
    leaf is-power-enabled {
      type boolean;
      description "is power enabled";
    }
    leaf coeff1 {
      type uint32;
      description "coeff1";
    }
    leaf coeff2 {
      type uint32;
      description "coeff2";
    }
    leaf admin-state {
      type Admin-state;
      description "Admin State";
    }
    leaf oper-state {
      type Oper-state;
      description "Oper State";
    }
    leaf error-state {
      type Link-error-state;
      description "Error State";
    }
    leaf num-admin-shuts {
      type uint32;
      description "num admin shuts";
    }
  }

  grouping FIA-EDM-EVENT-LOG {
    description "FIA EDM EVENT LOG";
    leaf event {
      type uint32;
      description "event";
    }
    leaf timestamp {
      type string;
      description "timestamp";
    }
  }

  grouping FIA-EDM-EVENT-HISTORY {
    description "FIA EDM EVENT HISTORY";
    leaf event-log-count {
      type uint32;
      description "event log count";
    }
    leaf event-log-start {
      type uint32;
      description "event log start";
    }
    leaf rack-num {
      type uint32;
      description "rack num";
    }
    leaf slot-num {
      type uint32;
      description "slot num";
    }
    leaf asic-instance {
      type uint32;
      description "asic instance";
    }
    leaf is-valid {
      type boolean;
      description "is valid";
    }

    list event-log {
      max-elements "100";
      description "event log";
      uses FIA-EDM-EVENT-LOG;
    }
  }

  grouping FIA-EDM-EVENT-HISTORY-INFO {
    description "FIA EDM EVENT HISTORY INFO";
    leaf total-asics {
      type uint8;
      description "total asics";
    }

    list event-history {
      max-elements "40";
      description "event history";
      uses FIA-EDM-EVENT-HISTORY;
    }
  }

  grouping FIA-EDM-OIR-HISTORY {
    description "FIA EDM OIR HISTORY";
    leaf card-flag {
      type int32;
      description "card flag";
    }
    leaf card-type {
      type int32;
      description "card type";
    }
    leaf reg-flag {
      type int32;
      description "reg flag";
    }
    leaf evt-flag {
      type int32;
      description "evt flag";
    }
    leaf rack-num {
      type int32;
      description "rack num";
    }
    leaf instance {
      type int32;
      description "instance";
    }
    leaf cur-card-state {
      type int32;
      description "cur card state";
    }
  }

  grouping FIA-EDM-OIR-RECORD-CIRCULAR-BUFFER {
    description "FIA EDM OIR RECORD CIRCULAR BUFFER";
    leaf count {
      type int32;
      description "count";
    }
    leaf start {
      type int32;
      description "start";
    }
    leaf end {
      type int32;
      description "end";
    }

    list fia-oir-info {
      max-elements "10";
      description "fia oir info";
      uses FIA-EDM-OIR-HISTORY;
    }
  }

  grouping FIA-EDM-CARD-INFO {
    description "FIA EDM CARD INFO";

    container oir-circular-buffer {
      description "oir circular buffer";
      uses FIA-EDM-OIR-RECORD-CIRCULAR-BUFFER;
    }
    leaf card-type {
      type int32;
      description "card type";
    }
    leaf card-name {
      type string;
      description "card name";
    }
    leaf slot-no {
      type int32;
      description "slot no";
    }
    leaf card-flag {
      type int32;
      description "card flag";
    }
    leaf evt-flag {
      type int32;
      description "evt flag";
    }
    leaf reg-flag {
      type int32;
      description "reg flag";
    }
    leaf instance {
      type int32;
      description "instance";
    }
    leaf card-state {
      type uint8;
      description "card state";
    }
    leaf exp-num-asics {
      type uint32;
      description "exp num asics";
    }
    leaf exp-num-asics-per-fsdb {
      type uint32;
      description "exp num asics per fsdb";
    }
    leaf is-powered {
      type boolean;
      description "is powered";
    }
    leaf cxp-avail-bitmap {
      type uint64;
      description "cxp avail bitmap";
    }
    leaf num-ilkns-per-asic {
      type uint32;
      description "num ilkns per asic";
    }
    leaf num-local-ports-per-ilkn {
      type uint32;
      description "num local ports per ilkn";
    }
    leaf num-cos-per-port {
      type uint8;
      description "num cos per port";
    }
  }

  grouping FIA-EDM-DEVICE {
    description "FIA EDM DEVICE";

    container asic-id {
      description "asic id";
      uses FIA-EDM-ASIC-IDENTITY;
    }
    leaf is-valid {
      type boolean;
      description "is valid";
    }
    leaf fapid {
      type uint32;
      description "fapid";
    }
    leaf hotplug-event {
      type uint32;
      description "hotplug event";
    }
    leaf slice-state {
      type Slice-state;
      description "Slice State";
    }
    leaf admin-state {
      type Admin-state;
      description "Admin State";
    }
    leaf oper-state {
      type Asic-oper-state;
      description "Oper State";
    }
    leaf asic-state {
      type Asic-access-state;
      description "Asic State";
    }
    leaf last-init-cause {
      type Asic-init-method;
      description "last init cause";
    }
    leaf num-pon-resets {
      type uint32;
      description "num pon resets";
    }
    leaf num-hard-resets {
      type uint32;
      description "num hard resets";
    }
    leaf local-switch-state {
      type boolean;
      description "local switch state";
    }
    leaf startup-wb-mtime-str {
      type string;
      description "startup wb mtime str";
    }
    leaf startup-wb-outof-sync {
      type boolean;
      description "startup wb outof sync";
    }
    leaf local-wb-sync-end-str {
      type string;
      description "local wb sync end str";
    }
    leaf remote-wb-sync-end-str {
      type string;
      description "remote wb sync end str";
    }
    leaf local-wb-sync-pending {
      type boolean;
      description "local wb sync pending";
    }
    leaf sdk-delay-msec {
      type uint32;
      description "sdk delay msec";
    }
  }

  grouping FIA-EDM-DRIVER-INFO {
    description "FIA EDM DRIVER INFO";
    leaf drv-version {
      type uint32;
      description "drv version";
    }
    leaf coeff-major-rev {
      type uint32;
      description "coeff major rev";
    }
    leaf coeff-minor-rev {
      type uint32;
      description "coeff minor rev";
    }
    leaf functional-role {
      type uint8;
      description "functional role";
    }
    leaf issu-role {
      type uint8;
      description "issu role";
    }
    leaf node-id {
      type string;
      description "node id";
    }
    leaf rack-type {
      type int32;
      description "rack type";
    }
    leaf rack-num {
      type uint8;
      description "rack num";
    }
    leaf is-driver-ready {
      type boolean;
      description "is driver ready";
    }
    leaf card-avail-mask {
      type uint32;
      description "card avail mask";
    }
    leaf asic-avail-mask {
      type uint64;
      description "asic avail mask";
    }
    leaf exp-asic-avail-mask {
      type uint64;
      description "exp asic avail mask";
    }
    leaf ucmc-ratio {
      type uint32;
      description "ucmc ratio";
    }
    leaf asic-oper-notify-to-fsdb-pending-bmap {
      type uint64;
      description "asic oper notify to fsdb pending bmap";
    }
    leaf is-full-fgid-download-req {
      type boolean;
      description "is full fgid download req";
    }
    leaf is-fgid-download-in-progress {
      type boolean;
      description "is fgid download in progress";
    }
    leaf is-fgid-download-completed {
      type boolean;
      description "is fgid download completed";
    }
    leaf fsdb-conn-active {
      type boolean;
      description "fsdb conn active";
    }
    leaf fgid-conn-active {
      type boolean;
      description "fgid conn active";
    }
    leaf issu-mgr-conn-active {
      type boolean;
      description "issu mgr conn active";
    }
    leaf fsdb-reg-active {
      type boolean;
      description "fsdb reg active";
    }
    leaf fgid-reg-active {
      type boolean;
      description "fgid reg active";
    }
    leaf issu-mgr-reg-active {
      type boolean;
      description "issu mgr reg active";
    }
    leaf num-pm-conn-reqs {
      type uint8;
      description "num pm conn reqs";
    }
    leaf num-fsdb-conn-reqs {
      type uint8;
      description "num fsdb conn reqs";
    }
    leaf num-fgid-conn-reqs {
      type uint8;
      description "num fgid conn reqs";
    }
    leaf num-fstats-conn-reqs {
      type uint8;
      description "num fstats conn reqs";
    }
    leaf num-cm-conn-reqs {
      type uint8;
      description "num cm conn reqs";
    }
    leaf num-issu-mgr-conn-reqs {
      type uint8;
      description "num issu mgr conn reqs";
    }
    leaf num-peer-fia-conn-reqs {
      type uint8;
      description "num peer fia conn reqs";
    }
    leaf is-gaspp-registered {
      type boolean;
      description "is gaspp registered";
    }
    leaf is-cih-registered {
      type boolean;
      description "is cih registered";
    }
    leaf drvr-initial-startup-timestamp {
      type string;
      description "drvr initial startup timestamp";
    }
    leaf drvr-current-startup-timestamp {
      type string;
      description "drvr current startup timestamp";
    }
    leaf num-intf-ports {
      type uint32;
      description "num intf ports";
    }
    leaf uc-weight {
      type uint8;
      description "uc weight";
    }
    leaf respawn-count {
      type uint8;
      description "respawn count";
    }
    leaf total-asics {
      type uint8;
      description "total asics";
    }
    leaf issu-ready-ntfy-pending {
      type boolean;
      description "issu ready ntfy pending";
    }
    leaf issu-abort-sent {
      type boolean;
      description "issu abort sent";
    }
    leaf issu-abort-rcvd {
      type boolean;
      description "issu abort rcvd";
    }
    leaf fabric-mode {
      type uint8;
      description "fabric mode";
    }
    leaf fc-mode {
      type Fc-mode;
      description "FC Mode";
    }
    leaf board-rev-id {
      type uint32;
      description "board rev id";
    }
    leaf all-wb-insync {
      type boolean;
      description "all wb insync";
    }
    leaf all-wb-insync-since {
      type uint32;
      description "all wb insync since";
    }
    leaf all-startup-wb-insync {
      type boolean;
      description "all startup wb insync";
    }
    leaf plane-a-bitmap {
      type uint32;
      description "planeA bitmap";
    }
    leaf plane-b-bitmap {
      type uint32;
      description "planeB bitmap";
    }

    list device-info {
      max-elements "40";
      description "device info";
      uses FIA-EDM-DEVICE;
    }

    list card-info {
      max-elements "16";
      description "card info";
      uses FIA-EDM-CARD-INFO;
    }
  }

  grouping FIA-EDM-STATE-CHANGE {
    description "FIA EDM STATE CHANGE";
    leaf admin-state {
      type Admin-state;
      description "Admin State";
    }
    leaf oper-state {
      type Oper-state;
      description "Oper State";
    }
    leaf error-state {
      type Link-error-state;
      description "Error State";
    }
    leaf timestamp {
      type uint64;
      description "timestamp";
    }
    leaf reasons {
      type string;
      description "reasons";
    }
  }

  grouping FIA-EDM-HISTORY {
    description "FIA EDM HISTORY";
    leaf histnum {
      type uint8;
      description "histnum";
    }
    leaf start-index {
      type uint8;
      description "start index";
    }

    list hist {
      max-elements "5";
      description "hist";
      uses FIA-EDM-STATE-CHANGE;
    }
  }

  grouping FIA-EDM-ASIC-IDENTITY {
    description "FIA EDM ASIC IDENTITY";
    leaf rack-type {
      type Rack;
      description "Rack Type";
    }
    leaf asic-type {
      type Asic;
      description "Asic Type";
    }
    leaf rack-num {
      type uint32;
      description "rack num";
    }
    leaf slot-num {
      type uint32;
      description "slot num";
    }
    leaf asic-instance {
      type uint32;
      description "asic instance";
    }
  }

  grouping FIA-EDM-LINK-IDENTITY {
    description "FIA EDM LINK IDENTITY";

    container asic-id {
      description "asic id";
      uses FIA-EDM-ASIC-IDENTITY;
    }
    leaf link-type {
      type Link;
      description "Link Type";
    }
    leaf link-stage {
      type Link-stage;
      description "Link Stage";
    }
    leaf link-num {
      type uint32;
      description "link num";
    }
    leaf phy-link-num {
      type uint32;
      description "phy link num";
    }
  }

  grouping FIA-EDM-RXLINK {
    description "FIA EDM RXLINK";

    container this-link {
      description "this link";
      uses FIA-EDM-LINK-IDENTITY;
    }

    container far-end-link {
      description "far end link";
      uses FIA-EDM-LINK-IDENTITY;
    }

    container far-end-link-in-hw {
      description "far end link in hw";
      uses FIA-EDM-LINK-IDENTITY;
    }

    container history {
      description "history";
      uses FIA-EDM-HISTORY;
    }
    leaf speed {
      type uint32;
      description "speed";
    }
    leaf stage {
      type Link-stage;
      description "Stage";
    }
    leaf is-link-valid {
      type boolean;
      description "is link valid";
    }
    leaf is-conf-pending {
      type boolean;
      description "is conf pending";
    }
    leaf admin-state {
      type Admin-state;
      description "Admin State";
    }
    leaf oper-state {
      type Oper-state;
      description "Oper State";
    }
    leaf error-state {
      type Link-error-state;
      description "Error State";
    }
    leaf flags {
      type string;
      description "flags";
    }
    leaf flap-cnt {
      type uint32;
      description "flap cnt";
    }
    leaf num-admin-shuts {
      type uint32;
      description "num admin shuts";
    }
    leaf correctable-errors {
      type uint64;
      description "correctable errors";
    }
    leaf uncorrectable-errors {
      type uint64;
      description "uncorrectable errors";
    }
  }
}
