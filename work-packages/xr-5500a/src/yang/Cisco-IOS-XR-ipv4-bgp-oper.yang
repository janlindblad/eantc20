module Cisco-IOS-XR-ipv4-bgp-oper {

  /*** NAMESPACE / PREFIX DEFINITION ***/

  namespace "http://cisco.com/ns/yang/Cisco-IOS-XR-ipv4-bgp-oper";


  prefix "ipv4-bgp-oper";

  /*** LINKAGE (IMPORTS / INCLUDES) ***/

  import ietf-inet-types { prefix "inet"; }

  import Cisco-IOS-XR-types { prefix "xr"; }

  import Cisco-IOS-XR-ipv4-bgp-datatypes { prefix "dt1"; }

  include Cisco-IOS-XR-ipv4-bgp-oper-sub1 {
    revision-date 2017-09-07;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-bgp package operational data.

     This module contains definitions
     for the following management objects:
       bgp: BGP operational data

     Copyright (c) 2013-2018 by Cisco Systems, Inc.
     All rights reserved.";

  revision "2017-09-07" {
    description
      "Fixed type translation error.";
  }

  revision "2017-06-26" {
    description
      "Change identifiers to be more readable.";
  }

  revision "2017-05-01" {
    description
      "Fixing backward compatibility error in module.";
  }

  revision "2015-08-27" {
    description
      "IOS XR 5.3.2 revision.";
  }

  typedef Bgp-rpki-edm-af {
    type enumeration {
      enum ipv4 {
        value 2;
        description "IPv4";
      }
      enum ipv6 {
        value 10;
        description "IPv6";
      }
    }
    description "Bgp rpki edm af";
  }
  typedef Bgp-route {
    type enumeration {
      enum used {
        value 0;
        description "Used path from neighbor";
      }
      enum received-only {
        value 1;
        description "Received only path from neighbor";
      }
      enum safi-labeled-unicast-used {
        value 2;
        description
          "Used path from neighbor received via
          labeled-unicast SAFI";
      }
      enum safi-labeled-unicast-received-only {
        value 3;
        description
          "Received only path from neighbor received via
          labeled-unicast SAFI";
      }
      enum rib {
        value 4;
        description "Redistributed from the RIB";
      }
      enum aggregate {
        value 5;
        description "Locally generated aggregate";
      }
    }
    description "Bgp route";
  }
  typedef Bgp-entity {
    type enumeration {
      enum af-group {
        value 0;
        description "Address family group";
      }
      enum session-group {
        value 1;
        description "Session group";
      }
      enum neighbor-group {
        value 2;
        description "Neighbor group";
      }
      enum neighbor {
        value 3;
        description "Neighbor";
      }
    }
    description "Bgp entity";
  }
  typedef Bgp-route-distinguisher {
    type string;
    description "Bgp route distinguisher";
  }

  grouping UPDATE-GENERATION-PROCESS {
    description "Common node of instance-active, instance-standby";

    container update-generation-process {
      description "Update generation for the process";
      uses BGP-UPDGEN-PROC-BAG;
    }
  }

  grouping PATH {
    description
      "Common node of path-table, path-used-table,
      path-labeled-table";

    list path {
      description "A BGP path table entry";
      leaf rd {
        type Bgp-route-distinguisher;
        description "Route Distinguisher value";
      }
      leaf network {
        type xr:Cisco-ios-xr-string;
        description
          "Network prefix in dotted decimal format for ip
          prefix, else in hex string format";
      }
      leaf prefix-length {
        type uint32;
        description "Network prefix Length";
      }
      leaf neighbor-address {
        type inet:ip-address-no-zone;
        description "Neighbor adddress";
      }
      leaf route-type {
        type Bgp-route;
        description "Route Type";
      }
      leaf source-rd {
        type Bgp-route-distinguisher;
        description "Source Route Distinguisher value";
      }
      leaf orig-source-rd {
        type Bgp-route-distinguisher;
        description "Original Source Route Distinguisher";
      }
      leaf path-id {
        type uint32;
        description "Received Path ID";
      }
      uses BGP-PATH-BAG;
    }
  }

  grouping BMP {
    description "Common node of default-vrf, vrf";

    container bmp {
      description "BMP related Operational Data";

      container server-summaries {
        description "Table of BMP Servers";

        list server-summary {
          key "server-id";
          description "Summary Information about BMP server";
          leaf server-id {
            type uint32 {
              range "1..8";
            }
            description "BMP Server ID";
          }
          uses BGP-BMP-SRVR-BAG;
        }
      }

      container server-neighbors {
        description "Table of Neighbors for a BMP Server";

        list server-neighbor {
          key "server-id";
          description
            "BMP Server under which neighbor info are
            needed";

          container monitored-neighbors {
            description
              "List of Neighbors under which BMP Server is
              confgiured";

            list monitored-neighbor {
              key "neighbor-address";
              description
                "Information about a neighbor monitored by
                BMP server";
              leaf neighbor-address {
                type inet:ip-address-no-zone;
                description "Neighbor address";
              }
              uses BGP-BMP-NBR-BAG;
            }
          }
          leaf server-id {
            type uint32 {
              range "1..8";
            }
            description "BMP Server ID";
          }
        }
      }
    }
  }

  grouping ATTRIBUTE-FILTER-GROUP-TABLE {
    description "Common node of instance-active, instance-standby";

    container attribute-filter-groups {
      description "All attribute-filter groups in this instance";

      list attribute-filter-group {
        key "group-name";
        description "Attribute-filter group";
        leaf group-name {
          type xr:Cisco-ios-xr-string;
          description "Attribute-filter group name";
        }
        uses BGP-ATTRFILTER-GROUP-BAG;
      }
    }
  }

  grouping ATTRIBUTE-TABLE {
    description
      "Common node of instance-active, instance-standby,
      af";

    container attributes {
      description "The BGP Attribute table";

      list attribute {
        description "A BGP Attribute table entry";
        leaf attribute-iid {
          type uint32;
          description "Attribute IID";
        }
        leaf attribute-cache-bucket {
          type uint32;
          description "Attribute cache bucket";
        }
        leaf attribute-cache-id {
          type uint32;
          description "Attribute cache ID";
        }
        uses BGP-ATTR-BAG;
      }
    }
  }

  grouping SESSION-TABLE {
    description "Common node of default-vrf, vrf";

    container sessions {
      description "The BGP session table";

      list session {
        key "neighbor-address";
        description "A BGP session table entry";
        leaf neighbor-address {
          type inet:ip-address-no-zone;
          description "Neighbor address";
        }
        uses BGP-NBR-BRIEF-BAG;
      }
    }
  }

  grouping POSTIT-TABLE {
    description "Common node of default-vrf, vrf";

    container postits {
      description "The BGP Neighbor table";

      list postit {
        key "neighbor-address";
        description "A BGP Postit table entry";
        leaf neighbor-address {
          type inet:ip-address-no-zone;
          description "Neighbor address";
        }
        uses BGP-NEIGHBOR-NSR-BAG;
      }
    }
  }

  grouping UPDATE-INBOUND-ERROR-PROCESS {
    description "Common node of instance-active, instance-standby";

    container update-inbound-error-process {
      description
        "Update inbound error information for the process";
      uses BGP-UPDERR-PROC-BAG;
    }
  }

  grouping NEXT-HOP-VRF {
    description "Common node of default-vrf, vrf";

    container next-hop-vrf {
      description "A BGP Next-hop VRF table entry";
      uses BGP-NEXTHOP-VRF-BAG;
    }
  }

  grouping RPKI-SUMMARY {
    description "Common node of instance-active, instance-standby";

    container rpki-summary {
      description "RPKI Summary Info";
      uses BGP-RPKI-SUMMARY-BAG;
    }
  }

  grouping VRF-TABLE {
    description "Common node of instance-active, instance-standby";

    container vrfs {
      description "VRF related operational data";

      list vrf {
        key "vrf-name";
        description "Operational data for a particular VRF";
        leaf vrf-name {
          type xr:Cisco-ios-xr-string;
          description "Name of the VRF";
        }
        uses UPDATE-INBOUND-ERROR-VRF;
        uses AF-TABLE;
        uses INFORMATION;
        uses UPDATE-INBOUND-FILTER-VRF;
        uses POSTIT-TABLE;
        uses GLOBAL-PROCESS-INFO;
        uses UPDATE-INBOUND-ERROR-NEIGHBOR-TABLE;
        uses UPDATE-INBOUND-FILTER-NEIGHBOR-TABLE;
        uses BMP;
        uses PROCESS-INFO;
        uses SESSION-TABLE;
        uses NEIGHBOR-TABLE;
        uses NEXT-HOP-VRF;
        uses NEIGHBOR-RANGE-TABLE;
        uses MESSAGE-LOG-TABLE;
      }
    }
  }

  grouping UPDATE-INBOUND-FILTER-VRF {
    description "Common node of default-vrf, vrf";

    container update-inbound-filter-vrf {
      description
        "Update inbound filtering information for the VRF";
      uses BGP-UPDFILTER-VRF-BAG;
    }
  }

  grouping INFORMATION {
    description "Common node of default-vrf, vrf";

    container information {
      description "Meta data for VRF";
      uses BGP-VRF-INFO-BAG;
    }
  }

  grouping ENTITY-CONFIGURATION-TABLE {
    description
      "Common node of config-instance-default-vrf,
      config-vrf";

    container entity-configurations {
      description "The BGP Entity Configuration table";

      list entity-configuration {
        description "A BGP Entity Configuration table entry";
        leaf entity-type {
          type Bgp-entity;
          description "Entity type";
        }
        leaf neighbor-address {
          type inet:ip-address-no-zone;
          description "Neighbor address";
        }
        leaf entity-name {
          type xr:Cisco-ios-xr-string;
          description "Entity name";
        }
        leaf length {
          type uint32;
          description "Neighbor addr prefix length";
        }
        uses BGP-CONFIG-ENTITY-BAG;
      }
    }
  }

  grouping DEFAULT-VRF {
    description "Common node of instance-active, instance-standby";

    container default-vrf {
      description "Default VRF related operational data";
      uses UPDATE-INBOUND-ERROR-VRF;
      uses AF-TABLE;
      uses INFORMATION;
      uses UPDATE-INBOUND-FILTER-VRF;
      uses POSTIT-TABLE;
      uses GLOBAL-PROCESS-INFO;
      uses UPDATE-INBOUND-ERROR-NEIGHBOR-TABLE;
      uses UPDATE-INBOUND-FILTER-NEIGHBOR-TABLE;
      uses BMP;
      uses PROCESS-INFO;
      uses SESSION-TABLE;
      uses NEIGHBOR-TABLE;
      uses NEXT-HOP-VRF;
      uses NEIGHBOR-RANGE-TABLE;
      uses MESSAGE-LOG-TABLE;
    }
  }

  grouping UPDATE-INBOUND-ERROR-VRF {
    description "Common node of default-vrf, vrf";

    container update-inbound-error-vrf {
      description "Update inbound error information for the VRF";
      uses BGP-UPDERR-VRF-BAG;
    }
  }

  grouping UPDATE-INBOUND-FILTER-NEIGHBOR-TABLE {
    description "Common node of default-vrf, vrf";

    container update-inbound-filter-neighbors {
      description
        "Update inbound filtering information for all
        neighbors";

      list update-inbound-filter-neighbor {
        key "neighbor-address";
        description
          "Update inbound filtering information for
          neighbor";
        leaf neighbor-address {
          type inet:ip-address-no-zone;
          description "Neighbor address";
        }
        uses BGP-UPDFILTER-NBR-BAG;
      }
    }
  }

  grouping NEIGHBOR-RANGE-TABLE {
    description
      "Common node of default-vrf, vrfCommon node of
      default-vrf, vrf";

    container neighbor-ranges {
      description "The BGP Dynamic Neighbor Range table";

      list neighbor-range {
        key "neighbor-range-address";
        description "A BGP Neighbor Range table entry";
        leaf neighbor-range-address {
          type inet:ip-prefix;
          description "Neighbor Range prefix";
        }
        uses BGP-NBR-RANGE-BAG;
      }
    }
  }

  grouping CONFIGURATION-USER-TABLE {
    description
      "Common node of config-instance-default-vrf,
      config-vrf";

    container configuration-users {
      description "The BGP configuration users table";

      list configuration-user {
        description "A BGP configuration user table entry";
        leaf entity-type {
          type Bgp-entity;
          description "Entity type";
        }
        leaf neighbor-address {
          type inet:ip-address-no-zone;
          description "Neighbor address";
        }
        leaf entity-name {
          type xr:Cisco-ios-xr-string;
          description "Entity name";
        }
        leaf length {
          type uint32;
          description "Neighbor addr prefix length";
        }
        uses BGP-CONFIG-RELATIVES-BAG;
      }
    }
  }

  grouping NEIGHBOR {
    description "Common node of neighbors, neighbor-af-table";

    list neighbor {
      key "neighbor-address";
      description "A BGP Neighbor table entry";
      leaf neighbor-address {
        type inet:ip-address-no-zone;
        description "Neighbor address";
      }
      uses BGP-NBR-BAG;
    }
  }

  grouping UPDATE-INBOUND-ERROR-NEIGHBOR-TABLE {
    description "Common node of default-vrf, vrf";

    container update-inbound-error-neighbors {
      description
        "Update inbound error information for all
        neighbors";

      list update-inbound-error-neighbor {
        key "neighbor-address";
        description "Update inbound error information for neighbor";
        leaf neighbor-address {
          type inet:ip-address-no-zone;
          description "Neighbor address";
        }
        uses BGP-UPDERR-NBR-BAG;
      }
    }
  }

  grouping RPKI-SERVER-LIST {
    description "Common node of instance-active, instance-standby";

    container rpki-server-list {
      description "RPKI Server Table";
      uses BGP-RPKI-CACHES-BAG;
    }
  }

  grouping GLOBAL-PROCESS-INFO {
    description "Common node of default-vrf, vrf";

    container global-process-info {
      description "The Global Process information table";
      uses BGP-GLOBAL-PROCESS-INFO-BAG;
    }
  }

  grouping RT-TABLE {
    description "Common node of instance-active, instance-standby";

    container rt-entries {
      description "BGP Route Target Sets Table";

      list rt-entry {
        description "BGP Route Target Set Entry";
        leaf route-target-lower-bytes {
          type uint32;
          description "Lower 4 bytes of RT";
        }
        leaf route-target-upper-bytes {
          type uint32;
          description "Upper 4 bytes of RT";
        }
        leaf af-name {
          type dt1:Bgp-address-family;
          description "Address family";
        }
        leaf request-id {
          type uint32;
          description "Random Request ID";
        }
        uses BGP-VRF-RT-BAG;
      }
    }
  }

  grouping RPKI-ROUTE-TABLE {
    description "Common node of instance-active, instance-standby";

    container rpki-routes {
      description "BGP RPKI ROA table";

      list rpki-route {
        description "RPKI Path Group";
        leaf af-name {
          type Bgp-rpki-edm-af;
          description "Address family";
        }
        leaf address {
          type xr:Cisco-ios-xr-string;
          description "Route Address (IPv4 / IPv6)";
        }
        leaf minimum {
          type uint32;
          description "Minimum Prefix Length";
        }
        leaf maximum {
          type uint32;
          description "Maximum Prefix Length";
        }
        uses BGP-RPKI-ROUTES-BAG;
      }
    }
  }

  grouping NEIGHBOR-TABLE {
    description "Common node of default-vrf, vrf";

    container neighbors {
      description "The BGP Neighbor table";
      uses NEIGHBOR;
    }
  }

  grouping MESSAGE-LOG-TABLE {
    description "Common node of default-vrf, vrf";

    container message-logs {
      description "The BGP Neighbor Message table";

      list message-log {
        description "A BGP Message log entry";
        leaf neighbor-address {
          type inet:ip-address-no-zone;
          description "Neighbor address";
        }
        leaf direction {
          type uint32;
          description "Direction";
        }
        uses BGP-MSGLOG-NBR-BAG;
      }
    }
  }

  grouping AF-TABLE {
    description "Common node of default-vrf, vrf";

    container afs {
      description "BGP address family table";

      list af {
        key "af-name";
        description "A particular address family";

        container rpki-refresh-af-table {
          description "RPKI Refresh Table (per AF)";

          container rpki-refresh-af {
            description "RPKI Refresh List";
            uses BGP-RPKI-REFRESH-LIST-BAG;
          }
        }

        container policies {
          description "The BGP Policy Table";

          list policy {
            description "A BGP Policy table entry";
            leaf rd {
              type Bgp-route-distinguisher;
              description "Route Distinguisher value";
            }
            leaf network {
              type xr:Cisco-ios-xr-string;
              description
                "Network prefix in dotted decimal format for
                ip prefix, else in hex string format";
            }
            leaf prefix-length {
              type uint32;
              description "Network prefix Length";
            }
            leaf neighbor-address {
              type inet:ip-address-no-zone;
              description "Neighbor address";
            }
            uses BGP-PATH-ADV-BAG;
          }
        }

        container convergence {
          description "A BGP Convergence table entry";
          uses BGP-CONVERGENCE-BAG;
        }

        container af-process-info {
          description "A BGP Process address family table entry";
          uses BGP-PROCESS-INFO-AF-BAG;
        }

        container path-used-table {
          description "The BGP Path Used Table";
          uses PATH;
        }

        container bmp-path-table-generic {
          description "Summary Info about BMP Table";
          uses BGP-BMP-TBL-GBL-BAG;
        }

        container rpc-sets {
          description "BGP next-hop set table";

          list rpc-set {
            key "rpc-set-index";
            description "A BGP next-hop set";
            leaf rpc-set-index {
              type uint32;
              description "Nexthop set index";
            }
            uses BGP-RPC-SET-BAG;
          }
        }

        container global-af-process-info {
          description
            "The Global Address Family Process information
            table";
          uses BGP-GLOBAL-PROCESS-INFO-AF-BAG;
        }

        container advertised-path-xr {
          description "The BGP Advertised path table (bestpath)";

          list advertised-path {
            description
              "A BGP Advertised path table entry (bestpath)";
            leaf rd {
              type Bgp-route-distinguisher;
              description "Route Distinguisher value";
            }
            leaf network {
              type xr:Cisco-ios-xr-string;
              description
                "Network prefix in dotted decimal format for
                ip prefix, else in hex string format";
            }
            leaf prefix-length {
              type uint32;
              description "Network prefix Length";
            }
            leaf neighbor-address {
              type inet:ip-address-no-zone;
              description "Neighbor address";
            }
            uses BGP-PATH-BAG;
          }
        }

        container sourced-networks {
          description "The BGP Convergence table";

          list sourced-network {
            key "network";
            description "A BGP network command table entry";
            leaf network {
              type inet:ip-prefix;
              description "Network in prefix/length format";
            }
            uses BGP-STATIC-ROUTES-BAG;
          }
        }

        container update-groups {
          description "The BGP Update group table";

          list update-group {
            description "A BGP Update group table entry";
            leaf update-group-id {
              type uint32;
              description "Update group index";
            }
            leaf filter-group-id {
              type uint32;
              description "Filter group index";
            }
            uses BGP-UPDGRP-BAG;
          }
        }

        container update-generation-sub-groups {
          description "Update generation for all sub-groups";

          list update-generation-sub-group {
            description "Update generation for sub-group";
            leaf update-group-index {
              type uint32;
              description "Update-group index";
            }
            leaf sub-group-index {
              type uint32;
              description "Sub-group index";
            }
            leaf sub-group-id {
              type uint32;
              description "Sub-group ID";
            }
            uses BGP-UPDGEN-SUBGRP-BAG;
          }
        }

        container next-hop-address-families {
          description "Address family of nexthop table";

          list next-hop-address-family {
            key "next-hop-af-name";
            description "Nexthop Address family";

            container next-hop-af-vrf-af {
              description "A BGP Next-hop VRF AF table entry";
              uses BGP-NEXTHOP-VRF-AF-BAG;
            }

            container next-hop-afs {
              description "The BGP Next-hop table";

              list next-hop-af {
                description "A BGP Next hop entry";
                leaf next-hop-address {
                  type inet:ip-address-no-zone;
                  description "Next hop address";
                }
                leaf attribute-set {
                  type xr:Cisco-ios-xr-string;
                  description "Attribute Set Name";
                }
                uses BGP-NEXTHOP-BAG;
              }
            }
            leaf next-hop-af-name {
              type dt1:Bgp-address-family;
              description "Address family";
            }
          }
        }

        container rt-set-counters {
          description "The RT-set counter table";

          list rt-set-counter {
            key "rt-set-id";
            description "One RT-set counter table entry";
            leaf rt-set-id {
              type uint32;
              description "RTSet ID";
            }
            uses BGP-RTSET-BAG;
          }
        }

        container bmp-paths {
          description "The paths in BMP Table";

          list bmp-path {
            description "A BMP path table entry";
            leaf network {
              type xr:Cisco-ios-xr-string;
              description
                "Network prefix in dotted decimal format for
                ip prefix, else in hex string format";
            }
            leaf prefix-length {
              type uint32;
              description "Network prefix Length";
            }
            uses BGP-BMP-NET-BAG;
          }
        }

        container update-generation-update-groups {
          description "Update generation for all update-groups";

          list update-generation-update-group {
            key "update-group-index";
            description "Update generation for update-group";
            leaf update-group-index {
              type uint32;
              description "Update-group index";
            }
            uses BGP-UPDGEN-UPDGRP-BAG;
          }
        }

        container update-generation-filter-groups {
          description
            "Update generation for all filter-groups under
            a sub-group";

          list update-generation-filter-group {
            description "Update generation for filter-group";
            leaf update-group-index {
              type uint32;
              description "Update-group index";
            }
            leaf sub-group-index {
              type uint32;
              description "Sub-group index";
            }
            leaf sub-group-id {
              type uint32;
              description "Sub-group ID";
            }
            leaf filter-group-index {
              type uint32;
              description "Filter-group index";
            }
            uses BGP-UPDGEN-FILTERGRP-BAG;
          }
        }

        container networks {
          description "The BGP Network Table";

          list network {
            description "A BGP Network table entry";
            leaf rd {
              type Bgp-route-distinguisher;
              description "Route Distinguisher value";
            }
            leaf network {
              type xr:Cisco-ios-xr-string;
              description
                "Network prefix in dotted decimal format for
                ip prefix, else in hex string format";
            }
            leaf prefix-length {
              type uint32;
              description "Prefix Length";
            }
            uses BGP-NET-BAG;
          }
        }

        container path-table {
          description "The BGP Path Table";
          uses PATH;
        }

        container epes {
          description "The BGP Egress Engineering table";

          list epe {
            description "A BGP Egress Engineering table entry";
            leaf epe-key-length {
              type uint32;
              description "Epe Key Length";
            }
            leaf epe-set-key {
              type xr:Cisco-ios-xr-string;
              description "Epe Set Key";
            }
            uses BGP-EPE-SET-BAG;
          }
        }

        container advertised-path-counts {
          description "The BGP Advertised paths table (bestpath)";

          list advertised-path-count {
            key "neighbor-address";
            description
              "The BGP Advertised path table Count
              (bestpath)";
            leaf neighbor-address {
              type inet:ip-address-no-zone;
              description "Neighbor address";
            }
            uses BGP-NBR-ADV-CNT-BAG;
          }
        }

        container path-labeled-table {
          description "The BGP Path Labeled Table";
          uses PATH;
        }

        container advertised-paths {
          description "The BGP Advertised paths table (add-paths)";

          list advertised-path {
            description
              "A BGP Advertised paths table entry
              (add-paths)";
            leaf rd {
              type Bgp-route-distinguisher;
              description "Route Distinguisher value";
            }
            leaf network {
              type xr:Cisco-ios-xr-string;
              description
                "Network prefix in dotted decimal format for
                ip prefix, else in hex string format";
            }
            leaf prefix-length {
              type uint32;
              description "Network prefix length";
            }
            leaf neighbor-address {
              type inet:ip-address-no-zone;
              description "Neighbor ";
            }
            uses BGP-PATH-MULTI;
          }
        }

        container neighbor-af-table {
          description "The BGP Neighbor AF table";
          uses NEIGHBOR;
        }

        container update-generation-neighbors {
          description "Update generation for all neighbors";

          list update-generation-neighbor {
            description "Update generation for neighbor";
            leaf update-group-index {
              type uint32;
              description "Update-group index";
            }
            leaf sub-group-index {
              type uint32;
              description "Sub-group index";
            }
            leaf sub-group-id {
              type uint32;
              description "Sub-group ID";
            }
            leaf filter-group-index {
              type uint32;
              description "Filter-group index";
            }
            leaf neighbor-address {
              type inet:ip-address-no-zone;
              description "Neighbor address";
            }
            uses BGP-UPDGEN-NBR-BAG;
          }
        }

        container update-generation-address-family {
          description "Update generation for address-family";
          uses BGP-UPDGEN-AF-BAG;
        }

        container dampenings {
          description "The BGP Dampening table";

          list dampening {
            description "A BGP Dampening table entry";
            leaf reuse {
              type uint32;
              description "Reuse array index";
            }
            leaf version {
              type uint32;
              description "Version number";
            }
            leaf rd {
              type Bgp-route-distinguisher;
              description "Route Distinguisher value";
            }
            leaf network {
              type xr:Cisco-ios-xr-string;
              description
                "Network prefix in dotted decimal format for
                ip prefix, else in hex string format";
            }
            leaf length {
              type uint32;
              description "Prefix length";
            }
            leaf neighbor-address {
              type inet:ip-address-no-zone;
              description "Neighbor address";
            }
            leaf source-rd {
              type Bgp-route-distinguisher;
              description "Source Route Distinguisher value";
            }
            leaf orig-source-rd {
              type Bgp-route-distinguisher;
              description
                "Original Source Route Distinguisher value";
            }
            leaf path-id {
              type uint32;
              description "Received Path ID";
            }
            uses BGP-PATH-BAG;
          }
        }

        container prefix-filters {
          description "The BGP Prefix Filter table";

          list prefix-filter {
            key "neighbor-address";
            description "A BGP prefix filter table entry";
            leaf neighbor-address {
              type inet:ip-address-no-zone;
              description "Neighbor address";
            }
            uses BGP-RCV-PFXLST-BAG;
          }
        }
        leaf af-name {
          type dt1:Bgp-address-family;
          description "Address family";
        }
        uses ATTRIBUTE-TABLE;
      }
    }
  }

  grouping PROCESS-INFO {
    description
      "Common node of default-vrf, vrfCommon node of
      default-vrf, vrf";

    container process-info {
      description "A Process instance table entry";
      uses BGP-PROCESS-INFO-BAG;
    }
  }

  grouping CONFIGURATION-INHERITANCE-TABLE {
    description
      "Common node of config-instance-default-vrf,
      config-vrf";

    container configuration-inheritances {
      description "The BGP configurataion inheritance table";

      list configuration-inheritance {
        description "A BGP configuration inheritance table entry";
        leaf entity-type {
          type Bgp-entity;
          description "Entity type";
        }
        leaf neighbor-address {
          type inet:ip-address-no-zone;
          description "Neighbor address";
        }
        leaf entity-name {
          type xr:Cisco-ios-xr-string;
          description "Entity name";
        }
        leaf length {
          type uint32;
          description "Neighbor addr prefix length";
        }
        uses BGP-CONFIG-RELATIVES-BAG;
      }
    }
  }

  grouping UPDATE-INBOUND-FILTER-PROCESS {
    description "Common node of instance-active, instance-standby";

    container update-inbound-filter-process {
      description
        "Update inbound filtering information for the
        process";
      uses BGP-UPDFILTER-PROC-BAG;
    }
  }

  container bgp {
    config false;
    description "BGP operational data";

    container config-instances {
      description "Instance specific BGP data";

      list config-instance {
        key "instance-name";
        description "Instance specific BGP data";

        container config-instance-default-vrf {
          description "Default VRF related configuration data";
          uses ENTITY-CONFIGURATION-TABLE;
          uses CONFIGURATION-USER-TABLE;
          uses CONFIGURATION-INHERITANCE-TABLE;
        }

        container config-vrfs {
          description "VRF related configuration data";

          list config-vrf {
            key "vrf-name";
            description "Configuration data for a particular VRF";
            leaf vrf-name {
              type xr:Cisco-ios-xr-string;
              description "Name of the VRF";
            }
            uses ENTITY-CONFIGURATION-TABLE;
            uses CONFIGURATION-USER-TABLE;
            uses CONFIGURATION-INHERITANCE-TABLE;
          }
        }
        leaf instance-name {
          type xr:Cisco-ios-xr-string;
          description "Name of the BGP instance";
        }
      }
    }

    container instances {
      description "Instance specific BGP data";

      list instance {
        key "instance-name";
        description "Instance specific BGP data";

        container instance-active {
          description "Active BGP operational data";

          container segment-routing {
            description "Segment Rotuing related Operational Data";

            container srv6 {
              description "SRv6 related Operational Data";

              container summary {
                description "BGP SRv6 Summary";
                uses BGP-SRV6-SUMMARY-BAG;
              }

              container locator-entries {
                description "BGP SRv6 Locator Table";

                list locator-entry {
                  key "locator-name";
                  description "BGP SRv6 Locator Table Entry";
                  leaf locator-name {
                    type xr:Cisco-ios-xr-string;
                    description "Locator Name";
                  }
                  uses BGP-SRV6-LOCATOR-BAG;
                }
              }

              container sid-manager {
                description "BGP SRv6 SID Manager";
                uses BGP-SRV6-SID-MANAGER-BAG;
              }
            }
          }

          container label-entries {
            description "BGP Label Table";

            list label-entry {
              key "label";
              description "BGP Label Entry";
              leaf label {
                type uint32;
                description "Label index";
              }
              uses BGP-LABEL-BAG;
            }
          }

          container label-summary {
            description "BGP Label Summary";
            uses BGP-LABEL-SUMMARY-BAG;
          }

          container label-rpf-entries {
            description "BGP Label RPF Table";

            list label-rpf-entry {
              key "label";
              description "BGP Label RPF Entry";
              leaf label {
                type uint32;
                description "Label index";
              }
              uses BGP-LABEL-RPF-BAG;
            }
          }
          uses UPDATE-GENERATION-PROCESS;
          uses VRF-TABLE;
          uses DEFAULT-VRF;
          uses UPDATE-INBOUND-FILTER-PROCESS;
          uses ATTRIBUTE-TABLE;
          uses RT-TABLE;
          uses ATTRIBUTE-FILTER-GROUP-TABLE;
          uses RPKI-SERVER-LIST;
          uses RPKI-ROUTE-TABLE;
          uses UPDATE-INBOUND-ERROR-PROCESS;
          uses RPKI-SUMMARY;
        }

        container instance-standby {
          description "Standby BGP operational data";
          uses UPDATE-GENERATION-PROCESS;
          uses VRF-TABLE;
          uses DEFAULT-VRF;
          uses UPDATE-INBOUND-FILTER-PROCESS;
          uses ATTRIBUTE-TABLE;
          uses RT-TABLE;
          uses ATTRIBUTE-FILTER-GROUP-TABLE;
          uses RPKI-SERVER-LIST;
          uses RPKI-ROUTE-TABLE;
          uses UPDATE-INBOUND-ERROR-PROCESS;
          uses RPKI-SUMMARY;
        }
        leaf instance-name {
          type xr:Cisco-ios-xr-string;
          description "Name of the BGP instance";
        }
      }
    }

    container bpm-instances-table {
      description "BGP instances information";

      container bpm-instances {
        description "BGP instances information";
        uses BGP-INSTANCES-INFO-BAG;
      }
    }
  }
}
