module Cisco-IOS-XR-ncs5500-qos-oper {

  /*** NAMESPACE / PREFIX DEFINITION ***/

  namespace "http://cisco.com/ns/yang/Cisco-IOS-XR-ncs5500-qos-oper";


  prefix "ncs5500-qos-oper";

  /*** LINKAGE (IMPORTS / INCLUDES) ***/

  import Cisco-IOS-XR-types { prefix "xr"; }

  include Cisco-IOS-XR-ncs5500-qos-oper-sub2 {
    revision-date 2015-11-09;
  }

  include Cisco-IOS-XR-ncs5500-qos-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ncs5500-qos package operational data.

     This module contains definitions
     for the following management objects:
       platform-qos: DNX QoS EA operational data

     Copyright (c) 2013-2018 by Cisco Systems, Inc.
     All rights reserved.";

  revision "2015-11-09" {
    description
      "IOS XR 6.0 revision.";
  }


  grouping QOS-CLASS-TABLE {
    description "Common node of input, output";

    container qos-class-table {
      description "QoS list of class names";
      uses CLASS;
    }
  }

  grouping CLASS {
    description "Common node of class-table, qos-class-table";

    list class {
      key "level-one-class-name";
      description "QoS policy class";
      leaf level-one-class-name {
        type string;
        description "QoS policy class name at level 1";
      }
      leaf level-two-class-name {
        type string;
        description "QoS policy child class name at level 2";
      }
      uses DNX-QOSEA-SHOW-CLASS-ST;
    }
  }

  grouping POLICY-DETAILS {
    description
      "Common node of interface, bundle-interface-single
      , bundle-interface, member-interface";

    container policy-details {
      description "Policy Details";
      uses DNX-QOSEA-SHOW-IF-QOS-INFO-ST;
    }
  }

  grouping MEMBER-INTERFACE-TABLE {
    description
      "Common node of bundle-interface-single,
      bundle-interface";

    container member-interfaces {
      description "QoS list of member interfaces";

      list member-interface {
        key "interface-name";
        description "QoS interface names";
        leaf interface-name {
          type xr:Interface-name;
          description "Member interface";
        }
        uses POLICY-DETAILS;
        uses CLASS-TABLE;
      }
    }
  }

  grouping OUTPUT {
    description "Common node of qos-interfaces, interface";

    container output {
      description "QoS policy direction egress";
      uses QOS-CLASS-TABLE;
    }
  }

  grouping CLASS-TABLE {
    description
      "Common node of interface, bundle-interface-single
      , bundle-interface, member-interface";

    container class-table {
      description "QoS list of class names";
      uses CLASS;
    }
  }

  container platform-qos {
    config false;
    description "DNX QoS EA operational data";

    container nodes {
      description
        "List of nodes with platform specific QoS
        configuration";

      list node {
        key "node-name";
        description "Node with platform specific QoS configuration";

        container bundle-interfaces {
          description "QoS list of bundle interfaces";

          list bundle-interface {
            description "QoS interface names";
            leaf interface-name {
              type xr:Interface-name;
              description "Bundle interface name";
            }
            leaf npu-id {
              type uint32;
              description "NPU ID";
            }
            leaf qos-direction {
              type string;
              description
                "The interface direction on which QoS is
                applied to.";
            }
            uses POLICY-DETAILS;
            uses MEMBER-INTERFACE-TABLE;
            uses CLASS-TABLE;
          }
        }

        container interfaces {
          description "QoS list of interfaces";

          list interface {
            key "interface-name";
            description "QoS interface names";
            leaf interface-name {
              type xr:Interface-name;
              description "The name of the interface";
            }
            uses POLICY-DETAILS;
            uses OUTPUT;
            uses CLASS-TABLE;
          }
        }

        container qos-interfaces {
          description "QoS list of interfaces";

          list qos-interface {
            key "interface-name";
            description "QoS interface names";

            container input {
              description "QoS policy direction ingress";
              uses QOS-CLASS-TABLE;
            }
            leaf interface-name {
              type xr:Interface-name;
              description "The name of the interface";
            }
            uses OUTPUT;
          }
        }

        container bundle-interface-singles {
          description "QoS list of bundle interfaces";

          list bundle-interface-single {
            key "interface-name";
            description "QoS interface names";
            leaf interface-name {
              type xr:Interface-name;
              description "Bundle interface name";
            }
            uses POLICY-DETAILS;
            uses MEMBER-INTERFACE-TABLE;
            uses CLASS-TABLE;
          }
        }

        container remote-interfaces {
          description "QoS list of remote interfaces";

          list remote-interface {
            key "interface-name";
            description "QoS remote interface names";
            leaf interface-name {
              type xr:Interface-name;
              description "The name of the remote interface";
            }
            uses DNX-QOSEA-SHOW-REMOTE-IF-INFO-ST;
          }
        }
        leaf node-name {
          type xr:Node-id;
          description "Node name";
        }
      }
    }
  }
}
